-- ************************************************************************************
--        Snell Card:IQUAV10
--        Module Id#:545
--       Command Set:12
--          Filename:SNELL-IQUAV10-CMD-MIB.mib
--       Source File:nemocombined.xml
--        Source Ver:5.7..12
--    Logging Source:nemologging.csv
--            Author:jonathanriches
--              Date:12/10/2011
--              Time:17:43
--
-- Copyright (c) 2010 Snell Ltd
-- All rights reserved.
--
-- ************************************************************************************

SNELL-IQUAV10-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQUAV10,
    moduleIQUAV10MIB
        FROM SNELL-WILCOX-PRODUCT-REG;

moduleIQUAV10CmdMi MODULE-IDENTITY
    LAST-UPDATED "1110121743Z"
    ORGANIZATION "Snell Ltd"
    CONTACT-INFO
        "Primary Author:jonathanriches

         postal:    Hartman House
                    Danehill
                    Lower Earley,
                    Reading, Berks
                    RG6 4PB
         phone:     +44 (0)118 9866123
         email:     support.uk@snellgroup.com"
    DESCRIPTION
        "This file defines the Snell card, command set translations."
    ::= { moduleIQUAV10MIB 1 }




--********************************************************************************
--*
--*  Snell Card:
--*  command set:
--*  list commands/menus:
--*
--******************************************************************************
    iquav10CmdTable OBJECT-TYPE
        SYNTAX          SEQUENCE OF Iquav10CmdEntry
        MAX-ACCESS      not-accessible
        STATUS          current
        DESCRIPTION
                "Note the instance of this table is relected in the command set Version"
        ::= { moduleIQUAV10 1 }

    iquav10CmdEntry OBJECT-TYPE
        SYNTAX          Iquav10CmdEntry
        MAX-ACCESS      not-accessible
        STATUS          current
        DESCRIPTION
                "Entry in command table."
        INDEX   { iquav10SlotIndex }
        ::= { iquav10CmdTable 1 }

    Iquav10CmdEntry ::=
        SEQUENCE {
            iquav10SlotIndex
                Unsigned32,
            iquav10Video1VideoInputInput1Std
                RollCallString,
            iquav10Video1VideoInputInput2Std
                RollCallString,
            iquav10Video1VideoInputInputAnalogStd
                RollCallString,
            iquav10Video1VideoInputIPSelect
                INTEGER,
            iquav10VideoInputValidStandards108050p
                INTEGER,
            iquav10VideoInputValidStandards108059p
                INTEGER,
            iquav10VideoInputValidStandards108025i
                INTEGER,
            iquav10VideoInputValidStandards108029i
                INTEGER,
            iquav10VideoInputValidStandards72050p
                INTEGER,
            iquav10VideoInputValidStandards72059p
                INTEGER,
            iquav10VideoInputValidStandards62525i
                INTEGER,
            iquav10VideoInputValidStandards52529i
                INTEGER,
            iquav10VideoInputValidStandards108023psf
                INTEGER,
            iquav10VideoInputValidStandards108025psf
                INTEGER,
            iquav10VideoInputValidStandards108025p
                INTEGER,
            iquav10VideoInputValidStandards108029p
                INTEGER,
            iquav10VideoInputErrorsErrorReset
                INTEGER,
            iquav10VideoInputErrorsResetSec
                RollCallString,
            iquav10VideoInputErrorsCRCErrs1
                RollCallString,
            iquav10VideoInputErrorsANCErrs1
                RollCallString,
            iquav10VideoInputErrorsCRCErrs2
                RollCallString,
            iquav10VideoInputErrorsANCErrs2
                RollCallString,
            iquav10VideoInputErrorsCRCErrSec1
                RollCallString,
            iquav10VideoInputErrorsANCErrSec1
                RollCallString,
            iquav10VideoInputErrorsCRCErrSec2
                RollCallString,
            iquav10VideoInputErrorsANCErrSec2
                RollCallString,
            iquav10Video1VideoInputSDAnlgEncode
                INTEGER,
            iquav10Video1VideoInputAnlgType
                INTEGER,
            iquav10Video1VideoInputPedComposDec
                INTEGER,
            iquav10Video1VideoInputYCDelay
                INTEGER,
            iquav10Video1BackupEnable
                INTEGER,
            iquav10Video1BackupORInput1State
                RollCallString,
            iquav10Video1BackupORInput2State
                RollCallString,
            iquav10Video1BackupRevertDelay
                INTEGER,
            iquav10Video1BackupPriority
                INTEGER,
            iquav10Video1BackupQualifyInvStd
                INTEGER,
            iquav10Video1BackupQualifyCRCErr
                INTEGER,
            iquav10Video1BackupQualifyANCErr
                INTEGER,
            iquav10Video1BackupQualifyAudioFail
                INTEGER,
            iquav10BackupInput1SelStatInp1OK
                RollCallString,
            iquav10BackupInput1SelStatInp2FAIL
                RollCallString,
            iquav10BackupInput1SelStatInp2Err
                RollCallString,
            iquav10BackupInput1SelStatAUDFail2
                RollCallString,
            iquav10BackupInput1SelStatStd2
                RollCallString,
            iquav10BackupInput1SelStatGPI1
                RollCallString,
            iquav10BackupInput1SelStatGPI2
                RollCallString,
            iquav10BackupInput1SelEnblInp1OK
                INTEGER,
            iquav10BackupInput1SelEnblInp2FAIL
                INTEGER,
            iquav10BackupInput1SelEnblInp2Err
                INTEGER,
            iquav10BackupInput1SelEnblGPI1
                INTEGER,
            iquav10BackupInput1SelEnblGPI2
                INTEGER,
            iquav10BackupInput1SelEnblStdInp2
                INTEGER,
            iquav10BackupInput1SelDlyInp1OK
                INTEGER,
            iquav10BackupInput1SelDlyInp2FAIL
                INTEGER,
            iquav10BackupInput1SelDlyInp2Err
                INTEGER,
            iquav10BackupInput1SelDlyGPI1
                INTEGER,
            iquav10BackupInput1SelDlyGPI2
                INTEGER,
            iquav10BackupInput1SelDlyAud2FAIL
                INTEGER,
            iquav10BackupInput1SelDlyStd2
                INTEGER,
            iquav10BackupInput1SelGPI1State
                INTEGER,
            iquav10BackupInput1SelGPI2State
                INTEGER,
            iquav10BackupInput1SelInp12AudFailG1C1
                INTEGER,
            iquav10BackupInput1SelInp12AudFailG1C2
                INTEGER,
            iquav10BackupInput1SelInp12AudFailG2C1
                INTEGER,
            iquav10BackupInput1SelInp12AudFailG2C2
                INTEGER,
            iquav10BackupInput1SelInp12AudFailG3C1
                INTEGER,
            iquav10BackupInput1SelInp12AudFailG3C2
                INTEGER,
            iquav10BackupInput1SelInp12AudFailG4C1
                INTEGER,
            iquav10BackupInput1SelInp12AudFailG4C2
                INTEGER,
            iquav10BackupInput1SelInp12AudFailLockGrp
                INTEGER,
            iquav10BackupInput1SelSelAll
                INTEGER,
            iquav10BackupInput1SelSelNone
                INTEGER,
            iquav10BackupInput2SelStatInp2OK
                RollCallString,
            iquav10BackupInput2SelStatInp1FAIL
                RollCallString,
            iquav10BackupInput2SelStatInp1Err
                RollCallString,
            iquav10BackupInput2SelStatAUDFail1
                RollCallString,
            iquav10BackupInput2SelStatStd1
                RollCallString,
            iquav10BackupInput2SelStatGPI1
                RollCallString,
            iquav10BackupInput2SelStatGPI2
                RollCallString,
            iquav10BackupInput2SelEnblInp2OK
                INTEGER,
            iquav10BackupInput2SelEnblInp1FAIL
                INTEGER,
            iquav10BackupInput2SelEnblInp1Err
                INTEGER,
            iquav10BackupInput2SelEnblGPI1
                INTEGER,
            iquav10BackupInput2SelEnblGPI2
                INTEGER,
            iquav10BackupInput2SelEnblAudInp1Err
                INTEGER,
            iquav10BackupInput2SelEnblStdInp1
                INTEGER,
            iquav10BackupInput2SelInp21AudFailG1C1
                INTEGER,
            iquav10BackupInput2SelInp21AudFailG1C2
                INTEGER,
            iquav10BackupInput2SelInp21AudFailG2C1
                INTEGER,
            iquav10BackupInput2SelInp21AudFailG2C2
                INTEGER,
            iquav10BackupInput2SelInp21AudFailG3C1
                INTEGER,
            iquav10BackupInput2SelInp21AudFailG3C2
                INTEGER,
            iquav10BackupInput2SelInp21AudFailG4C1
                INTEGER,
            iquav10BackupInput2SelInp21AudFailG4C2
                INTEGER,
            iquav10BackupInput2SelDlyInp2OK
                INTEGER,
            iquav10BackupInput2SelDlyInp1FAIL
                INTEGER,
            iquav10BackupInput2SelDlyInp1Err
                INTEGER,
            iquav10BackupInput2SelDlyGPI1
                INTEGER,
            iquav10BackupInput2SelDlyGPI2
                INTEGER,
            iquav10BackupInput2SelDlyAud1FAIL
                INTEGER,
            iquav10BackupInput2SelDlyStd1
                INTEGER,
            iquav10BackupInput2SelGPI1State
                INTEGER,
            iquav10BackupInput2SelGPI2State
                INTEGER,
            iquav10BackupInput2SelInp21AudFailLockGrp
                INTEGER,
            iquav10BackupInput2SelSelAll
                INTEGER,
            iquav10BackupInput2SelSelNone
                INTEGER,
            iquav10Video2VideoOutputConversionStandard
                INTEGER,
            iquav10Video2VideoOutputOutputAType
                INTEGER,
            iquav10Video2VideoOutputOutputBType
                INTEGER,
            iquav10Video2VideoOutputOutput1Std
                RollCallString,
            iquav10VideoOutputVideoProcMasterGain
                INTEGER,
            iquav10VideoOutputVideoProcYGain
                INTEGER,
            iquav10VideoOutputVideoProcCGain
                INTEGER,
            iquav10VideoOutputVideoProcBlackLevel
                INTEGER,
            iquav10VideoOutputVideoProcHueLevel
                INTEGER,
            iquav10VideoOutputVideoProcActiveSig
                INTEGER,
            iquav10Video2VideoOutputDefaultOutput
                INTEGER,
            iquav10Video2VideoOutputOutputMode
                INTEGER,
            iquav10Video2VideoOutputPatternType
                INTEGER,
            iquav10Video2VideoOutputSDAnlgEncode
                INTEGER,
            iquav10Video2VideoOutputPedComposEnc
                INTEGER,
            iquav10Video2VideoOutputAnlgType
                INTEGER,
            iquav10VideoOutputUserCaptionsEnable
                INTEGER,
            iquav10VideoOutputUserCaptionsEnableAlt
                INTEGER,
            iquav10VideoOutputUserCaptionsText
                RollCallString,
            iquav10VideoOutputUserCaptionsTextAlt
                RollCallString,
            iquav10VideoOutputUserCaptionsXPos
                INTEGER,
            iquav10VideoOutputUserCaptionsYPos
                INTEGER,
            iquav10VideoOutputUserCaptionsXSize
                INTEGER,
            iquav10VideoOutputUserCaptionsYSize
                INTEGER,
            iquav10Video2VideoOutputLastRefStd
                INTEGER,
            iquav10Video2VideoOutputLastFrameRate
                INTEGER,
            iquav10PictureAdvancedHEnhanceEnable
                INTEGER,
            iquav10PictureAdvancedHEnhanceFrequencyBand
                INTEGER,
            iquav10PictureAdvancedHEnhancePreset
                INTEGER,
            iquav10PictureAdvancedHEnhanceGain
                INTEGER,
            iquav10PictureAdvancedHEnhanceNoiseRejection
                INTEGER,
            iquav10PictureRGBLegaliserRange
                INTEGER,
            iquav10PictureLumaClipperEnable
                INTEGER,
            iquav10PictureLumaClipperWhitemax
                INTEGER,
            iquav10PictureLumaClipperBlackmin
                INTEGER,
            iquav10PictureOutputPictureColorimetry
                INTEGER,
            iquav10PictureEnhanceNoiseThreshold
                INTEGER,
            iquav10PictureEnhanceSharpnessThreshold
                INTEGER,
            iquav10PictureEnhanceSharpnessAmplitude
                INTEGER,
            iquav10PictureOutputPictureFilmCadence
                RollCallString,
            iquav10PictureOutputColorCorrectGreenOffset
                INTEGER,
            iquav10PictureOutputColorCorrectBlueOffset
                INTEGER,
            iquav10PictureOutputColorCorrectRedOffset
                INTEGER,
            iquav10PictureOutputColorCorrectGangOffset
                INTEGER,
            iquav10PictureOutputColorCorrectGreenGain
                INTEGER,
            iquav10PictureOutputColorCorrectBlueGain
                INTEGER,
            iquav10PictureOutputColorCorrectRedGain
                INTEGER,
            iquav10PictureOutputColorCorrectGangGain
                INTEGER,
            iquav10PictureOutputColorCorrectGreenGamma
                INTEGER,
            iquav10PictureOutputColorCorrectBlueGamma
                INTEGER,
            iquav10PictureOutputColorCorrectRedGamma
                INTEGER,
            iquav10PictureOutputColorCorrectGangGamma
                INTEGER,
            iquav10PictureOutputOutputBorderLeft
                INTEGER,
            iquav10PictureOutputOutputBorderRight
                INTEGER,
            iquav10PictureOutputOutputBorderTop
                INTEGER,
            iquav10PictureOutputOutputBorderBottom
                INTEGER,
            iquav10PictureOutputOutputBorderRed
                INTEGER,
            iquav10PictureOutputOutputBorderGreen
                INTEGER,
            iquav10PictureOutputOutputBorderBlue
                INTEGER,
            iquav10ARCCtrlRecallDisplayMemory
                INTEGER,
            iquav10ARCCtrlSelDisplayMemory
                INTEGER,
            iquav10ARCCtrlSaveset
                INTEGER,
            iquav10ARCCtrlSaveDispMemory
                INTEGER,
            iquav10ARCCtrlDispMemoryNameChangeName
                RollCallString,
            iquav10ARCCtrlARCSize
                INTEGER,
            iquav10ARCCtrlARCApect
                INTEGER,
            iquav10ARCCtrlARCTilt
                INTEGER,
            iquav10ARCCtrlARCPan
                INTEGER,
            iquav10ARCCtrlInputCropLeft
                INTEGER,
            iquav10ARCCtrlInputCropRight
                INTEGER,
            iquav10ARCCtrlInputCropTop
                INTEGER,
            iquav10ARCCtrlInputCropBottom
                INTEGER,
            iquav10ARCCtrlSelStdPreset
                INTEGER,
            iquav10ARCCtrlRecallStdPreset
                INTEGER,
            iquav10ARCCtrlDefaultALLMemory
                INTEGER,
            iquav10ARCCtrlLastDisplayMemory
                RollCallString,
            iquav10ARCCtrl43AFDMapping2
                INTEGER,
            iquav10ARCCtrl43AFDMapping3
                INTEGER,
            iquav10ARCCtrl43AFDMapping4
                INTEGER,
            iquav10ARCCtrl43AFDMapping8
                INTEGER,
            iquav10ARCCtrl43AFDMapping9
                INTEGER,
            iquav10ARCCtrl43AFDMapping10
                INTEGER,
            iquav10ARCCtrl43AFDMapping11
                INTEGER,
            iquav10ARCCtrl43AFDMapping12
                INTEGER,
            iquav10ARCCtrl43AFDMapping13
                INTEGER,
            iquav10ARCCtrl43AFDMapping14
                INTEGER,
            iquav10ARCCtrl43AFDMapping15
                INTEGER,
            iquav10ARCCtrl43AFDMapping16
                INTEGER,
            iquav10ARCCtrl169AFDMapping2
                INTEGER,
            iquav10ARCCtrl169AFDMapping3
                INTEGER,
            iquav10ARCCtrl169AFDMapping4
                INTEGER,
            iquav10ARCCtrl169AFDMapping8
                INTEGER,
            iquav10ARCCtrl169AFDMapping9
                INTEGER,
            iquav10ARCCtrl169AFDMapping10
                INTEGER,
            iquav10ARCCtrl169AFDMapping11
                INTEGER,
            iquav10ARCCtrl169AFDMapping12
                INTEGER,
            iquav10ARCCtrl169AFDMapping13
                INTEGER,
            iquav10ARCCtrl169AFDMapping14
                INTEGER,
            iquav10ARCCtrl169AFDMapping15
                INTEGER,
            iquav10ARCCtrl169AFDMapping16
                INTEGER,
            iquav10ARCCtrlNoSignalMapping
                INTEGER,
            iquav10ARCCtrlForceMapping
                INTEGER,
            iquav10ARCCtrl43ARCMapping2
                INTEGER,
            iquav10ARCCtrl43ARCMapping3
                INTEGER,
            iquav10ARCCtrl43ARCMapping4
                INTEGER,
            iquav10ARCCtrl43ARCMapping8
                INTEGER,
            iquav10ARCCtrl43ARCMapping9
                INTEGER,
            iquav10ARCCtrl43ARCMapping10
                INTEGER,
            iquav10ARCCtrl43ARCMapping11
                INTEGER,
            iquav10ARCCtrl43ARCMapping12
                INTEGER,
            iquav10ARCCtrl43ARCMapping13
                INTEGER,
            iquav10ARCCtrl43ARCMapping14
                INTEGER,
            iquav10ARCCtrl43ARCMapping15
                INTEGER,
            iquav10ARCCtrl43ARCMapping16
                INTEGER,
            iquav10ARCCtrl169ARCMapping2
                INTEGER,
            iquav10ARCCtrl169ARCMapping3
                INTEGER,
            iquav10ARCCtrl169ARCMapping4
                INTEGER,
            iquav10ARCCtrl169ARCMapping8
                INTEGER,
            iquav10ARCCtrl169ARCMapping9
                INTEGER,
            iquav10ARCCtrl169ARCMapping10
                INTEGER,
            iquav10ARCCtrl169ARCMapping11
                INTEGER,
            iquav10ARCCtrl169ARCMapping12
                INTEGER,
            iquav10ARCCtrl169ARCMapping13
                INTEGER,
            iquav10ARCCtrl169ARCMapping14
                INTEGER,
            iquav10ARCCtrl169ARCMapping15
                INTEGER,
            iquav10ARCCtrl169ARCMapping16
                INTEGER,
            iquav10ARCCtrlNoSignalARCMapping
                INTEGER,
            iquav10ARCCtrlForceARCMapping
                INTEGER,
            iquav10GenlockBlankingGenlockStandard
                INTEGER,
            iquav10GenlockBlankingGenlockDelayMode
                INTEGER,
            iquav10GenlockSetDelayDelayFrames
                INTEGER,
            iquav10GenlockSetDelayVerticalPhase
                INTEGER,
            iquav10GenlockSetDelayHorizontalPhase
                INTEGER,
            iquav10GenlockSetDelayVerticalDelay
                INTEGER,
            iquav10GenlockSetDelayHorizontalDelay
                INTEGER,
            iquav10GenlockBlankingGenlockRefLogHide
                RollCallString,
            iquav10GenlockDolbyELineStandard
                INTEGER,
            iquav10GenlockDolbyELineAutoLineNo
                INTEGER,
            iquav10DolbyELineUserDolbyELinePair1
                INTEGER,
            iquav10DolbyELineUserDolbyELinePair2
                INTEGER,
            iquav10DolbyELineUserDolbyELinePair3
                INTEGER,
            iquav10DolbyELineUserDolbyELinePair4
                INTEGER,
            iquav10DolbyELineUserDolbyELinePair5
                INTEGER,
            iquav10DolbyELineUserDolbyELinePair6
                INTEGER,
            iquav10DolbyELineUserDolbyELinePair7
                INTEGER,
            iquav10DolbyELineUserDolbyELinePair8
                INTEGER,
            iquav10GenlockDolbyELineUserLine525i29
                INTEGER,
            iquav10GenlockDolbyELineUserLine625i25
                INTEGER,
            iquav10GenlockDolbyELineUserLine720p23
                INTEGER,
            iquav10GenlockDolbyELineUserLine720p24
                INTEGER,
            iquav10GenlockDolbyELineUserLine720p25
                INTEGER,
            iquav10GenlockDolbyELineUserLine720p29
                INTEGER,
            iquav10GenlockDolbyELineUserLine720p30
                INTEGER,
            iquav10GenlockDolbyELineUserLine720p50
                INTEGER,
            iquav10GenlockDolbyELineUserLine720p59
                INTEGER,
            iquav10GenlockDolbyELineUserLine720p60
                INTEGER,
            iquav10GenlockDolbyELineUserLine1080i25
                INTEGER,
            iquav10GenlockDolbyELineUserLine1080i29
                INTEGER,
            iquav10GenlockDolbyELineUserLine1080i30
                INTEGER,
            iquav10GenlockDolbyELineUserLine1080p23sf
                INTEGER,
            iquav10GenlockDolbyELineUserLine1080p24sf
                INTEGER,
            iquav10GenlockDolbyELineUserLine1080p25sf
                INTEGER,
            iquav10GenlockDolbyELineUserLine1080p23
                INTEGER,
            iquav10GenlockDolbyELineUserLine1080p24
                INTEGER,
            iquav10GenlockDolbyELineUserLine1080p25
                INTEGER,
            iquav10GenlockDolbyELineUserLine1080p29
                INTEGER,
            iquav10GenlockDolbyELineUserLine1080p30
                INTEGER,
            iquav10GenlockDolbyELineUserLine1080p50
                INTEGER,
            iquav10GenlockDolbyELineUserLine1080p59
                INTEGER,
            iquav10GenlockDolbyELineUserLine1080p60
                INTEGER,
            iquav10GenlockDolbyELineAutoAlign1
                INTEGER,
            iquav10GenlockDolbyELineAutoAlign2
                INTEGER,
            iquav10GenlockDolbyELineAutoAlign3
                INTEGER,
            iquav10GenlockDolbyELineAutoAlign4
                INTEGER,
            iquav10GenlockDolbyELineAutoAlign5
                INTEGER,
            iquav10GenlockDolbyELineAutoAlign6
                INTEGER,
            iquav10GenlockDolbyELineAutoAlign7
                INTEGER,
            iquav10GenlockDolbyELineAutoAlign8
                INTEGER,
            iquav10WSSCtrlEnableMapper
                INTEGER,
            iquav10WSSCtrlIPWSSSignal
                INTEGER,
            iquav10WSSCtrlOPWSS43
                INTEGER,
            iquav10WSSCtrlDispMem43
                INTEGER,
            iquav10WSSCtrlWidescreenIP2016
                INTEGER,
            iquav10WSSCtrlWidescreenIPPriority
                INTEGER,
            iquav10WSSCtrlWidescreenIPWSSInEnable
                INTEGER,
            iquav10WSSCtrlWidescreenIPVIInEnable
                INTEGER,
            iquav10WSSCtrlWidescreenOP2016
                INTEGER,
            iquav10WSSCtrlWidescreenOPWSSOutEnable
                INTEGER,
            iquav10WSSCtrlWidescreenOPVIOutEnable
                INTEGER,
            iquav10WSSCtrlLine1ReadAFD
                RollCallString,
            iquav10WSSCtrlLine1ReadAR
                RollCallString,
            iquav10WSSCtrlLine1WriteAFD
                RollCallString,
            iquav10WSSCtrlLine1WriteAR
                RollCallString,
            iquav10WSSCtrlPreset
                INTEGER,
            iquav10WSSCtrlPreset43
                INTEGER,
            iquav10WSSCtrlPreset169
                INTEGER,
            iquav10WSSCtrlNewNumber
                INTEGER,
            iquav10WSSCtrlBlank62523
                INTEGER,
            iquav10WSSCtrlBlank625336
                INTEGER,
            iquav10WSSCtrlBlank52521
                INTEGER,
            iquav10WSSCtrlBlank52522
                INTEGER,
            iquav10WSSCtrlBlank525283
                INTEGER,
            iquav10WSSCtrlBlank525284
                INTEGER,
            iquav10AncillaryDataSMPTE20162016IPF1Status
                RollCallString,
            iquav10AncillaryDataSMPTE20162016OPF1Line
                INTEGER,
            iquav10AncillaryDataSMPTE20162016OPF2Line
                INTEGER,
            iquav10AncillaryDataSMPTE20162016Follow
                INTEGER,
            iquav10AncillaryDataSDVBILine7
                INTEGER,
            iquav10AncillaryDataSDVBILine8
                INTEGER,
            iquav10AncillaryDataSDVBILine9
                INTEGER,
            iquav10AncillaryDataSDVBILine10
                INTEGER,
            iquav10AncillaryDataSDVBILine11
                INTEGER,
            iquav10AncillaryDataSDVBILine12
                INTEGER,
            iquav10AncillaryDataSDVBILine13
                INTEGER,
            iquav10AncillaryDataSDVBILine14
                INTEGER,
            iquav10AncillaryDataSDVBILine15
                INTEGER,
            iquav10AncillaryDataSDVBILine16
                INTEGER,
            iquav10AncillaryDataSDVBILine17
                INTEGER,
            iquav10AncillaryDataSDVBILine18
                INTEGER,
            iquav10AncillaryDataSDVBILine19
                INTEGER,
            iquav10AncillaryDataSDVBILine20
                INTEGER,
            iquav10AncillaryDataSDVBILine21
                INTEGER,
            iquav10AncillaryDataSDVBILine22
                INTEGER,
            iquav10AncillaryDataSDVBILine23
                INTEGER,
            iquav10AncillaryDataSDVBIVIIPStatus
                INTEGER,
            iquav10AncillaryDataSDVBIWSSIPStatus
                INTEGER,
            iquav10AncillaryDataSDVBIVITCIPStatus
                INTEGER,
            iquav10AncillaryDataSDVBIWSTIPStatus
                INTEGER,
            iquav10AncillaryDataSDVBICC608IPStatus
                INTEGER,
            iquav10AncillaryDataHDVANCATCEnable
                INTEGER,
            iquav10AncillaryDataHDVANCATCIPF1Line
                RollCallString,
            iquav10AncillaryDataHDVANCATCOPF1Line
                INTEGER,
            iquav10AncillaryDataHDVANCATCOPF2Line
                INTEGER,
            iquav10AncillaryDataHDVANCATCFollow
                INTEGER,
            iquav10AncillaryDataHDVANCHDCaptionEnable
                INTEGER,
            iquav10AncillaryDataHDVANCHDCaptionIPLine
                RollCallString,
            iquav10AncillaryDataHDVANCHDCaptionOPLine
                INTEGER,
            iquav10HDVANCHDCaptionHDFollowIPLine
                INTEGER,
            iquav10AudioInputDisembed18Disembed11procamp
                INTEGER,
            iquav10AudioInputDisembed18Disembed12procamp
                INTEGER,
            iquav10Disembed18Disembed1Mute11
                INTEGER,
            iquav10Disembed18Disembed1Mute12
                INTEGER,
            iquav10Disembed18Disembed1Stereo1
                INTEGER,
            iquav10AudioInputDisembed18Disembed11invert
                INTEGER,
            iquav10AudioInputDisembed18Disembed12invert
                INTEGER,
            iquav10Disembed18Disembed1dolbyLine
                RollCallString,
            iquav10AudioInputDisembed18Disembed21procamp
                INTEGER,
            iquav10AudioInputDisembed18Disembed22procamp
                INTEGER,
            iquav10Disembed18Disembed2Mute21
                INTEGER,
            iquav10Disembed18Disembed2Mute22
                INTEGER,
            iquav10Disembed18Disembed2Stereo2
                INTEGER,
            iquav10AudioInputDisembed18Disembed21invert
                INTEGER,
            iquav10AudioInputDisembed18Disembed22invert
                INTEGER,
            iquav10Disembed18Disembed2dolbyLine
                RollCallString,
            iquav10AudioInputDisembed18Disembed31procamp
                INTEGER,
            iquav10AudioInputDisembed18Disembed32procamp
                INTEGER,
            iquav10Disembed18Disembed3Mute31
                INTEGER,
            iquav10Disembed18Disembed3Mute32
                INTEGER,
            iquav10Disembed18Disembed3Stereo3
                INTEGER,
            iquav10AudioInputDisembed18Disembed31invert
                INTEGER,
            iquav10AudioInputDisembed18Disembed32invert
                INTEGER,
            iquav10Disembed18Disembed3dolbyLine
                RollCallString,
            iquav10AudioInputDisembed18Disembed41procamp
                INTEGER,
            iquav10AudioInputDisembed18Disembed42procamp
                INTEGER,
            iquav10Disembed18Disembed4Mute41
                INTEGER,
            iquav10Disembed18Disembed4Mute42
                INTEGER,
            iquav10Disembed18Disembed4Stereo4
                INTEGER,
            iquav10AudioInputDisembed18Disembed41invert
                INTEGER,
            iquav10AudioInputDisembed18Disembed42invert
                INTEGER,
            iquav10Disembed18Disembed4dolbyLine
                RollCallString,
            iquav10AudioInputDisembed18Disembed51procamp
                INTEGER,
            iquav10AudioInputDisembed18Disembed52procamp
                INTEGER,
            iquav10Disembed18Disembed5Mute51
                INTEGER,
            iquav10Disembed18Disembed5Mute52
                INTEGER,
            iquav10Disembed18Disembed5Stereo5
                INTEGER,
            iquav10AudioInputDisembed18Disembed51invert
                INTEGER,
            iquav10AudioInputDisembed18Disembed52invert
                INTEGER,
            iquav10Disembed18Disembed5dolbyLine
                RollCallString,
            iquav10AudioInputDisembed18Disembed61procamp
                INTEGER,
            iquav10AudioInputDisembed18Disembed62procamp
                INTEGER,
            iquav10Disembed18Disembed6Mute61
                INTEGER,
            iquav10Disembed18Disembed6Mute62
                INTEGER,
            iquav10Disembed18Disembed6Stereo6
                INTEGER,
            iquav10AudioInputDisembed18Disembed61invert
                INTEGER,
            iquav10AudioInputDisembed18Disembed62invert
                INTEGER,
            iquav10Disembed18Disembed6dolbyLine
                RollCallString,
            iquav10AudioInputDisembed18Disembed71procamp
                INTEGER,
            iquav10AudioInputDisembed18Disembed72procamp
                INTEGER,
            iquav10Disembed18Disembed7Mute71
                INTEGER,
            iquav10Disembed18Disembed7Mute72
                INTEGER,
            iquav10Disembed18Disembed7Stereo7
                INTEGER,
            iquav10AudioInputDisembed18Disembed71invert
                INTEGER,
            iquav10AudioInputDisembed18Disembed72invert
                INTEGER,
            iquav10Disembed18Disembed7dolbyLine
                RollCallString,
            iquav10AudioInputDisembed18Disembed81procamp
                INTEGER,
            iquav10AudioInputDisembed18Disembed82procamp
                INTEGER,
            iquav10Disembed18Disembed8Mute81
                INTEGER,
            iquav10Disembed18Disembed8Mute82
                INTEGER,
            iquav10Disembed18Disembed8Stereo8
                INTEGER,
            iquav10AudioInputDisembed18Disembed81invert
                INTEGER,
            iquav10AudioInputDisembed18Disembed82invert
                INTEGER,
            iquav10Disembed18Disembed8dolbyLine
                RollCallString,
            iquav10AudioInputDisembed18ProcampSaveset
                INTEGER,
            iquav10AudioInputAESInput18AESInput11procamp
                INTEGER,
            iquav10AudioInputAESInput18AESInput12procamp
                INTEGER,
            iquav10AESInput18AESInput1Mute11
                INTEGER,
            iquav10AESInput18AESInput1Mute12
                INTEGER,
            iquav10AESInput18AESInput1Stereo1
                INTEGER,
            iquav10AudioInputAESInput18AESInput11invert
                INTEGER,
            iquav10AudioInputAESInput18AESInput12invert
                INTEGER,
            iquav10AESInput18AESInput1AESIO
                INTEGER,
            iquav10AudioInputAESInput18AESInput21procamp
                INTEGER,
            iquav10AudioInputAESInput18AESInput22procamp
                INTEGER,
            iquav10AESInput18AESInput2Mute21
                INTEGER,
            iquav10AESInput18AESInput2Mute22
                INTEGER,
            iquav10AESInput18AESInput2Stereo2
                INTEGER,
            iquav10AudioInputAESInput18AESInput21invert
                INTEGER,
            iquav10AudioInputAESInput18AESInput22invert
                INTEGER,
            iquav10AESInput18AESInput2AESIO
                INTEGER,
            iquav10AudioInputAESInput18AESInput31procamp
                INTEGER,
            iquav10AudioInputAESInput18AESInput32procamp
                INTEGER,
            iquav10AESInput18AESInput3Mute31
                INTEGER,
            iquav10AESInput18AESInput3Mute32
                INTEGER,
            iquav10AESInput18AESInput3Stereo3
                INTEGER,
            iquav10AudioInputAESInput18AESInput31invert
                INTEGER,
            iquav10AudioInputAESInput18AESInput32invert
                INTEGER,
            iquav10AESInput18AESInput3AESIO
                INTEGER,
            iquav10AudioInputAESInput18AESInput41procamp
                INTEGER,
            iquav10AudioInputAESInput18AESInput42procamp
                INTEGER,
            iquav10AESInput18AESInput4Mute41
                INTEGER,
            iquav10AESInput18AESInput4Mute42
                INTEGER,
            iquav10AESInput18AESInput4Stereo4
                INTEGER,
            iquav10AudioInputAESInput18AESInput41invert
                INTEGER,
            iquav10AudioInputAESInput18AESInput42invert
                INTEGER,
            iquav10AESInput18AESInput4AESIO
                INTEGER,
            iquav10AudioInputAESInput18AESInput51procamp
                INTEGER,
            iquav10AudioInputAESInput18AESInput52procamp
                INTEGER,
            iquav10AESInput18AESInput5Mute51
                INTEGER,
            iquav10AESInput18AESInput5Mute52
                INTEGER,
            iquav10AESInput18AESInput5Stereo5
                INTEGER,
            iquav10AudioInputAESInput18AESInput51invert
                INTEGER,
            iquav10AudioInputAESInput18AESInput52invert
                INTEGER,
            iquav10AESInput18AESInput5AESIO
                INTEGER,
            iquav10AudioInputAESInput18AESInput61procamp
                INTEGER,
            iquav10AudioInputAESInput18AESInput62procamp
                INTEGER,
            iquav10AESInput18AESInput6Mute61
                INTEGER,
            iquav10AESInput18AESInput6Mute62
                INTEGER,
            iquav10AESInput18AESInput6Stereo6
                INTEGER,
            iquav10AudioInputAESInput18AESInput61invert
                INTEGER,
            iquav10AudioInputAESInput18AESInput62invert
                INTEGER,
            iquav10AESInput18AESInput6AESIO
                INTEGER,
            iquav10AudioInputAESInput18AESInput71procamp
                INTEGER,
            iquav10AudioInputAESInput18AESInput72procamp
                INTEGER,
            iquav10AESInput18AESInput7Mute71
                INTEGER,
            iquav10AESInput18AESInput7Mute72
                INTEGER,
            iquav10AESInput18AESInput7Stereo7
                INTEGER,
            iquav10AudioInputAESInput18AESInput71invert
                INTEGER,
            iquav10AudioInputAESInput18AESInput72invert
                INTEGER,
            iquav10AESInput18AESInput7AESIO
                INTEGER,
            iquav10AudioInputAESInput18AESInput81procamp
                INTEGER,
            iquav10AudioInputAESInput18AESInput82procamp
                INTEGER,
            iquav10AESInput18AESInput8Mute81
                INTEGER,
            iquav10AESInput18AESInput8Mute82
                INTEGER,
            iquav10AESInput18AESInput8Stereo8
                INTEGER,
            iquav10AudioInputAESInput18AESInput81invert
                INTEGER,
            iquav10AudioInputAESInput18AESInput82invert
                INTEGER,
            iquav10AESInput18AESInput8AESIO
                INTEGER,
            iquav10AudioInputAnalogInput12AnalogInput11procamp
                INTEGER,
            iquav10AudioInputAnalogInput12AnalogInput12procamp
                INTEGER,
            iquav10AnalogInput12AnalogInput1Mute11
                INTEGER,
            iquav10AnalogInput12AnalogInput1Mute12
                INTEGER,
            iquav10AnalogInput12AnalogInput1Stereo1
                INTEGER,
            iquav10AudioInputAnalogInput12AnalogInput11invert
                INTEGER,
            iquav10AudioInputAnalogInput12AnalogInput12invert
                INTEGER,
            iquav10AudioInputAnalogInput12AnalogInput21procamp
                INTEGER,
            iquav10AudioInputAnalogInput12AnalogInput22procamp
                INTEGER,
            iquav10AnalogInput12AnalogInput2Mute21
                INTEGER,
            iquav10AnalogInput12AnalogInput2Mute22
                INTEGER,
            iquav10AnalogInput12AnalogInput2Stereo2
                INTEGER,
            iquav10AudioInputAnalogInput12AnalogInput21invert
                INTEGER,
            iquav10AudioInputAnalogInput12AnalogInput22invert
                INTEGER,
            iquav10AudioOutputEmbed18Embed11procamp
                INTEGER,
            iquav10AudioOutputEmbed18Embed12procamp
                INTEGER,
            iquav10Embed18Embed1Mute11
                INTEGER,
            iquav10Embed18Embed1Mute12
                INTEGER,
            iquav10Embed18Embed1Stereo1
                INTEGER,
            iquav10Embed18Embed1dolbyLine
                RollCallString,
            iquav10AudioOutputEmbed18Embed21procamp
                INTEGER,
            iquav10AudioOutputEmbed18Embed22procamp
                INTEGER,
            iquav10Embed18Embed2Mute21
                INTEGER,
            iquav10Embed18Embed2Mute22
                INTEGER,
            iquav10Embed18Embed2Stereo2
                INTEGER,
            iquav10Embed18Embed2dolbyLine
                RollCallString,
            iquav10AudioOutputEmbed18Embed31procamp
                INTEGER,
            iquav10AudioOutputEmbed18Embed32procamp
                INTEGER,
            iquav10Embed18Embed3Mute31
                INTEGER,
            iquav10Embed18Embed3Mute32
                INTEGER,
            iquav10Embed18Embed3Stereo3
                INTEGER,
            iquav10Embed18Embed3dolbyLine
                RollCallString,
            iquav10AudioOutputEmbed18Embed41procamp
                INTEGER,
            iquav10AudioOutputEmbed18Embed42procamp
                INTEGER,
            iquav10Embed18Embed4Mute41
                INTEGER,
            iquav10Embed18Embed4Mute42
                INTEGER,
            iquav10Embed18Embed4Stereo4
                INTEGER,
            iquav10Embed18Embed4dolbyLine
                RollCallString,
            iquav10AudioOutputEmbed18Embed51procamp
                INTEGER,
            iquav10AudioOutputEmbed18Embed52procamp
                INTEGER,
            iquav10Embed18Embed5Mute51
                INTEGER,
            iquav10Embed18Embed5Mute52
                INTEGER,
            iquav10Embed18Embed5Stereo5
                INTEGER,
            iquav10Embed18Embed5dolbyLine
                RollCallString,
            iquav10AudioOutputEmbed18Embed61procamp
                INTEGER,
            iquav10AudioOutputEmbed18Embed62procamp
                INTEGER,
            iquav10Embed18Embed6Mute61
                INTEGER,
            iquav10Embed18Embed6Mute62
                INTEGER,
            iquav10Embed18Embed6Stereo6
                INTEGER,
            iquav10Embed18Embed6dolbyLine
                RollCallString,
            iquav10AudioOutputEmbed18Embed71procamp
                INTEGER,
            iquav10AudioOutputEmbed18Embed72procamp
                INTEGER,
            iquav10Embed18Embed7Mute71
                INTEGER,
            iquav10Embed18Embed7Mute72
                INTEGER,
            iquav10Embed18Embed7Stereo7
                INTEGER,
            iquav10Embed18Embed7dolbyLine
                RollCallString,
            iquav10AudioOutputEmbed18Embed81procamp
                INTEGER,
            iquav10AudioOutputEmbed18Embed82procamp
                INTEGER,
            iquav10Embed18Embed8Mute81
                INTEGER,
            iquav10Embed18Embed8Mute82
                INTEGER,
            iquav10Embed18Embed8Stereo8
                INTEGER,
            iquav10Embed18Embed8dolbyLine
                RollCallString,
            iquav10Embed18GroupEmbGroup1
                INTEGER,
            iquav10Embed18GroupEmbGroup2
                INTEGER,
            iquav10Embed18GroupEmbGroup3
                INTEGER,
            iquav10Embed18GroupEmbGroup4
                INTEGER,
            iquav10AudioOutputAESOutput18AESOutput11procamp
                INTEGER,
            iquav10AudioOutputAESOutput18AESOutput12procamp
                INTEGER,
            iquav10AESOutput18AESOutput1Mute11
                INTEGER,
            iquav10AESOutput18AESOutput1Mute12
                INTEGER,
            iquav10AESOutput18AESOutput1Stereo1
                INTEGER,
            iquav10AudioOutputAESOutput18AESOutput21procamp
                INTEGER,
            iquav10AudioOutputAESOutput18AESOutput22procamp
                INTEGER,
            iquav10AESOutput18AESOutput2Mute21
                INTEGER,
            iquav10AESOutput18AESOutput2Mute22
                INTEGER,
            iquav10AESOutput18AESOutput2Stereo2
                INTEGER,
            iquav10AudioOutputAESOutput18AESOutput31procamp
                INTEGER,
            iquav10AudioOutputAESOutput18AESOutput32procamp
                INTEGER,
            iquav10AESOutput18AESOutput3Mute31
                INTEGER,
            iquav10AESOutput18AESOutput3Mute32
                INTEGER,
            iquav10AESOutput18AESOutput3Stereo3
                INTEGER,
            iquav10AudioOutputAESOutput18AESOutput41procamp
                INTEGER,
            iquav10AudioOutputAESOutput18AESOutput42procamp
                INTEGER,
            iquav10AESOutput18AESOutput4Mute41
                INTEGER,
            iquav10AESOutput18AESOutput4Mute42
                INTEGER,
            iquav10AESOutput18AESOutput4Stereo4
                INTEGER,
            iquav10AudioOutputAESOutput18AESOutput51procamp
                INTEGER,
            iquav10AudioOutputAESOutput18AESOutput52procamp
                INTEGER,
            iquav10AESOutput18AESOutput5Mute51
                INTEGER,
            iquav10AESOutput18AESOutput5Mute52
                INTEGER,
            iquav10AESOutput18AESOutput5Stereo5
                INTEGER,
            iquav10AudioOutputAESOutput18AESOutput61procamp
                INTEGER,
            iquav10AudioOutputAESOutput18AESOutput62procamp
                INTEGER,
            iquav10AESOutput18AESOutput6Mute61
                INTEGER,
            iquav10AESOutput18AESOutput6Mute62
                INTEGER,
            iquav10AESOutput18AESOutput6Stereo6
                INTEGER,
            iquav10AudioOutputAESOutput18AESOutput71procamp
                INTEGER,
            iquav10AudioOutputAESOutput18AESOutput72procamp
                INTEGER,
            iquav10AESOutput18AESOutput7Mute71
                INTEGER,
            iquav10AESOutput18AESOutput7Mute72
                INTEGER,
            iquav10AESOutput18AESOutput7Stereo7
                INTEGER,
            iquav10AudioOutputAESOutput18AESOutput81procamp
                INTEGER,
            iquav10AudioOutputAESOutput18AESOutput82procamp
                INTEGER,
            iquav10AESOutput18AESOutput8Mute81
                INTEGER,
            iquav10AESOutput18AESOutput8Mute82
                INTEGER,
            iquav10AESOutput18AESOutput8Stereo8
                INTEGER,
            iquav10AudioOutputAnalogOutput12AnalogOutput11procamp
                INTEGER,
            iquav10AudioOutputAnalogOutput12AnalogOutput12procamp
                INTEGER,
            iquav10AnalogOutput12AnalogOutput1Mute11
                INTEGER,
            iquav10AnalogOutput12AnalogOutput1Mute12
                INTEGER,
            iquav10AnalogOutput12AnalogOutput1Stereo1
                INTEGER,
            iquav10AudioOutputAnalogOutput12AnalogOutput21procamp
                INTEGER,
            iquav10AudioOutputAnalogOutput12AnalogOutput22procamp
                INTEGER,
            iquav10AnalogOutput12AnalogOutput2Mute21
                INTEGER,
            iquav10AnalogOutput12AnalogOutput2Mute22
                INTEGER,
            iquav10AnalogOutput12AnalogOutput2Stereo2
                INTEGER,
            iquav10AudSetupDelaySelectTotalDelayBus1
                RollCallString,
            iquav10AudSetupDelaySelectTotalDelayBus2
                RollCallString,
            iquav10AudSetupDelaySelectTotalDelayBus3
                RollCallString,
            iquav10AudSetupDelaySelectTotalDelayBus4
                RollCallString,
            iquav10AudSetupDelaySelectTotalDelayBus5
                RollCallString,
            iquav10AudSetupDelaySelectTotalDelayBus6
                RollCallString,
            iquav10AudSetupDelaySelectTotalDelayBus7
                RollCallString,
            iquav10AudSetupDelaySelectTotalDelayBus8
                RollCallString,
            iquav10AudSetupDelaySelectBus1Delay
                INTEGER,
            iquav10AudSetupDelaySelectBus2Delay
                INTEGER,
            iquav10AudSetupDelaySelectBus3Delay
                INTEGER,
            iquav10AudSetupDelaySelectBus4Delay
                INTEGER,
            iquav10AudSetupDelaySelectBus5Delay
                INTEGER,
            iquav10AudSetupDelaySelectBus6Delay
                INTEGER,
            iquav10AudSetupDelaySelectBus7Delay
                INTEGER,
            iquav10AudSetupDelaySelectBus8Delay
                INTEGER,
            iquav10AudSetupDelaySelectBus1Fine
                INTEGER,
            iquav10AudSetupDelaySelectBus2Fine
                INTEGER,
            iquav10AudSetupDelaySelectBus3Fine
                INTEGER,
            iquav10AudSetupDelaySelectBus4Fine
                INTEGER,
            iquav10AudSetupDelaySelectBus5Fine
                INTEGER,
            iquav10AudSetupDelaySelectBus6Fine
                INTEGER,
            iquav10AudSetupDelaySelectBus7Fine
                INTEGER,
            iquav10AudSetupDelaySelectBus8Fine
                INTEGER,
            iquav10AudSetupDelaySelectBusBulkDelay
                INTEGER,
            iquav10AudSetupDelaySelectThreshold
                INTEGER,
            iquav10AudSetupDelaySelectRtrack14
                INTEGER,
            iquav10AudSetupDelaySelectRtrack15
                INTEGER,
            iquav10AudSetupDelaySelectRtrack16
                INTEGER,
            iquav10AudSetupDelaySelectRtrack17
                INTEGER,
            iquav10AudSetupDelaySelectEnableBulk
                INTEGER,
            iquav10AudSetupDelaySelectEnableVideo
                INTEGER,
            iquav10AudioAudSetupRollTrack14
                RollCallString,
            iquav10AudioAudSetupRollTrack15
                RollCallString,
            iquav10AudioAudSetupRollTrack16
                RollCallString,
            iquav10AudioAudSetupRollTrack17
                RollCallString,
            iquav10AudioAudSetupCurrentVidDelay
                RollCallString,
            iquav10AudioAudSetupMinVidAudDelay
                RollCallString,
            iquav10AudioAudSetupCurrRTrack14Delay
                RollCallString,
            iquav10AudioAudSetupCurrRlTrack15Delay
                RollCallString,
            iquav10AudioAudSetupCurrRTrack16Delay
                RollCallString,
            iquav10AudioAudSetupCurrRTrack17Delay
                RollCallString,
            iquav10AudSetupTonesFreq0
                INTEGER,
            iquav10AudSetupTonesFreq1
                INTEGER,
            iquav10AudSetupTonesFreq2
                INTEGER,
            iquav10AudSetupTonesFreq3
                INTEGER,
            iquav10AudSetupTonesFreq4
                INTEGER,
            iquav10AudSetupTonesFreq5
                INTEGER,
            iquav10AudSetupTonesFreq6
                INTEGER,
            iquav10AudSetupTonesFreq7
                INTEGER,
            iquav10AudSetupTonesIdent0
                INTEGER,
            iquav10AudSetupTonesIdent1
                INTEGER,
            iquav10AudSetupTonesIdent2
                INTEGER,
            iquav10AudSetupTonesIdent3
                INTEGER,
            iquav10AudSetupTonesIdent4
                INTEGER,
            iquav10AudSetupTonesIdent5
                INTEGER,
            iquav10AudSetupTonesIdent6
                INTEGER,
            iquav10AudSetupTonesIdent7
                INTEGER,
            iquav10AudioAudSetupNeg1Frame
                INTEGER,
            iquav10AudioAudSetupNeg1ms
                INTEGER,
            iquav10AudioAudSetupNeg4samp
                INTEGER,
            iquav10AudioAudSetupPos4samp
                INTEGER,
            iquav10AudioAudSetupPos1ms
                INTEGER,
            iquav10AudioAudSetupPos1Frame
                INTEGER,
            iquav10AudioAudSetupSilentLevel
                INTEGER,
            iquav10AudioAudSetupOverloadLevel
                INTEGER,
            iquav10AudioAudSetupLevelTimeout
                INTEGER,
            iquav10AudioAudSetupLevelUpdateEnb
                INTEGER,
            iquav10AudioAudSetupAudLevel
                RollCallString,
            iquav10AudioAudSetupHeadroomIn
                INTEGER,
            iquav10AudioAudSetupLineupIn
                INTEGER,
            iquav10AudioAudSetupHeadroomOut
                INTEGER,
            iquav10AudioAudSetupLineupOut
                INTEGER,
            iquav10AudioRoutingInputRouteDest1
                INTEGER,
            iquav10AudioRoutingInputRouteDest2
                INTEGER,
            iquav10AudioRoutingInputRouteDest3
                INTEGER,
            iquav10AudioRoutingInputRouteDest4
                INTEGER,
            iquav10AudioRoutingInputRouteDest5
                INTEGER,
            iquav10AudioRoutingInputRouteDest6
                INTEGER,
            iquav10AudioRoutingInputRouteDest7
                INTEGER,
            iquav10AudioRoutingInputRouteDest8
                INTEGER,
            iquav10AudioRoutingInputNameAnalog
                RollCallString,
            iquav10AudioRoutingInputNameDlby1
                RollCallString,
            iquav10AudioRoutingInputNameDlby2
                RollCallString,
            iquav10AudioRoutingInputNameDlby3
                RollCallString,
            iquav10AudioRoutingInputNameDlby4
                RollCallString,
            iquav10AudioRoutingInputNameDlby5
                RollCallString,
            iquav10AudioRoutingInputHideAES1
                RollCallString,
            iquav10AudioRoutingInputHideAES2
                RollCallString,
            iquav10AudioRoutingInputHideAES3
                RollCallString,
            iquav10AudioRoutingInputHideAES4
                RollCallString,
            iquav10AudioRoutingInputHideAES5
                RollCallString,
            iquav10AudioRoutingInputHideAES6
                RollCallString,
            iquav10AudioRoutingInputHideAES7
                RollCallString,
            iquav10AudioRoutingInputHideAES8
                RollCallString,
            iquav10AudioRoutingOutputHideAES1
                RollCallString,
            iquav10AudioRoutingOutputHideAES2
                RollCallString,
            iquav10AudioRoutingOutputHideAES3
                RollCallString,
            iquav10AudioRoutingOutputHideAES4
                RollCallString,
            iquav10AudioRoutingOutputHideAES5
                RollCallString,
            iquav10AudioRoutingOutputHideAES6
                RollCallString,
            iquav10AudioRoutingOutputHideAES7
                RollCallString,
            iquav10AudioRoutingOutputHideAES8
                RollCallString,
            iquav10AudioRoutingDolbyDecodeSource
                INTEGER,
            iquav10AudioRoutingDolbyDecodeNum
                INTEGER,
            iquav10AudioOutputRoutingOutDest1
                INTEGER,
            iquav10AudioOutputRoutingOutDest2
                INTEGER,
            iquav10AudioOutputRoutingOutDest3
                INTEGER,
            iquav10AudioOutputRoutingOutDest4
                INTEGER,
            iquav10AudioOutputRoutingOutDest5
                INTEGER,
            iquav10AudioOutputRoutingOutDest6
                INTEGER,
            iquav10AudioOutputRoutingOutDest7
                INTEGER,
            iquav10AudioOutputRoutingOutDest8
                INTEGER,
            iquav10AudioOutputRoutingOutDest9
                INTEGER,
            iquav10AudioOutputRoutingOutDest10
                INTEGER,
            iquav10AudioOutputRoutingOutDest11
                INTEGER,
            iquav10AudioOutputRoutingOutDest12
                INTEGER,
            iquav10AudioOutputRoutingOutDest13
                INTEGER,
            iquav10AudioOutputRoutingOutDest14
                INTEGER,
            iquav10AudioOutputRoutingOutDest15
                INTEGER,
            iquav10AudioOutputRoutingOutDest16
                INTEGER,
            iquav10AudioOutputRoutingOutDest17
                INTEGER,
            iquav10AudioOutputRoutingOutDest18
                INTEGER,
            iquav10AudioOutputRoutingOutDest19
                INTEGER,
            iquav10AudioOutputRoutingOutDest20
                INTEGER,
            iquav10AudioOutputRoutingOutDest21
                INTEGER,
            iquav10AudioOutputRoutingOutDest22
                INTEGER,
            iquav10AudioOutputRoutingOutDest23
                INTEGER,
            iquav10AudioOutputRoutingOutDest24
                INTEGER,
            iquav10AudioOutputRoutingOutDest25
                INTEGER,
            iquav10AudioOutputRoutingOutDest26
                INTEGER,
            iquav10AudioOutputRoutingOutDest27
                INTEGER,
            iquav10AudioOutputRoutingOutDest28
                INTEGER,
            iquav10AudioOutputRoutingOutDest29
                INTEGER,
            iquav10AudioOutputRoutingOutDest30
                INTEGER,
            iquav10AudioOutputRoutingOutDest31
                INTEGER,
            iquav10AudioOutputRoutingOutDest32
                INTEGER,
            iquav10AudioOutputRoutingOutDest33
                INTEGER,
            iquav10AudioOutputRoutingOutDest34
                INTEGER,
            iquav10AudioOutputRoutingOutDest35
                INTEGER,
            iquav10AudioOutputRoutingOutDest36
                INTEGER,
            iquav10AudioOutputRoutingDolbyEncEnb
                RollCallString,
            iquav10AudioOutputRoutingUpmixEnb
                RollCallString,
            iquav10AudioProcDefaultEmbed
                INTEGER,
            iquav10AudioProcDefaultAesOut
                INTEGER,
            iquav10AudioProcDefaultAnlgOut
                INTEGER,
            iquav10AudioRoutingMatrixBus1audsel
                INTEGER,
            iquav10AudioRoutingMatrixBus2audsel
                INTEGER,
            iquav10AudioRoutingMatrixBus3audsel
                INTEGER,
            iquav10AudioRoutingMatrixBus4audsel
                INTEGER,
            iquav10AudioRoutingMatrixBus5audsel
                INTEGER,
            iquav10AudioRoutingMatrixBus6audsel
                INTEGER,
            iquav10AudioRoutingMatrixBus7audsel
                INTEGER,
            iquav10AudioRoutingMatrixBus8audsel
                INTEGER,
            iquav10AudioOutRouteMatrixEmbed12MatrixEmbed11audsel
                INTEGER,
            iquav10AudioOutRouteMatrixEmbed12MatrixEmbed12audsel
                INTEGER,
            iquav10AudioOutRouteMatrixEmbed12MatrixEmbed21audsel
                INTEGER,
            iquav10AudioOutRouteMatrixEmbed12MatrixEmbed22audsel
                INTEGER,
            iquav10AudioOutRouteMatrixEmbed34MatrixEmbed31audsel
                INTEGER,
            iquav10AudioOutRouteMatrixEmbed34MatrixEmbed32audsel
                INTEGER,
            iquav10AudioOutRouteMatrixEmbed34MatrixEmbed41audsel
                INTEGER,
            iquav10AudioOutRouteMatrixEmbed34MatrixEmbed42audsel
                INTEGER,
            iquav10AudioOutRouteMatrixEmbed56MatrixEmbed51audsel
                INTEGER,
            iquav10AudioOutRouteMatrixEmbed56MatrixEmbed52audsel
                INTEGER,
            iquav10AudioOutRouteMatrixEmbed56MatrixEmbed61audsel
                INTEGER,
            iquav10AudioOutRouteMatrixEmbed56MatrixEmbed62audsel
                INTEGER,
            iquav10AudioOutRouteMatrixEmbed78MatrixEmbed71audsel
                INTEGER,
            iquav10AudioOutRouteMatrixEmbed78MatrixEmbed72audsel
                INTEGER,
            iquav10AudioOutRouteMatrixEmbed78MatrixEmbed81audsel
                INTEGER,
            iquav10AudioOutRouteMatrixEmbed78MatrixEmbed82audsel
                INTEGER,
            iquav10AudioOutRouteMatrixAES12MatrixAES11audsel
                INTEGER,
            iquav10AudioOutRouteMatrixAES12MatrixAES12audsel
                INTEGER,
            iquav10AudioOutRouteMatrixAES12MatrixAES21audsel
                INTEGER,
            iquav10AudioOutRouteMatrixAES12MatrixAES22audsel
                INTEGER,
            iquav10AudioOutRouteMatrixAES34MatrixAES31audsel
                INTEGER,
            iquav10AudioOutRouteMatrixAES34MatrixAES32audsel
                INTEGER,
            iquav10AudioOutRouteMatrixAES34MatrixAES41audsel
                INTEGER,
            iquav10AudioOutRouteMatrixAES34MatrixAES42audsel
                INTEGER,
            iquav10AudioOutRouteMatrixAES56MatrixAES51audsel
                INTEGER,
            iquav10AudioOutRouteMatrixAES56MatrixAES52audsel
                INTEGER,
            iquav10AudioOutRouteMatrixAES56MatrixAES61audsel
                INTEGER,
            iquav10AudioOutRouteMatrixAES56MatrixAES62audsel
                INTEGER,
            iquav10AudioOutRouteMatrixAES78MatrixAES71audsel
                INTEGER,
            iquav10AudioOutRouteMatrixAES78MatrixAES72audsel
                INTEGER,
            iquav10AudioOutRouteMatrixAES78MatrixAES81audsel
                INTEGER,
            iquav10AudioOutRouteMatrixAES78MatrixAES82audsel
                INTEGER,
            iquav10AudioOutRouteMatrixAnlg12MatrixAnlg11audsel
                INTEGER,
            iquav10AudioOutRouteMatrixAnlg12MatrixAnlg12audsel
                INTEGER,
            iquav10AudioOutRouteMatrixAnlg12MatrixAnlg21audsel
                INTEGER,
            iquav10AudioOutRouteMatrixAnlg12MatrixAnlg22audsel
                INTEGER,
            iquav10AudioOutRouteMatrixDefaultsEmbOut
                INTEGER,
            iquav10AudioOutRouteMatrixDefaultsAESOut
                INTEGER,
            iquav10AudioOutRouteMatrixDefaultsAnlgOut
                INTEGER,
            iquav10UpMixerLoud14Source1ProcGain
                INTEGER,
            iquav10UpMixerLoud14Source1Mute
                INTEGER,
            iquav10UpMixerLoud14Source1Src
                INTEGER,
            iquav10UpMixerLoud14Source2ProcGain
                INTEGER,
            iquav10UpMixerLoud14Source2Mute
                INTEGER,
            iquav10UpMixerLoud14Source2Src
                INTEGER,
            iquav10UpMixerLoud14Source3ProcGain
                INTEGER,
            iquav10UpMixerLoud14Source3Mute
                INTEGER,
            iquav10UpMixerLoud14Source3Src
                INTEGER,
            iquav10UpMixerLoud14Source4ProcGain
                INTEGER,
            iquav10UpMixerLoud14Source4Mute
                INTEGER,
            iquav10UpMixerLoud14Source4Src
                INTEGER,
            iquav10UpMixerLoud14Mode
                INTEGER,
            iquav10UpMixerLoud14Status
                RollCallString,
            iquav10UpMixerLoud14XfadeBypass
                INTEGER,
            iquav10UpMixerLoud14XfadeUpmix
                INTEGER,
            iquav10UpMixerLoud14Detect
                INTEGER,
            iquav10UpMixerLoud14CenterWidth
                INTEGER,
            iquav10UpMixerLoud14Surround
                INTEGER,
            iquav10UpMixerLoud14AlgorithmType
                INTEGER,
            iquav10UpMixerLoud58LoudnessPreset1
                INTEGER,
            iquav10UpMixerLoud58LoudnessMasterLevel1
                INTEGER,
            iquav10UpMixerLoud58LoudnessName1
                RollCallString,
            iquav10UpMixerLoud58LoudnessBypass1
                INTEGER,
            iquav10UpMixerLoud58LoudnessPreset2
                INTEGER,
            iquav10UpMixerLoud58LoudnessMasterLevel2
                INTEGER,
            iquav10UpMixerLoud58LoudnessName2
                RollCallString,
            iquav10UpMixerLoud58LoudnessBypass2
                INTEGER,
            iquav10UpMixerLoud58Source5ProcGain
                INTEGER,
            iquav10UpMixerLoud58Source5Mute
                INTEGER,
            iquav10UpMixerLoud58Source5Src
                INTEGER,
            iquav10UpMixerLoud58Source6ProcGain
                INTEGER,
            iquav10UpMixerLoud58Source6Mute
                INTEGER,
            iquav10UpMixerLoud58Source6Src
                INTEGER,
            iquav10UpMixerLoud58Source7ProcGain
                INTEGER,
            iquav10UpMixerLoud58Source7Mute
                INTEGER,
            iquav10UpMixerLoud58Source7Src
                INTEGER,
            iquav10UpMixerLoud58Source8ProcGain
                INTEGER,
            iquav10UpMixerLoud58Source8Mute
                INTEGER,
            iquav10UpMixerLoud58Source8Src
                INTEGER,
            iquav10UpMixerLoud58UpmixHide
                RollCallString,
            iquav10UpMixerLoud58Chan1Name
                RollCallString,
            iquav10UpMixerLoud58Chan2Name
                RollCallString,
            iquav10UpMixerLoud58Chan3Name
                RollCallString,
            iquav10UpMixerLoud58Chan4Name
                RollCallString,
            iquav10UpMixerLoud58Chan5Name
                RollCallString,
            iquav10UpMixerLoud58Chan6Name
                RollCallString,
            iquav10UpMixerLoud58Chan7Name
                RollCallString,
            iquav10UpMixerLoud58Chan8Name
                RollCallString,
            iquav10UpMixerLoud58Chan1NameIn
                RollCallString,
            iquav10UpMixerLoud58Chan2NameIn
                RollCallString,
            iquav10UpMixerLoud58Chan3NameIn
                RollCallString,
            iquav10UpMixerLoud58Chan4NameIn
                RollCallString,
            iquav10UpMixerLoud58Chan5NameIn
                RollCallString,
            iquav10UpMixerLoud58Chan6NameIn
                RollCallString,
            iquav10UpMixerLoud58Chan7NameIn
                RollCallString,
            iquav10UpMixerLoud58Chan8NameIn
                RollCallString,
            iquav10UpMixerLoud58DialogHide
                RollCallString,
            iquav10LoudCustomBlock1Name
                RollCallString,
            iquav10LoudCustomBlock1inagcfreeze
                INTEGER,
            iquav10LoudCustomBlock1inagcgate
                INTEGER,
            iquav10LoudCustomBlock1inagcratio
                INTEGER,
            iquav10LoudCustomBlock1inagcrange
                INTEGER,
            iquav10LoudCustomBlock1inagcthresh
                INTEGER,
            iquav10LoudCustomBlock1inagcattack
                INTEGER,
            iquav10LoudCustomBlock1inagcrelease
                INTEGER,
            iquav10LoudCustomBlock1peqfreq1
                INTEGER,
            iquav10LoudCustomBlock1peqq1
                INTEGER,
            iquav10LoudCustomBlock1peqlevel1
                INTEGER,
            iquav10LoudCustomBlock1peqfreq2
                INTEGER,
            iquav10LoudCustomBlock1peqq2
                INTEGER,
            iquav10LoudCustomBlock1peqlevel2
                INTEGER,
            iquav10LoudCustomBlock1peqfreq3
                INTEGER,
            iquav10LoudCustomBlock1peqq3
                INTEGER,
            iquav10LoudCustomBlock1peqlevel3
                INTEGER,
            iquav10LoudCustomBlock1mbagcatk1
                INTEGER,
            iquav10LoudCustomBlock1mbagcrel1
                INTEGER,
            iquav10LoudCustomBlock1mbagcthresh1
                INTEGER,
            iquav10LoudCustomBlock1mbagcoutlev1
                INTEGER,
            iquav10LoudCustomBlock1mbagclimthresh1
                INTEGER,
            iquav10LoudCustomBlock1mbagcinfthr1
                INTEGER,
            iquav10LoudCustomBlock1mbagcatk2
                INTEGER,
            iquav10LoudCustomBlock1mbagcrel2
                INTEGER,
            iquav10LoudCustomBlock1mbagcthresh2
                INTEGER,
            iquav10LoudCustomBlock1mbagcoutlev2
                INTEGER,
            iquav10LoudCustomBlock1mbagclimthresh2
                INTEGER,
            iquav10LoudCustomBlock1mbagcinfthr2
                INTEGER,
            iquav10LoudCustomBlock1mbagcatk3
                INTEGER,
            iquav10LoudCustomBlock1mbagcrel3
                INTEGER,
            iquav10LoudCustomBlock1mbagcthresh3
                INTEGER,
            iquav10LoudCustomBlock1mbagcoutlev3
                INTEGER,
            iquav10LoudCustomBlock1mbagclimthresh3
                INTEGER,
            iquav10LoudCustomBlock1mbagcinfthr3
                INTEGER,
            iquav10LoudCustomBlock1mbagcatk4
                INTEGER,
            iquav10LoudCustomBlock1mbagcrel4
                INTEGER,
            iquav10LoudCustomBlock1mbagcthresh4
                INTEGER,
            iquav10LoudCustomBlock1mbagcoutlev4
                INTEGER,
            iquav10LoudCustomBlock1mbagclimthresh4
                INTEGER,
            iquav10LoudCustomBlock1mbagcinfthr4
                INTEGER,
            iquav10LoudCustomBlock1mbagcatk5
                INTEGER,
            iquav10LoudCustomBlock1mbagcrel5
                INTEGER,
            iquav10LoudCustomBlock1mbagcthresh5
                INTEGER,
            iquav10LoudCustomBlock1mbagcoutlev5
                INTEGER,
            iquav10LoudCustomBlock1mbagclimthresh5
                INTEGER,
            iquav10LoudCustomBlock1mbagcinfthr5
                INTEGER,
            iquav10LoudCustomBlock1mbrange
                INTEGER,
            iquav10LoudCustomBlock1mbprogrise
                INTEGER,
            iquav10LoudCustomBlock1mbsoftclip1
                INTEGER,
            iquav10LoudCustomBlock1mbsoftclip2
                INTEGER,
            iquav10LoudCustomBlock1mbratio
                INTEGER,
            iquav10LoudCustomBlock1mblimdrive
                INTEGER,
            iquav10LoudCustomBlock1CustomPreset
                INTEGER,
            iquav10LoudCustomBlock1Copyto2
                INTEGER,
            iquav10LoudCustomBlock2Name
                RollCallString,
            iquav10LoudCustomBlock2inagcfreeze
                INTEGER,
            iquav10LoudCustomBlock2inagcgate
                INTEGER,
            iquav10LoudCustomBlock2inagcratio
                INTEGER,
            iquav10LoudCustomBlock2inagcrange
                INTEGER,
            iquav10LoudCustomBlock2inagcthresh
                INTEGER,
            iquav10LoudCustomBlock2inagcattack
                INTEGER,
            iquav10LoudCustomBlock2inagcrelease
                INTEGER,
            iquav10LoudCustomBlock2peqfreq1
                INTEGER,
            iquav10LoudCustomBlock2peqq1
                INTEGER,
            iquav10LoudCustomBlock2peqlevel1
                INTEGER,
            iquav10LoudCustomBlock2peqfreq2
                INTEGER,
            iquav10LoudCustomBlock2peqq2
                INTEGER,
            iquav10LoudCustomBlock2peqlevel2
                INTEGER,
            iquav10LoudCustomBlock2peqfreq3
                INTEGER,
            iquav10LoudCustomBlock2peqq3
                INTEGER,
            iquav10LoudCustomBlock2peqlevel3
                INTEGER,
            iquav10LoudCustomBlock2mbagcatk1
                INTEGER,
            iquav10LoudCustomBlock2mbagcrel1
                INTEGER,
            iquav10LoudCustomBlock2mbagcthresh1
                INTEGER,
            iquav10LoudCustomBlock2mbagcoutlev1
                INTEGER,
            iquav10LoudCustomBlock2mbagclimthresh1
                INTEGER,
            iquav10LoudCustomBlock2mbagcinfthr1
                INTEGER,
            iquav10LoudCustomBlock2mbagcatk2
                INTEGER,
            iquav10LoudCustomBlock2mbagcrel2
                INTEGER,
            iquav10LoudCustomBlock2mbagcthresh2
                INTEGER,
            iquav10LoudCustomBlock2mbagcoutlev2
                INTEGER,
            iquav10LoudCustomBlock2mbagclimthresh2
                INTEGER,
            iquav10LoudCustomBlock2mbagcinfthr2
                INTEGER,
            iquav10LoudCustomBlock2mbagcatk3
                INTEGER,
            iquav10LoudCustomBlock2mbagcrel3
                INTEGER,
            iquav10LoudCustomBlock2mbagcthresh3
                INTEGER,
            iquav10LoudCustomBlock2mbagcoutlev3
                INTEGER,
            iquav10LoudCustomBlock2mbagclimthresh3
                INTEGER,
            iquav10LoudCustomBlock2mbagcinfthr3
                INTEGER,
            iquav10LoudCustomBlock2mbagcatk4
                INTEGER,
            iquav10LoudCustomBlock2mbagcrel4
                INTEGER,
            iquav10LoudCustomBlock2mbagcthresh4
                INTEGER,
            iquav10LoudCustomBlock2mbagcoutlev4
                INTEGER,
            iquav10LoudCustomBlock2mbagclimthresh4
                INTEGER,
            iquav10LoudCustomBlock2mbagcinfthr4
                INTEGER,
            iquav10LoudCustomBlock2mbagcatk5
                INTEGER,
            iquav10LoudCustomBlock2mbagcrel5
                INTEGER,
            iquav10LoudCustomBlock2mbagcthresh5
                INTEGER,
            iquav10LoudCustomBlock2mbagcoutlev5
                INTEGER,
            iquav10LoudCustomBlock2mbagclimthresh5
                INTEGER,
            iquav10LoudCustomBlock2mbagcinfthr5
                INTEGER,
            iquav10LoudCustomBlock2mbrange
                INTEGER,
            iquav10LoudCustomBlock2mbprogrise
                INTEGER,
            iquav10LoudCustomBlock2mbsoftclip1
                INTEGER,
            iquav10LoudCustomBlock2mbsoftclip2
                INTEGER,
            iquav10LoudCustomBlock2mbratio
                INTEGER,
            iquav10LoudCustomBlock2mblimdrive
                INTEGER,
            iquav10LoudCustomBlock2CustomPreset
                INTEGER,
            iquav10LoudCustomBlock2Copyto1
                INTEGER,
            iquav10LoudCustomMasterLevelCustom1
                INTEGER,
            iquav10LoudCustomMasterLevelCustom2
                INTEGER,
            iquav10LoudCustomMasterLevelGen51
                INTEGER,
            iquav10LoudCustomMasterLevelLight51
                INTEGER,
            iquav10LoudCustomMasterLevelHeavy51
                INTEGER,
            iquav10LoudCustomMasterLevelLoud51
                INTEGER,
            iquav10LoudCustomMasterLevelLoudLimit51
                INTEGER,
            iquav10LoudCustomMasterLevelProtect51
                INTEGER,
            iquav10LoudCustomMasterLevelGenSterA
                INTEGER,
            iquav10LoudCustomMasterLevelLightSterA
                INTEGER,
            iquav10LoudCustomMasterLevelHeavySterA
                INTEGER,
            iquav10LoudCustomMasterLevelLoudSterA
                INTEGER,
            iquav10LoudCustomMasterLevelLoudLimitSterA
                INTEGER,
            iquav10LoudCustomMasterLevelProtectSterA
                INTEGER,
            iquav10LoudCustomMasterLevelGenSterB
                INTEGER,
            iquav10LoudCustomMasterLevelLightSterB
                INTEGER,
            iquav10LoudCustomMasterLevelHeavySterB
                INTEGER,
            iquav10LoudCustomMasterLevelLoudSterB
                INTEGER,
            iquav10LoudCustomMasterLevelLoudLimitSterB
                INTEGER,
            iquav10LoudCustomMasterLevelProtectSterB
                INTEGER,
            iquav10Mixers13Select
                INTEGER,
            iquav10Mixers13Source1ProcGain
                INTEGER,
            iquav10Mixers13Source1Invert
                INTEGER,
            iquav10Mixers13Source1Mute
                INTEGER,
            iquav10Mixers13Source1Src
                INTEGER,
            iquav10Mixers13Source1Name
                RollCallString,
            iquav10Mixers13Source2ProcGain
                INTEGER,
            iquav10Mixers13Source2Invert
                INTEGER,
            iquav10Mixers13Source2Mute
                INTEGER,
            iquav10Mixers13Source2Src
                INTEGER,
            iquav10Mixers13Source2Name
                RollCallString,
            iquav10Mixers13Source3ProcGain
                INTEGER,
            iquav10Mixers13Source3Invert
                INTEGER,
            iquav10Mixers13Source3Mute
                INTEGER,
            iquav10Mixers13Source3Src
                INTEGER,
            iquav10Mixers13Source3Name
                RollCallString,
            iquav10Mixers13MixerLoRo
                INTEGER,
            iquav10Mixers46Source4ProcGain
                INTEGER,
            iquav10Mixers46Source4Invert
                INTEGER,
            iquav10Mixers46Source4Mute
                INTEGER,
            iquav10Mixers46Source4Src
                INTEGER,
            iquav10Mixers46Source4Name
                RollCallString,
            iquav10Mixers46Source5ProcGain
                INTEGER,
            iquav10Mixers46Source5Invert
                INTEGER,
            iquav10Mixers46Source5Mute
                INTEGER,
            iquav10Mixers46Source5Src
                INTEGER,
            iquav10Mixers46Source5Name
                RollCallString,
            iquav10Mixers46Source6ProcGain
                INTEGER,
            iquav10Mixers46Source6Invert
                INTEGER,
            iquav10Mixers46Source6Mute
                INTEGER,
            iquav10Mixers46Source6Src
                INTEGER,
            iquav10Mixers46Source6Name
                RollCallString,
            iquav10DolbyDecodeDolbyDecoderDetectMode
                INTEGER,
            iquav10DolbyDecodeDolbyDecoderAESChannelSelect
                INTEGER,
            iquav10DolbyDecodeDolbyDecoderPCMLatency
                INTEGER,
            iquav10DolbyDecodeDolbyDecoderListeningModeDolbyD
                INTEGER,
            iquav10DolbyDecodeDolbyDecoderDynamicRange
                INTEGER,
            iquav10DolbyDecoderAuxChannelProgramSelect
                INTEGER,
            iquav10DolbyDecoderAuxChannelDynamicRange
                INTEGER,
            iquav10DolbyDecoderAuxChannelOutputMode
                INTEGER,
            iquav10DolbyDecoderDecoderStatusBitstreamFormat
                RollCallString,
            iquav10DolbyDecoderDecoderStatusBitstreamStatus
                RollCallString,
            iquav10DolbyDecoderDecoderStatusDCRCErrorCount
                RollCallString,
            iquav10DolbyDecoderDecoderStatusDCRCErrorTime
                RollCallString,
            iquav10DolbyDecoderDecoderStatusECRCErrorCount
                RollCallString,
            iquav10DolbyDecoderDecoderStatusECRCErrorTime
                RollCallString,
            iquav10DolbyDecoderDecoderStatusResetErrors
                INTEGER,
            iquav10DolbyDecoderDecoderStatusResetTime
                RollCallString,
            iquav10DolbyDecoderOutputsA1A2A1Gain
                INTEGER,
            iquav10DolbyDecoderOutputsA1A2A2Gain
                INTEGER,
            iquav10DolbyDecoderOutputsA1A2MuteA1
                INTEGER,
            iquav10DolbyDecoderOutputsA1A2MuteA2
                INTEGER,
            iquav10DolbyDecoderOutputsA1A2StereoA
                INTEGER,
            iquav10DolbyDecoderOutputsB3B4B3Gain
                INTEGER,
            iquav10DolbyDecoderOutputsB3B4B4Gain
                INTEGER,
            iquav10DolbyDecoderOutputsB3B4MuteB3
                INTEGER,
            iquav10DolbyDecoderOutputsB3B4MuteB4
                INTEGER,
            iquav10DolbyDecoderOutputsB3B4StereoB
                INTEGER,
            iquav10DolbyDecoderOutputsC5C6C5Gain
                INTEGER,
            iquav10DolbyDecoderOutputsC5C6C6Gain
                INTEGER,
            iquav10DolbyDecoderOutputsC5C6MuteC5
                INTEGER,
            iquav10DolbyDecoderOutputsC5C6MuteC6
                INTEGER,
            iquav10DolbyDecoderOutputsC5C6StereoC
                INTEGER,
            iquav10DolbyDecoderOutputsD7D8D7Gain
                INTEGER,
            iquav10DolbyDecoderOutputsD7D8D8Gain
                INTEGER,
            iquav10DolbyDecoderOutputsD7D8MuteD7
                INTEGER,
            iquav10DolbyDecoderOutputsD7D8MuteD8
                INTEGER,
            iquav10DolbyDecoderOutputsD7D8StereoD
                INTEGER,
            iquav10DolbyDecoderOutputsMLMRMLGain
                INTEGER,
            iquav10DolbyDecoderOutputsMLMRMRGain
                INTEGER,
            iquav10DolbyDecoderOutputsMLMRMuteML
                INTEGER,
            iquav10DolbyDecoderOutputsMLMRMuteMR
                INTEGER,
            iquav10DolbyDecoderOutputsMLMRStereoM
                INTEGER,
            iquav10DolbyDecodeDolbyDecoderOutputsMasterGain
                INTEGER,
            iquav10DolbyDecodeDolbyDecoderOutputsMasterMute
                INTEGER,
            iquav10DolbyEncInp14Source1ProcGain
                INTEGER,
            iquav10DolbyEncInp14Source1Mute
                INTEGER,
            iquav10DolbyEncInp14Source1Src
                INTEGER,
            iquav10DolbyEncInp14Source2ProcGain
                INTEGER,
            iquav10DolbyEncInp14Source2Mute
                INTEGER,
            iquav10DolbyEncInp14Source2Src
                INTEGER,
            iquav10DolbyEncInp14Source3ProcGain
                INTEGER,
            iquav10DolbyEncInp14Source3Mute
                INTEGER,
            iquav10DolbyEncInp14Source3Src
                INTEGER,
            iquav10DolbyEncInp14Source4ProcGain
                INTEGER,
            iquav10DolbyEncInp14Source4Mute
                INTEGER,
            iquav10DolbyEncInp14Source4Src
                INTEGER,
            iquav10DolbyEncInp58Source5ProcGain
                INTEGER,
            iquav10DolbyEncInp58Source5Mute
                INTEGER,
            iquav10DolbyEncInp58Source5Src
                INTEGER,
            iquav10DolbyEncInp58Source6ProcGain
                INTEGER,
            iquav10DolbyEncInp58Source6Mute
                INTEGER,
            iquav10DolbyEncInp58Source6Src
                INTEGER,
            iquav10DolbyEncInp58Source7ProcGain
                INTEGER,
            iquav10DolbyEncInp58Source7Mute
                INTEGER,
            iquav10DolbyEncInp58Source7Src
                INTEGER,
            iquav10DolbyEncInp58Source8ProcGain
                INTEGER,
            iquav10DolbyEncInp58Source8Mute
                INTEGER,
            iquav10DolbyEncInp58Source8Src
                INTEGER,
            iquav10DolbyControlDolbyEncoderControlSampleRateConversion
                INTEGER,
            iquav10DolbyControlDolbyEncoderControlMetaRevertMode
                INTEGER,
            iquav10DolbyControlDolbyEncoderControlEncodingMode
                INTEGER,
            iquav10DolbyControlDolbyEEncoderCntrlBitDepth
                INTEGER,
            iquav10DolbyControlDolbyEEncoderCntrlMetadataSource
                INTEGER,
            iquav10DolbyControlDolbyEEncoderCntrlInternalConfig
                INTEGER,
            iquav10DolbyControlDolbyEEncoderCntrlDefaultAllMeta
                INTEGER,
            iquav10DolbyControlDolbyIntMetaCntrlCopyExtMetadata
                INTEGER,
            iquav10DolbyControlDolbyIntMetaCntrlDefaultProgramMeta
                INTEGER,
            iquav10DolbyControlDolbyIntMetaCntrlDialogueNorm
                INTEGER,
            iquav10DolbyControlDolbyIntMetaCntrlChannelMode
                INTEGER,
            iquav10DolbyControlDolbyIntMetaCntrlLFEChannel
                INTEGER,
            iquav10DolbyControlDolbyIntMetaCntrlBitstreamMode
                INTEGER,
            iquav10DolbyControlDolbyIntMetaCntrlRFMode
                INTEGER,
            iquav10DolbyControlDolbyIntMetaCntrlLineMode
                INTEGER,
            iquav10DolbyIntMetaCntrlAudioProductionInfoExists
                INTEGER,
            iquav10DolbyIntMetaCntrlAudioProductionInfoMixLevel
                INTEGER,
            iquav10DolbyIntMetaCntrlAudioProductionInfoRoomType
                INTEGER,
            iquav10DolbyControlDolbyIntMetaCntrlCentreMixLevel
                INTEGER,
            iquav10DolbyControlDolbyIntMetaCntrlSurroundMixLevel
                INTEGER,
            iquav10DolbyControlDolbyIntMetaCntrlSurroundMode
                INTEGER,
            iquav10DolbyControlDolbyIntMetaCntrlCopyright
                INTEGER,
            iquav10DolbyIntMetaCntrlExtendedBSI1Exists
                INTEGER,
            iquav10DolbyIntMetaCntrlExtendedBSI1StereoDownmixMode
                INTEGER,
            iquav10DolbyIntMetaCntrlExtendedBSI1LtRtCentreMixLevel
                INTEGER,
            iquav10DolbyIntMetaCntrlExtendedBSI1LtRtSurrMixLevel
                INTEGER,
            iquav10DolbyIntMetaCntrlExtendedBSI1LoRoCentreMixLevel
                INTEGER,
            iquav10DolbyIntMetaCntrlExtendedBSI1LoRoSurrMixLevel
                INTEGER,
            iquav10DolbyIntMetaCntrlExtendedBSI2Exists
                INTEGER,
            iquav10DolbyIntMetaCntrlExtendedBSI2SurroundEXMode
                INTEGER,
            iquav10DolbyIntMetaCntrlExtendedBSI2LowpassFilter
                INTEGER,
            iquav10DolbyIntMetaCntrlExtendedBSI2LFEFIlter
                INTEGER,
            iquav10DolbyIntMetaCntrlExtendedBSI2SurrPhaseShiftFltr
                INTEGER,
            iquav10DolbyIntMetaCntrlExtendedBSI2Surr3dBAttenuator
                INTEGER,
            iquav10DolbyControlDolbyIntMetaCntrlProgramDescriptionL
                RollCallString,
            iquav10DolbyControlDolbyIntMetaCntrlProgramDescriptionR
                RollCallString,
            iquav10DolbyControlDolbyIntMetaCntrlIntMetaSaveset
                INTEGER,
            iquav10DolbyControlDolbyDEncoderCntrlInternalMode
                INTEGER,
            iquav10DolbyControlDolbyDEncoderCntrlBitstreamFormat
                INTEGER,
            iquav10DolbyControlDolbyDEncoderCntrlMetadataSource
                INTEGER,
            iquav10DolbyControlDolbyDEncoderCntrlIntMetaDataRate
                INTEGER,
            iquav10DolbyControlDolbyDEncoderCntrlExtMetaDataRate
                INTEGER,
            iquav10DolbyControlDolbyDEncoderCntrlStreamNumber
                INTEGER,
            iquav10DolbyControlDolbyMetaProgSelMetaProgramSelect
                INTEGER,
            iquav10DolbyStatusDolbyCommonStatusVideoSync
                RollCallString,
            iquav10DolbyStatusDolbyCommonStatusFrameRate
                RollCallString,
            iquav10DolbyStatusDolbyCommonStatusProgramConfig
                RollCallString,
            iquav10DolbyStatusDolbyCommonStatusFWVersion
                RollCallString,
            iquav10DolbyStatusDolbyCommonStatusDeviceName
                RollCallString,
            iquav10DolbyCommonStatusChannelAssignmentDolbyA1
                RollCallString,
            iquav10DolbyCommonStatusChannelAssignmentDolbyA2
                RollCallString,
            iquav10DolbyCommonStatusChannelAssignmentDolbyB3
                RollCallString,
            iquav10DolbyCommonStatusChannelAssignmentDolbyB4
                RollCallString,
            iquav10DolbyCommonStatusChannelAssignmentDolbyC5
                RollCallString,
            iquav10DolbyCommonStatusChannelAssignmentDolbyC6
                RollCallString,
            iquav10DolbyCommonStatusChannelAssignmentDolbyD7
                RollCallString,
            iquav10DolbyCommonStatusChannelAssignmentDolbyD8
                RollCallString,
            iquav10DolbyCommonStatusChnlPairAssignmentDolby12
                RollCallString,
            iquav10DolbyCommonStatusChnlPairAssignmentDolby34
                RollCallString,
            iquav10DolbyCommonStatusChnlPairAssignmentDolby56
                RollCallString,
            iquav10DolbyCommonStatusChnlPairAssignmentDolby78
                RollCallString,
            iquav10DolbyStatusDolbyExtProgStatusP1Status
                RollCallString,
            iquav10DolbyStatusDolbyExtProgStatusP2Status
                RollCallString,
            iquav10DolbyStatusDolbyExtProgStatusP3Status
                RollCallString,
            iquav10DolbyStatusDolbyExtProgStatusP4Status
                RollCallString,
            iquav10DolbyStatusDolbyExtProgStatusP5Status
                RollCallString,
            iquav10DolbyStatusDolbyExtProgStatusP6Status
                RollCallString,
            iquav10DolbyStatusDolbyExtProgStatusP7Status
                RollCallString,
            iquav10DolbyStatusDolbyExtProgStatusP8Status
                RollCallString,
            iquav10DolbyStatusDolbyMetadataStatusProgramDescriptionL
                RollCallString,
            iquav10DolbyStatusDolbyMetadataStatusProgramDescriptionR
                RollCallString,
            iquav10DolbyStatusDolbyMetadataStatusDialogueNorm
                RollCallString,
            iquav10DolbyStatusDolbyMetadataStatusChannelMode
                RollCallString,
            iquav10DolbyStatusDolbyMetadataStatusLFE
                RollCallString,
            iquav10DolbyStatusDolbyMetadataStatusBitstreamMode
                RollCallString,
            iquav10DolbyStatusDolbyMetadataStatusRFMode
                RollCallString,
            iquav10DolbyStatusDolbyMetadataStatusLineMode
                RollCallString,
            iquav10DolbyStatusDolbyMetadataStatusCentreMixLevel
                RollCallString,
            iquav10DolbyStatusDolbyMetadataStatusSurroundMixLevel
                RollCallString,
            iquav10DolbyStatusDolbyMetadataStatusSurroundMode
                RollCallString,
            iquav10DolbyStatusDolbyMetadataStatusCopyright
                RollCallString,
            iquav10DolbyMetadataStatusAudioProductionInfoAudioProdInfoExists
                RollCallString,
            iquav10DolbyMetadataStatusAudioProductionInfoMixLevel
                RollCallString,
            iquav10DolbyMetadataStatusAudioProductionInfoRoomType
                RollCallString,
            iquav10DolbyStatusDolbyMetadataStatusExtendedBSI1Exists
                RollCallString,
            iquav10DolbyMetadataStatusExtendedBSI1StereoDownmixMode
                RollCallString,
            iquav10DolbyMetadataStatusExtendedBSI1LtRtCentreMixLevel
                RollCallString,
            iquav10DolbyMetadataStatusExtendedBSI1LtRtSurrMixLevel
                RollCallString,
            iquav10DolbyMetadataStatusExtendedBSI1LoRoCentreMixLevel
                RollCallString,
            iquav10DolbyMetadataStatusExtendedBSI1LoRoSurrMixLevel
                RollCallString,
            iquav10DolbyStatusDolbyMetadataStatusExtendedBSI2Exists
                RollCallString,
            iquav10DolbyMetadataStatusExtendedBSI2SurroundEXMode
                RollCallString,
            iquav10DolbyMetadataStatusExtendedBSI2LowpassFilter
                RollCallString,
            iquav10DolbyMetadataStatusExtendedBSI2LFEFilter
                RollCallString,
            iquav10DolbyMetadataStatusExtendedBSI2SurrPhaseShiftFltr
                RollCallString,
            iquav10DolbyMetadataStatusExtendedBSI2Surr3dBAtten
                RollCallString,
            iquav10DolbyStatusDolbyEncoderStatusStatus
                RollCallString,
            iquav10DolbyStatusDolbyEncoderStatusBitstreamStatus
                RollCallString,
            iquav10DolbyStatusDolbyEncoderStatusReversionStatus
                RollCallString,
            iquav10DolbyStatusDolbyEncoderStatusHWVersion
                RollCallString,
            iquav10DolbyStatusDolbyEncoderStatusOPProgramConfig
                RollCallString,
            iquav10RollCallMemoriesMemoriesABCRecallMemory
                INTEGER,
            iquav10RollCallMemoriesMemoriesABCSelMemory
                INTEGER,
            iquav10RollCallMemoriesMemoriesABCSaveMemory
                INTEGER,
            iquav10RollCallMemoriesMemoriesABCClearMemory
                INTEGER,
            iquav10MemoriesABCMemoryNameChangeName
                RollCallString,
            iquav10MemoriesABCMemoryNameLastUserMemory
                RollCallString,
            iquav10RollCallMemoriesMemoriesABCMemoryName1
                RollCallString,
            iquav10RollCallMemoriesMemoriesABCMemoryName2
                RollCallString,
            iquav10RollCallMemoriesMemoriesABCMemoryName3
                RollCallString,
            iquav10RollCallMemoriesMemoriesABCMemoryName4
                RollCallString,
            iquav10RollCallMemoriesMemoriesABCMemoryName5
                RollCallString,
            iquav10RollCallMemoriesMemoriesABCMemoryName6
                RollCallString,
            iquav10RollCallMemoriesMemoriesABCMemoryName7
                RollCallString,
            iquav10RollCallMemoriesMemoriesABCMemoryName8
                RollCallString,
            iquav10RollCallMemoriesMemoriesABCMemoryName9
                RollCallString,
            iquav10RollCallMemoriesMemoriesABCMemoryName10
                RollCallString,
            iquav10RollCallMemoriesMemoriesABCMemoryName11
                RollCallString,
            iquav10RollCallMemoriesMemoriesABCMemoryName12
                RollCallString,
            iquav10RollCallMemoriesMemoriesABCMemoryName13
                RollCallString,
            iquav10RollCallMemoriesMemoriesABCMemoryName14
                RollCallString,
            iquav10RollCallMemoriesMemoriesABCMemoryName15
                RollCallString,
            iquav10RollCallMemoriesMemoriesABCMemoryName16
                RollCallString,
            iquav10Logging1AESInputAudLoggingLogAESInput1state
                INTEGER,
            iquav10Logging1AESInputAudLoggingAESInput1state
                RollCallString,
            iquav10Logging1AESInputAudLoggingLogAESInput2state
                INTEGER,
            iquav10Logging1AESInputAudLoggingAESInput2state
                RollCallString,
            iquav10Logging1AESInputAudLoggingLogAESInput3state
                INTEGER,
            iquav10Logging1AESInputAudLoggingAESInput3state
                RollCallString,
            iquav10Logging1AESInputAudLoggingLogAESInput4state
                INTEGER,
            iquav10Logging1AESInputAudLoggingAESInput4state
                RollCallString,
            iquav10Logging1AESInputAudLoggingLogAESInput5state
                INTEGER,
            iquav10Logging1AESInputAudLoggingAESInput5state
                RollCallString,
            iquav10Logging1AESInputAudLoggingLogAESInput6state
                INTEGER,
            iquav10Logging1AESInputAudLoggingAESInput6state
                RollCallString,
            iquav10Logging1AESInputAudLoggingLogAESInput7state
                INTEGER,
            iquav10Logging1AESInputAudLoggingAESInput7state
                RollCallString,
            iquav10Logging1AESInputAudLoggingLogAESInput8state
                INTEGER,
            iquav10Logging1AESInputAudLoggingAESInput8state
                RollCallString,
            iquav10Logging1OutEmbAudLoggingLogOutEmb11state
                INTEGER,
            iquav10Logging1OutEmbAudLoggingOutEmb11state
                RollCallString,
            iquav10Logging1OutEmbAudLoggingLogOutEmb12state
                INTEGER,
            iquav10Logging1OutEmbAudLoggingOutEmb12state
                RollCallString,
            iquav10Logging1OutEmbAudLoggingLogOutEmb21state
                INTEGER,
            iquav10Logging1OutEmbAudLoggingOutEmb21state
                RollCallString,
            iquav10Logging1OutEmbAudLoggingLogOutEmb22state
                INTEGER,
            iquav10Logging1OutEmbAudLoggingOutEmb22state
                RollCallString,
            iquav10Logging1OutEmbAudLoggingLogOutEmb31state
                INTEGER,
            iquav10Logging1OutEmbAudLoggingOutEmb31state
                RollCallString,
            iquav10Logging1OutEmbAudLoggingLogOutEmb32state
                INTEGER,
            iquav10Logging1OutEmbAudLoggingOutEmb32state
                RollCallString,
            iquav10Logging1OutEmbAudLoggingLogOutEmb41state
                INTEGER,
            iquav10Logging1OutEmbAudLoggingOutEmb41state
                RollCallString,
            iquav10Logging1OutEmbAudLoggingLogOutEmb42state
                INTEGER,
            iquav10Logging1OutEmbAudLoggingOutEmb42state
                RollCallString,
            iquav10Logging1OutEmbAudLoggingLogOutEmb51state
                INTEGER,
            iquav10Logging1OutEmbAudLoggingOutEmb51state
                RollCallString,
            iquav10Logging1OutEmbAudLoggingLogOutEmb52state
                INTEGER,
            iquav10Logging1OutEmbAudLoggingOutEmb52state
                RollCallString,
            iquav10Logging1OutEmbAudLoggingLogOutEmb61state
                INTEGER,
            iquav10Logging1OutEmbAudLoggingOutEmb61state
                RollCallString,
            iquav10Logging1OutEmbAudLoggingLogOutEmb62state
                INTEGER,
            iquav10Logging1OutEmbAudLoggingOutEmb62state
                RollCallString,
            iquav10Logging1OutEmbAudLoggingLogOutEmb71state
                INTEGER,
            iquav10Logging1OutEmbAudLoggingOutEmb71state
                RollCallString,
            iquav10Logging1OutEmbAudLoggingLogOutEmb72state
                INTEGER,
            iquav10Logging1OutEmbAudLoggingOutEmb72state
                RollCallString,
            iquav10Logging1OutEmbAudLoggingLogOutEmb81state
                INTEGER,
            iquav10Logging1OutEmbAudLoggingOutEmb81state
                RollCallString,
            iquav10Logging1OutEmbAudLoggingLogOutEmb82state
                INTEGER,
            iquav10Logging1OutEmbAudLoggingOutEmb82state
                RollCallString,
            iquav10Logging1AESOutputAudLoggingLogAESOutput11state
                INTEGER,
            iquav10Logging1AESOutputAudLoggingAESOutput11state
                RollCallString,
            iquav10Logging1AESOutputAudLoggingLogAESOutput12state
                INTEGER,
            iquav10Logging1AESOutputAudLoggingAESOutput12state
                RollCallString,
            iquav10Logging1AESOutputAudLoggingLogAESOutput21state
                INTEGER,
            iquav10Logging1AESOutputAudLoggingAESOutput21state
                RollCallString,
            iquav10Logging1AESOutputAudLoggingLogAESOutput22state
                INTEGER,
            iquav10Logging1AESOutputAudLoggingAESOutput22state
                RollCallString,
            iquav10Logging1AESOutputAudLoggingLogAESOutput31state
                INTEGER,
            iquav10Logging1AESOutputAudLoggingAESOutput31state
                RollCallString,
            iquav10Logging1AESOutputAudLoggingLogAESOutput32state
                INTEGER,
            iquav10Logging1AESOutputAudLoggingAESOutput32state
                RollCallString,
            iquav10Logging1AESOutputAudLoggingLogAESOutput41state
                INTEGER,
            iquav10Logging1AESOutputAudLoggingAESOutput41state
                RollCallString,
            iquav10Logging1AESOutputAudLoggingLogAESOutput42state
                INTEGER,
            iquav10Logging1AESOutputAudLoggingAESOutput42state
                RollCallString,
            iquav10Logging1AESOutputAudLoggingLogAESOutput51state
                INTEGER,
            iquav10Logging1AESOutputAudLoggingAESOutput51state
                RollCallString,
            iquav10Logging1AESOutputAudLoggingLogAESOutput52state
                INTEGER,
            iquav10Logging1AESOutputAudLoggingAESOutput52state
                RollCallString,
            iquav10Logging1AESOutputAudLoggingLogAESOutput61state
                INTEGER,
            iquav10Logging1AESOutputAudLoggingAESOutput61state
                RollCallString,
            iquav10Logging1AESOutputAudLoggingLogAESOutput62state
                INTEGER,
            iquav10Logging1AESOutputAudLoggingAESOutput62state
                RollCallString,
            iquav10Logging1AESOutputAudLoggingLogAESOutput71state
                INTEGER,
            iquav10Logging1AESOutputAudLoggingAESOutput71state
                RollCallString,
            iquav10Logging1AESOutputAudLoggingLogAESOutput72state
                INTEGER,
            iquav10Logging1AESOutputAudLoggingAESOutput72state
                RollCallString,
            iquav10Logging1AESOutputAudLoggingLogAESOutput81state
                INTEGER,
            iquav10Logging1AESOutputAudLoggingAESOutput81state
                RollCallString,
            iquav10Logging1AESOutputAudLoggingLogAESOutput82state
                INTEGER,
            iquav10Logging1AESOutputAudLoggingAESOutput82state
                RollCallString,
            iquav10Logging1AnlgOutAudLoggingLogAnlgOut11state
                INTEGER,
            iquav10Logging1AnlgOutAudLoggingAnlgOutput11state
                RollCallString,
            iquav10Logging1AnlgOutAudLoggingLogAnlgOut12state
                INTEGER,
            iquav10Logging1AnlgOutAudLoggingAnlgOutput12state
                RollCallString,
            iquav10Logging1AnlgOutAudLoggingLogAnlgOut21state
                INTEGER,
            iquav10Logging1AnlgOutAudLoggingAnlgOutput21state
                RollCallString,
            iquav10Logging1AnlgOutAudLoggingLogAnlgOut22state
                INTEGER,
            iquav10Logging1AnlgOutAudLoggingAnlgOutput22state
                RollCallString,
            iquav10Logging1DolbyDecoderLoggingLogBitstreamFormat
                INTEGER,
            iquav10Logging1DolbyDecoderLoggingBitstreamFormat
                RollCallString,
            iquav10Logging1DolbyDecoderLoggingLogBitstreamStatus
                INTEGER,
            iquav10Logging1DolbyDecoderLoggingBitstreamStatus
                RollCallString,
            iquav10Logging1DolbyDecoderLoggingLogDCRCErrors
                INTEGER,
            iquav10Logging1DolbyDecoderLoggingDCRCErrorCount
                RollCallString,
            iquav10Logging1DolbyDecoderLoggingLogECRCErrors
                INTEGER,
            iquav10Logging1DolbyDecoderLoggingECRCErrorCount
                RollCallString,
            iquav10Logging1DolbyEncoderLoggingLogEncoderStatus
                INTEGER,
            iquav10Logging1DolbyEncoderLoggingEncoderStatus
                RollCallString,
            iquav10Logging1DolbyEncoderLoggingLogBitstreamStatus
                INTEGER,
            iquav10Logging1DolbyEncoderLoggingBitstreamStatus
                RollCallString,
            iquav10Logging1DolbyEncoderLoggingLogReversionStatus
                INTEGER,
            iquav10Logging1DolbyEncoderLoggingReversionStatus
                RollCallString,
            iquav10Logging1DolbyLoggingLogVideoSync
                INTEGER,
            iquav10Logging1DolbyLoggingVideoSync
                RollCallString,
            iquav10Logging1DolbyLoggingLogFrameRate
                INTEGER,
            iquav10Logging1DolbyLoggingFrameRate
                RollCallString,
            iquav10Logging1DolbyLoggingLogProgramConfig
                INTEGER,
            iquav10Logging1DolbyLoggingProgramConfig
                RollCallString,
            iquav10Logging1DolbyMetadataLoggingLogSelectedProgram
                INTEGER,
            iquav10Logging1DolbyMetadataLoggingSelectedProgram
                RollCallString,
            iquav10Logging1DolbyMetadataLoggingLogProgramDescriptor
                INTEGER,
            iquav10Logging1DolbyMetadataLoggingProgramDescriptor
                RollCallString,
            iquav10Logging1DolbyMetadataLoggingProgramDescPt2
                RollCallString,
            iquav10Logging1DolbyMetadataLoggingLogChannelMode
                INTEGER,
            iquav10Logging1DolbyMetadataLoggingChannelMode
                RollCallString,
            iquav10Logging1DolbyMetadataLoggingLogLFEChannel
                INTEGER,
            iquav10Logging1DolbyMetadataLoggingLFEChannel
                RollCallString,
            iquav10Logging1DolbyMetadataLoggingLogDialogueNorm
                INTEGER,
            iquav10Logging1DolbyMetadataLoggingDialogueNorm
                RollCallString,
            iquav10Logging1AncillaryDataLoggingLogVIInp1
                INTEGER,
            iquav10Logging1AncillaryDataLoggingVIInp1
                RollCallString,
            iquav10Logging1AncillaryDataLoggingLogWSSInp1
                INTEGER,
            iquav10Logging1AncillaryDataLoggingWSSInp1
                RollCallString,
            iquav10Logging1AncillaryDataLoggingLogVITCInp1
                INTEGER,
            iquav10Logging1AncillaryDataLoggingVITCInp1
                RollCallString,
            iquav10Logging1AncillaryDataLoggingLogWSTInp1
                INTEGER,
            iquav10Logging1AncillaryDataLoggingWSTInp1
                RollCallString,
            iquav10Logging1AncillaryDataLoggingLogCC608Inp1
                INTEGER,
            iquav10Logging1AncillaryDataLoggingCC608Inp1
                RollCallString,
            iquav10Logging1AncillaryDataLoggingLog2016Inp1
                INTEGER,
            iquav10Logging1AncillaryDataLogging2016Inp1
                RollCallString,
            iquav10Logging1AncillaryDataLoggingLogATCInp1
                INTEGER,
            iquav10Logging1AncillaryDataLoggingATCInp1
                RollCallString,
            iquav10Logging1AncillaryDataLoggingLogCC708Inp1
                INTEGER,
            iquav10Logging1AncillaryDataLoggingCC708Inp1
                RollCallString,
            iquav10Logging1AncillaryDataLoggingLogARInp1
                INTEGER,
            iquav10Logging1AncillaryDataLoggingARInp1
                RollCallString,
            iquav10Logging1AncillaryDataLoggingLogAFDInp1
                INTEGER,
            iquav10Logging1AncillaryDataLoggingAFDInp1
                RollCallString,
            iquav10Logging1AncillaryDataLoggingLogVIInp2
                INTEGER,
            iquav10Logging1AncillaryDataLoggingVIInp2
                RollCallString,
            iquav10Logging1AncillaryDataLoggingLogWSSInp2
                INTEGER,
            iquav10Logging1AncillaryDataLoggingWSSInp2
                RollCallString,
            iquav10Logging1AncillaryDataLoggingLogVITCInp2
                INTEGER,
            iquav10Logging1AncillaryDataLoggingVITCInp2
                RollCallString,
            iquav10Logging1AncillaryDataLoggingLogWSTInp2
                INTEGER,
            iquav10Logging1AncillaryDataLoggingWSTInp2
                RollCallString,
            iquav10Logging1AncillaryDataLoggingLogCC608Inp2
                INTEGER,
            iquav10Logging1AncillaryDataLoggingCC608Inp2
                RollCallString,
            iquav10Logging1AncillaryDataLoggingLog2016Inp2
                INTEGER,
            iquav10Logging1AncillaryDataLogging2016Inp2
                RollCallString,
            iquav10Logging1AncillaryDataLoggingLogATCInp2
                INTEGER,
            iquav10Logging1AncillaryDataLoggingATCInp2
                RollCallString,
            iquav10Logging1AncillaryDataLoggingLogCC708Inp2
                INTEGER,
            iquav10Logging1AncillaryDataLoggingCC708Inp2
                RollCallString,
            iquav10Logging1AncillaryDataLoggingLogARInp2
                INTEGER,
            iquav10Logging1AncillaryDataLoggingARInp2
                RollCallString,
            iquav10Logging1AncillaryDataLoggingLogAFDInp2
                INTEGER,
            iquav10Logging1AncillaryDataLoggingAFDInp2
                RollCallString,
            iquav10Logging1AncillaryDataLoggingLogOutput
                INTEGER,
            iquav10Logging1AncillaryDataLoggingOutput
                RollCallString,
            iquav10Logging1AncillaryDataLoggingLogOPAR
                INTEGER,
            iquav10Logging1AncillaryDataLoggingOPAR
                RollCallString,
            iquav10Logging1AncillaryDataLoggingLogOPAFD
                INTEGER,
            iquav10Logging1AncillaryDataLoggingOPAFD
                RollCallString,
            iquav10Logging2VideoRefLogInp1Type
                INTEGER,
            iquav10Logging2VideoRefInp1Type
                RollCallString,
            iquav10Logging2VideoRefLogInp1State
                INTEGER,
            iquav10Logging2VideoRefInp1State
                RollCallString,
            iquav10Logging2VideoRefLogInp1Std
                INTEGER,
            iquav10Logging2VideoRefInp1Std
                RollCallString,
            iquav10Logging2VideoRefLogInp1SDIErrs
                INTEGER,
            iquav10Logging2VideoRefInp1SDIErrs
                RollCallString,
            iquav10Logging2VideoRefLogInp1SDIErrSec
                INTEGER,
            iquav10Logging2VideoRefInp1SDIErrSec
                RollCallString,
            iquav10Logging2VideoRefLogInp1ANCerrs
                INTEGER,
            iquav10Logging2VideoRefInp1ANCerrs
                RollCallString,
            iquav10Logging2VideoRefLogInp1ANCerrSec
                INTEGER,
            iquav10Logging2VideoRefInp1ANCerrSec
                RollCallString,
            iquav10Logging2VideoRefLogInp2Type
                INTEGER,
            iquav10Logging2VideoRefInp2Type
                RollCallString,
            iquav10Logging2VideoRefLogInp2State
                INTEGER,
            iquav10Logging2VideoRefInp2State
                RollCallString,
            iquav10Logging2VideoRefLogInp2Std
                INTEGER,
            iquav10Logging2VideoRefInp2Std
                RollCallString,
            iquav10Logging2VideoRefLogInp2SDIErrs
                INTEGER,
            iquav10Logging2VideoRefInp2SDIErrs
                RollCallString,
            iquav10Logging2VideoRefLogInp2SDIErrSec
                INTEGER,
            iquav10Logging2VideoRefInp2SDIErrSec
                RollCallString,
            iquav10Logging2VideoRefLogInp2ANCerrs
                INTEGER,
            iquav10Logging2VideoRefInp2ANCerrs
                RollCallString,
            iquav10Logging2VideoRefLogInp2ANCerrSec
                INTEGER,
            iquav10Logging2VideoRefInp2ANCerrSec
                RollCallString,
            iquav10Logging2VideoRefLogInp3Type
                INTEGER,
            iquav10Logging2VideoRefInp3Type
                RollCallString,
            iquav10Logging2VideoRefLogInp3State
                INTEGER,
            iquav10Logging2VideoRefInp3State
                RollCallString,
            iquav10Logging2VideoRefLogInp3Std
                INTEGER,
            iquav10Logging2VideoRefInp3Std
                RollCallString,
            iquav10Logging2VideoRefLogOutp1Type
                INTEGER,
            iquav10Logging2VideoRefOutp1Type
                RollCallString,
            iquav10Logging2VideoRefLogOutp1State
                INTEGER,
            iquav10Logging2VideoRefOutp1State
                RollCallString,
            iquav10Logging2VideoRefLogOutp1Std
                INTEGER,
            iquav10Logging2VideoRefOutp1Std
                RollCallString,
            iquav10Logging2VideoRefLogOutp2State
                INTEGER,
            iquav10Logging2VideoRefOutp2State
                RollCallString,
            iquav10Logging2VideoRefLogOutp2Std
                INTEGER,
            iquav10Logging2VideoRefOutp2Std
                RollCallString,
            iquav10Logging2VideoRefLogOutp1
                INTEGER,
            iquav10Logging2VideoRefOutp1
                RollCallString,
            iquav10Logging2VideoRefLogOutp1Capt
                INTEGER,
            iquav10Logging2VideoRefOutp1Capt
                RollCallString,
            iquav10Logging2VideoRefLogRefType
                INTEGER,
            iquav10Logging2VideoRefRefType
                RollCallString,
            iquav10Logging2VideoRefLogRefState
                INTEGER,
            iquav10Logging2VideoRefRefState
                RollCallString,
            iquav10Logging2VideoRefLogRefStd
                INTEGER,
            iquav10Logging2VideoRefRefStd
                RollCallString,
            iquav10Logging2VideoRefLogGenlockState
                INTEGER,
            iquav10Logging2VideoRefGenlocState
                RollCallString,
            iquav10Logging2VideoRefLogInp1Ident
                INTEGER,
            iquav10Logging2VideoRefInp1Ident
                RollCallString,
            iquav10Logging2VideoRefLogInp1Name
                INTEGER,
            iquav10Logging2VideoRefInp1Name
                RollCallString,
            iquav10Logging2VideoRefLogInp2Ident
                INTEGER,
            iquav10Logging2VideoRefInp2Ident
                RollCallString,
            iquav10Logging2VideoRefLogInp2Name
                INTEGER,
            iquav10Logging2VideoRefInp2Name
                RollCallString,
            iquav10Logging2VideoRefLogInp3Ident
                INTEGER,
            iquav10Logging2VideoRefInp3Ident
                RollCallString,
            iquav10Logging2VideoRefLogInp3Name
                INTEGER,
            iquav10Logging2VideoRefInp3Name
                RollCallString,
            iquav10Logging2VideoRefLogOutp2Type
                INTEGER,
            iquav10Logging2VideoRefOutp2Type
                RollCallString,
            iquav10Logging2VideoRefLogOutp2
                INTEGER,
            iquav10Logging2VideoRefOutp2
                RollCallString,
            iquav10Logging2VideoRefLogOutp2Capt
                INTEGER,
            iquav10Logging2VideoRefOutp2Capt
                RollCallString,
            iquav10Logging2InEmbAudLoggingInpEmb1state
                RollCallString,
            iquav10Logging2InEmbAudLoggingInpEmb2state
                RollCallString,
            iquav10Logging2InEmbAudLoggingInpEmb3state
                RollCallString,
            iquav10Logging2InEmbAudLoggingInpEmb4state
                RollCallString,
            iquav10Logging2InEmbAudLoggingInpEmb5state
                RollCallString,
            iquav10Logging2InEmbAudLoggingInpEmb6state
                RollCallString,
            iquav10Logging2InEmbAudLoggingInpEmb7state
                RollCallString,
            iquav10Logging2InEmbAudLoggingInpEmb8state
                RollCallString,
            iquav10Logging2In1EmbAudLoggingLogInp1Emb1state
                INTEGER,
            iquav10Logging2In1EmbAudLoggingInp1Emb1state
                RollCallString,
            iquav10Logging2In1EmbAudLoggingLogInp1Emb2state
                INTEGER,
            iquav10Logging2In1EmbAudLoggingInp1Emb2state
                RollCallString,
            iquav10Logging2In1EmbAudLoggingLogInp1Emb3state
                INTEGER,
            iquav10Logging2In1EmbAudLoggingInp1Emb3state
                RollCallString,
            iquav10Logging2In1EmbAudLoggingLogInp1Emb4state
                INTEGER,
            iquav10Logging2In1EmbAudLoggingInp1Emb4state
                RollCallString,
            iquav10Logging2In1EmbAudLoggingLogInp1Emb5state
                INTEGER,
            iquav10Logging2In1EmbAudLoggingInp1Emb5state
                RollCallString,
            iquav10Logging2In1EmbAudLoggingLogInp1Emb6state
                INTEGER,
            iquav10Logging2In1EmbAudLoggingInp1Emb6state
                RollCallString,
            iquav10Logging2In1EmbAudLoggingLogInp1Emb7state
                INTEGER,
            iquav10Logging2In1EmbAudLoggingInp1Emb7state
                RollCallString,
            iquav10Logging2In1EmbAudLoggingLogInp1Emb8state
                INTEGER,
            iquav10Logging2In1EmbAudLoggingInp1Emb8state
                RollCallString,
            iquav10Logging2In2EmbAudLoggingLogInp2Emb1state
                INTEGER,
            iquav10Logging2In2EmbAudLoggingInp2Emb1state
                RollCallString,
            iquav10Logging2In2EmbAudLoggingLogInp2Emb2state
                INTEGER,
            iquav10Logging2In2EmbAudLoggingInp2Emb2state
                RollCallString,
            iquav10Logging2In2EmbAudLoggingLogInp2Emb3state
                INTEGER,
            iquav10Logging2In2EmbAudLoggingInp2Emb3state
                RollCallString,
            iquav10Logging2In2EmbAudLoggingLogInp2Emb4state
                INTEGER,
            iquav10Logging2In2EmbAudLoggingInp2Emb4state
                RollCallString,
            iquav10Logging2In2EmbAudLoggingLogInp2Emb5state
                INTEGER,
            iquav10Logging2In2EmbAudLoggingInp2Emb5state
                RollCallString,
            iquav10Logging2In2EmbAudLoggingLogInp2Emb6state
                INTEGER,
            iquav10Logging2In2EmbAudLoggingInp2Emb6state
                RollCallString,
            iquav10Logging2In2EmbAudLoggingLogInp2Emb7state
                INTEGER,
            iquav10Logging2In2EmbAudLoggingInp2Emb7state
                RollCallString,
            iquav10Logging2In2EmbAudLoggingLogInp2Emb8state
                INTEGER,
            iquav10Logging2In2EmbAudLoggingInp2Emb8state
                RollCallString,
            iquav10Logging2DolbyEAlignLogOutEmb1dolby
                INTEGER,
            iquav10Logging2DolbyEAlignOutEmb1Dolby
                RollCallString,
            iquav10Logging2DolbyEAlignLogOutEmb2dolby
                INTEGER,
            iquav10Logging2DolbyEAlignOutEmb2Dolby
                RollCallString,
            iquav10Logging2DolbyEAlignLogOutEmb3dolby
                INTEGER,
            iquav10Logging2DolbyEAlignOutEmb3Dolby
                RollCallString,
            iquav10Logging2DolbyEAlignLogOutEmb4dolby
                INTEGER,
            iquav10Logging2DolbyEAlignOutEmb4Dolby
                RollCallString,
            iquav10Logging2DolbyEAlignLogOutEmb5dolby
                INTEGER,
            iquav10Logging2DolbyEAlignOutEmb5Dolby
                RollCallString,
            iquav10Logging2DolbyEAlignLogOutEmb6dolby
                INTEGER,
            iquav10Logging2DolbyEAlignOutEmb6Dolby
                RollCallString,
            iquav10Logging2DolbyEAlignLogOutEmb7dolby
                INTEGER,
            iquav10Logging2DolbyEAlignOutEmb7Dolby
                RollCallString,
            iquav10Logging2DolbyEAlignLogOutEmb8dolby
                INTEGER,
            iquav10Logging2DolbyEAlignOutEmb8Dolby
                RollCallString,
            iquav10Logging2MiscLoggingLogSerialNo
                INTEGER,
            iquav10Logging2MiscLoggingSerialNo
                RollCallString,
            iquav10Logging2MiscLoggingLogOSVersion
                INTEGER,
            iquav10Logging2MiscLoggingOSVersion
                RollCallString,
            iquav10Logging2MiscLoggingLogBuildNo
                INTEGER,
            iquav10Logging2MiscLoggingBuildNo
                RollCallString,
            iquav10Logging2MiscLoggingLogHardwareVer
                INTEGER,
            iquav10Logging2MiscLoggingHardwareVer
                RollCallString,
            iquav10Logging2MiscLoggingLogFirmwareVer
                INTEGER,
            iquav10Logging2MiscLoggingFirmwareVer
                RollCallString,
            iquav10Logging2MiscLoggingLogUpTime
                INTEGER,
            iquav10Logging2MiscLoggingUpTime
                RollCallString,
            iquav10Logging2MiscLoggingLogLicensedOpt
                INTEGER,
            iquav10Logging2MiscLoggingLicensedOptions
                RollCallString,
            iquav10Logging2MiscLoggingLogLicensedOpt2
                INTEGER,
            iquav10Logging2MiscLoggingLicensedOptions2
                RollCallString,
            iquav10Logging2MiscLoggingLogTemp1State
                INTEGER,
            iquav10Logging2MiscLoggingTemp1State
                RollCallString,
            iquav10Logging2MiscLoggingLogTemp1Name
                INTEGER,
            iquav10Logging2MiscLoggingTemp1Name
                RollCallString,
            iquav10Logging2MiscLoggingLogRearId
                INTEGER,
            iquav10Logging2MiscLoggingRearID
                RollCallString,
            iquav10Logging2MiscLoggingLogSlotWidth
                INTEGER,
            iquav10Logging2MiscLoggingSlotWidth
                RollCallString,
            iquav10Logging2MiscLoggingLogSlotStart
                INTEGER,
            iquav10Logging2MiscLoggingSlotStart
                RollCallString,
            iquav10Logging2MiscLoggingLogRearStatus
                INTEGER,
            iquav10Logging2MiscLoggingRearSTATUS
                RollCallString,
            iquav10RollCallMemoriesRollTrackDisableAll
                INTEGER,
            iquav10RollCallMemoriesRollTrackIndex
                INTEGER,
            iquav10RollCallMemoriesRollTrackSource
                INTEGER,
            iquav10RollCallMemoriesRollTrackAddress
                RollCallString,
            iquav10RollCallMemoriesRollTrackCommand
                RollCallString,
            iquav10RollCallMemoriesRollTrackStatus
                RollCallString,
            iquav10RollCallMemoriesRollTrackSending
                RollCallString,
            iquav10RollCallMemoriesHideGpio
                INTEGER,
            iquav10RollCallMemoriesHideInpAES14
                INTEGER,
            iquav10RollCallMemoriesHideInpAES18
                INTEGER,
            iquav10RollCallMemoriesHideInpLogAES14
                INTEGER,
            iquav10RollCallMemoriesHideInpLogAES18
                INTEGER,
            iquav10RollCallMemoriesHideOutAES14
                INTEGER,
            iquav10RollCallMemoriesHideOutAES18
                INTEGER,
            iquav10RollCallMemoriesHideOutLogAES14
                INTEGER,
            iquav10RollCallMemoriesHideOutLogAES18
                INTEGER,
            iquav10GPIOGPI1GPIO1Mode
                INTEGER,
            iquav10GPIOGPI1GPI1IPHighSelect
                INTEGER,
            iquav10GPIOGPI1GPI1IPLowSelect
                INTEGER,
            iquav10GPIOGPI1GPO1OPSelect
                INTEGER,
            iquav10GPIOGPI1InvertGPIO1
                INTEGER,
            iquav10GPIOGPI1Status
                RollCallString,
            iquav10GPIOGPI2GPIO2Mode
                INTEGER,
            iquav10GPIOGPI2GPI2IPHighSelect
                INTEGER,
            iquav10GPIOGPI2GPI2IPLowSelect
                INTEGER,
            iquav10GPIOGPI2GPO2OPSelect
                INTEGER,
            iquav10GPIOGPI2InvertGPIO2
                INTEGER,
            iquav10GPIOGPI2Status
                RollCallString,
            iquav10SetupDisplay
                INTEGER,
            iquav10SetupProduct
                RollCallString,
            iquav10SetupRelease
                RollCallString,
            iquav10SetupBuild
                RollCallString,
            iquav10SetupKOS
                RollCallString,
            iquav10SetupSerialNo
                RollCallString,
            iquav10SetupFactoryDefault
                INTEGER,
            iquav10SetupRestart
                INTEGER,
            iquav10SetupDefaultSettings
                INTEGER,
            iquav10SetupSerialNumber
                RollCallString,
            iquav10SetupBoardID
                INTEGER,
            iquav10SetupSaveID
                INTEGER,
            iquav10SetupFpgaBoardType
                RollCallString,
            iquav10SetupFpgaSerialNo
                RollCallString,
            iquav10SetupFpgaSoftVer
                RollCallString,
            iquav10SetupFpgaVer
                RollCallString,
            iquav10SetupFpgaTIVer
                RollCallString,
            iquav10SetupFpgaDolbyModId
                RollCallString,
            iquav10SetupFpgaProtVer
                RollCallString,
            iquav10SetupFpgaProgCRC
                RollCallString,
            iquav10SetupFpgaUptime
                RollCallString,
            iquav10SetupFpgaENGVXPVer
                RollCallString,
            iquav10SetupFpgaENGSharcVer
                RollCallString,
            iquav10SetupFpgaENGAlteraVer
                RollCallString,
            iquav10SetupFpgaENGVCCint
                RollCallString,
            iquav10SetupFpgaENGVCCaux
                RollCallString,
            iquav10SetupOptionsOption1
                RollCallString,
            iquav10SetupOptionsOption2
                RollCallString,
            iquav10SetupOptionsOption3
                RollCallString,
            iquav10SetupOptionsOption4
                RollCallString,
            iquav10SetupOptionsOption5
                RollCallString,
            iquav10SetupOptionsOption6
                RollCallString,
            iquav10SetupOptionsOption7
                RollCallString,
            iquav10SetupOptionsOption8
                RollCallString,
            iquav10SetupOptionsOption9
                RollCallString,
            iquav10SetupOptionsMask
                INTEGER,
            iquav10SetupDemoNonDemoRestart
                INTEGER,
            iquav10SetupDemoPeriod
                INTEGER,
            iquav10SetupDemoRestartMode
                INTEGER,
            iquav10SetupDemoRemainingDemo
                INTEGER,
            iquav10SetupDemoRemaining24h
                INTEGER,
            iquav10SetupDemoStatus
                INTEGER,
            iquav10SetupRestartHard
                INTEGER,
            iquav10SetupInput1Name
                RollCallString,
            iquav10SetupInput2Name
                RollCallString,
            iquav10SetupInput3Name
                RollCallString,
            iquav10SetupCalibrationVideoIn0
                INTEGER,
            iquav10SetupCalibrationVideoIn1
                INTEGER,
            iquav10SetupCalibrationVideoIn2
                INTEGER,
            iquav10SetupCalibrationVideoIn3
                INTEGER,
            iquav10SetupCalibrationVideoIn4
                INTEGER,
            iquav10SetupCalibrationVideoIn5
                INTEGER,
            iquav10SetupCalibrationVideoIn6
                INTEGER,
            iquav10SetupCalibrationVideoIn7
                INTEGER,
            iquav10SetupCalibrationVideoIn20
                INTEGER,
            iquav10SetupCalibrationVideoIn21
                INTEGER,
            iquav10SetupCalibrationVideoIn22
                INTEGER,
            iquav10SetupCalibrationVideoIn23
                INTEGER,
            iquav10SetupCalibrationVideoOut0
                INTEGER,
            iquav10SetupCalibrationVideoOut1
                INTEGER,
            iquav10SetupCalibrationVideoOut2
                INTEGER,
            iquav10SetupCalibrationVideoOut3
                INTEGER,
            iquav10SetupCalibrationVideoOut4
                INTEGER,
            iquav10SetupCalibrationVideoOut5
                INTEGER,
            iquav10SetupCalibrationVideoOut6
                INTEGER,
            iquav10SetupCalibrationVideoOut7
                INTEGER,
            iquav10SetupCalibrationVideoOut8
                INTEGER,
            iquav10SetupCalibrationVideoOut9
                INTEGER,
            iquav10SetupCalibrationVideoOut10
                INTEGER,
            iquav10SetupCalibrationVideoOut11
                INTEGER,
            iquav10SetupCalibrationAudio0
                INTEGER,
            iquav10SetupCalibrationAudio1
                INTEGER,
            iquav10SetupCalibrationAudio2
                INTEGER,
            iquav10SetupCalibrationAudio3
                INTEGER,
            iquav10SetupCalibrationAudio4
                INTEGER,
            iquav10SetupCalibrationAudio5
                INTEGER,
            iquav10SetupCalibrationAudio6
                INTEGER,
            iquav10SetupCalibrationAudio7
                INTEGER,
            iquav10SetupCalibrationCalibrateTake
                INTEGER,
            iquav10SetupCalibrationCalibratePreset
                INTEGER,
            iquav10SetupCalibrationCalibrateDefault
                INTEGER,
            iquav10SetupCalibrationCalibrateFactory
                INTEGER,
            iquav10SetupCalibrationCalUnlock
                RollCallString,
            iquav10LKFS1SourceLSrc
                INTEGER,
            iquav10LKFS1SourceRSrc
                INTEGER,
            iquav10LKFS1SourceLSSrc
                INTEGER,
            iquav10LKFS1SourceRSSrc
                INTEGER,
            iquav10LKFS1SourceCSrc
                INTEGER,
            iquav10LKFS1ResetSession
                INTEGER,
            iquav10LKFS1SessLevel
                RollCallString,
            iquav10LKFS1SessTime
                RollCallString,
            iquav10LKFS1currrate
                INTEGER,
            iquav10LKFS1CurrLevelTime
                RollCallString,
            iquav10LKFS1CurrLevel
                RollCallString,
            iquav10LKFS1CurrLevel2
                RollCallString,
            iquav10LKFS1RollMapUpd
                RollCallString,
            iquav10LKFS1UpdateRate
                INTEGER,
            iquav10LKFS2SourceLSrc
                INTEGER,
            iquav10LKFS2SourceRSrc
                INTEGER,
            iquav10LKFS2SourceLSSrc
                INTEGER,
            iquav10LKFS2SourceRSSrc
                INTEGER,
            iquav10LKFS2SourceCSrc
                INTEGER,
            iquav10LKFS2SessLevel
                RollCallString,
            iquav10LKFS2CurrLevel
                RollCallString,
            iquav10LKFS2CurrLevel2
                RollCallString
        }

    iquav10SlotIndex OBJECT-TYPE
        SYNTAX            Unsigned32
        MAX-ACCESS        not-accessible
        STATUS            current
        DESCRIPTION
                "The unique Index value for each slot.  Its value
                ranges between 1 and the value of slotNumber."
        ::= { iquav10CmdEntry 99999 }


    iquav10Video1VideoInputInput1Std OBJECT-TYPE
        SYNTAX            RollCallString
        MAX-ACCESS        read-only
        STATUS            current
        DESCRIPTION
                "CMNT: - Input 1 Standard
                 TYPE: - Display
                 PAGE: - Video1
                    Input 1 Std  cmdID= 40703  "
        ::= { iquav10CmdEntry 40703 }


    iquav10Video1VideoInputInput2Std OBJECT-TYPE
        SYNTAX            RollCallString
        MAX-ACCESS        read-only
        STATUS            current
        DESCRIPTION
                "CMNT: - Input 2 Standard
                 TYPE: - Display
                 PAGE: - Video1
                    Input 2 Std  cmdID= 40704  "
        ::= { iquav10CmdEntry 40704 }


    iquav10Video1VideoInputInputAnalogStd OBJECT-TYPE
        SYNTAX            RollCallString
        MAX-ACCESS        read-only
        STATUS            current
        DESCRIPTION
                "CMNT: - Input Analog Standard
                 TYPE: - Display
                 PAGE: - Video1
                    Input Analog Std  cmdID= 40705  "
        ::= { iquav10CmdEntry 40705 }


    iquav10Video1VideoInputIPSelect OBJECT-TYPE
        SYNTAX            INTEGER {
                            valInput1(0),
                            valInput2(1),
                            valAnalog(2)
                            }
        MAX-ACCESS        read-write
        STATUS            current
        DESCRIPTION
                "CMNT: - Select video input
                 TYPE: - RadiobuttonList
                 PAGE: - Video1
                    I/P Select  cmdID= 33024
                    Input 1  value= 0
                    Input 2  value= 1
                    Analog  value= 2  "
        ::= { iquav10CmdEntry 33024 }


    iquav10VideoInputValidStandards108050p OBJECT-TYPE
        SYNTAX            INTEGER { disable(0), enable(1)  }
        MAX-ACCESS        read-write
        STATUS            current
        DESCRIPTION
                "CMNT: - Select valid input standards
                 TYPE: - Checkbox
                 PAGE: - Video Input
                    1080/50p  cmdID= 33004  "
        ::= { iquav10CmdEntry 33004 }


    iquav10VideoInputValidStandards108059p OBJECT-TYPE
        SYNTAX            INTEGER { disable(0), enable(1)  }
        MAX-ACCESS        read-write
        STATUS            current
        DESCRIPTION
                "CMNT: - Select valid input standards
                 TYPE: - Checkbox
                 PAGE: - Video Input
                    1080/59p  cmdID= 33005  "
        ::= { iquav10CmdEntry 33005 }


    iquav10VideoInputValidStandards108025i OBJECT-TYPE
        SYNTAX            INTEGER { disable(0), enable(1)  }
        MAX-ACCESS        read-write
        STATUS            current
        DESCRIPTION
                "CMNT: - Select valid input standards
                 TYPE: - Checkbox
                 PAGE: - Video Input
                    1080/25i  cmdID= 33006  "
        ::= { iquav10CmdEntry 33006 }


    iquav10VideoInputValidStandards108029i OBJECT-TYPE
        SYNTAX            INTEGER { disable(0), enable(1)  }
        MAX-ACCESS        read-write
        STATUS            current
        DESCRIPTION
                "CMNT: - Select valid input standards
                 TYPE: - Checkbox
                 PAGE: - Video Input
                    1080/29i  cmdID= 33007  "
        ::= { iquav10CmdEntry 33007 }


    iquav10VideoInputValidStandards72050p OBJECT-TYPE
        SYNTAX            INTEGER { disable(0), enable(1)  }
        MAX-ACCESS        read-write
        STATUS            current
        DESCRIPTION
                "CMNT: - Select valid input standards
                 TYPE: - Checkbox
                 PAGE: - Video Input
                    720/50p  cmdID= 33010  "
        ::= { iquav10CmdEntry 33010 }


    iquav10VideoInputValidStandards72059p OBJECT-TYPE
        SYNTAX            INTEGER { disable(0), enable(1)  }
        MAX-ACCESS        read-write
        STATUS            current
        DESCRIPTION
                "CMNT: - Select valid input standards
                 TYPE: - Checkbox
                 PAGE: - Video Input
                    720/59p  cmdID= 33011  "
        ::= { iquav10CmdEntry 33011 }


    iquav10VideoInputValidStandards62525i OBJECT-TYPE
        SYNTAX            INTEGER { disable(0), enable(1)  }
        MAX-ACCESS        read-write
        STATUS            current
        DESCRIPTION
                "CMNT: - Select valid input standards
                 TYPE: - Checkbox
                 PAGE: - Video Input
                    625/25i  cmdID= 33009  "
        ::= { iquav10CmdEntry 33009 }


    iquav10VideoInputValidStandards52529i OBJECT-TYPE
        SYNTAX            INTEGER { disable(0), enable(1)  }
        MAX-ACCESS        read-write
        STATUS            current
        DESCRIPTION
                "CMNT: - Select valid input standards
                 TYPE: - Checkbox
                 PAGE: - Video Input
                    525/29i  cmdID= 33008  "
        ::= { iquav10CmdEntry 33008 }


    iquav10VideoInputValidStandards108023psf OBJECT-TYPE
        SYNTAX            INTEGER { disable(0), enable(1)  }
        MAX-ACCESS        read-write
        STATUS            current
        DESCRIPTION
                "CMNT: - Select valid input standards
                 TYPE: - Checkbox
                 PAGE: - Video Input
                    1080/23psf  cmdID= 33046  "
        ::= { iquav10CmdEntry 33046 }


    iquav10VideoInputValidStandards108025psf OBJECT-TYPE
        SYNTAX            INTEGER { disable(0), enable(1)  }
        MAX-ACCESS        read-write
        STATUS            current
        DESCRIPTION
                "CMNT: - Select valid input standards
                 TYPE: - Checkbox
                 PAGE: - Video Input
                    1080/25psf  cmdID= 33047  "
        ::= { iquav10CmdEntry 33047 }


    iquav10VideoInputValidStandards108025p OBJECT-TYPE
        SYNTAX            INTEGER { disable(0), enable(1)  }
        MAX-ACCESS        read-write
        STATUS            current
        DESCRIPTION
                "CMNT: - Select valid input standards
                 TYPE: - Checkbox
                 PAGE: - Video Input
                    1080/25p  cmdID= 33048  "
        ::= { iquav10CmdEntry 33048 }


    iquav10VideoInputValidStandards108029p OBJECT-TYPE
        SYNTAX            INTEGER { disable(0), enable(1)  }
        MAX-ACCESS        read-write
        STATUS            current
        DESCRIPTION
                "CMNT: - Select valid input standards
                 TYPE: - Checkbox
                 PAGE: - Video Input
                    1080/29p  cmdID= 33049  "
        ::= { iquav10CmdEntry 33049 }


    iquav10VideoInputErrorsErrorReset OBJECT-TYPE
        SYNTAX            INTEGER { noAction(0),valErrorReset(1) }
        MAX-ACCESS        read-write
        STATUS            current
        DESCRIPTION
                "CMNT: - 
                 TYPE: - Button
                 PAGE: - Video Input
                    Error Reset  cmdID= 33014
                    value= 1  "
        ::= { iquav10CmdEntry 33014 }


    iquav10VideoInputErrorsResetSec OBJECT-TYPE
        SYNTAX            RollCallString
        MAX-ACCESS        read-only
        STATUS            current
        DESCRIPTION
                "CMNT: - 
                 TYPE: - Display
                 PAGE: - Video Input
                    ResetSec  cmdID= 33015  "
        ::= { iquav10CmdEntry 33015 }


    iquav10VideoInputErrorsCRCErrs1 OBJECT-TYPE
        SYNTAX            RollCallString
        MAX-ACCESS        read-only
        STATUS            current
        DESCRIPTION
                "CMNT: - 
                 TYPE: - Display
                 PAGE: - Video Input
                    CRC Errs1  cmdID= 33016  "
        ::= { iquav10CmdEntry 33016 }


    iquav10VideoInputErrorsANCErrs1 OBJECT-TYPE
        SYNTAX            RollCallString
        MAX-ACCESS        read-only
        STATUS            current
        DESCRIPTION
                "CMNT: - 
                 TYPE: - Display
                 PAGE: - Video Input
                    ANC Errs1  cmdID= 33020  "
        ::= { iquav10CmdEntry 33020 }


    iquav10VideoInputErrorsCRCErrs2 OBJECT-TYPE
        SYNTAX            RollCallString
        MAX-ACCESS        read-only
        STATUS            current
        DESCRIPTION
                "CMNT: - 
                 TYPE: - Display
                 PAGE: - Video Input
                    CRC Errs2  cmdID= 33018  "
        ::= { iquav10CmdEntry 33018 }


    iquav10VideoInputErrorsANCErrs2 OBJECT-TYPE
        SYNTAX            RollCallString
        MAX-ACCESS        read-only
        STATUS            current
        DESCRIPTION
                "CMNT: - 
                 TYPE: - Display
                 PAGE: - Video Input
                    ANC Errs2  cmdID= 33022  "
        ::= { iquav10CmdEntry 33022 }


    iquav10VideoInputErrorsCRCErrSec1 OBJECT-TYPE
        SYNTAX            RollCallString
        MAX-ACCESS        read-only
        STATUS            current
        DESCRIPTION
                "CMNT: - 
                 TYPE: - Display
                 PAGE: - Video Input
                    CRC ErrSec1  cmdID= 33017  "
        ::= { iquav10CmdEntry 33017 }


    iquav10VideoInputErrorsANCErrSec1 OBJECT-TYPE
        SYNTAX            RollCallString
        MAX-ACCESS        read-only
        STATUS            current
        DESCRIPTION
                "CMNT: - 
                 TYPE: - Display
                 PAGE: - Video Input
                    ANC ErrSec1  cmdID= 33021  "
        ::= { iquav10CmdEntry 33021 }


    iquav10VideoInputErrorsCRCErrSec2 OBJECT-TYPE
        SYNTAX            RollCallString
        MAX-ACCESS        read-only
        STATUS            current
        DESCRIPTION
                "CMNT: - 
                 TYPE: - Display
                 PAGE: - Video Input
                    CRC ErrSec2  cmdID= 33019  "
        ::= { iquav10CmdEntry 33019 }


    iquav10VideoInputErrorsANCErrSec2 OBJECT-TYPE
        SYNTAX            RollCallString
        MAX-ACCESS        read-only
        STATUS            current
        DESCRIPTION
                "CMNT: - 
                 TYPE: - Display
                 PAGE: - Video Input
                    ANC ErrSec2  cmdID= 33023  "
        ::= { iquav10CmdEntry 33023 }


    iquav10Video1VideoInputSDAnlgEncode OBJECT-TYPE
        SYNTAX            INTEGER {
                            valSMPTE(0),
                            valBetaCam(1),
                            valMII(2)
                            }
        MAX-ACCESS        read-write
        STATUS            current
        DESCRIPTION
                "CMNT: - SD Analog Decoding YPbPr
                 TYPE: - RadiobuttonList
                 PAGE: - Video1
                    SD Anlg Encode  cmdID= 33037
                    SMPTE  value= 0
                    BetaCam  value= 1
                    MII  value= 2  "
        ::= { iquav10CmdEntry 33037 }


    iquav10Video1VideoInputAnlgType OBJECT-TYPE
        SYNTAX            INTEGER {
                            valCompositeSD(0),
                            valYCSD(1),
                            valYPbPrSDHD(2),
                            valGBR(3)
                            }
        MAX-ACCESS        read-write
        STATUS            current
        DESCRIPTION
                "CMNT: - Analog Input Type
                 TYPE: - RadiobuttonList
                 PAGE: - Video1
                    Anlg Type  cmdID= 33040
                    Composite (SD)  value= 0
                    Y/C (SD)  value= 1
                    YPbPr (SD/HD)  value= 2
                    GBR  value= 3  "
        ::= { iquav10CmdEntry 33040 }


    iquav10Video1VideoInputPedComposDec OBJECT-TYPE
        SYNTAX            INTEGER {
                            valPedestalnaNTSCnJ(0),
                            valPedestalNTSC(1)
                            }
        MAX-ACCESS        read-write
        STATUS            current
        DESCRIPTION
                "CMNT: - SD Analog Decoding Composite
                 TYPE: - RadiobuttonList
                 PAGE: - Video1
                    Ped Compos Dec  cmdID= 33042
                    Pedestal:n/aNTSC-J  value= 0
                    Pedestal:NTSC  value= 1  "
        ::= { iquav10CmdEntry 33042 }


    iquav10Video1VideoInputYCDelay OBJECT-TYPE
        SYNTAX            INTEGER
        MAX-ACCESS        read-write
        STATUS            current
        DESCRIPTION
                "CMNT: - 
                 TYPE: - Number
                 PAGE: - Video1
                    YC Delay  cmdID= 32999
                    min= -8  max= 7  step= 1  format= %0.0f  div_scale= 1  preset= 0
                    Min = -8  Max = 7  Step = 1  Preset = 0  "
        ::= { iquav10CmdEntry 32999 }


    iquav10Video1BackupEnable OBJECT-TYPE
        SYNTAX            INTEGER { disable(0), enable(1)  }
        MAX-ACCESS        read-write
        STATUS            current
        DESCRIPTION
                "CMNT: - Input Backup Enable
                 TYPE: - Checkbox
                 PAGE: - Video1
                    Backup Enable  cmdID= 39100  "
        ::= { iquav10CmdEntry 39100 }


    iquav10Video1BackupORInput1State OBJECT-TYPE
        SYNTAX            RollCallString
        MAX-ACCESS        read-only
        STATUS            current
        DESCRIPTION
                "CMNT: - Input 1 OR State
                 TYPE: - Display
                 PAGE: - Video1
                    OR Input1 State  cmdID= 39101  "
        ::= { iquav10CmdEntry 39101 }


    iquav10Video1BackupORInput2State OBJECT-TYPE
        SYNTAX            RollCallString
        MAX-ACCESS        read-only
        STATUS            current
        DESCRIPTION
                "CMNT: - Input 2 OR State
                 TYPE: - Display
                 PAGE: - Video1
                    OR Input2 State  cmdID= 39102  "
        ::= { iquav10CmdEntry 39102 }


    iquav10Video1BackupRevertDelay OBJECT-TYPE
        SYNTAX            INTEGER
        MAX-ACCESS        read-write
        STATUS            current
        DESCRIPTION
                "CMNT: - Backup Reversion Delay
                 TYPE: - Number
                 PAGE: - Video1
                    Revert Delay  cmdID= 39141
                    min= 0  max= 1000  step= 10  format= %0.0f s  div_scale= 10  preset= 0
                    Min = 0 s  Max = 100 s  Step = 1 s  Preset = 0 s  "
        ::= { iquav10CmdEntry 39141 }


    iquav10Video1BackupPriority OBJECT-TYPE
        SYNTAX            INTEGER {
                            valNone(0),
                            valPriority1(1),
                            valPriority2(2)
                            }
        MAX-ACCESS        read-write
        STATUS            current
        DESCRIPTION
                "CMNT: - Input Backup Priority
                 TYPE: - RadiobuttonList
                 PAGE: - Video1
                    Priority  cmdID= 39103
                    None  value= 0
                    Priority 1  value= 1
                    Priority 2  value= 2  "
        ::= { iquav10CmdEntry 39103 }


    iquav10Video1BackupQualifyInvStd OBJECT-TYPE
        SYNTAX            INTEGER { disable(0), enable(1)  }
        MAX-ACCESS        read-write
        STATUS            current
        DESCRIPTION
                "CMNT: - Backup Invalid Standard
                 TYPE: - Checkbox
                 PAGE: - Video1
                    Qualify Inv Std  cmdID= 39104  "
        ::= { iquav10CmdEntry 39104 }


    iquav10Video1BackupQualifyCRCErr OBJECT-TYPE
        SYNTAX            INTEGER { disable(0), enable(1)  }
        MAX-ACCESS        read-write
        STATUS            current
        DESCRIPTION
                "CMNT: - Backup CRC Error
                 TYPE: - Checkbox
                 PAGE: - Video1
                    Qualify CRC Err  cmdID= 39105  "
        ::= { iquav10CmdEntry 39105 }


    iquav10Video1BackupQualifyANCErr OBJECT-TYPE
        SYNTAX            INTEGER { disable(0), enable(1)  }
        MAX-ACCESS        read-write
        STATUS            current
        DESCRIPTION
                "CMNT: - Backup ANC Error
                 TYPE: - Checkbox
                 PAGE: - Video1
                    Qualify ANC Err  cmdID= 39106  "
        ::= { iquav10CmdEntry 39106 }


    iquav10Video1BackupQualifyAudioFail OBJECT-TYPE
        SYNTAX            INTEGER { disable(0), enable(1)  }
        MAX-ACCESS        read-write
        STATUS            current
        DESCRIPTION
                "CMNT: - Backup Qual Audio Lost
                 TYPE: - Checkbox
                 PAGE: - Video1
                    Qualify Audio Fail  cmdID= 39142  "
        ::= { iquav10CmdEntry 39142 }


    iquav10BackupInput1SelStatInp1OK OBJECT-TYPE
        SYNTAX            RollCallString
        MAX-ACCESS        read-only
        STATUS            current
        DESCRIPTION
                "CMNT: - Backup Sel 1 Inp 1 OK Status
                 TYPE: - Display
                 PAGE: - Backup
                    Stat Inp1 OK  cmdID= 39127  "
        ::= { iquav10CmdEntry 39127 }


    iquav10BackupInput1SelStatInp2FAIL OBJECT-TYPE
        SYNTAX            RollCallString
        MAX-ACCESS        read-only
        STATUS            current
        DESCRIPTION
                "CMNT: - Backup Sel 1 Inp 2 FAIL Status
                 TYPE: - Display
                 PAGE: - Backup
                    Stat Inp2 FAIL  cmdID= 39128  "
        ::= { iquav10CmdEntry 39128 }


    iquav10BackupInput1SelStatInp2Err OBJECT-TYPE
        SYNTAX            RollCallString
        MAX-ACCESS        read-only
        STATUS            current
        DESCRIPTION
                "CMNT: - Backup Sel 1 Inp 2 ERR Status
                 TYPE: - Display
                 PAGE: - Backup
                    Stat Inp2 Err  cmdID= 39139  "
        ::= { iquav10CmdEntry 39139 }


    iquav10BackupInput1SelStatAUDFail2 OBJECT-TYPE
        SYNTAX            RollCallString
        MAX-ACCESS        read-only
        STATUS            current
        DESCRIPTION
                "CMNT: - Backup Reversion Delay
                 TYPE: - Display
                 PAGE: - Backup
                    Stat AUD Fail 2  cmdID= 39144  "
        ::= { iquav10CmdEntry 39144 }


    iquav10BackupInput1SelStatStd2 OBJECT-TYPE
        SYNTAX            RollCallString
        MAX-ACCESS        read-only
        STATUS            current
        DESCRIPTION
                "CMNT: - 
                 TYPE: - Display
                 PAGE: - Backup
                    Stat Std 2  cmdID= 39173  "
        ::= { iquav10CmdEntry 39173 }


    iquav10BackupInput1SelStatGPI1 OBJECT-TYPE
        SYNTAX            RollCallString
        MAX-ACCESS        read-only
        STATUS            current
        DESCRIPTION
                "CMNT: - Backup Sel 1 GPI 1 Status
                 TYPE: - Display
                 PAGE: - Backup
                    Stat GPI 1  cmdID= 39129  "
        ::= { iquav10CmdEntry 39129 }


    iquav10BackupInput1SelStatGPI2 OBJECT-TYPE
        SYNTAX            RollCallString
        MAX-ACCESS        read-only
        STATUS            current
        DESCRIPTION
                "CMNT: - Backup Sel 1 GPI 2 Status
                 TYPE: - Display
                 PAGE: - Backup
                    Stat GPI 2  cmdID= 39130  "
        ::= { iquav10CmdEntry 39130 }


    iquav10BackupInput1SelEnblInp1OK OBJECT-TYPE
        SYNTAX            INTEGER { disable(0), enable(1)  }
        MAX-ACCESS        read-write
        STATUS            current
        DESCRIPTION
                "CMNT: - Backup Sel 1 Inp 1 OK
                 TYPE: - Checkbox
                 PAGE: - Backup
                    Enbl Inp1 OK  cmdID= 39107  "
        ::= { iquav10CmdEntry 39107 }


    iquav10BackupInput1SelEnblInp2FAIL OBJECT-TYPE
        SYNTAX            INTEGER { disable(0), enable(1)  }
        MAX-ACCESS        read-write
        STATUS            current
        DESCRIPTION
                "CMNT: - Backup Sel 1 Inp 2 FAIL
                 TYPE: - Checkbox
                 PAGE: - Backup
                    Enbl Inp2 FAIL  cmdID= 39108  "
        ::= { iquav10CmdEntry 39108 }


    iquav10BackupInput1SelEnblInp2Err OBJECT-TYPE
        SYNTAX            INTEGER { disable(0), enable(1)  }
        MAX-ACCESS        read-write
        STATUS            current
        DESCRIPTION
                "CMNT: - Backup Sel 1 Inp 2 ERR
                 TYPE: - Checkbox
                 PAGE: - Backup
                    Enbl Inp2 Err  cmdID= 39135  "
        ::= { iquav10CmdEntry 39135 }


    iquav10BackupInput1SelEnblGPI1 OBJECT-TYPE
        SYNTAX            INTEGER { disable(0), enable(1)  }
        MAX-ACCESS        read-write
        STATUS            current
        DESCRIPTION
                "CMNT: - Backup Sel 1 GPI 1
                 TYPE: - Checkbox
                 PAGE: - Backup
                    Enbl GPI 1  cmdID= 39109  "
        ::= { iquav10CmdEntry 39109 }


    iquav10BackupInput1SelEnblGPI2 OBJECT-TYPE
        SYNTAX            INTEGER { disable(0), enable(1)  }
        MAX-ACCESS        read-write
        STATUS            current
        DESCRIPTION
                "CMNT: - Backup Sel 1 GPI 2
                 TYPE: - Checkbox
                 PAGE: - Backup
                    Enbl GPI 2  cmdID= 39110  "
        ::= { iquav10CmdEntry 39110 }


    iquav10BackupInput1SelEnblStdInp2 OBJECT-TYPE
        SYNTAX            INTEGER { disable(0), enable(1)  }
        MAX-ACCESS        read-write
        STATUS            current
        DESCRIPTION
                "CMNT: - 
                 TYPE: - Checkbox
                 PAGE: - Backup
                    Enbl Std Inp2  cmdID= 39172  "
        ::= { iquav10CmdEntry 39172 }


    iquav10BackupInput1SelDlyInp1OK OBJECT-TYPE
        SYNTAX            INTEGER
        MAX-ACCESS        read-write
        STATUS            current
        DESCRIPTION
                "CMNT: - Backup Sel 1 Inp 1 OK Delay
                 TYPE: - Number
                 PAGE: - Backup
                    Dly Inp1 OK  cmdID= 39115
                    min= 10  max= 100  step= 1  format= %0.1f s  div_scale= 10  preset= 10
                    Min = 1.0 s  Max = 10.0 s  Step = 0.1 s  Preset = 1.0 s  "
        ::= { iquav10CmdEntry 39115 }


    iquav10BackupInput1SelDlyInp2FAIL OBJECT-TYPE
        SYNTAX            INTEGER
        MAX-ACCESS        read-write
        STATUS            current
        DESCRIPTION
                "CMNT: - Backup Sel 1 Inp 2 FAIL Delay
                 TYPE: - Number
                 PAGE: - Backup
                    Dly Inp2 FAIL  cmdID= 39116
                    min= 0  max= 100  step= 1  format= %0.1f s  div_scale= 10  preset= 1
                    Min = 0.0 s  Max = 10.0 s  Step = 0.1 s  Preset = 0.1 s  "
        ::= { iquav10CmdEntry 39116 }


    iquav10BackupInput1SelDlyInp2Err OBJECT-TYPE
        SYNTAX            INTEGER
        MAX-ACCESS        read-write
        STATUS            current
        DESCRIPTION
                "CMNT: - Backup Sel 1 Inp 2 ERR Delay
                 TYPE: - Number
                 PAGE: - Backup
                    Dly Inp2 Err  cmdID= 39137
                    min= 10  max= 100  step= 10  format= %0.0f s  div_scale= 10  preset= 50
                    Min = 1 s  Max = 10 s  Step = 1 s  Preset = 5 s  "
        ::= { iquav10CmdEntry 39137 }


    iquav10BackupInput1SelDlyGPI1 OBJECT-TYPE
        SYNTAX            INTEGER
        MAX-ACCESS        read-write
        STATUS            current
        DESCRIPTION
                "CMNT: - Backup Sel 1 GPI 1 Delay
                 TYPE: - Number
                 PAGE: - Backup
                    Dly GPI 1  cmdID= 39117
                    min= 0  max= 100  step= 1  format= %0.1f s  div_scale= 10  preset= 0
                    Min = 0.0 s  Max = 10.0 s  Step = 0.1 s  Preset = 0.0 s  "
        ::= { iquav10CmdEntry 39117 }


    iquav10BackupInput1SelDlyGPI2 OBJECT-TYPE
        SYNTAX            INTEGER
        MAX-ACCESS        read-write
        STATUS            current
        DESCRIPTION
                "CMNT: - Backup Sel 1 GPI 2 Delay
                 TYPE: - Number
                 PAGE: - Backup
                    Dly GPI 2  cmdID= 39118
                    min= 0  max= 100  step= 1  format= %0.1f s  div_scale= 10  preset= 0
                    Min = 0.0 s  Max = 10.0 s  Step = 0.1 s  Preset = 0.0 s  "
        ::= { iquav10CmdEntry 39118 }


    iquav10BackupInput1SelDlyAud2FAIL OBJECT-TYPE
        SYNTAX            INTEGER
        MAX-ACCESS        read-write
        STATUS            current
        DESCRIPTION
                "CMNT: - Backup Inp1 2 aud Fail Delay
                 TYPE: - Number
                 PAGE: - Backup
                    Dly Aud2 FAIL  cmdID= 39145
                    min= 10  max= 100  step= 1  format= %0.1f s  div_scale= 10  preset= 10
                    Min = 1.0 s  Max = 10.0 s  Step = 0.1 s  Preset = 1.0 s  "
        ::= { iquav10CmdEntry 39145 }


    iquav10BackupInput1SelDlyStd2 OBJECT-TYPE
        SYNTAX            INTEGER
        MAX-ACCESS        read-write
        STATUS            current
        DESCRIPTION
                "CMNT: - 
                 TYPE: - Number
                 PAGE: - Backup
                    Dly Std 2  cmdID= 39171
                    min= 0  max= 100  step= 1  format= %0.1f s  div_scale= 10  preset= 10
                    Min = 0.0 s  Max = 10.0 s  Step = 0.1 s  Preset = 1.0 s  "
        ::= { iquav10CmdEntry 39171 }


    iquav10BackupInput1SelGPI1State OBJECT-TYPE
        SYNTAX            INTEGER {
                            valHigh(1),
                            valLow(0)
                            }
        MAX-ACCESS        read-write
        STATUS            current
        DESCRIPTION
                "CMNT: - Backup Sel 1 GPI 1 val
                 TYPE: - RadiobuttonList
                 PAGE: - Backup
                    GPI 1 State  cmdID= 39123
                    High  value= 1
                    Low  value= 0  "
        ::= { iquav10CmdEntry 39123 }


    iquav10BackupInput1SelGPI2State OBJECT-TYPE
        SYNTAX            INTEGER {
                            valHigh(1),
                            valLow(0)
                            }
        MAX-ACCESS        read-write
        STATUS            current
        DESCRIPTION
                "CMNT: - Backup Sel 1 GPI 2 val
                 TYPE: - RadiobuttonList
                 PAGE: - Backup
                    GPI 2 State  cmdID= 39124
                    High  value= 1
                    Low  value= 0  "
        ::= { iquav10CmdEntry 39124 }


    iquav10BackupInput1SelInp12AudFailG1C1 OBJECT-TYPE
        SYNTAX            INTEGER { disable(0), enable(1)  }
        MAX-ACCESS        read-write
        STATUS            current
        DESCRIPTION
                "CMNT: - Backup Inp1 2 Aud Fail G1C1
                 TYPE: - Checkbox
                 PAGE: - Backup
                    Inp1 2 Aud Fail G1C1  cmdID= 39149  "
        ::= { iquav10CmdEntry 39149 }


    iquav10BackupInput1SelInp12AudFailG1C2 OBJECT-TYPE
        SYNTAX            INTEGER { disable(0), enable(1)  }
        MAX-ACCESS        read-write
        STATUS            current
        DESCRIPTION
                "CMNT: - Backup Inp1 2 Aud Fail G1C2
                 TYPE: - Checkbox
                 PAGE: - Backup
                    Inp1 2 Aud Fail G1C2  cmdID= 39150  "
        ::= { iquav10CmdEntry 39150 }


    iquav10BackupInput1SelInp12AudFailG2C1 OBJECT-TYPE
        SYNTAX            INTEGER { disable(0), enable(1)  }
        MAX-ACCESS        read-write
        STATUS            current
        DESCRIPTION
                "CMNT: - Backup Inp1 2 Aud Fail G2C1
                 TYPE: - Checkbox
                 PAGE: - Backup
                    Inp1 2 Aud Fail G2C1  cmdID= 39151  "
        ::= { iquav10CmdEntry 39151 }


    iquav10BackupInput1SelInp12AudFailG2C2 OBJECT-TYPE
        SYNTAX            INTEGER { disable(0), enable(1)  }
        MAX-ACCESS        read-write
        STATUS            current
        DESCRIPTION
                "CMNT: - Backup Inp1 2 Aud Fail G2C2
                 TYPE: - Checkbox
                 PAGE: - Backup
                    Inp1 2 Aud Fail G2C2  cmdID= 39152  "
        ::= { iquav10CmdEntry 39152 }


    iquav10BackupInput1SelInp12AudFailG3C1 OBJECT-TYPE
        SYNTAX            INTEGER { disable(0), enable(1)  }
        MAX-ACCESS        read-write
        STATUS            current
        DESCRIPTION
                "CMNT: - Backup Inp1 2 Aud Fail G3C1
                 TYPE: - Checkbox
                 PAGE: - Backup
                    Inp1 2 Aud Fail G3C1  cmdID= 39153  "
        ::= { iquav10CmdEntry 39153 }


    iquav10BackupInput1SelInp12AudFailG3C2 OBJECT-TYPE
        SYNTAX            INTEGER { disable(0), enable(1)  }
        MAX-ACCESS        read-write
        STATUS            current
        DESCRIPTION
                "CMNT: - Backup Inp1 2 Aud Fail G3C2
                 TYPE: - Checkbox
                 PAGE: - Backup
                    Inp1 2 Aud Fail G3C2  cmdID= 39154  "
        ::= { iquav10CmdEntry 39154 }


    iquav10BackupInput1SelInp12AudFailG4C1 OBJECT-TYPE
        SYNTAX            INTEGER { disable(0), enable(1)  }
        MAX-ACCESS        read-write
        STATUS            current
        DESCRIPTION
                "CMNT: - Backup Inp1 2 Aud Fail G4C1
                 TYPE: - Checkbox
                 PAGE: - Backup
                    Inp1 2 Aud Fail G4C1  cmdID= 39155  "
        ::= { iquav10CmdEntry 39155 }


    iquav10BackupInput1SelInp12AudFailG4C2 OBJECT-TYPE
        SYNTAX            INTEGER { disable(0), enable(1)  }
        MAX-ACCESS        read-write
        STATUS            current
        DESCRIPTION
                "CMNT: - Backup Inp1 2 Aud Fail G4C2
                 TYPE: - Checkbox
                 PAGE: - Backup
                    Inp1 2 Aud Fail G4C2  cmdID= 39156  "
        ::= { iquav10CmdEntry 39156 }


    iquav10BackupInput1SelInp12AudFailLockGrp OBJECT-TYPE
        SYNTAX            INTEGER { disable(0), enable(1)  }
        MAX-ACCESS        read-write
        STATUS            current
        DESCRIPTION
                "CMNT: - Backup Inp1 2 Aud Fail Lock Grp
                 TYPE: - Checkbox
                 PAGE: - Backup
                    Inp1 2 Aud Fail Lock Grp  cmdID= 39148  "
        ::= { iquav10CmdEntry 39148 }


    iquav10BackupInput1SelSelAll OBJECT-TYPE
        SYNTAX            INTEGER { noAction(0),valSelAll(1) }
        MAX-ACCESS        read-write
        STATUS            current
        DESCRIPTION
                "CMNT: - Backup Inp1 2 Aud Fail Sel All
                 TYPE: - Button
                 PAGE: - Backup
                    Sel All  cmdID= 39146
                    value= 1  "
        ::= { iquav10CmdEntry 39146 }


    iquav10BackupInput1SelSelNone OBJECT-TYPE
        SYNTAX            INTEGER { noAction(0),valSelNone(1) }
        MAX-ACCESS        read-write
        STATUS            current
        DESCRIPTION
                "CMNT: - Backup Inp1 2 Aud Fail Sel None
                 TYPE: - Button
                 PAGE: - Backup
                    Sel None  cmdID= 39147
                    value= 1  "
        ::= { iquav10CmdEntry 39147 }


    iquav10BackupInput2SelStatInp2OK OBJECT-TYPE
        SYNTAX            RollCallString
        MAX-ACCESS        read-only
        STATUS            current
        DESCRIPTION
                "CMNT: - Backup Sel 2 Inp 2 OK Status
                 TYPE: - Display
                 PAGE: - Backup
                    Stat Inp2 OK  cmdID= 39131  "
        ::= { iquav10CmdEntry 39131 }


    iquav10BackupInput2SelStatInp1FAIL OBJECT-TYPE
        SYNTAX            RollCallString
        MAX-ACCESS        read-only
        STATUS            current
        DESCRIPTION
                "CMNT: - Backup Sel 2 Inp 1 FAIL Status
                 TYPE: - Display
                 PAGE: - Backup
                    Stat Inp1 FAIL  cmdID= 39132  "
        ::= { iquav10CmdEntry 39132 }


    iquav10BackupInput2SelStatInp1Err OBJECT-TYPE
        SYNTAX            RollCallString
        MAX-ACCESS        read-only
        STATUS            current
        DESCRIPTION
                "CMNT: - Backup Sel 2 Inp 1 ERR Status
                 TYPE: - Display
                 PAGE: - Backup
                    Stat Inp1 Err  cmdID= 39140  "
        ::= { iquav10CmdEntry 39140 }


    iquav10BackupInput2SelStatAUDFail1 OBJECT-TYPE
        SYNTAX            RollCallString
        MAX-ACCESS        read-only
        STATUS            current
        DESCRIPTION
                "CMNT: - Backup Reversion Delay
                 TYPE: - Display
                 PAGE: - Backup
                    Stat AUD Fail 1  cmdID= 39158  "
        ::= { iquav10CmdEntry 39158 }


    iquav10BackupInput2SelStatStd1 OBJECT-TYPE
        SYNTAX            RollCallString
        MAX-ACCESS        read-only
        STATUS            current
        DESCRIPTION
                "CMNT: - 
                 TYPE: - Display
                 PAGE: - Backup
                    Stat Std 1  cmdID= 39176  "
        ::= { iquav10CmdEntry 39176 }


    iquav10BackupInput2SelStatGPI1 OBJECT-TYPE
        SYNTAX            RollCallString
        MAX-ACCESS        read-only
        STATUS            current
        DESCRIPTION
                "CMNT: - Backup Sel 2 GPI 1 Status
                 TYPE: - Display
                 PAGE: - Backup
                    Stat GPI 1  cmdID= 39133  "
        ::= { iquav10CmdEntry 39133 }


    iquav10BackupInput2SelStatGPI2 OBJECT-TYPE
        SYNTAX            RollCallString
        MAX-ACCESS        read-only
        STATUS            current
        DESCRIPTION
                "CMNT: - Backup Sel 2 GPI 2 Status
                 TYPE: - Display
                 PAGE: - Backup
                    Stat GPI 2  cmdID= 39134  "
        ::= { iquav10CmdEntry 39134 }


    iquav10BackupInput2SelEnblInp2OK OBJECT-TYPE
        SYNTAX            INTEGER { disable(0), enable(1)  }
        MAX-ACCESS        read-write
        STATUS            current
        DESCRIPTION
                "CMNT: - Backup Sel 2 Inp 2 OK
                 TYPE: - Checkbox
                 PAGE: - Backup
                    Enbl Inp2 OK  cmdID= 39111  "
        ::= { iquav10CmdEntry 39111 }


    iquav10BackupInput2SelEnblInp1FAIL OBJECT-TYPE
        SYNTAX            INTEGER { disable(0), enable(1)  }
        MAX-ACCESS        read-write
        STATUS            current
        DESCRIPTION
                "CMNT: - Backup Sel 2 Inp 1 FAIL
                 TYPE: - Checkbox
                 PAGE: - Backup
                    Enbl Inp1 FAIL  cmdID= 39112  "
        ::= { iquav10CmdEntry 39112 }


    iquav10BackupInput2SelEnblInp1Err OBJECT-TYPE
        SYNTAX            INTEGER { disable(0), enable(1)  }
        MAX-ACCESS        read-write
        STATUS            current
        DESCRIPTION
                "CMNT: - Backup Sel 2 Inp 1 ERR
                 TYPE: - Checkbox
                 PAGE: - Backup
                    Enbl Inp1 Err  cmdID= 39136  "
        ::= { iquav10CmdEntry 39136 }


    iquav10BackupInput2SelEnblGPI1 OBJECT-TYPE
        SYNTAX            INTEGER { disable(0), enable(1)  }
        MAX-ACCESS        read-write
        STATUS            current
        DESCRIPTION
                "CMNT: - Backup Sel 2 GPI 1
                 TYPE: - Checkbox
                 PAGE: - Backup
                    Enbl GPI 1  cmdID= 39113  "
        ::= { iquav10CmdEntry 39113 }


    iquav10BackupInput2SelEnblGPI2 OBJECT-TYPE
        SYNTAX            INTEGER { disable(0), enable(1)  }
        MAX-ACCESS        read-write
        STATUS            current
        DESCRIPTION
                "CMNT: - Backup Sel 2 GPI 2
                 TYPE: - Checkbox
                 PAGE: - Backup
                    Enbl GPI 2  cmdID= 39114  "
        ::= { iquav10CmdEntry 39114 }


    iquav10BackupInput2SelEnblAudInp1Err OBJECT-TYPE
        SYNTAX            INTEGER { disable(0), enable(1)  }
        MAX-ACCESS        read-write
        STATUS            current
        DESCRIPTION
                "CMNT: - Backup Inp2 1 Aud Fail Enable
                 TYPE: - Checkbox
                 PAGE: - Backup
                    Enbl Aud Inp1 Err  cmdID= 39157  "
        ::= { iquav10CmdEntry 39157 }


    iquav10BackupInput2SelEnblStdInp1 OBJECT-TYPE
        SYNTAX            INTEGER { disable(0), enable(1)  }
        MAX-ACCESS        read-write
        STATUS            current
        DESCRIPTION
                "CMNT: - 
                 TYPE: - Checkbox
                 PAGE: - Backup
                    Enbl Std Inp 1  cmdID= 39175  "
        ::= { iquav10CmdEntry 39175 }


    iquav10BackupInput2SelInp21AudFailG1C1 OBJECT-TYPE
        SYNTAX            INTEGER { disable(0), enable(1)  }
        MAX-ACCESS        read-write
        STATUS            current
        DESCRIPTION
                "CMNT: - Backup Inp2 1 Aud Fail G1C1
                 TYPE: - Checkbox
                 PAGE: - Backup
                    Inp2 1 Aud Fail G1C1  cmdID= 39163  "
        ::= { iquav10CmdEntry 39163 }


    iquav10BackupInput2SelInp21AudFailG1C2 OBJECT-TYPE
        SYNTAX            INTEGER { disable(0), enable(1)  }
        MAX-ACCESS        read-write
        STATUS            current
        DESCRIPTION
                "CMNT: - Backup Inp2 1 Aud Fail G1C2
                 TYPE: - Checkbox
                 PAGE: - Backup
                    Inp2 1 Aud Fail G1C2  cmdID= 39164  "
        ::= { iquav10CmdEntry 39164 }


    iquav10BackupInput2SelInp21AudFailG2C1 OBJECT-TYPE
        SYNTAX            INTEGER { disable(0), enable(1)  }
        MAX-ACCESS        read-write
        STATUS            current
        DESCRIPTION
                "CMNT: - Backup Inp2 1 Aud Fail G2C1
                 TYPE: - Checkbox
                 PAGE: - Backup
                    Inp2 1 Aud Fail G2C1  cmdID= 39165  "
        ::= { iquav10CmdEntry 39165 }


    iquav10BackupInput2SelInp21AudFailG2C2 OBJECT-TYPE
        SYNTAX            INTEGER { disable(0), enable(1)  }
        MAX-ACCESS        read-write
        STATUS            current
        DESCRIPTION
                "CMNT: - Backup Inp2 1 Aud Fail G2C2
                 TYPE: - Checkbox
                 PAGE: - Backup
                    Inp2 1 Aud Fail G2C2  cmdID= 39166  "
        ::= { iquav10CmdEntry 39166 }


    iquav10BackupInput2SelInp21AudFailG3C1 OBJECT-TYPE
        SYNTAX            INTEGER { disable(0), enable(1)  }
        MAX-ACCESS        read-write
        STATUS            current
        DESCRIPTION
                "CMNT: - Backup Inp2 1 Aud Fail G3C1
                 TYPE: - Checkbox
                 PAGE: - Backup
                    Inp2 1 Aud Fail G3C1  cmdID= 39167  "
        ::= { iquav10CmdEntry 39167 }


    iquav10BackupInput2SelInp21AudFailG3C2 OBJECT-TYPE
        SYNTAX            INTEGER { disable(0), enable(1)  }
        MAX-ACCESS        read-write
        STATUS            current
        DESCRIPTION
                "CMNT: - Backup Inp2 1 Aud Fail G3C2
                 TYPE: - Checkbox
                 PAGE: - Backup
                    Inp2 1 Aud Fail G3C2  cmdID= 39168  "
        ::= { iquav10CmdEntry 39168 }


    iquav10BackupInput2SelInp21AudFailG4C1 OBJECT-TYPE
        SYNTAX            INTEGER { disable(0), enable(1)  }
        MAX-ACCESS        read-write
        STATUS            current
        DESCRIPTION
                "CMNT: - Backup Inp2 1 Aud Fail G4C1
                 TYPE: - Checkbox
                 PAGE: - Backup
                    Inp2 1 Aud Fail G4C1  cmdID= 39169  "
        ::= { iquav10CmdEntry 39169 }


    iquav10BackupInput2SelInp21AudFailG4C2 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Inp2 1 Aud Fail G4C2  cmdID= 39170  "
        ::= { iquav10CmdEntry 39170 }


    iquav10BackupInput2SelDlyInp2OK OBJECT-TYPE
        SYNTAX            INTEGER
        MAX-ACCESS        read-write
        STATUS            current
        DESCRIPTION
                "CMNT: - Backup Sel 2 Inp 2 OK Delay
                 TYPE: - Number
                 PAGE: - Backup
                    Dly Inp2 OK  cmdID= 39119
                    min= 10  max= 100  step= 1  format= %0.1f s  div_scale= 10  preset= 10
                    Min = 1.0 s  Max = 10.0 s  Step = 0.1 s  Preset = 1.0 s  "
        ::= { iquav10CmdEntry 39119 }


    iquav10BackupInput2SelDlyInp1FAIL OBJECT-TYPE
        SYNTAX            INTEGER
        MAX-ACCESS        read-write
        STATUS            current
        DESCRIPTION
                "CMNT: - Backup Sel 2 Inp 1 FAIL Delay
                 TYPE: - Number
                 PAGE: - Backup
                    Dly Inp1 FAIL  cmdID= 39120
                    min= 0  max= 100  step= 1  format= %0.1f s  div_scale= 10  preset= 1
                    Min = 0.0 s  Max = 10.0 s  Step = 0.1 s  Preset = 0.1 s  "
        ::= { iquav10CmdEntry 39120 }


    iquav10BackupInput2SelDlyInp1Err OBJECT-TYPE
        SYNTAX            INTEGER
        MAX-ACCESS        read-write
        STATUS            current
        DESCRIPTION
                "CMNT: - Backup Sel 2 Inp 1 ERR Delay
                 TYPE: - Number
                 PAGE: - Backup
                    Dly Inp1 Err  cmdID= 39138
                    min= 10  max= 100  step= 10  format= %0.0f s  div_scale= 10  preset= 50
                    Min = 1 s  Max = 10 s  Step = 1 s  Preset = 5 s  "
        ::= { iquav10CmdEntry 39138 }


    iquav10BackupInput2SelDlyGPI1 OBJECT-TYPE
        SYNTAX            INTEGER
        MAX-ACCESS        read-write
        STATUS            current
        DESCRIPTION
                "CMNT: - Backup Sel 2 GPI 1 Delay
                 TYPE: - Number
                 PAGE: - Backup
                    Dly GPI 1  cmdID= 39121
                    min= 0  max= 100  step= 1  format= %0.1f s  div_scale= 10  preset= 0
                    Min = 0.0 s  Max = 10.0 s  Step = 0.1 s  Preset = 0.0 s  "
        ::= { iquav10CmdEntry 39121 }


    iquav10BackupInput2SelDlyGPI2 OBJECT-TYPE
        SYNTAX            INTEGER
        MAX-ACCESS        read-write
        STATUS            current
        DESCRIPTION
                "CMNT: - Backup Sel 2 GPI 2 Delay
                 TYPE: - Number
                 PAGE: - Backup
                    Dly GPI 2  cmdID= 39122
                    min= 0  max= 100  step= 1  format= %0.1f s  div_scale= 10  preset= 0
                    Min = 0.0 s  Max = 10.0 s  Step = 0.1 s  Preset = 0.0 s  "
        ::= { iquav10CmdEntry 39122 }


    iquav10BackupInput2SelDlyAud1FAIL OBJECT-TYPE
        SYNTAX            INTEGER
        MAX-ACCESS        read-write
        STATUS            current
        DESCRIPTION
                "CMNT: - Backup Inp2 1 Aud Fail Delay
                 TYPE: - Number
                 PAGE: - Backup
                    Dly Aud1 FAIL  cmdID= 39159
                    min= 10  max= 100  step= 1  format= %0.1f s  div_scale= 10  preset= 10
                    Min = 1.0 s  Max = 10.0 s  Step = 0.1 s  Preset = 1.0 s  "
        ::= { iquav10CmdEntry 39159 }


    iquav10BackupInput2SelDlyStd1 OBJECT-TYPE
        SYNTAX            INTEGER
        MAX-ACCESS        read-write
        STATUS            current
        DESCRIPTION
                "CMNT: - 
                 TYPE: - Number
                 PAGE: - Backup
                    Dly Std 1  cmdID= 39174
                    min= 0  max= 100  step= 1  format= %0.1f s  div_scale= 10  preset= 10
                    Min = 0.0 s  Max = 10.0 s  Step = 0.1 s  Preset = 1.0 s  "
        ::= { iquav10CmdEntry 39174 }


    iquav10BackupInput2SelGPI1State OBJECT-TYPE
        SYNTAX            INTEGER {
                            valOn(0),
                            valOff(1)
                            }
        MAX-ACCESS        read-write
        STATUS            current
        DESCRIPTION
                "CMNT: - Backup Sel 2 GPI 1 val
                 TYPE: - RadiobuttonList
                 PAGE: - Backup
                    GPI 1 State  cmdID= 39125
                    On  value= 0
                    Off  value= 1  "
        ::= { iquav10CmdEntry 39125 }


    iquav10BackupInput2SelGPI2State OBJECT-TYPE
        SYNTAX            INTEGER {
                            valOn(0),
                            valOff(1)
                            }
        MAX-ACCESS        read-write
        STATUS            current
        DESCRIPTION
                "CMNT: - Backup Sel 2 GPI 2 val
                 TYPE: - RadiobuttonList
                 PAGE: - Backup
                    GPI 2 State  cmdID= 39126
                    On  value= 0
                    Off  value= 1  "
        ::= { iquav10CmdEntry 39126 }


    iquav10BackupInput2SelInp21AudFailLockGrp OBJECT-TYPE
        SYNTAX            INTEGER { disable(0), enable(1)  }
        MAX-ACCESS        read-write
        STATUS            current
        DESCRIPTION
                "CMNT: - Backup Inp2 1 Aud Fail Lock Grp
                 TYPE: - Checkbox
                 PAGE: - Backup
                    Inp2 1 Aud Fail Lock Grp  cmdID= 39162  "
        ::= { iquav10CmdEntry 39162 }


    iquav10BackupInput2SelSelAll OBJECT-TYPE
        SYNTAX            INTEGER { noAction(0),valSelAll(1) }
        MAX-ACCESS        read-write
        STATUS            current
        DESCRIPTION
                "CMNT: - Backup Inp2 1 Aud Fail Sel All
                 TYPE: - Button
                 PAGE: - Backup
                    Sel All  cmdID= 39160
                    value= 1  "
        ::= { iquav10CmdEntry 39160 }


    iquav10BackupInput2SelSelNone OBJECT-TYPE
        SYNTAX            INTEGER { noAction(0),valSelNone(1) }
        MAX-ACCESS        read-write
        STATUS            current
        DESCRIPTION
                "CMNT: - Backup Inp2 1 Aud Fail Sel None
                 TYPE: - Button
                 PAGE: - Backup
                    Sel None  cmdID= 39161
                    value= 1  "
        ::= { iquav10CmdEntry 39161 }


    iquav10Video2VideoOutputConversionStandard OBJECT-TYPE
        SYNTAX            INTEGER {
                            val1080p(3),
                            val1080i(1),
                            val720p(2),
                            valSD(0),
                            val1080p2529(5),
                            val1080psf(4)
                            }
        MAX-ACCESS        read-write
        STATUS            current
        DESCRIPTION
                "CMNT: - Conversion standard
                 TYPE: - RadiobuttonList
                 PAGE: - Video2
                    Conversion Standard  cmdID= 40700
                    1080p  value= 3
                    1080i  value= 1
                    720p  value= 2
                    SD  value= 0
                    1080p25/29  value= 5
                    1080psf  value= 4  "
        ::= { iquav10CmdEntry 40700 }


    iquav10Video2VideoOutputOutputAType OBJECT-TYPE
        SYNTAX            INTEGER {
                            valProcessed(0),
                            valReclocked(1)
                            }
        MAX-ACCESS        read-write
        STATUS            current
        DESCRIPTION
                "CMNT: - Output A type
                 TYPE: - RadiobuttonList
                 PAGE: - Video2
                    Output A Type  cmdID= 40701
                    Processed  value= 0
                    Reclocked  value= 1  "
        ::= { iquav10CmdEntry 40701 }


    iquav10Video2VideoOutputOutputBType OBJECT-TYPE
        SYNTAX            INTEGER {
                            valProcessed(0),
                            valReclocked(1)
                            }
        MAX-ACCESS        read-write
        STATUS            current
        DESCRIPTION
                "CMNT: - Output B type
                 TYPE: - RadiobuttonList
                 PAGE: - Video2
                    Output B Type  cmdID= 40702
                    Processed  value= 0
                    Reclocked  value= 1  "
        ::= { iquav10CmdEntry 40702 }


    iquav10Video2VideoOutputOutput1Std OBJECT-TYPE
        SYNTAX            RollCallString
        MAX-ACCESS        read-only
        STATUS            current
        DESCRIPTION
                "CMNT: - Output 1 Standard
                 TYPE: - Display
                 PAGE: - Video2
                    Output 1 Std  cmdID= 40706  "
        ::= { iquav10CmdEntry 40706 }


    iquav10VideoOutputVideoProcMasterGain OBJECT-TYPE
        SYNTAX            INTEGER
        MAX-ACCESS        read-write
        STATUS            current
        DESCRIPTION
                "CMNT: - Video Master Gain
                 TYPE: - Number
                 PAGE: - Video Output
                    Master Gain  cmdID= 33000
                    min= 0  max= 2000  step= 1  format= %d  div_scale= 1  preset= 1000
                    Min = 0  Max = 0  Step = 0  Preset = 0  "
        ::= { iquav10CmdEntry 33000 }


    iquav10VideoOutputVideoProcYGain OBJECT-TYPE
        SYNTAX            INTEGER
        MAX-ACCESS        read-write
        STATUS            current
        DESCRIPTION
                "CMNT: - Video Luminance gain
                 TYPE: - Number
                 PAGE: - Video Output
                    Y Gain  cmdID= 33001
                    min= 0  max= 2000  step= 1  format= %d  div_scale= 1  preset= 1000
                    Min = 0  Max = 0  Step = 0  Preset = 0  "
        ::= { iquav10CmdEntry 33001 }


    iquav10VideoOutputVideoProcCGain OBJECT-TYPE
        SYNTAX            INTEGER
        MAX-ACCESS        read-write
        STATUS            current
        DESCRIPTION
                "CMNT: - Video CbCr Gain
                 TYPE: - Number
                 PAGE: - Video Output
                    C Gain  cmdID= 33003
                    min= 0  max= 2000  step= 1  format= %d  div_scale= 1  preset= 1000
                    Min = 0  Max = 0  Step = 0  Preset = 0  "
        ::= { iquav10CmdEntry 33003 }


    iquav10VideoOutputVideoProcBlackLevel OBJECT-TYPE
        SYNTAX            INTEGER
        MAX-ACCESS        read-write
        STATUS            current
        DESCRIPTION
                "CMNT: - Video Black Level
                 TYPE: - Number
                 PAGE: - Video Output
                    Black Level  cmdID= 33002
                    min= -200  max= 200  step= 1  format= %0.0f mV  div_scale= 1  preset= 0
                    Min = -200 mV  Max = 200 mV  Step = 1 mV  Preset = 0 mV  "
        ::= { iquav10CmdEntry 33002 }


    iquav10VideoOutputVideoProcHueLevel OBJECT-TYPE
        SYNTAX            INTEGER
        MAX-ACCESS        read-write
        STATUS            current
        DESCRIPTION
                "CMNT: - Video Hue
                 TYPE: - Number
                 PAGE: - Video Output
                    Hue Level  cmdID= 33025
                    min= -180  max= 180  step= 1  format= %0.0f degrees  div_scale= 1  preset= 0
                    Min = -180 degrees  Max = 180 degrees  Step = 1 degrees  Preset = 0 degrees  "
        ::= { iquav10CmdEntry 33025 }


    iquav10VideoOutputVideoProcActiveSig OBJECT-TYPE
        SYNTAX            INTEGER { disable(0), enable(1)  }
        MAX-ACCESS        read-write
        STATUS            current
        DESCRIPTION
                "CMNT: - Active signalling video passthrough
                 TYPE: - Checkbox
                 PAGE: - Video Output
                    ActiveSig  cmdID= 32998  "
        ::= { iquav10CmdEntry 32998 }


    iquav10Video2VideoOutputDefaultOutput OBJECT-TYPE
        SYNTAX            INTEGER {
                            valBlack(1),
                            valFreeze(2),
                            valOutPattern(3)
                            }
        MAX-ACCESS        read-write
        STATUS            current
        DESCRIPTION
                "CMNT: - What to do on input loss
                 TYPE: - RadiobuttonList
                 PAGE: - Video2
                    Default Output  cmdID= 33026
                    Black  value= 1
                    Freeze  value= 2
                    Out Pattern  value= 3  "
        ::= { iquav10CmdEntry 33026 }


    iquav10Video2VideoOutputOutputMode OBJECT-TYPE
        SYNTAX            INTEGER {
                            valDefaultVideo(0),
                            valBlack(1),
                            valFreeze(2),
                            valOutPattern(3)
                            }
        MAX-ACCESS        read-write
        STATUS            current
        DESCRIPTION
                "CMNT: - Video Output mode
                 TYPE: - RadiobuttonList
                 PAGE: - Video2
                    Output Mode  cmdID= 33027
                    Default Video  value= 0
                    Black  value= 1
                    Freeze  value= 2
                    Out Pattern  value= 3  "
        ::= { iquav10CmdEntry 33027 }


    iquav10Video2VideoOutputPatternType OBJECT-TYPE
        SYNTAX            INTEGER {
                            val75ColorBars(0),
                            val100ColorBars(1),
                            valSMPTEBars(2),
                            valTartanBars(9),
                            valBlack(8),
                            valPluge(3),
                            valRamp(4),
                            valSweep(5),
                            valPulseBar(6),
                            valBurst(7)
                            }
        MAX-ACCESS        read-write
        STATUS            current
        DESCRIPTION
                "CMNT: - TPG pattern type
                 TYPE: - RadiobuttonList
                 PAGE: - Video2
                    Pattern Type  cmdID= 33028
                    75% Color Bars  value= 0
                    100% Color Bars  value= 1
                    SMPTE Bars  value= 2
                    Tartan Bars  value= 9
                    Black  value= 8
                    Pluge  value= 3
                    Ramp  value= 4
                    Sweep  value= 5
                    Pulse & Bar  value= 6
                    Burst  value= 7  "
        ::= { iquav10CmdEntry 33028 }


    iquav10Video2VideoOutputSDAnlgEncode OBJECT-TYPE
        SYNTAX            INTEGER {
                            valSMPTE(0),
                            valBetaCam(1),
                            valMII(2)
                            }
        MAX-ACCESS        read-write
        STATUS            current
        DESCRIPTION
                "CMNT: - SD Analog Encoding YPbPr
                 TYPE: - RadiobuttonList
                 PAGE: - Video2
                    SD Anlg Encode  cmdID= 33038
                    SMPTE  value= 0
                    BetaCam  value= 1
                    MII  value= 2  "
        ::= { iquav10CmdEntry 33038 }


    iquav10Video2VideoOutputPedComposEnc OBJECT-TYPE
        SYNTAX            INTEGER {
                            valPedestalOffNTSCnJ(0),
                            valPedestalOnNTSC(1)
                            }
        MAX-ACCESS        read-write
        STATUS            current
        DESCRIPTION
                "CMNT: - SD Analog Encoding Composite
                 TYPE: - RadiobuttonList
                 PAGE: - Video2
                    Ped Compos Enc  cmdID= 33041
                    Pedestal Off:NTSC-J  value= 0
                    Pedestal On:NTSC  value= 1  "
        ::= { iquav10CmdEntry 33041 }


    iquav10Video2VideoOutputAnlgType OBJECT-TYPE
        SYNTAX            INTEGER {
                            valCompositeSD(0),
                            valYCSD(1),
                            valYPbPrSDHD(2),
                            valGBR(3)
                            }
        MAX-ACCESS        read-write
        STATUS            current
        DESCRIPTION
                "CMNT: - Analog Output Type
                 TYPE: - RadiobuttonList
                 PAGE: - Video2
                    Anlg Type  cmdID= 33039
                    Composite (SD)  value= 0
                    Y/C (SD)  value= 1
                    YPbPr (SD/HD)  value= 2
                    GBR  value= 3  "
        ::= { iquav10CmdEntry 33039 }


    iquav10VideoOutputUserCaptionsEnable OBJECT-TYPE
        SYNTAX            INTEGER { disable(0), enable(1)  }
        MAX-ACCESS        read-write
        STATUS            current
        DESCRIPTION
                "CMNT: - 
                 TYPE: - Checkbox
                 PAGE: - Video Output
                    Enable  cmdID= 6080  "
        ::= { iquav10CmdEntry 6080 }


    iquav10VideoOutputUserCaptionsEnableAlt OBJECT-TYPE
        SYNTAX            INTEGER { disable(0), enable(1)  }
        MAX-ACCESS        read-write
        STATUS            current
        DESCRIPTION
                "CMNT: - 
                 TYPE: - Checkbox
                 PAGE: - Video Output
                    EnableAlt  cmdID= 6087  "
        ::= { iquav10CmdEntry 6087 }


    iquav10VideoOutputUserCaptionsText OBJECT-TYPE
        SYNTAX            RollCallString
        MAX-ACCESS        read-write
        STATUS            current
        DESCRIPTION
                "CMNT: - 
                 TYPE: - Editstring
                 PAGE: - Video Output
                    Text  cmdID= 6085
                    preset= IQUAV10"
        ::= { iquav10CmdEntry 6085 }


    iquav10VideoOutputUserCaptionsTextAlt OBJECT-TYPE
        SYNTAX            RollCallString
        MAX-ACCESS        read-write
        STATUS            current
        DESCRIPTION
                "CMNT: - 
                 TYPE: - Editstring
                 PAGE: - Video Output
                    TextAlt  cmdID= 6086
                    preset= IQUAV10*"
        ::= { iquav10CmdEntry 6086 }


    iquav10VideoOutputUserCaptionsXPos OBJECT-TYPE
        SYNTAX            INTEGER
        MAX-ACCESS        read-write
        STATUS            current
        DESCRIPTION
                "CMNT: - 
                 TYPE: - Number
                 PAGE: - Video Output
                    X Pos  cmdID= 6081
                    min= 0  max= 1000  step= 1  format= %0.1f  div_scale= 10  preset= 0
                    Min = 0.0  Max = 100.0  Step = 0.1  Preset = 0.0  "
        ::= { iquav10CmdEntry 6081 }


    iquav10VideoOutputUserCaptionsYPos OBJECT-TYPE
        SYNTAX            INTEGER
        MAX-ACCESS        read-write
        STATUS            current
        DESCRIPTION
                "CMNT: - 
                 TYPE: - Number
                 PAGE: - Video Output
                    Y Pos  cmdID= 6082
                    min= -1000  max= 0  step= 1  format= %0.1f  div_scale= 10  preset= 0
                    Min = -100.0  Max = 0.0  Step = 0.1  Preset = 0.0  "
        ::= { iquav10CmdEntry 6082 }


    iquav10VideoOutputUserCaptionsXSize OBJECT-TYPE
        SYNTAX            INTEGER
        MAX-ACCESS        read-write
        STATUS            current
        DESCRIPTION
                "CMNT: - 
                 TYPE: - Number
                 PAGE: - Video Output
                    X Size  cmdID= 6083
                    min= 1  max= 10  step= 1  format= %0.0f  div_scale= 1  preset= 1
                    Min = 1  Max = 10  Step = 1  Preset = 1  "
        ::= { iquav10CmdEntry 6083 }


    iquav10VideoOutputUserCaptionsYSize OBJECT-TYPE
        SYNTAX            INTEGER
        MAX-ACCESS        read-write
        STATUS            current
        DESCRIPTION
                "CMNT: - 
                 TYPE: - Number
                 PAGE: - Video Output
                    Y Size  cmdID= 6084
                    min= 1  max= 10  step= 1  format= %0.0f  div_scale= 1  preset= 1
                    Min = 1  Max = 10  Step = 1  Preset = 1  "
        ::= { iquav10CmdEntry 6084 }


    iquav10Video2VideoOutputLastRefStd OBJECT-TYPE
        SYNTAX            INTEGER
        MAX-ACCESS        read-write
        STATUS            current
        DESCRIPTION
                "CMNT: - Last Known ref std
                 TYPE: - Number
                 PAGE: - Video2
                    LastRefStd  cmdID= 36145
                    min= 0  max= 10  step= 1  format= %d  div_scale= 1  preset= 0
                    Min = 0  Max = 0  Step = 0  Preset = 0  "
        ::= { iquav10CmdEntry 36145 }


    iquav10Video2VideoOutputLastFrameRate OBJECT-TYPE
        SYNTAX            INTEGER
        MAX-ACCESS        read-write
        STATUS            current
        DESCRIPTION
                "CMNT: - Last Known Input rate
                 TYPE: - Number
                 PAGE: - Video2
                    LastFrameRate  cmdID= 36146
                    min= 0  max= 2  step= 1  format= %d  div_scale= 1  preset= 0
                    Min = 0  Max = 0  Step = 0  Preset = 0  "
        ::= { iquav10CmdEntry 36146 }


    iquav10PictureAdvancedHEnhanceEnable OBJECT-TYPE
        SYNTAX            INTEGER { disable(0), enable(1)  }
        MAX-ACCESS        read-write
        STATUS            current
        DESCRIPTION
                "CMNT: - 
                 TYPE: - Checkbox
                 PAGE: - Picture
                    Enable  cmdID= 6030  "
        ::= { iquav10CmdEntry 6030 }


    iquav10PictureAdvancedHEnhanceFrequencyBand OBJECT-TYPE
        SYNTAX            INTEGER {
                            valLow(2),
                            valMedium(1),
                            valHigh(0)
                            }
        MAX-ACCESS        read-write
        STATUS            current
        DESCRIPTION
                "CMNT: - 
                 TYPE: - RadiobuttonList
                 PAGE: - Picture
                    Frequency Band  cmdID= 6031
                    Low  value= 2
                    Medium  value= 1
                    High  value= 0  "
        ::= { iquav10CmdEntry 6031 }


    iquav10PictureAdvancedHEnhancePreset OBJECT-TYPE
        SYNTAX            INTEGER {
                            valLow(1),
                            valMedium(2),
                            valHigh(3),
                            valSuper(4),
                            valCustom(0)
                            }
        MAX-ACCESS        read-write
        STATUS            current
        DESCRIPTION
                "CMNT: - 
                 TYPE: - RadiobuttonList
                 PAGE: - Picture
                    Preset  cmdID= 6034
                    Low  value= 1
                    Medium  value= 2
                    High  value= 3
                    Super  value= 4
                    Custom  value= 0  "
        ::= { iquav10CmdEntry 6034 }


    iquav10PictureAdvancedHEnhanceGain OBJECT-TYPE
        SYNTAX            INTEGER
        MAX-ACCESS        read-write
        STATUS            current
        DESCRIPTION
                "CMNT: - 
                 TYPE: - Number
                 PAGE: - Picture
                    Gain  cmdID= 6032
                    min= 0  max= 192  step= 8  format= %0.1f  div_scale= 16  preset= 0
                    Min = 0.0  Max = 12.0  Step = 0.5  Preset = 0.0  "
        ::= { iquav10CmdEntry 6032 }


    iquav10PictureAdvancedHEnhanceNoiseRejection OBJECT-TYPE
        SYNTAX            INTEGER
        MAX-ACCESS        read-write
        STATUS            current
        DESCRIPTION
                "CMNT: - 
                 TYPE: - Number
                 PAGE: - Picture
                    Noise Rejection  cmdID= 6033
                    min= 0  max= 100  step= 1  format= %0.0f%%  div_scale= 1  preset= 0
                    Min = 0%  Max = 100%  Step = 1%  Preset = 0%  "
        ::= { iquav10CmdEntry 6033 }


    iquav10PictureRGBLegaliserRange OBJECT-TYPE
        SYNTAX            INTEGER {
                            val700mV(0),
                            val721mV(1),
                            val735mV(2),
                            val746mV(3)
                            }
        MAX-ACCESS        read-write
        STATUS            current
        DESCRIPTION
                "CMNT: - 
                 TYPE: - RadiobuttonList
                 PAGE: - Picture
                    Range  cmdID= 6061
                    700 mV  value= 0
                    721 mV  value= 1
                    735 mV  value= 2
                    746 mV  value= 3  "
        ::= { iquav10CmdEntry 6061 }


    iquav10PictureLumaClipperEnable OBJECT-TYPE
        SYNTAX            INTEGER { disable(0), enable(1)  }
        MAX-ACCESS        read-write
        STATUS            current
        DESCRIPTION
                "CMNT: - 
                 TYPE: - Checkbox
                 PAGE: - Picture
                    Enable  cmdID= 6070  "
        ::= { iquav10CmdEntry 6070 }


    iquav10PictureLumaClipperWhitemax OBJECT-TYPE
        SYNTAX            INTEGER
        MAX-ACCESS        read-write
        STATUS            current
        DESCRIPTION
                "CMNT: - 
                 TYPE: - Number
                 PAGE: - Picture
                    White max  cmdID= 6071
                    min= 90  max= 109  step= 1  format= %0.0f %%  div_scale= 1  preset= 103
                    Min = 90 %  Max = 109 %  Step = 1 %  Preset = 103 %  "
        ::= { iquav10CmdEntry 6071 }


    iquav10PictureLumaClipperBlackmin OBJECT-TYPE
        SYNTAX            INTEGER
        MAX-ACCESS        read-write
        STATUS            current
        DESCRIPTION
                "CMNT: - 
                 TYPE: - Number
                 PAGE: - Picture
                    Black min  cmdID= 6072
                    min= -7  max= 10  step= 1  format= %0.0f %%  div_scale= 1  preset= -1
                    Min = -7 %  Max = 10 %  Step = 1 %  Preset = -1 %  "
        ::= { iquav10CmdEntry 6072 }


    iquav10PictureOutputPictureColorimetry OBJECT-TYPE
        SYNTAX            INTEGER {
                            valAuto(0),
                            valNone(1),
                            valBT709toRec601(2),
                            valRec601toBT709(3)
                            }
        MAX-ACCESS        read-write
        STATUS            current
        DESCRIPTION
                "CMNT: - 
                 TYPE: - RadiobuttonList
                 PAGE: - Picture Output
                    Colorimetry  cmdID= 6043
                    Auto  value= 0
                    None  value= 1
                    BT709toRec601  value= 2
                    Rec601toBT709  value= 3  "
        ::= { iquav10CmdEntry 6043 }


    iquav10PictureEnhanceNoiseThreshold OBJECT-TYPE
        SYNTAX            INTEGER
        MAX-ACCESS        read-write
        STATUS            current
        DESCRIPTION
                "CMNT: - 
                 TYPE: - Number
                 PAGE: - Picture
                    Noise Threshold  cmdID= 6041
                    min= 0  max= 255  step= 1  format= %0.0f  div_scale= 1  preset= 0
                    Min = 0  Max = 255  Step = 1  Preset = 0  "
        ::= { iquav10CmdEntry 6041 }


    iquav10PictureEnhanceSharpnessThreshold OBJECT-TYPE
        SYNTAX            INTEGER
        MAX-ACCESS        read-write
        STATUS            current
        DESCRIPTION
                "CMNT: - 
                 TYPE: - Number
                 PAGE: - Picture
                    Sharpness Threshold  cmdID= 6042
                    min= 0  max= 255  step= 1  format= %0.0f  div_scale= 1  preset= 0
                    Min = 0  Max = 255  Step = 1  Preset = 0  "
        ::= { iquav10CmdEntry 6042 }


    iquav10PictureEnhanceSharpnessAmplitude OBJECT-TYPE
        SYNTAX            INTEGER
        MAX-ACCESS        read-write
        STATUS            current
        DESCRIPTION
                "CMNT: - 
                 TYPE: - Number
                 PAGE: - Picture
                    Sharpness Amplitude  cmdID= 6044
                    min= 0  max= 255  step= 1  format= %0.0f  div_scale= 1  preset= 0
                    Min = 0  Max = 255  Step = 1  Preset = 0  "
        ::= { iquav10CmdEntry 6044 }


    iquav10PictureOutputPictureFilmCadence OBJECT-TYPE
        SYNTAX            RollCallString
        MAX-ACCESS        read-only
        STATUS            current
        DESCRIPTION
                "CMNT: - Film cadence
                 TYPE: - Display
                 PAGE: - Picture Output
                    Film Cadence  cmdID= 40707  "
        ::= { iquav10CmdEntry 40707 }


    iquav10PictureOutputColorCorrectGreenOffset OBJECT-TYPE
        SYNTAX            INTEGER
        MAX-ACCESS        read-write
        STATUS            current
        DESCRIPTION
                "CMNT: - COLOR correct offset Green
                 TYPE: - Number
                 PAGE: - Picture Output
                    GreenOffset  cmdID= 40861
                    min= 0  max= 203200  step= 100  format= %0.2f%%  div_scale= 1016  preset= 101600
                    Min = 0.00%  Max = 200.00%  Step = 0.10%  Preset = 100.00%  "
        ::= { iquav10CmdEntry 40861 }


    iquav10PictureOutputColorCorrectBlueOffset OBJECT-TYPE
        SYNTAX            INTEGER
        MAX-ACCESS        read-write
        STATUS            current
        DESCRIPTION
                "CMNT: - COLOR correct offset Blue
                 TYPE: - Number
                 PAGE: - Picture Output
                    BlueOffset  cmdID= 40862
                    min= 0  max= 203200  step= 100  format= %0.2f%%  div_scale= 1016  preset= 101600
                    Min = 0.00%  Max = 200.00%  Step = 0.10%  Preset = 100.00%  "
        ::= { iquav10CmdEntry 40862 }


    iquav10PictureOutputColorCorrectRedOffset OBJECT-TYPE
        SYNTAX            INTEGER
        MAX-ACCESS        read-write
        STATUS            current
        DESCRIPTION
                "CMNT: - COLOR correct offset Red
                 TYPE: - Number
                 PAGE: - Picture Output
                    RedOffset  cmdID= 40863
                    min= 0  max= 203200  step= 100  format= %0.2f%%  div_scale= 1016  preset= 101600
                    Min = 0.00%  Max = 200.00%  Step = 0.10%  Preset = 100.00%  "
        ::= { iquav10CmdEntry 40863 }


    iquav10PictureOutputColorCorrectGangOffset OBJECT-TYPE
        SYNTAX            INTEGER { disable(0), enable(1)  }
        MAX-ACCESS        read-write
        STATUS            current
        DESCRIPTION
                "CMNT: - COLOR correct offset gang
                 TYPE: - Checkbox
                 PAGE: - Picture Output
                    GangOffset  cmdID= 40870  "
        ::= { iquav10CmdEntry 40870 }


    iquav10PictureOutputColorCorrectGreenGain OBJECT-TYPE
        SYNTAX            INTEGER
        MAX-ACCESS        read-write
        STATUS            current
        DESCRIPTION
                "CMNT: - COLOR correct gain Green
                 TYPE: - Number
                 PAGE: - Picture Output
                    GreenGain  cmdID= 40864
                    min= 0  max= 2000  step= 1  format= %0.1f%%  div_scale= 10  preset= 1000
                    Min = 0.0%  Max = 200.0%  Step = 0.1%  Preset = 100.0%  "
        ::= { iquav10CmdEntry 40864 }


    iquav10PictureOutputColorCorrectBlueGain OBJECT-TYPE
        SYNTAX            INTEGER
        MAX-ACCESS        read-write
        STATUS            current
        DESCRIPTION
                "CMNT: - COLOR correct gain Blue
                 TYPE: - Number
                 PAGE: - Picture Output
                    BlueGain  cmdID= 40865
                    min= 0  max= 2000  step= 1  format= %0.1f%%  div_scale= 10  preset= 1000
                    Min = 0.0%  Max = 200.0%  Step = 0.1%  Preset = 100.0%  "
        ::= { iquav10CmdEntry 40865 }


    iquav10PictureOutputColorCorrectRedGain OBJECT-TYPE
        SYNTAX            INTEGER
        MAX-ACCESS        read-write
        STATUS            current
        DESCRIPTION
                "CMNT: - COLOR correct gain Red
                 TYPE: - Number
                 PAGE: - Picture Output
                    RedGain  cmdID= 40866
                    min= 0  max= 2000  step= 1  format= %0.1f%%  div_scale= 10  preset= 1000
                    Min = 0.0%  Max = 200.0%  Step = 0.1%  Preset = 100.0%  "
        ::= { iquav10CmdEntry 40866 }


    iquav10PictureOutputColorCorrectGangGain OBJECT-TYPE
        SYNTAX            INTEGER { disable(0), enable(1)  }
        MAX-ACCESS        read-write
        STATUS            current
        DESCRIPTION
                "CMNT: - COLOR correct gain gang
                 TYPE: - Checkbox
                 PAGE: - Picture Output
                    GangGain  cmdID= 40871  "
        ::= { iquav10CmdEntry 40871 }


    iquav10PictureOutputColorCorrectGreenGamma OBJECT-TYPE
        SYNTAX            INTEGER
        MAX-ACCESS        read-write
        STATUS            current
        DESCRIPTION
                "CMNT: - COLOR correct gamma Green
                 TYPE: - Number
                 PAGE: - Picture Output
                    GreenGamma  cmdID= 40867
                    min= 0  max= 1000  step= 1  format= %0.0f  div_scale= 1  preset= 500
                    Min = 0  Max = 1000  Step = 1  Preset = 500  "
        ::= { iquav10CmdEntry 40867 }


    iquav10PictureOutputColorCorrectBlueGamma OBJECT-TYPE
        SYNTAX            INTEGER
        MAX-ACCESS        read-write
        STATUS            current
        DESCRIPTION
                "CMNT: - COLOR correct gamma Blue
                 TYPE: - Number
                 PAGE: - Picture Output
                    BlueGamma  cmdID= 40868
                    min= 0  max= 1000  step= 1  format= %0.0f  div_scale= 1  preset= 500
                    Min = 0  Max = 1000  Step = 1  Preset = 500  "
        ::= { iquav10CmdEntry 40868 }


    iquav10PictureOutputColorCorrectRedGamma OBJECT-TYPE
        SYNTAX            INTEGER
        MAX-ACCESS        read-write
        STATUS            current
        DESCRIPTION
                "CMNT: - COLOR correct gamma Red
                 TYPE: - Number
                 PAGE: - Picture Output
                    RedGamma  cmdID= 40869
                    min= 0  max= 1000  step= 1  format= %0.0f  div_scale= 1  preset= 500
                    Min = 0  Max = 1000  Step = 1  Preset = 500  "
        ::= { iquav10CmdEntry 40869 }


    iquav10PictureOutputColorCorrectGangGamma OBJECT-TYPE
        SYNTAX            INTEGER { disable(0), enable(1)  }
        MAX-ACCESS        read-write
        STATUS            current
        DESCRIPTION
                "CMNT: - COLOR correct gamma gang
                 TYPE: - Checkbox
                 PAGE: - Picture Output
                    GangGamma  cmdID= 40872  "
        ::= { iquav10CmdEntry 40872 }


    iquav10PictureOutputOutputBorderLeft OBJECT-TYPE
        SYNTAX            INTEGER
        MAX-ACCESS        read-write
        STATUS            current
        DESCRIPTION
                "CMNT: - 
                 TYPE: - Number
                 PAGE: - Picture Output
                    Left  cmdID= 6009
                    min= 0  max= 1920  step= 1  format= %0.0f  div_scale= 1  preset= 0
                    Min = 0  Max = 1920  Step = 1  Preset = 0  "
        ::= { iquav10CmdEntry 6009 }


    iquav10PictureOutputOutputBorderRight OBJECT-TYPE
        SYNTAX            INTEGER
        MAX-ACCESS        read-write
        STATUS            current
        DESCRIPTION
                "CMNT: - 
                 TYPE: - Number
                 PAGE: - Picture Output
                    Right  cmdID= 6010
                    min= 0  max= 1920  step= 1  format= %0.0f  div_scale= 1  preset= 0
                    Min = 0  Max = 1920  Step = 1  Preset = 0  "
        ::= { iquav10CmdEntry 6010 }


    iquav10PictureOutputOutputBorderTop OBJECT-TYPE
        SYNTAX            INTEGER
        MAX-ACCESS        read-write
        STATUS            current
        DESCRIPTION
                "CMNT: - 
                 TYPE: - Number
                 PAGE: - Picture Output
                    Top  cmdID= 6011
                    min= 0  max= 1080  step= 1  format= %0.0f  div_scale= 1  preset= 0
                    Min = 0  Max = 1080  Step = 1  Preset = 0  "
        ::= { iquav10CmdEntry 6011 }


    iquav10PictureOutputOutputBorderBottom OBJECT-TYPE
        SYNTAX            INTEGER
        MAX-ACCESS        read-write
        STATUS            current
        DESCRIPTION
                "CMNT: - 
                 TYPE: - Number
                 PAGE: - Picture Output
                    Bottom  cmdID= 6012
                    min= 0  max= 1080  step= 1  format= %0.0f  div_scale= 1  preset= 0
                    Min = 0  Max = 1080  Step = 1  Preset = 0  "
        ::= { iquav10CmdEntry 6012 }


    iquav10PictureOutputOutputBorderRed OBJECT-TYPE
        SYNTAX            INTEGER
        MAX-ACCESS        read-write
        STATUS            current
        DESCRIPTION
                "CMNT: - 
                 TYPE: - Number
                 PAGE: - Picture Output
                    Red  cmdID= 6013
                    min= 0  max= 255  step= 1  format= %0.0f  div_scale= 1  preset= 127
                    Min = 0  Max = 255  Step = 1  Preset = 127  "
        ::= { iquav10CmdEntry 6013 }


    iquav10PictureOutputOutputBorderGreen OBJECT-TYPE
        SYNTAX            INTEGER
        MAX-ACCESS        read-write
        STATUS            current
        DESCRIPTION
                "CMNT: - 
                 TYPE: - Number
                 PAGE: - Picture Output
                    Green  cmdID= 6014
                    min= 0  max= 255  step= 1  format= %0.0f  div_scale= 1  preset= 127
                    Min = 0  Max = 255  Step = 1  Preset = 127  "
        ::= { iquav10CmdEntry 6014 }


    iquav10PictureOutputOutputBorderBlue OBJECT-TYPE
        SYNTAX            INTEGER
        MAX-ACCESS        read-write
        STATUS            current
        DESCRIPTION
                "CMNT: - 
                 TYPE: - Number
                 PAGE: - Picture Output
                    Blue  cmdID= 6015
                    min= 0  max= 255  step= 1  format= %0.0f  div_scale= 1  preset= 127
                    Min = 0  Max = 255  Step = 1  Preset = 127  "
        ::= { iquav10CmdEntry 6015 }


    iquav10ARCCtrlRecallDisplayMemory OBJECT-TYPE
        SYNTAX            INTEGER {
                            valNoneSelected(0),
                            valDisplayMemory1(1),
                            valDisplayMemory2(2),
                            valDisplayMemory3(3),
                            valDisplayMemory4(4),
                            valDisplayMemory5(5),
                            valDisplayMemory6(6),
                            valDisplayMemory7(7),
                            valDisplayMemory8(8),
                            valDisplayMemory9(9),
                            valDisplayMemory10(10),
                            valDisplayMemory11(11),
                            valDisplayMemory12(12),
                            valDisplayMemory13(13),
                            valDisplayMemory14(14),
                            valDisplayMemory15(15),
                            valDisplayMemory16(16),
                            valDisplayMemory17(17),
                            valDisplayMemory18(18),
                            valDisplayMemory19(19),
                            valDisplayMemory20(20),
                            valDisplayMemory21(21),
                            valDisplayMemory22(22),
                            valDisplayMemory23(23),
                            valDisplayMemory24(24),
                            valDisplayMemory25(25),
                            valDisplayMemory26(26),
                            valDisplayMemory27(27),
                            valDisplayMemory28(28),
                            valDisplayMemory29(29),
                            valDisplayMemory30(30),
                            valDisplayMemory31(31),
                            valDisplayMemory32(32)
                            }
        MAX-ACCESS        read-write
        STATUS            current
        DESCRIPTION
                "CMNT: - 
                 TYPE: - RadiobuttonList
                 PAGE: - ARC Ctrl
                    Recall Display Memory  cmdID= 38701
                    None Selected  value= 0
                    Display Memory 1  value= 1
                    Display Memory 2  value= 2
                    Display Memory 3  value= 3
                    Display Memory 4  value= 4
                    Display Memory 5  value= 5
                    Display Memory 6  value= 6
                    Display Memory 7  value= 7
                    Display Memory 8  value= 8
                    Display Memory 9  value= 9
                    Display Memory 10  value= 10
                    Display Memory 11  value= 11
                    Display Memory 12  value= 12
                    Display Memory 13  value= 13
                    Display Memory 14  value= 14
                    Display Memory 15  value= 15
                    Display Memory 16  value= 16
                    Display Memory 17  value= 17
                    Display Memory 18  value= 18
                    Display Memory 19  value= 19
                    Display Memory 20  value= 20
                    Display Memory 21  value= 21
                    Display Memory 22  value= 22
                    Display Memory 23  value= 23
                    Display Memory 24  value= 24
                    Display Memory 25  value= 25
                    Display Memory 26  value= 26
                    Display Memory 27  value= 27
                    Display Memory 28  value= 28
                    Display Memory 29  value= 29
                    Display Memory 30  value= 30
                    Display Memory 31  value= 31
                    Display Memory 32  value= 32  "
        ::= { iquav10CmdEntry 38701 }


    iquav10ARCCtrlSelDisplayMemory OBJECT-TYPE
        SYNTAX            INTEGER {
                            valDisplayMemory1(1),
                            valDisplayMemory2(2),
                            valDisplayMemory3(3),
                            valDisplayMemory4(4),
                            valDisplayMemory5(5),
                            valDisplayMemory6(6),
                            valDisplayMemory7(7),
                            valDisplayMemory8(8),
                            valDisplayMemory9(9),
                            valDisplayMemory10(10),
                            valDisplayMemory11(11),
                            valDisplayMemory12(12),
                            valDisplayMemory13(13),
                            valDisplayMemory14(14),
                            valDisplayMemory15(15),
                            valDisplayMemory16(16),
                            valDisplayMemory17(17),
                            valDisplayMemory18(18),
                            valDisplayMemory19(19),
                            valDisplayMemory20(20),
                            valDisplayMemory21(21),
                            valDisplayMemory22(22),
                            valDisplayMemory23(23),
                            valDisplayMemory24(24),
                            valDisplayMemory25(25),
                            valDisplayMemory26(26),
                            valDisplayMemory27(27),
                            valDisplayMemory28(28),
                            valDisplayMemory29(29),
                            valDisplayMemory30(30),
                            valDisplayMemory31(31),
                            valDisplayMemory32(32)
                            }
        MAX-ACCESS        read-write
        STATUS            current
        DESCRIPTION
                "CMNT: - 
                 TYPE: - RadiobuttonList
                 PAGE: - ARC Ctrl
                    Sel Display Memory  cmdID= 6040
                    Display Memory 1  value= 1
                    Display Memory 2  value= 2
                    Display Memory 3  value= 3
                    Display Memory 4  value= 4
                    Display Memory 5  value= 5
                    Display Memory 6  value= 6
                    Display Memory 7  value= 7
                    Display Memory 8  value= 8
                    Display Memory 9  value= 9
                    Display Memory 10  value= 10
                    Display Memory 11  value= 11
                    Display Memory 12  value= 12
                    Display Memory 13  value= 13
                    Display Memory 14  value= 14
                    Display Memory 15  value= 15
                    Display Memory 16  value= 16
                    Display Memory 17  value= 17
                    Display Memory 18  value= 18
                    Display Memory 19  value= 19
                    Display Memory 20  value= 20
                    Display Memory 21  value= 21
                    Display Memory 22  value= 22
                    Display Memory 23  value= 23
                    Display Memory 24  value= 24
                    Display Memory 25  value= 25
                    Display Memory 26  value= 26
                    Display Memory 27  value= 27
                    Display Memory 28  value= 28
                    Display Memory 29  value= 29
                    Display Memory 30  value= 30
                    Display Memory 31  value= 31
                    Display Memory 32  value= 32  "
        ::= { iquav10CmdEntry 6040 }


    iquav10ARCCtrlSaveset OBJECT-TYPE
        SYNTAX            INTEGER
        MAX-ACCESS        read-write
        STATUS            current
        DESCRIPTION
                "CMNT: - 
                 TYPE: - Number
                 PAGE: - ARC Ctrl
                    Saveset  cmdID= 6045
                    min= 0  max= 33  step= 1  format= %d  div_scale= 1  preset= 0
                    Min = 0  Max = 0  Step = 0  Preset = 0  "
        ::= { iquav10CmdEntry 6045 }


    iquav10ARCCtrlSaveDispMemory OBJECT-TYPE
        SYNTAX            INTEGER { noAction(0),valSaveDispMemory(1) }
        MAX-ACCESS        read-write
        STATUS            current
        DESCRIPTION
                "CMNT: - 
                 TYPE: - Button
                 PAGE: - ARC Ctrl
                    Save Disp Memory  cmdID= 38705
                    value= 1  "
        ::= { iquav10CmdEntry 38705 }


    iquav10ARCCtrlDispMemoryNameChangeName OBJECT-TYPE
        SYNTAX            RollCallString
        MAX-ACCESS        read-write
        STATUS            current
        DESCRIPTION
                "CMNT: - 
                 TYPE: - Editstring
                 PAGE: - ARC Ctrl
                    Change Name  cmdID= 38703
                    preset= Display Memory"
        ::= { iquav10CmdEntry 38703 }


    iquav10ARCCtrlARCSize OBJECT-TYPE
        SYNTAX            INTEGER
        MAX-ACCESS        read-write
        STATUS            current
        DESCRIPTION
                "CMNT: - 
                 TYPE: - Number
                 PAGE: - ARC Ctrl
                    Size  cmdID= 6000
                    min= 600  max= 1500  step= 1  format= %0.1f%  div_scale= 10  preset= 1000
                    Min = 60.0  Max = 150.0  Step = 0.1  Preset = 100.0  "
        ::= { iquav10CmdEntry 6000 }


    iquav10ARCCtrlARCApect OBJECT-TYPE
        SYNTAX            INTEGER
        MAX-ACCESS        read-write
        STATUS            current
        DESCRIPTION
                "CMNT: - 
                 TYPE: - Number
                 PAGE: - ARC Ctrl
                    Apect  cmdID= 6001
                    min= 600  max= 2000  step= 1  format= %0.1f%  div_scale= 10  preset= 1000
                    Min = 60.0  Max = 200.0  Step = 0.1  Preset = 100.0  "
        ::= { iquav10CmdEntry 6001 }


    iquav10ARCCtrlARCTilt OBJECT-TYPE
        SYNTAX            INTEGER
        MAX-ACCESS        read-write
        STATUS            current
        DESCRIPTION
                "CMNT: - 
                 TYPE: - Number
                 PAGE: - ARC Ctrl
                    Tilt  cmdID= 6002
                    min= -750  max= 750  step= 1  format= %0.1f%  div_scale= 10  preset= 0
                    Min = -75.0  Max = 75.0  Step = 0.1  Preset = 0.0  "
        ::= { iquav10CmdEntry 6002 }


    iquav10ARCCtrlARCPan OBJECT-TYPE
        SYNTAX            INTEGER
        MAX-ACCESS        read-write
        STATUS            current
        DESCRIPTION
                "CMNT: - 
                 TYPE: - Number
                 PAGE: - ARC Ctrl
                    Pan  cmdID= 6003
                    min= -750  max= 750  step= 1  format= %0.1f%  div_scale= 10  preset= 0
                    Min = -75.0  Max = 75.0  Step = 0.1  Preset = 0.0  "
        ::= { iquav10CmdEntry 6003 }


    iquav10ARCCtrlInputCropLeft OBJECT-TYPE
        SYNTAX            INTEGER
        MAX-ACCESS        read-write
        STATUS            current
        DESCRIPTION
                "CMNT: - 
                 TYPE: - Number
                 PAGE: - ARC Ctrl
                    Left  cmdID= 6005
                    min= 0  max= 4095  step= 1  format= %0.0f  div_scale= 1  preset= 0
                    Min = 0  Max = 4095  Step = 1  Preset = 0  "
        ::= { iquav10CmdEntry 6005 }


    iquav10ARCCtrlInputCropRight OBJECT-TYPE
        SYNTAX            INTEGER
        MAX-ACCESS        read-write
        STATUS            current
        DESCRIPTION
                "CMNT: - 
                 TYPE: - Number
                 PAGE: - ARC Ctrl
                    Right  cmdID= 6006
                    min= 0  max= 4095  step= 1  format= %0.0f  div_scale= 1  preset= 0
                    Min = 0  Max = 4095  Step = 1  Preset = 0  "
        ::= { iquav10CmdEntry 6006 }


    iquav10ARCCtrlInputCropTop OBJECT-TYPE
        SYNTAX            INTEGER
        MAX-ACCESS        read-write
        STATUS            current
        DESCRIPTION
                "CMNT: - 
                 TYPE: - Number
                 PAGE: - ARC Ctrl
                    Top  cmdID= 6007
                    min= 0  max= 2047  step= 1  format= %0.0f  div_scale= 1  preset= 0
                    Min = 0  Max = 2047  Step = 1  Preset = 0  "
        ::= { iquav10CmdEntry 6007 }


    iquav10ARCCtrlInputCropBottom OBJECT-TYPE
        SYNTAX            INTEGER
        MAX-ACCESS        read-write
        STATUS            current
        DESCRIPTION
                "CMNT: - 
                 TYPE: - Number
                 PAGE: - ARC Ctrl
                    Bottom  cmdID= 6008
                    min= 0  max= 2047  step= 1  format= %0.0f  div_scale= 1  preset= 0
                    Min = 0  Max = 2047  Step = 1  Preset = 0  "
        ::= { iquav10CmdEntry 6008 }


    iquav10ARCCtrlSelStdPreset OBJECT-TYPE
        SYNTAX            INTEGER {
                            valFullFrame(0),
                            valBox169Top169(1),
                            val43Box149Top169(2),
                            valBox169169(3),
                            valBox4343(4),
                            val43box169(5),
                            val169box43(6),
                            val43box149169(7),
                            val169box14943(8)
                            }
        MAX-ACCESS        read-write
        STATUS            current
        DESCRIPTION
                "CMNT: - 
                 TYPE: - RadiobuttonList
                 PAGE: - ARC Ctrl
                    Sel Std. Preset  cmdID= 38704
                    Full Frame  value= 0
                    Box 16:9 Top > 16:9  value= 1
                    4:3 Box14:9Top>16:9  value= 2
                    Box 16:9 > 16:9  value= 3
                    Box 4:3 > 4:3  value= 4
                    4:3 > box 16:9  value= 5
                    16:9 > box 4:3  value= 6
                    4:3 box 14:9 > 16:9  value= 7
                    16:9 box 14:9 > 4:3  value= 8  "
        ::= { iquav10CmdEntry 38704 }


    iquav10ARCCtrlRecallStdPreset OBJECT-TYPE
        SYNTAX            INTEGER { noAction(0),valRecallStdPreset(1) }
        MAX-ACCESS        read-write
        STATUS            current
        DESCRIPTION
                "CMNT: - 
                 TYPE: - Button
                 PAGE: - ARC Ctrl
                    Recall Std Preset  cmdID= 38700
                    value= 1  "
        ::= { iquav10CmdEntry 38700 }


    iquav10ARCCtrlDefaultALLMemory OBJECT-TYPE
        SYNTAX            INTEGER { noAction(0),valDefaultALLMemory(1) }
        MAX-ACCESS        read-write
        STATUS            current
        DESCRIPTION
                "CMNT: - 
                 TYPE: - Button
                 PAGE: - ARC Ctrl
                    Default ALL Memory  cmdID= 38702
                    value= 1  "
        ::= { iquav10CmdEntry 38702 }


    iquav10ARCCtrlLastDisplayMemory OBJECT-TYPE
        SYNTAX            RollCallString
        MAX-ACCESS        read-only
        STATUS            current
        DESCRIPTION
                "CMNT: - 
                 TYPE: - Display
                 PAGE: - ARC Ctrl
                    Last Display Memory  cmdID= 38706  "
        ::= { iquav10CmdEntry 38706 }


    iquav10ARCCtrl43AFDMapping2 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 2  cmdID= 39017
                    min= 2  max= 143  step= 1  format= 0  div_scale= 1  preset= 2
                    Min = 0  Max = 0  Step = 0  Preset = 0  "
        ::= { iquav10CmdEntry 39017 }


    iquav10ARCCtrl43AFDMapping3 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 3  cmdID= 39018
                    min= 2  max= 143  step= 1  format= 0  div_scale= 1  preset= 3
                    Min = 0  Max = 0  Step = 0  Preset = 0  "
        ::= { iquav10CmdEntry 39018 }


    iquav10ARCCtrl43AFDMapping4 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 4  cmdID= 39019
                    min= 2  max= 143  step= 1  format= 0  div_scale= 1  preset= 4
                    Min = 0  Max = 0  Step = 0  Preset = 0  "
        ::= { iquav10CmdEntry 39019 }


    iquav10ARCCtrl43AFDMapping8 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 8  cmdID= 39023
                    min= 2  max= 143  step= 1  format= 0  div_scale= 1  preset= 8
                    Min = 0  Max = 0  Step = 0  Preset = 0  "
        ::= { iquav10CmdEntry 39023 }


    iquav10ARCCtrl43AFDMapping9 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 9  cmdID= 39024
                    min= 2  max= 143  step= 1  format= 0  div_scale= 1  preset= 9
                    Min = 0  Max = 0  Step = 0  Preset = 0  "
        ::= { iquav10CmdEntry 39024 }


    iquav10ARCCtrl43AFDMapping10 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 10  cmdID= 39025
                    min= 2  max= 143  step= 1  format= 0  div_scale= 1  preset= 10
                    Min = 0  Max = 0  Step = 0  Preset = 0  "
        ::= { iquav10CmdEntry 39025 }


    iquav10ARCCtrl43AFDMapping11 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 11  cmdID= 39026
                    min= 2  max= 143  step= 1  format= 0  div_scale= 1  preset= 11
                    Min = 0  Max = 0  Step = 0  Preset = 0  "
        ::= { iquav10CmdEntry 39026 }


    iquav10ARCCtrl43AFDMapping12 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 12  cmdID= 39027
                    min= 2  max= 143  step= 1  format= 0  div_scale= 1  preset= 12
                    Min = 0  Max = 0  Step = 0  Preset = 0  "
        ::= { iquav10CmdEntry 39027 }


    iquav10ARCCtrl43AFDMapping13 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 13  cmdID= 39028
                    min= 2  max= 143  step= 1  format= 0  div_scale= 1  preset= 13
                    Min = 0  Max = 0  Step = 0  Preset = 0  "
        ::= { iquav10CmdEntry 39028 }


    iquav10ARCCtrl43AFDMapping14 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 14  cmdID= 39029
                    min= 2  max= 143  step= 1  format= 0  div_scale= 1  preset= 14
                    Min = 0  Max = 0  Step = 0  Preset = 0  "
        ::= { iquav10CmdEntry 39029 }


    iquav10ARCCtrl43AFDMapping15 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 15  cmdID= 39030
                    min= 2  max= 143  step= 1  format= 0  div_scale= 1  preset= 15
                    Min = 0  Max = 0  Step = 0  Preset = 0  "
        ::= { iquav10CmdEntry 39030 }


    iquav10ARCCtrl43AFDMapping16 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 16  cmdID= 39031
                    min= 2  max= 143  step= 1  format= 0  div_scale= 1  preset= 8
                    Min = 0  Max = 0  Step = 0  Preset = 0  "
        ::= { iquav10CmdEntry 39031 }


    iquav10ARCCtrl169AFDMapping2 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 2  cmdID= 39034
                    min= 2  max= 143  step= 1  format= 0  div_scale= 1  preset= 130
                    Min = 0  Max = 0  Step = 0  Preset = 0  "
        ::= { iquav10CmdEntry 39034 }


    iquav10ARCCtrl169AFDMapping3 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 3  cmdID= 39035
                    min= 2  max= 143  step= 1  format= 0  div_scale= 1  preset= 131
                    Min = 0  Max = 0  Step = 0  Preset = 0  "
        ::= { iquav10CmdEntry 39035 }


    iquav10ARCCtrl169AFDMapping4 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 4  cmdID= 39036
                    min= 2  max= 143  step= 1  format= 0  div_scale= 1  preset= 132
                    Min = 0  Max = 0  Step = 0  Preset = 0  "
        ::= { iquav10CmdEntry 39036 }


    iquav10ARCCtrl169AFDMapping8 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 8  cmdID= 39040
                    min= 2  max= 143  step= 1  format= 0  div_scale= 1  preset= 136
                    Min = 0  Max = 0  Step = 0  Preset = 0  "
        ::= { iquav10CmdEntry 39040 }


    iquav10ARCCtrl169AFDMapping9 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 9  cmdID= 39041
                    min= 2  max= 143  step= 1  format= 0  div_scale= 1  preset= 137
                    Min = 0  Max = 0  Step = 0  Preset = 0  "
        ::= { iquav10CmdEntry 39041 }


    iquav10ARCCtrl169AFDMapping10 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 10  cmdID= 39042
                    min= 2  max= 143  step= 1  format= 0  div_scale= 1  preset= 138
                    Min = 0  Max = 0  Step = 0  Preset = 0  "
        ::= { iquav10CmdEntry 39042 }


    iquav10ARCCtrl169AFDMapping11 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 11  cmdID= 39043
                    min= 2  max= 143  step= 1  format= 0  div_scale= 1  preset= 139
                    Min = 0  Max = 0  Step = 0  Preset = 0  "
        ::= { iquav10CmdEntry 39043 }


    iquav10ARCCtrl169AFDMapping12 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 12  cmdID= 39044
                    min= 2  max= 143  step= 1  format= 0  div_scale= 1  preset= 140
                    Min = 0  Max = 0  Step = 0  Preset = 0  "
        ::= { iquav10CmdEntry 39044 }


    iquav10ARCCtrl169AFDMapping13 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 13  cmdID= 39045
                    min= 2  max= 143  step= 1  format= 0  div_scale= 1  preset= 141
                    Min = 0  Max = 0  Step = 0  Preset = 0  "
        ::= { iquav10CmdEntry 39045 }


    iquav10ARCCtrl169AFDMapping14 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 14  cmdID= 39046
                    min= 2  max= 143  step= 1  format= 0  div_scale= 1  preset= 142
                    Min = 0  Max = 0  Step = 0  Preset = 0  "
        ::= { iquav10CmdEntry 39046 }


    iquav10ARCCtrl169AFDMapping15 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 15  cmdID= 39047
                    min= 2  max= 143  step= 1  format= 0  div_scale= 1  preset= 143
                    Min = 0  Max = 0  Step = 0  Preset = 0  "
        ::= { iquav10CmdEntry 39047 }


    iquav10ARCCtrl169AFDMapping16 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 16  cmdID= 39048
                    min= 2  max= 143  step= 1  format= 0  div_scale= 1  preset= 136
                    Min = 0  Max = 0  Step = 0  Preset = 0  "
        ::= { iquav10CmdEntry 39048 }


    iquav10ARCCtrlNoSignalMapping OBJECT-TYPE
        SYNTAX            INTEGER
        MAX-ACCESS        read-write
        STATUS            current
        DESCRIPTION
                "CMNT: - No signal AFD Mapping
                 TYPE: - Number
                 PAGE: - ARC Ctrl
                    No Signal Mapping  cmdID= 39049
                    min= 2  max= 143  step= 1  format= 0  div_scale= 1  preset= 8
                    Min = 0  Max = 0  Step = 0  Preset = 0  "
        ::= { iquav10CmdEntry 39049 }


    iquav10ARCCtrlForceMapping OBJECT-TYPE
        SYNTAX            INTEGER
        MAX-ACCESS        read-write
        STATUS            current
        DESCRIPTION
                "CMNT: - Force AFD Mapping
                 TYPE: - Number
                 PAGE: - ARC Ctrl
                    Force Mapping  cmdID= 39079
                    min= 2  max= 143  step= 1  format= 0  div_scale= 1  preset= 8
                    Min = 0  Max = 0  Step = 0  Preset = 0  "
        ::= { iquav10CmdEntry 39079 }


    iquav10ARCCtrl43ARCMapping2 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  2  cmdID= 39050
                    min= 0  max= 32  step= 1  format= 0  div_scale= 1  preset= 1
                    Min = 0  Max = 0  Step = 0  Preset = 0  "
        ::= { iquav10CmdEntry 39050 }


    iquav10ARCCtrl43ARCMapping3 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  3  cmdID= 39051
                    min= 0  max= 32  step= 1  format= 0  div_scale= 1  preset= 1
                    Min = 0  Max = 0  Step = 0  Preset = 0  "
        ::= { iquav10CmdEntry 39051 }


    iquav10ARCCtrl43ARCMapping4 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  4  cmdID= 39052
                    min= 0  max= 32  step= 1  format= 0  div_scale= 1  preset= 1
                    Min = 0  Max = 0  Step = 0  Preset = 0  "
        ::= { iquav10CmdEntry 39052 }


    iquav10ARCCtrl43ARCMapping8 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  8  cmdID= 39053
                    min= 0  max= 32  step= 1  format= 0  div_scale= 1  preset= 1
                    Min = 0  Max = 0  Step = 0  Preset = 0  "
        ::= { iquav10CmdEntry 39053 }


    iquav10ARCCtrl43ARCMapping9 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  9  cmdID= 39054
                    min= 0  max= 32  step= 1  format= 0  div_scale= 1  preset= 1
                    Min = 0  Max = 0  Step = 0  Preset = 0  "
        ::= { iquav10CmdEntry 39054 }


    iquav10ARCCtrl43ARCMapping10 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  10  cmdID= 39055
                    min= 0  max= 32  step= 1  format= 0  div_scale= 1  preset= 1
                    Min = 0  Max = 0  Step = 0  Preset = 0  "
        ::= { iquav10CmdEntry 39055 }


    iquav10ARCCtrl43ARCMapping11 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  11  cmdID= 39056
                    min= 0  max= 32  step= 1  format= 0  div_scale= 1  preset= 1
                    Min = 0  Max = 0  Step = 0  Preset = 0  "
        ::= { iquav10CmdEntry 39056 }


    iquav10ARCCtrl43ARCMapping12 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  12  cmdID= 39057
                    min= 0  max= 32  step= 1  format= 0  div_scale= 1  preset= 0
                    Min = 0  Max = 0  Step = 0  Preset = 0  "
        ::= { iquav10CmdEntry 39057 }


    iquav10ARCCtrl43ARCMapping13 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  13  cmdID= 39058
                    min= 0  max= 32  step= 1  format= 0  div_scale= 1  preset= 1
                    Min = 0  Max = 0  Step = 0  Preset = 0  "
        ::= { iquav10CmdEntry 39058 }


    iquav10ARCCtrl43ARCMapping14 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  14  cmdID= 39059
                    min= 0  max= 32  step= 1  format= 0  div_scale= 1  preset= 1
                    Min = 0  Max = 0  Step = 0  Preset = 0  "
        ::= { iquav10CmdEntry 39059 }


    iquav10ARCCtrl43ARCMapping15 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  15  cmdID= 39060
                    min= 0  max= 32  step= 1  format= 0  div_scale= 1  preset= 1
                    Min = 0  Max = 0  Step = 0  Preset = 0  "
        ::= { iquav10CmdEntry 39060 }


    iquav10ARCCtrl43ARCMapping16 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  16  cmdID= 39061
                    min= 0  max= 32  step= 1  format= 0  div_scale= 1  preset= 0
                    Min = 0  Max = 0  Step = 0  Preset = 0  "
        ::= { iquav10CmdEntry 39061 }


    iquav10ARCCtrl169ARCMapping2 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  2  cmdID= 39062
                    min= 0  max= 32  step= 1  format= 0  div_scale= 1  preset= 1
                    Min = 0  Max = 0  Step = 0  Preset = 0  "
        ::= { iquav10CmdEntry 39062 }


    iquav10ARCCtrl169ARCMapping3 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  3  cmdID= 39063
                    min= 0  max= 32  step= 1  format= 0  div_scale= 1  preset= 1
                    Min = 0  Max = 0  Step = 0  Preset = 0  "
        ::= { iquav10CmdEntry 39063 }


    iquav10ARCCtrl169ARCMapping4 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  4  cmdID= 39064
                    min= 0  max= 32  step= 1  format= 0  div_scale= 1  preset= 1
                    Min = 0  Max = 0  Step = 0  Preset = 0  "
        ::= { iquav10CmdEntry 39064 }


    iquav10ARCCtrl169ARCMapping8 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  8  cmdID= 39065
                    min= 0  max= 32  step= 1  format= 0  div_scale= 1  preset= 1
                    Min = 0  Max = 0  Step = 0  Preset = 0  "
        ::= { iquav10CmdEntry 39065 }


    iquav10ARCCtrl169ARCMapping9 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  9  cmdID= 39066
                    min= 0  max= 32  step= 1  format= 0  div_scale= 1  preset= 1
                    Min = 0  Max = 0  Step = 0  Preset = 0  "
        ::= { iquav10CmdEntry 39066 }


    iquav10ARCCtrl169ARCMapping10 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  10  cmdID= 39067
                    min= 0  max= 32  step= 1  format= 0  div_scale= 1  preset= 1
                    Min = 0  Max = 0  Step = 0  Preset = 0  "
        ::= { iquav10CmdEntry 39067 }


    iquav10ARCCtrl169ARCMapping11 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  11  cmdID= 39068
                    min= 0  max= 32  step= 1  format= 0  div_scale= 1  preset= 1
                    Min = 0  Max = 0  Step = 0  Preset = 0  "
        ::= { iquav10CmdEntry 39068 }


    iquav10ARCCtrl169ARCMapping12 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  12  cmdID= 39069
                    min= 0  max= 32  step= 1  format= 0  div_scale= 1  preset= 0
                    Min = 0  Max = 0  Step = 0  Preset = 0  "
        ::= { iquav10CmdEntry 39069 }


    iquav10ARCCtrl169ARCMapping13 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  13  cmdID= 39070
                    min= 0  max= 32  step= 1  format= 0  div_scale= 1  preset= 1
                    Min = 0  Max = 0  Step = 0  Preset = 0  "
        ::= { iquav10CmdEntry 39070 }


    iquav10ARCCtrl169ARCMapping14 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  14  cmdID= 39071
                    min= 0  max= 32  step= 1  format= 0  div_scale= 1  preset= 1
                    Min = 0  Max = 0  Step = 0  Preset = 0  "
        ::= { iquav10CmdEntry 39071 }


    iquav10ARCCtrl169ARCMapping15 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  15  cmdID= 39072
                    min= 0  max= 32  step= 1  format= 0  div_scale= 1  preset= 1
                    Min = 0  Max = 0  Step = 0  Preset = 0  "
        ::= { iquav10CmdEntry 39072 }


    iquav10ARCCtrl169ARCMapping16 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping 16  cmdID= 39073
                    min= 0  max= 32  step= 1  format= 0  div_scale= 1  preset= 0
                    Min = 0  Max = 0  Step = 0  Preset = 0  "
        ::= { iquav10CmdEntry 39073 }


    iquav10ARCCtrlNoSignalARCMapping OBJECT-TYPE
        SYNTAX            INTEGER
        MAX-ACCESS        read-write
        STATUS            current
        DESCRIPTION
                "CMNT: - No signal ARC Mapping
                 TYPE: - Number
                 PAGE: - ARC Ctrl
                    No Signal ARC Mapping  cmdID= 39074
                    min= 0  max= 32  step= 1  format= 0  div_scale= 1  preset= 1
                    Min = 0  Max = 0  Step = 0  Preset = 0  "
        ::= { iquav10CmdEntry 39074 }


    iquav10ARCCtrlForceARCMapping OBJECT-TYPE
        SYNTAX            INTEGER
        MAX-ACCESS        read-write
        STATUS            current
        DESCRIPTION
                "CMNT: - Force ARC Mapping
                 TYPE: - Number
                 PAGE: - ARC Ctrl
                    Force ARC Mapping  cmdID= 39078
                    min= 0  max= 32  step= 1  format= 0  div_scale= 1  preset= 1
                    Min = 0  Max = 0  Step = 0  Preset = 0  "
        ::= { iquav10CmdEntry 39078 }


    iquav10GenlockBlankingGenlockStandard OBJECT-TYPE
        SYNTAX            INTEGER {
                            val52529i(1),
                            val62525i(2),
                            val72023p(3),
                            val72024p(4),
                            val72025p(5),
                            val72029p(6),
                            val72030p(7),
                            val72059p(8),
                            val72050p(9),
                            val72060p(10),
                            val108025i(11),
                            val108029i(12),
                            val108030i(13),
                            val108023sf(14),
                            val108024sf(15),
                            val108025sf(16),
                            val108023p(17),
                            val108024p(18),
                            val108025p(19),
                            val108029p(20),
                            val108030p(21),
                            val108050p(22),
                            val108059p(23),
                            val108060p(24)
                            }
        MAX-ACCESS        read-write
        STATUS            current
        DESCRIPTION
                "CMNT: - Select std for Ref display/set
                 TYPE: - RadiobuttonList
                 PAGE: - Genlock/Blanking
                    Standard  cmdID= 37203
                    525/29i  value= 1
                    625/25i  value= 2
                    720/23p  value= 3
                    720/24p  value= 4
                    720/25p  value= 5
                    720/29p  value= 6
                    720/30p  value= 7
                    720/59p  value= 8
                    720/50p  value= 9
                    720/60p  value= 10
                    1080/25i  value= 11
                    1080/29i  value= 12
                    1080/30i  value= 13
                    1080/23sf  value= 14
                    1080/24sf  value= 15
                    1080/25sf  value= 16
                    1080/23p  value= 17
                    1080/24p  value= 18
                    1080/25p  value= 19
                    1080/29p  value= 20
                    1080/30p  value= 21
                    1080/50p  value= 22
                    1080/59p  value= 23
                    1080/60p  value= 24  "
        ::= { iquav10CmdEntry 37203 }


    iquav10GenlockBlankingGenlockDelayMode OBJECT-TYPE
        SYNTAX            INTEGER {
                            valFreeRun(0),
                            valLocktoReference(1),
                            valManualHV(2)
                            }
        MAX-ACCESS        read-write
        STATUS            current
        DESCRIPTION
                "CMNT: - Video Reference Mode source: Free Run/LockRef/LockRef(Delay Mismatch)/Minimum/Frames/Manual/Manual ms
                 TYPE: - RadiobuttonList
                 PAGE: - Genlock/Blanking
                    Delay Mode  cmdID= 33029
                    Free Run  value= 0
                    Lock to Reference  value= 1
                    Manual H/V  value= 2  "
        ::= { iquav10CmdEntry 33029 }


    iquav10GenlockSetDelayDelayFrames OBJECT-TYPE
        SYNTAX            INTEGER
        MAX-ACCESS        read-write
        STATUS            current
        DESCRIPTION
                "CMNT: - Set video delay in frames
                 TYPE: - Number
                 PAGE: - Genlock
                    Delay Frames  cmdID= 33031
                    min= 0  max= 147  step= 1  format= %0.0f frames  div_scale= 1  preset= 1
                    Min = 0 frames  Max = 147 frames  Step = 1 frames  Preset = 1 frames  "
        ::= { iquav10CmdEntry 33031 }


    iquav10GenlockSetDelayVerticalPhase OBJECT-TYPE
        SYNTAX            INTEGER
        MAX-ACCESS        read-write
        STATUS            current
        DESCRIPTION
                "CMNT: - Reference vertical timing
                 TYPE: - Number
                 PAGE: - Genlock
                    Vertical Phase  cmdID= 33033
                    min= -1125  max= 1125  step= 1  format= %0.0f lines  div_scale= 1  preset= 0
                    Min = -1125 lines  Max = 1125 lines  Step = 1 lines  Preset = 0 lines  "
        ::= { iquav10CmdEntry 33033 }


    iquav10GenlockSetDelayHorizontalPhase OBJECT-TYPE
        SYNTAX            INTEGER
        MAX-ACCESS        read-write
        STATUS            current
        DESCRIPTION
                "CMNT: - Reference horizontal timing
                 TYPE: - Number
                 PAGE: - Genlock
                    Horizontal Phase  cmdID= 33032
                    min= -4125  max= 4125  step= 1  format= %0.0f pixels  div_scale= 1  preset= 0
                    Min = -4125 pixels  Max = 4125 pixels  Step = 1 pixels  Preset = 0 pixels  "
        ::= { iquav10CmdEntry 33032 }


    iquav10GenlockSetDelayVerticalDelay OBJECT-TYPE
        SYNTAX            INTEGER
        MAX-ACCESS        read-write
        STATUS            current
        DESCRIPTION
                "CMNT: - Reference vertical timing
                 TYPE: - Number
                 PAGE: - Genlock
                    Vertical Delay  cmdID= 33045
                    min= 0  max= 1125  step= 1  format= %0.0f lines  div_scale= 1  preset= 0
                    Min = 0 lines  Max = 1125 lines  Step = 1 lines  Preset = 0 lines  "
        ::= { iquav10CmdEntry 33045 }


    iquav10GenlockSetDelayHorizontalDelay OBJECT-TYPE
        SYNTAX            INTEGER
        MAX-ACCESS        read-write
        STATUS            current
        DESCRIPTION
                "CMNT: - Reference horizontal timing
                 TYPE: - Number
                 PAGE: - Genlock
                    Horizontal Delay  cmdID= 33044
                    min= 0  max= 4125  step= 1  format= %0.0f pixels  div_scale= 1  preset= 0
                    Min = 0 pixels  Max = 4125 pixels  Step = 1 pixels  Preset = 0 pixels  "
        ::= { iquav10CmdEntry 33044 }


    iquav10GenlockBlankingGenlockRefLogHide OBJECT-TYPE
        SYNTAX            RollCallString
        MAX-ACCESS        read-only
        STATUS            current
        DESCRIPTION
                "CMNT: - Hide logging for Reference
                 TYPE: - Display
                 PAGE: - Genlock/Blanking
                    RefLogHide  cmdID= 33175  "
        ::= { iquav10CmdEntry 33175 }


    iquav10GenlockDolbyELineStandard OBJECT-TYPE
        SYNTAX            INTEGER {
                            val52529i(1),
                            val62525i(2),
                            val72023p(3),
                            val72024p(4),
                            val72025p(5),
                            val72029p(6),
                            val72030p(7),
                            val72050p(8),
                            val72059p(9),
                            val72060p(10),
                            val108025i(11),
                            val108029i(12),
                            val108030i(13),
                            val108023psf(14),
                            val108024psf(15),
                            val108025psf(16),
                            val108023p(17),
                            val108024p(18),
                            val108025p(19),
                            val108029p(20),
                            val108030p(21),
                            val108050p(22),
                            val108059p(23),
                            val108060p(24)
                            }
        MAX-ACCESS        read-write
        STATUS            current
        DESCRIPTION
                "CMNT: - Select standard to display Dolby E Auto-Line for
                 TYPE: - RadiobuttonList
                 PAGE: - Genlock
                    Standard  cmdID= 38655
                    525/29i  value= 1
                    625/25i  value= 2
                    720/23p  value= 3
                    720/24p  value= 4
                    720/25p  value= 5
                    720/29p  value= 6
                    720/30p  value= 7
                    720/50p  value= 8
                    720/59p  value= 9
                    720/60p  value= 10
                    1080/25i  value= 11
                    1080/29i  value= 12
                    1080/30i  value= 13
                    1080/23psf  value= 14
                    1080/24psf  value= 15
                    1080/25psf  value= 16
                    1080/23p  value= 17
                    1080/24p  value= 18
                    1080/25p  value= 19
                    1080/29p  value= 20
                    1080/30p  value= 21
                    1080/50p  value= 22
                    1080/59p  value= 23
                    1080/60p  value= 24  "
        ::= { iquav10CmdEntry 38655 }


    iquav10GenlockDolbyELineAutoLineNo OBJECT-TYPE
        SYNTAX            INTEGER
        MAX-ACCESS        read-write
        STATUS            current
        DESCRIPTION
                "CMNT: - Select standard to display Dolby E Auto-Line for
                 TYPE: - Number
                 PAGE: - Genlock
                    Auto Line No.  cmdID= 38656
                    min= 0  max= 1125  step= 1  format= %0.0f  div_scale= 1  preset= 1
                    Min = 0  Max = 1125  Step = 1  Preset = 1  "
        ::= { iquav10CmdEntry 38656 }


    iquav10DolbyELineUserDolbyELinePair1 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair1  cmdID= 38670
                    Default  value= 0
                    User  value= 1  "
        ::= { iquav10CmdEntry 38670 }


    iquav10DolbyELineUserDolbyELinePair2 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair2  cmdID= 38671
                    Default  value= 0
                    User  value= 1  "
        ::= { iquav10CmdEntry 38671 }


    iquav10DolbyELineUserDolbyELinePair3 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair3  cmdID= 38672
                    Default  value= 0
                    User  value= 1  "
        ::= { iquav10CmdEntry 38672 }


    iquav10DolbyELineUserDolbyELinePair4 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair4  cmdID= 38673
                    Default  value= 0
                    User  value= 1  "
        ::= { iquav10CmdEntry 38673 }


    iquav10DolbyELineUserDolbyELinePair5 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair5  cmdID= 38674
                    Default  value= 0
                    User  value= 1  "
        ::= { iquav10CmdEntry 38674 }


    iquav10DolbyELineUserDolbyELinePair6 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair6  cmdID= 38675
                    Default  value= 0
                    User  value= 1  "
        ::= { iquav10CmdEntry 38675 }


    iquav10DolbyELineUserDolbyELinePair7 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair7  cmdID= 38676
                    Default  value= 0
                    User  value= 1  "
        ::= { iquav10CmdEntry 38676 }


    iquav10DolbyELineUserDolbyELinePair8 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair8  cmdID= 38677
                    Default  value= 0
                    User  value= 1  "
        ::= { iquav10CmdEntry 38677 }


    iquav10GenlockDolbyELineUserLine525i29 OBJECT-TYPE
        SYNTAX            INTEGER
        MAX-ACCESS        read-write
        STATUS            current
        DESCRIPTION
                "CMNT: - 
                 TYPE: - Number
                 PAGE: - Genlock
                    UserLine525i29  cmdID= 38684
                    min= 1  max= 525  step= 1  format= %d  div_scale= 1  preset= 14
                    Min = 0  Max = 0  Step = 0  Preset = 0  "
        ::= { iquav10CmdEntry 38684 }


    iquav10GenlockDolbyELineUserLine625i25 OBJECT-TYPE
        SYNTAX            INTEGER
        MAX-ACCESS        read-write
        STATUS            current
        DESCRIPTION
                "CMNT: - 
                 TYPE: - Number
                 PAGE: - Genlock
                    UserLine625i25  cmdID= 38685
                    min= 1  max= 625  step= 1  format= %d  div_scale= 1  preset= 12
                    Min = 0  Max = 0  Step = 0  Preset = 0  "
        ::= { iquav10CmdEntry 38685 }


    iquav10GenlockDolbyELineUserLine720p23 OBJECT-TYPE
        SYNTAX            INTEGER
        MAX-ACCESS        read-write
        STATUS            current
        DESCRIPTION
                "CMNT: - 
                 TYPE: - Number
                 PAGE: - Genlock
                    UserLine720p23  cmdID= 38686
                    min= 1  max= 750  step= 1  format= %d  div_scale= 1  preset= 28
                    Min = 0  Max = 0  Step = 0  Preset = 0  "
        ::= { iquav10CmdEntry 38686 }


    iquav10GenlockDolbyELineUserLine720p24 OBJECT-TYPE
        SYNTAX            INTEGER
        MAX-ACCESS        read-write
        STATUS            current
        DESCRIPTION
                "CMNT: - 
                 TYPE: - Number
                 PAGE: - Genlock
                    UserLine720p24  cmdID= 38687
                    min= 1  max= 750  step= 1  format= %d  div_scale= 1  preset= 28
                    Min = 0  Max = 0  Step = 0  Preset = 0  "
        ::= { iquav10CmdEntry 38687 }


    iquav10GenlockDolbyELineUserLine720p25 OBJECT-TYPE
        SYNTAX            INTEGER
        MAX-ACCESS        read-write
        STATUS            current
        DESCRIPTION
                "CMNT: - 
                 TYPE: - Number
                 PAGE: - Genlock
                    UserLine720p25  cmdID= 38688
                    min= 1  max= 750  step= 1  format= %d  div_scale= 1  preset= 28
                    Min = 0  Max = 0  Step = 0  Preset = 0  "
        ::= { iquav10CmdEntry 38688 }


    iquav10GenlockDolbyELineUserLine720p29 OBJECT-TYPE
        SYNTAX            INTEGER
        MAX-ACCESS        read-write
        STATUS            current
        DESCRIPTION
                "CMNT: - 
                 TYPE: - Number
                 PAGE: - Genlock
                    UserLine720p29  cmdID= 38689
                    min= 1  max= 750  step= 1  format= %d  div_scale= 1  preset= 28
                    Min = 0  Max = 0  Step = 0  Preset = 0  "
        ::= { iquav10CmdEntry 38689 }


    iquav10GenlockDolbyELineUserLine720p30 OBJECT-TYPE
        SYNTAX            INTEGER
        MAX-ACCESS        read-write
        STATUS            current
        DESCRIPTION
                "CMNT: - 
                 TYPE: - Number
                 PAGE: - Genlock
                    UserLine720p30  cmdID= 38690
                    min= 1  max= 750  step= 1  format= %d  div_scale= 1  preset= 28
                    Min = 0  Max = 0  Step = 0  Preset = 0  "
        ::= { iquav10CmdEntry 38690 }


    iquav10GenlockDolbyELineUserLine720p50 OBJECT-TYPE
        SYNTAX            INTEGER
        MAX-ACCESS        read-write
        STATUS            current
        DESCRIPTION
                "CMNT: - 
                 TYPE: - Number
                 PAGE: - Genlock
                    UserLine720p50  cmdID= 38683
                    min= 1  max= 750  step= 1  format= %d  div_scale= 1  preset= 28
                    Min = 0  Max = 0  Step = 0  Preset = 0  "
        ::= { iquav10CmdEntry 38683 }


    iquav10GenlockDolbyELineUserLine720p59 OBJECT-TYPE
        SYNTAX            INTEGER
        MAX-ACCESS        read-write
        STATUS            current
        DESCRIPTION
                "CMNT: - 
                 TYPE: - Number
                 PAGE: - Genlock
                    UserLine720p59  cmdID= 38682
                    min= 1  max= 750  step= 1  format= %d  div_scale= 1  preset= 32
                    Min = 0  Max = 0  Step = 0  Preset = 0  "
        ::= { iquav10CmdEntry 38682 }


    iquav10GenlockDolbyELineUserLine720p60 OBJECT-TYPE
        SYNTAX            INTEGER
        MAX-ACCESS        read-write
        STATUS            current
        DESCRIPTION
                "CMNT: - 
                 TYPE: - Number
                 PAGE: - Genlock
                    UserLine720p60  cmdID= 38691
                    min= 1  max= 750  step= 1  format= %d  div_scale= 1  preset= 32
                    Min = 0  Max = 0  Step = 0  Preset = 0  "
        ::= { iquav10CmdEntry 38691 }


    iquav10GenlockDolbyELineUserLine1080i25 OBJECT-TYPE
        SYNTAX            INTEGER
        MAX-ACCESS        read-write
        STATUS            current
        DESCRIPTION
                "CMNT: - 
                 TYPE: - Number
                 PAGE: - Genlock
                    UserLine1080i25  cmdID= 38681
                    min= 1  max= 1125  step= 1  format= %d  div_scale= 1  preset= 21
                    Min = 0  Max = 0  Step = 0  Preset = 0  "
        ::= { iquav10CmdEntry 38681 }


    iquav10GenlockDolbyELineUserLine1080i29 OBJECT-TYPE
        SYNTAX            INTEGER
        MAX-ACCESS        read-write
        STATUS            current
        DESCRIPTION
                "CMNT: - 
                 TYPE: - Number
                 PAGE: - Genlock
                    UserLine1080i29  cmdID= 38680
                    min= 1  max= 1125  step= 1  format= %d  div_scale= 1  preset= 24
                    Min = 0  Max = 0  Step = 0  Preset = 0  "
        ::= { iquav10CmdEntry 38680 }


    iquav10GenlockDolbyELineUserLine1080i30 OBJECT-TYPE
        SYNTAX            INTEGER
        MAX-ACCESS        read-write
        STATUS            current
        DESCRIPTION
                "CMNT: - 
                 TYPE: - Number
                 PAGE: - Genlock
                    UserLine1080i30  cmdID= 38692
                    min= 1  max= 1125  step= 1  format= %d  div_scale= 1  preset= 24
                    Min = 0  Max = 0  Step = 0  Preset = 0  "
        ::= { iquav10CmdEntry 38692 }


    iquav10GenlockDolbyELineUserLine1080p23sf OBJECT-TYPE
        SYNTAX            INTEGER
        MAX-ACCESS        read-write
        STATUS            current
        DESCRIPTION
                "CMNT: - 
                 TYPE: - Number
                 PAGE: - Genlock
                    UserLine1080p23sf  cmdID= 38693
                    min= 1  max= 1125  step= 1  format= %d  div_scale= 1  preset= 42
                    Min = 0  Max = 0  Step = 0  Preset = 0  "
        ::= { iquav10CmdEntry 38693 }


    iquav10GenlockDolbyELineUserLine1080p24sf OBJECT-TYPE
        SYNTAX            INTEGER
        MAX-ACCESS        read-write
        STATUS            current
        DESCRIPTION
                "CMNT: - 
                 TYPE: - Number
                 PAGE: - Genlock
                    UserLine1080p24sf  cmdID= 38694
                    min= 1  max= 1125  step= 1  format= %d  div_scale= 1  preset= 42
                    Min = 0  Max = 0  Step = 0  Preset = 0  "
        ::= { iquav10CmdEntry 38694 }


    iquav10GenlockDolbyELineUserLine1080p25sf OBJECT-TYPE
        SYNTAX            INTEGER
        MAX-ACCESS        read-write
        STATUS            current
        DESCRIPTION
                "CMNT: - 
                 TYPE: - Number
                 PAGE: - Genlock
                    UserLine1080p25sf  cmdID= 38695
                    min= 1  max= 1125  step= 1  format= %d  div_scale= 1  preset= 42
                    Min = 0  Max = 0  Step = 0  Preset = 0  "
        ::= { iquav10CmdEntry 38695 }


    iquav10GenlockDolbyELineUserLine1080p23 OBJECT-TYPE
        SYNTAX            INTEGER
        MAX-ACCESS        read-write
        STATUS            current
        DESCRIPTION
                "CMNT: - 
                 TYPE: - Number
                 PAGE: - Genlock
                    UserLine1080p23  cmdID= 38696
                    min= 1  max= 1125  step= 1  format= %d  div_scale= 1  preset= 42
                    Min = 0  Max = 0  Step = 0  Preset = 0  "
        ::= { iquav10CmdEntry 38696 }


    iquav10GenlockDolbyELineUserLine1080p24 OBJECT-TYPE
        SYNTAX            INTEGER
        MAX-ACCESS        read-write
        STATUS            current
        DESCRIPTION
                "CMNT: - 
                 TYPE: - Number
                 PAGE: - Genlock
                    UserLine1080p24  cmdID= 38697
                    min= 1  max= 1125  step= 1  format= %d  div_scale= 1  preset= 42
                    Min = 0  Max = 0  Step = 0  Preset = 0  "
        ::= { iquav10CmdEntry 38697 }


    iquav10GenlockDolbyELineUserLine1080p25 OBJECT-TYPE
        SYNTAX            INTEGER
        MAX-ACCESS        read-write
        STATUS            current
        DESCRIPTION
                "CMNT: - 
                 TYPE: - Number
                 PAGE: - Genlock
                    UserLine1080p25  cmdID= 38698
                    min= 1  max= 1125  step= 1  format= %d  div_scale= 1  preset= 42
                    Min = 0  Max = 0  Step = 0  Preset = 0  "
        ::= { iquav10CmdEntry 38698 }


    iquav10GenlockDolbyELineUserLine1080p29 OBJECT-TYPE
        SYNTAX            INTEGER
        MAX-ACCESS        read-write
        STATUS            current
        DESCRIPTION
                "CMNT: - 
                 TYPE: - Number
                 PAGE: - Genlock
                    UserLine1080p29  cmdID= 38699
                    min= 1  max= 1125  step= 1  format= %d  div_scale= 1  preset= 42
                    Min = 0  Max = 0  Step = 0  Preset = 0  "
        ::= { iquav10CmdEntry 38699 }


    iquav10GenlockDolbyELineUserLine1080p30 OBJECT-TYPE
        SYNTAX            INTEGER
        MAX-ACCESS        read-write
        STATUS            current
        DESCRIPTION
                "CMNT: - 
                 TYPE: - Number
                 PAGE: - Genlock
                    UserLine1080p30  cmdID= 38707
                    min= 1  max= 1125  step= 1  format= %d  div_scale= 1  preset= 42
                    Min = 0  Max = 0  Step = 0  Preset = 0  "
        ::= { iquav10CmdEntry 38707 }


    iquav10GenlockDolbyELineUserLine1080p50 OBJECT-TYPE
        SYNTAX            INTEGER
        MAX-ACCESS        read-write
        STATUS            current
        DESCRIPTION
                "CMNT: - 
                 TYPE: - Number
                 PAGE: - Genlock
                    UserLine1080p50  cmdID= 38679
                    min= 1  max= 1125  step= 1  format= %d  div_scale= 1  preset= 42
                    Min = 0  Max = 0  Step = 0  Preset = 0  "
        ::= { iquav10CmdEntry 38679 }


    iquav10GenlockDolbyELineUserLine1080p59 OBJECT-TYPE
        SYNTAX            INTEGER
        MAX-ACCESS        read-write
        STATUS            current
        DESCRIPTION
                "CMNT: - 
                 TYPE: - Number
                 PAGE: - Genlock
                    UserLine1080p59  cmdID= 38780
                    min= 1  max= 1125  step= 1  format= %d  div_scale= 1  preset= 47
                    Min = 0  Max = 0  Step = 0  Preset = 0  "
        ::= { iquav10CmdEntry 38780 }


    iquav10GenlockDolbyELineUserLine1080p60 OBJECT-TYPE
        SYNTAX            INTEGER
        MAX-ACCESS        read-write
        STATUS            current
        DESCRIPTION
                "CMNT: - 
                 TYPE: - Number
                 PAGE: - Genlock
                    UserLine1080p60  cmdID= 38711
                    min= 1  max= 1125  step= 1  format= %d  div_scale= 1  preset= 47
                    Min = 0  Max = 0  Step = 0  Preset = 0  "
        ::= { iquav10CmdEntry 38711 }


    iquav10GenlockDolbyELineAutoAlign1 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign1  cmdID= 38110  "
        ::= { iquav10CmdEntry 38110 }


    iquav10GenlockDolbyELineAutoAlign2 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign2  cmdID= 38111  "
        ::= { iquav10CmdEntry 38111 }


    iquav10GenlockDolbyELineAutoAlign3 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign3  cmdID= 38112  "
        ::= { iquav10CmdEntry 38112 }


    iquav10GenlockDolbyELineAutoAlign4 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign4  cmdID= 38113  "
        ::= { iquav10CmdEntry 38113 }


    iquav10GenlockDolbyELineAutoAlign5 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign5  cmdID= 38114  "
        ::= { iquav10CmdEntry 38114 }


    iquav10GenlockDolbyELineAutoAlign6 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign6  cmdID= 38115  "
        ::= { iquav10CmdEntry 38115 }


    iquav10GenlockDolbyELineAutoAlign7 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign7  cmdID= 38116  "
        ::= { iquav10CmdEntry 38116 }


    iquav10GenlockDolbyELineAutoAlign8 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign8  cmdID= 38117  "
        ::= { iquav10CmdEntry 38117 }


    iquav10WSSCtrlEnableMapper OBJECT-TYPE
        SYNTAX            INTEGER { disable(0), enable(1)  }
        MAX-ACCESS        read-write
        STATUS            current
        DESCRIPTION
                "CMNT: - 
                 TYPE: - Checkbox
                 PAGE: - WSS Ctrl
                    EnableMapper  cmdID= 38747  "
        ::= { iquav10CmdEntry 38747 }


    iquav10WSSCtrlIPWSSSignal OBJECT-TYPE
        SYNTAX            INTEGER {
                            val43nbox169top(2),
                            val43nbox149top(3),
                            val43nbox169ctr(4),
                            val43nCodedFrame(8),
                            val43n43(9),
                            val43n169(10),
                            val43n149(11),
                            val43Reserved12(12),
                            val43n43SP149(13),
                            val43n169SP149(14),
                            val43n169SP43(15),
                            val43nUnknownAll(16),
                            val169nbox169top(130),
                            val169nbox149top(131),
                            val169nbox169ctr(132),
                            val169nCodedFrame(136),
                            val169n43(137),
                            val169n169(138),
                            val169n149(139),
                            val169Reserved12(140),
                            val169n43SP149(141),
                            val169n169SP149(142),
                            val169n169SP43(143),
                            val169nUnknownAll(144),
                            valNoSignal(145),
                            valForceMode(146)
                            }
        MAX-ACCESS        read-write
        STATUS            current
        DESCRIPTION
                "CMNT: - 
                 TYPE: - RadiobuttonList
                 PAGE: - WSS Ctrl
                    I/P WSS Signal  cmdID= 38740
                    4:3-box 16:9 top  value= 2
                    4:3-box 14:9 top  value= 3
                    4:3-box>16:9ctr  value= 4
                    4:3-Coded Frame  value= 8
                    4:3-4:3  value= 9
                    4:3-16:9  value= 10
                    4:3-14:9  value= 11
                    4:3 Reserved(12)  value= 12
                    4:3-4:3 SP 14:9  value= 13
                    4:3-16:9 SP 14:9  value= 14
                    4:3-16:9 SP 4:3  value= 15
                    4:3-Unknown(All)  value= 16
                    16:9-box 16:9 top  value= 130
                    16:9-box 14:9 top  value= 131
                    16:9-box>16:9ctr  value= 132
                    16:9-Coded Frame  value= 136
                    16:9-4:3  value= 137
                    16:9-16:9  value= 138
                    16:9-14:9  value= 139
                    16:9 Reserved(12)  value= 140
                    16:9-4:3 SP 14:9  value= 141
                    16:9-16:9 SP14:9  value= 142
                    16:9-16:9 SP 4:3  value= 143
                    16:9-Unknown(All)  value= 144
                    No Signal  value= 145
                    Force Mode  value= 146  "
        ::= { iquav10CmdEntry 38740 }


    iquav10WSSCtrlOPWSS43 OBJECT-TYPE
        SYNTAX            INTEGER {
                            val43nbox169top(2),
                            val43nbox149top(3),
                            val43nbox169ctr(4),
                            val43nCodedFrame(8),
                            val43n43(9),
                            val43n169(10),
                            val43n149(11),
                            val43nreservedn12(12),
                            val43n43SP149(13),
                            val43n169SP149(14),
                            val43n169SP43(15),
                            val169nbox169top(130),
                            val169nbox149top(131),
                            val169nbox169ctr(132),
                            val169nCodedFrame(136),
                            val169n43(137),
                            val169n169(138),
                            val169n149(139),
                            val169nreservedn12(140),
                            val169n43SP149(141),
                            val169n169SP149(142),
                            val169n169SP43(143)
                            }
        MAX-ACCESS        read-write
        STATUS            current
        DESCRIPTION
                "CMNT: - 
                 TYPE: - RadiobuttonList
                 PAGE: - WSS Ctrl
                    O/P WSS 4:3  cmdID= 38745
                    4:3-box 16:9 top  value= 2
                    4:3-box 14:9 top  value= 3
                    4:3-box>16:9ctr  value= 4
                    4:3-Coded Frame  value= 8
                    4:3-4:3  value= 9
                    4:3-16:9  value= 10
                    4:3-14:9  value= 11
                    4:3-reserved-12  value= 12
                    4:3-4:3 SP 14:9  value= 13
                    4:3-16:9 SP14:9  value= 14
                    4:3-16:9 SP 4:3  value= 15
                    16:9-box 16:9 top  value= 130
                    16:9-box 14:9 top  value= 131
                    16:9-box>16:9ctr  value= 132
                    16:9-Coded Frame  value= 136
                    16:9-4:3  value= 137
                    16:9-16:9  value= 138
                    16:9-14:9  value= 139
                    16:9-reserved-12  value= 140
                    16:9-4:3 SP 14:9  value= 141
                    16:9-16:9 SP14:9  value= 142
                    16:9-16:9 SP 4:3  value= 143  "
        ::= { iquav10CmdEntry 38745 }


    iquav10WSSCtrlDispMem43 OBJECT-TYPE
        SYNTAX            INTEGER {
                            valNoChange(0),
                            valDisplayMemory1(1),
                            valDisplayMemory2(2),
                            valDisplayMemory3(3),
                            valDisplayMemory4(4),
                            valDisplayMemory5(5),
                            valDisplayMemory6(6),
                            valDisplayMemory7(7),
                            valDisplayMemory8(8),
                            valDisplayMemory9(9),
                            valDisplayMemory10(10),
                            valDisplayMemory11(11),
                            valDisplayMemory12(12),
                            valDisplayMemory13(13),
                            valDisplayMemory14(14),
                            valDisplayMemory15(15),
                            valDisplayMemory16(16),
                            valDisplayMemory17(17),
                            valDisplayMemory18(18),
                            valDisplayMemory19(19),
                            valDisplayMemory20(20),
                            valDisplayMemory21(21),
                            valDisplayMemory22(22),
                            valDisplayMemory23(23),
                            valDisplayMemory24(24),
                            valDisplayMemory25(25),
                            valDisplayMemory26(26),
                            valDisplayMemory27(27),
                            valDisplayMemory28(28),
                            valDisplayMemory29(29),
                            valDisplayMemory30(30),
                            valDisplayMemory31(31),
                            valDisplayMemory32(32)
                            }
        MAX-ACCESS        read-write
        STATUS            current
        DESCRIPTION
                "CMNT: - 
                 TYPE: - RadiobuttonList
                 PAGE: - WSS Ctrl
                    Disp Mem 4:3  cmdID= 38748
                    No Change  value= 0
                    Display Memory 1  value= 1
                    Display Memory 2  value= 2
                    Display Memory 3  value= 3
                    Display Memory 4  value= 4
                    Display Memory 5  value= 5
                    Display Memory 6  value= 6
                    Display Memory 7  value= 7
                    Display Memory 8  value= 8
                    Display Memory 9  value= 9
                    Display Memory 10  value= 10
                    Display Memory 11  value= 11
                    Display Memory 12  value= 12
                    Display Memory 13  value= 13
                    Display Memory 14  value= 14
                    Display Memory 15  value= 15
                    Display Memory 16  value= 16
                    Display Memory 17  value= 17
                    Display Memory 18  value= 18
                    Display Memory 19  value= 19
                    Display Memory 20  value= 20
                    Display Memory 21  value= 21
                    Display Memory 22  value= 22
                    Display Memory 23  value= 23
                    Display Memory 24  value= 24
                    Display Memory 25  value= 25
                    Display Memory 26  value= 26
                    Display Memory 27  value= 27
                    Display Memory 28  value= 28
                    Display Memory 29  value= 29
                    Display Memory 30  value= 30
                    Display Memory 31  value= 31
                    Display Memory 32  value= 32  "
        ::= { iquav10CmdEntry 38748 }


    iquav10WSSCtrlWidescreenIP2016 OBJECT-TYPE
        SYNTAX            INTEGER { disable(0), enable(1)  }
        MAX-ACCESS        read-write
        STATUS            current
        DESCRIPTION
                "CMNT: - 
                 TYPE: - Checkbox
                 PAGE: - WSS Ctrl
                    2016  cmdID= 38724  "
        ::= { iquav10CmdEntry 38724 }


    iquav10WSSCtrlWidescreenIPPriority OBJECT-TYPE
        SYNTAX            INTEGER {
                            valWSS(0),
                            valVI(1)
                            }
        MAX-ACCESS        read-write
        STATUS            current
        DESCRIPTION
                "CMNT: - 
                 TYPE: - RadiobuttonList
                 PAGE: - WSS Ctrl
                    Priority  cmdID= 38750
                    WSS  value= 0
                    VI  value= 1  "
        ::= { iquav10CmdEntry 38750 }


    iquav10WSSCtrlWidescreenIPWSSInEnable OBJECT-TYPE
        SYNTAX            INTEGER {
                            valOff(0),
                            valWSSAFD(1),
                            valWSSETSI(2)
                            }
        MAX-ACCESS        read-write
        STATUS            current
        DESCRIPTION
                "CMNT: - 
                 TYPE: - RadiobuttonList
                 PAGE: - WSS Ctrl
                    WSS In Enable  cmdID= 38720
                    Off  value= 0
                    WSS AFD  value= 1
                    WSS ETSI  value= 2  "
        ::= { iquav10CmdEntry 38720 }


    iquav10WSSCtrlWidescreenIPVIInEnable OBJECT-TYPE
        SYNTAX            INTEGER {
                            valOff(0),
                            valVISMPTE(1),
                            valVIAFD(2),
                            valVIAFD2008(3)
                            }
        MAX-ACCESS        read-write
        STATUS            current
        DESCRIPTION
                "CMNT: - 
                 TYPE: - RadiobuttonList
                 PAGE: - WSS Ctrl
                    VI In Enable  cmdID= 38723
                    Off  value= 0
                    VI SMPTE  value= 1
                    VI AFD  value= 2
                    VI AFD 2008  value= 3  "
        ::= { iquav10CmdEntry 38723 }


    iquav10WSSCtrlWidescreenOP2016 OBJECT-TYPE
        SYNTAX            INTEGER { disable(0), enable(1)  }
        MAX-ACCESS        read-write
        STATUS            current
        DESCRIPTION
                "CMNT: - 
                 TYPE: - Checkbox
                 PAGE: - WSS Ctrl
                    2016  cmdID= 38734  "
        ::= { iquav10CmdEntry 38734 }


    iquav10WSSCtrlWidescreenOPWSSOutEnable OBJECT-TYPE
        SYNTAX            INTEGER {
                            valOff(0),
                            valWSSAFD(1),
                            valWSSETSI(2)
                            }
        MAX-ACCESS        read-write
        STATUS            current
        DESCRIPTION
                "CMNT: - 
                 TYPE: - RadiobuttonList
                 PAGE: - WSS Ctrl
                    WSS Out Enable  cmdID= 38730
                    Off  value= 0
                    WSS AFD  value= 1
                    WSS ETSI  value= 2  "
        ::= { iquav10CmdEntry 38730 }


    iquav10WSSCtrlWidescreenOPVIOutEnable OBJECT-TYPE
        SYNTAX            INTEGER {
                            valOff(0),
                            valVISMPTE(1),
                            valVIAFD(2),
                            valVIAFD2008(3)
                            }
        MAX-ACCESS        read-write
        STATUS            current
        DESCRIPTION
                "CMNT: - 
                 TYPE: - RadiobuttonList
                 PAGE: - WSS Ctrl
                    VI Out Enable  cmdID= 38733
                    Off  value= 0
                    VI SMPTE  value= 1
                    VI AFD  value= 2
                    VI AFD 2008  value= 3  "
        ::= { iquav10CmdEntry 38733 }


    iquav10WSSCtrlLine1ReadAFD OBJECT-TYPE
        SYNTAX            RollCallString
        MAX-ACCESS        read-only
        STATUS            current
        DESCRIPTION
                "CMNT: - SMTPE2016 Reader Line 1 AFD
                 TYPE: - Display
                 PAGE: - WSS Ctrl
                    Line1 Read AFD  cmdID= 39002  "
        ::= { iquav10CmdEntry 39002 }


    iquav10WSSCtrlLine1ReadAR OBJECT-TYPE
        SYNTAX            RollCallString
        MAX-ACCESS        read-only
        STATUS            current
        DESCRIPTION
                "CMNT: - SMTPE2016 Reader Line 1 AR
                 TYPE: - Display
                 PAGE: - WSS Ctrl
                    Line1 Read AR  cmdID= 39003  "
        ::= { iquav10CmdEntry 39003 }


    iquav10WSSCtrlLine1WriteAFD OBJECT-TYPE
        SYNTAX            RollCallString
        MAX-ACCESS        read-only
        STATUS            current
        DESCRIPTION
                "CMNT: - SMTPE2016 Writer Line 1 AFD
                 TYPE: - Display
                 PAGE: - WSS Ctrl
                    Line1 Write AFD  cmdID= 39010  "
        ::= { iquav10CmdEntry 39010 }


    iquav10WSSCtrlLine1WriteAR OBJECT-TYPE
        SYNTAX            RollCallString
        MAX-ACCESS        read-only
        STATUS            current
        DESCRIPTION
                "CMNT: - SMTPE2016 Writer Line 1 AR
                 TYPE: - Display
                 PAGE: - WSS Ctrl
                    Line1 Write AR  cmdID= 39011  "
        ::= { iquav10CmdEntry 39011 }


    iquav10WSSCtrlPreset OBJECT-TYPE
        SYNTAX            INTEGER { noAction(0),valPreset(1) }
        MAX-ACCESS        read-write
        STATUS            current
        DESCRIPTION
                "CMNT: - 
                 TYPE: - Button
                 PAGE: - WSS Ctrl
                    Preset  cmdID= 39075
                    value= 1  "
        ::= { iquav10CmdEntry 39075 }


    iquav10WSSCtrlPreset43 OBJECT-TYPE
        SYNTAX            INTEGER { noAction(0),valPreset43(1) }
        MAX-ACCESS        read-write
        STATUS            current
        DESCRIPTION
                "CMNT: - 
                 TYPE: - Button
                 PAGE: - WSS Ctrl
                    Preset4:3  cmdID= 39076
                    value= 1  "
        ::= { iquav10CmdEntry 39076 }


    iquav10WSSCtrlPreset169 OBJECT-TYPE
        SYNTAX            INTEGER { noAction(0),valPreset169(1) }
        MAX-ACCESS        read-write
        STATUS            current
        DESCRIPTION
                "CMNT: - 
                 TYPE: - Button
                 PAGE: - WSS Ctrl
                    Preset16:9  cmdID= 39077
                    value= 1  "
        ::= { iquav10CmdEntry 39077 }


    iquav10WSSCtrlNewNumber OBJECT-TYPE
        SYNTAX            INTEGER
        MAX-ACCESS        read-write
        STATUS            current
        DESCRIPTION
                "CMNT: - Force Input AFD store
                 TYPE: - Number
                 PAGE: - WSS Ctrl
                    New Number  cmdID= 43108
                    min= 0  max= 401  step= 1  format= %d  div_scale= 1  preset= 2
                    Min = 0  Max = 0  Step = 0  Preset = 0  "
        ::= { iquav10CmdEntry 43108 }


    iquav10WSSCtrlBlank62523 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank625_23  cmdID= 43228  "
        ::= { iquav10CmdEntry 43228 }


    iquav10WSSCtrlBlank625336 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank625_336  cmdID= 43229  "
        ::= { iquav10CmdEntry 43229 }


    iquav10WSSCtrlBlank52521 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_21  cmdID= 43230  "
        ::= { iquav10CmdEntry 43230 }


    iquav10WSSCtrlBlank52522 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_22  cmdID= 43231  "
        ::= { iquav10CmdEntry 43231 }


    iquav10WSSCtrlBlank525283 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_283  cmdID= 43232  "
        ::= { iquav10CmdEntry 43232 }


    iquav10WSSCtrlBlank525284 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_284  cmdID= 43233  "
        ::= { iquav10CmdEntry 43233 }


    iquav10AncillaryDataSMPTE20162016IPF1Status OBJECT-TYPE
        SYNTAX            RollCallString
        MAX-ACCESS        read-only
        STATUS            current
        DESCRIPTION
                "CMNT: - Ancillary data SMPTE2016 input line field 1
                 TYPE: - Display
                 PAGE: - Ancillary Data
                    2016 I/P F1 Status  cmdID= 42706  "
        ::= { iquav10CmdEntry 42706 }


    iquav10AncillaryDataSMPTE20162016OPF1Line OBJECT-TYPE
        SYNTAX            INTEGER
        MAX-ACCESS        read-write
        STATUS            current
        DESCRIPTION
                "CMNT: - Ancillary data SMPTE2016 output line field 1
                 TYPE: - Number
                 PAGE: - Ancillary Data
                    2016 O/P F1 Line  cmdID= 42707
                    min= 0  max= 63  step= 1  format= Line %0.0f  div_scale= 1  preset= 1
                    Min = Line 0  Max = Line 63  Step = Line 1  Preset = Line 1  "
        ::= { iquav10CmdEntry 42707 }


    iquav10AncillaryDataSMPTE20162016OPF2Line OBJECT-TYPE
        SYNTAX            INTEGER
        MAX-ACCESS        read-write
        STATUS            current
        DESCRIPTION
                "CMNT: - Ancillary data SMPTE2016 output line field 2
                 TYPE: - Number
                 PAGE: - Ancillary Data
                    2016 O/P F2 Line  cmdID= 42746
                    min= 0  max= 31  step= 1  format= Line %0.0f  div_scale= 1  preset= 1
                    Min = Line 0  Max = Line 31  Step = Line 1  Preset = Line 1  "
        ::= { iquav10CmdEntry 42746 }


    iquav10AncillaryDataSMPTE20162016Follow OBJECT-TYPE
        SYNTAX            INTEGER { disable(0), enable(1)  }
        MAX-ACCESS        read-write
        STATUS            current
        DESCRIPTION
                "CMNT: - Ancillary data SMPTE2016 follow input line
                 TYPE: - Checkbox
                 PAGE: - Ancillary Data
                    2016 Follow  cmdID= 42729  "
        ::= { iquav10CmdEntry 42729 }


    iquav10AncillaryDataSDVBILine7 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 7  cmdID= 42708
                    Off  value= 0
                    VI  value= 1
                    WSS  value= 2  "
        ::= { iquav10CmdEntry 42708 }


    iquav10AncillaryDataSDVBILine8 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 8  cmdID= 42709
                    Off  value= 0
                    VI  value= 1
                    WSS  value= 2  "
        ::= { iquav10CmdEntry 42709 }


    iquav10AncillaryDataSDVBILine9 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 9  cmdID= 42710
                    Off  value= 0
                    VI  value= 1
                    WSS  value= 2  "
        ::= { iquav10CmdEntry 42710 }


    iquav10AncillaryDataSDVBILine10 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 10  cmdID= 42711
                    Off  value= 0
                    VI  value= 1
                    WSS  value= 2  "
        ::= { iquav10CmdEntry 42711 }


    iquav10AncillaryDataSDVBILine11 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 11  cmdID= 42712
                    Off  value= 0
                    VI  value= 1
                    WSS  value= 2  "
        ::= { iquav10CmdEntry 42712 }


    iquav10AncillaryDataSDVBILine12 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 12  cmdID= 42713
                    Off  value= 0
                    VI  value= 1
                    WSS  value= 2  "
        ::= { iquav10CmdEntry 42713 }


    iquav10AncillaryDataSDVBILine13 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 13  cmdID= 42714
                    Off  value= 0
                    VI  value= 1
                    WSS  value= 2  "
        ::= { iquav10CmdEntry 42714 }


    iquav10AncillaryDataSDVBILine14 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 14  cmdID= 42715
                    Off  value= 0
                    VI  value= 1
                    WSS  value= 2  "
        ::= { iquav10CmdEntry 42715 }


    iquav10AncillaryDataSDVBILine15 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 15  cmdID= 42716
                    Off  value= 0
                    VI  value= 1
                    WSS  value= 2  "
        ::= { iquav10CmdEntry 42716 }


    iquav10AncillaryDataSDVBILine16 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 16  cmdID= 42717
                    Off  value= 0
                    VI  value= 1
                    WSS  value= 2  "
        ::= { iquav10CmdEntry 42717 }


    iquav10AncillaryDataSDVBILine17 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 17  cmdID= 42718
                    Off  value= 0
                    VI  value= 1
                    WSS  value= 2  "
        ::= { iquav10CmdEntry 42718 }


    iquav10AncillaryDataSDVBILine18 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 18  cmdID= 42719
                    Off  value= 0
                    VI  value= 1
                    WSS  value= 2  "
        ::= { iquav10CmdEntry 42719 }


    iquav10AncillaryDataSDVBILine19 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 19  cmdID= 42720
                    Off  value= 0
                    VI  value= 1
                    WSS  value= 2  "
        ::= { iquav10CmdEntry 42720 }


    iquav10AncillaryDataSDVBILine20 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 20  cmdID= 42721
                    Off  value= 0
                    VI  value= 1
                    WSS  value= 2  "
        ::= { iquav10CmdEntry 42721 }


    iquav10AncillaryDataSDVBILine21 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 21  cmdID= 42722
                    Off  value= 0
                    VI  value= 1
                    WSS  value= 2  "
        ::= { iquav10CmdEntry 42722 }


    iquav10AncillaryDataSDVBILine22 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 22  cmdID= 42723
                    Off  value= 0
                    VI  value= 1
                    WSS  value= 2  "
        ::= { iquav10CmdEntry 42723 }


    iquav10AncillaryDataSDVBILine23 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 23  cmdID= 42724
                    Off  value= 0
                    VI  value= 1
                    WSS  value= 2  "
        ::= { iquav10CmdEntry 42724 }


    iquav10AncillaryDataSDVBIVIIPStatus OBJECT-TYPE
        SYNTAX            INTEGER { disable(0), enable(1)  }
        MAX-ACCESS        read-write
        STATUS            current
        DESCRIPTION
                "CMNT: - Ancillary data video index present
                 TYPE: - Checkbox
                 PAGE: - Ancillary Data
                    VI I/P Status  cmdID= 42744  "
        ::= { iquav10CmdEntry 42744 }


    iquav10AncillaryDataSDVBIWSSIPStatus OBJECT-TYPE
        SYNTAX            INTEGER { disable(0), enable(1)  }
        MAX-ACCESS        read-write
        STATUS            current
        DESCRIPTION
                "CMNT: - Ancillary data wide screen signalling present
                 TYPE: - Checkbox
                 PAGE: - Ancillary Data
                    WSS I/P Status  cmdID= 42740  "
        ::= { iquav10CmdEntry 42740 }


    iquav10AncillaryDataSDVBIVITCIPStatus OBJECT-TYPE
        SYNTAX            INTEGER { disable(0), enable(1)  }
        MAX-ACCESS        read-write
        STATUS            current
        DESCRIPTION
                "CMNT: - Ancillary data vertical interval time code present
                 TYPE: - Checkbox
                 PAGE: - Ancillary Data
                    VITC I/P Status  cmdID= 42742  "
        ::= { iquav10CmdEntry 42742 }


    iquav10AncillaryDataSDVBIWSTIPStatus OBJECT-TYPE
        SYNTAX            INTEGER { disable(0), enable(1)  }
        MAX-ACCESS        read-write
        STATUS            current
        DESCRIPTION
                "CMNT: - Ancillary data world system teletext present
                 TYPE: - Checkbox
                 PAGE: - Ancillary Data
                    WST I/P Status  cmdID= 42741  "
        ::= { iquav10CmdEntry 42741 }


    iquav10AncillaryDataSDVBICC608IPStatus OBJECT-TYPE
        SYNTAX            INTEGER { disable(0), enable(1)  }
        MAX-ACCESS        read-write
        STATUS            current
        DESCRIPTION
                "CMNT: - Ancillary data closed caption CC608 present
                 TYPE: - Checkbox
                 PAGE: - Ancillary Data
                    CC608 I/P Status  cmdID= 42743  "
        ::= { iquav10CmdEntry 42743 }


    iquav10AncillaryDataHDVANCATCEnable OBJECT-TYPE
        SYNTAX            INTEGER { disable(0), enable(1)  }
        MAX-ACCESS        read-write
        STATUS            current
        DESCRIPTION
                "CMNT: - Ancillary time code enable output
                 TYPE: - Checkbox
                 PAGE: - Ancillary Data
                    ATC Enable  cmdID= 42702  "
        ::= { iquav10CmdEntry 42702 }


    iquav10AncillaryDataHDVANCATCIPF1Line OBJECT-TYPE
        SYNTAX            RollCallString
        MAX-ACCESS        read-only
        STATUS            current
        DESCRIPTION
                "CMNT: - Ancillary time code input line field 1
                 TYPE: - Display
                 PAGE: - Ancillary Data
                    ATC I/P F1 Line  cmdID= 42705  "
        ::= { iquav10CmdEntry 42705 }


    iquav10AncillaryDataHDVANCATCOPF1Line OBJECT-TYPE
        SYNTAX            INTEGER
        MAX-ACCESS        read-write
        STATUS            current
        DESCRIPTION
                "CMNT: - Ancillary time code output line field 1
                 TYPE: - Number
                 PAGE: - Ancillary Data
                    ATC O/P F1 Line  cmdID= 42703
                    min= 0  max= 63  step= 1  format= Line %0.0f  div_scale= 1  preset= 2
                    Min = Line 0  Max = Line 63  Step = Line 1  Preset = Line 2  "
        ::= { iquav10CmdEntry 42703 }


    iquav10AncillaryDataHDVANCATCOPF2Line OBJECT-TYPE
        SYNTAX            INTEGER
        MAX-ACCESS        read-write
        STATUS            current
        DESCRIPTION
                "CMNT: - Ancillary time code output line field 2
                 TYPE: - Number
                 PAGE: - Ancillary Data
                    ATC O/P F2 Line  cmdID= 42748
                    min= 0  max= 31  step= 1  format= Line %0.0f  div_scale= 1  preset= 2
                    Min = Line 0  Max = Line 31  Step = Line 1  Preset = Line 2  "
        ::= { iquav10CmdEntry 42748 }


    iquav10AncillaryDataHDVANCATCFollow OBJECT-TYPE
        SYNTAX            INTEGER { disable(0), enable(1)  }
        MAX-ACCESS        read-write
        STATUS            current
        DESCRIPTION
                "CMNT: - Ancillary time code follow input line
                 TYPE: - Checkbox
                 PAGE: - Ancillary Data
                    ATC Follow  cmdID= 42704  "
        ::= { iquav10CmdEntry 42704 }


    iquav10AncillaryDataHDVANCHDCaptionEnable OBJECT-TYPE
        SYNTAX            INTEGER { disable(0), enable(1)  }
        MAX-ACCESS        read-write
        STATUS            current
        DESCRIPTION
                "CMNT: - Ancillary data closed caption CC708 enable output
                 TYPE: - Checkbox
                 PAGE: - Ancillary Data
                    HD Caption Enable  cmdID= 42701  "
        ::= { iquav10CmdEntry 42701 }


    iquav10AncillaryDataHDVANCHDCaptionIPLine OBJECT-TYPE
        SYNTAX            RollCallString
        MAX-ACCESS        read-only
        STATUS            current
        DESCRIPTION
                "CMNT: - Ancillary data closed caption CC708 input line
                 TYPE: - Display
                 PAGE: - Ancillary Data
                    HD Caption I/P Line  cmdID= 42726  "
        ::= { iquav10CmdEntry 42726 }


    iquav10AncillaryDataHDVANCHDCaptionOPLine OBJECT-TYPE
        SYNTAX            INTEGER
        MAX-ACCESS        read-write
        STATUS            current
        DESCRIPTION
                "CMNT: - Ancillary data closed caption CC708 output line
                 TYPE: - Number
                 PAGE: - Ancillary Data
                    HD Caption O/P Line  cmdID= 42725
                    min= 0  max= 63  step= 1  format= Line %0.0f  div_scale= 1  preset= 3
                    Min = Line 0  Max = Line 63  Step = Line 1  Preset = Line 3  "
        ::= { iquav10CmdEntry 42725 }


    iquav10HDVANCHDCaptionHDFollowIPLine OBJECT-TYPE
        SYNTAX            INTEGER { disable(0), enable(1)  }
        MAX-ACCESS        read-write
        STATUS            current
        DESCRIPTION
                "CMNT: - Ancillary data closed caption CC708 follow input
                 TYPE: - Checkbox
                 PAGE: - HD VANC
                    HD Follow I/P Line  cmdID= 42700  "
        ::= { iquav10CmdEntry 42700 }


    iquav10AudioInputDisembed18Disembed11procamp OBJECT-TYPE
        SYNTAX            INTEGER
        MAX-ACCESS        read-write
        STATUS            current
        DESCRIPTION
                "CMNT: - Disembed Proc Amp Gain
                 TYPE: - Number
                 PAGE: - AudioInput
                    Disembed1_1_procamp  cmdID= 40000
                    min= -801  max= 120  step= 1  format= %0.1f dB  div_scale= 10  preset= 0
                    Min = -80.1 dB  Max = 12.0 dB  Step = 0.1 dB  Preset = 0.0 dB  "
        ::= { iquav10CmdEntry 40000 }


    iquav10AudioInputDisembed18Disembed12procamp OBJECT-TYPE
        SYNTAX            INTEGER
        MAX-ACCESS        read-write
        STATUS            current
        DESCRIPTION
                "CMNT: - Disembed Proc Amp Gain
                 TYPE: - Number
                 PAGE: - AudioInput
                    Disembed1_2_procamp  cmdID= 40001
                    min= -801  max= 120  step= 1  format= %0.1f dB  div_scale= 10  preset= 0
                    Min = -80.1 dB  Max = 12.0 dB  Step = 0.1 dB  Preset = 0.0 dB  "
        ::= { iquav10CmdEntry 40001 }


    iquav10Disembed18Disembed1Mute11 OBJECT-TYPE
        SYNTAX            INTEGER { disable(0), enable(1)  }
        MAX-ACCESS        read-write
        STATUS            current
        DESCRIPTION
                "CMNT: - 
                 TYPE: - Checkbox
                 PAGE: - Disembed1-8
                    Mute1_1  cmdID= 40032  "
        ::= { iquav10CmdEntry 40032 }


    iquav10Disembed18Disembed1Mute12 OBJECT-TYPE
        SYNTAX            INTEGER { disable(0), enable(1)  }
        MAX-ACCESS        read-write
        STATUS            current
        DESCRIPTION
                "CMNT: - 
                 TYPE: - Checkbox
                 PAGE: - Disembed1-8
                    Mute1_2  cmdID= 40033  "
        ::= { iquav10CmdEntry 40033 }


    iquav10Disembed18Disembed1Stereo1 OBJECT-TYPE
        SYNTAX            INTEGER { disable(0), enable(1)  }
        MAX-ACCESS        read-write
        STATUS            current
        DESCRIPTION
                "CMNT: - 
                 TYPE: - Checkbox
                 PAGE: - Disembed1-8
                    Stereo1  cmdID= 40048  "
        ::= { iquav10CmdEntry 40048 }


    iquav10AudioInputDisembed18Disembed11invert OBJECT-TYPE
        SYNTAX            INTEGER { disable(0), enable(1)  }
        MAX-ACCESS        read-write
        STATUS            current
        DESCRIPTION
                "CMNT: - 
                 TYPE: - Checkbox
                 PAGE: - AudioInput
                    Disembed1_1_invert  cmdID= 40016  "
        ::= { iquav10CmdEntry 40016 }


    iquav10AudioInputDisembed18Disembed12invert OBJECT-TYPE
        SYNTAX            INTEGER { disable(0), enable(1)  }
        MAX-ACCESS        read-write
        STATUS            current
        DESCRIPTION
                "CMNT: - 
                 TYPE: - Checkbox
                 PAGE: - AudioInput
                    Disembed1_2_invert  cmdID= 40017  "
        ::= { iquav10CmdEntry 40017 }


    iquav10Disembed18Disembed1dolbyLine OBJECT-TYPE
        SYNTAX            RollCallString
        MAX-ACCESS        read-only
        STATUS            current
        DESCRIPTION
                "CMNT: - 
                 TYPE: - Display
                 PAGE: - Disembed1-8
                    dolbyLine  cmdID= 40073  "
        ::= { iquav10CmdEntry 40073 }


    iquav10AudioInputDisembed18Disembed21procamp OBJECT-TYPE
        SYNTAX            INTEGER
        MAX-ACCESS        read-write
        STATUS            current
        DESCRIPTION
                "CMNT: - Disembed Proc Amp Gain
                 TYPE: - Number
                 PAGE: - AudioInput
                    Disembed2_1_procamp  cmdID= 40002
                    min= -801  max= 120  step= 1  format= %0.1f dB  div_scale= 10  preset= 0
                    Min = -80.1 dB  Max = 12.0 dB  Step = 0.1 dB  Preset = 0.0 dB  "
        ::= { iquav10CmdEntry 40002 }


    iquav10AudioInputDisembed18Disembed22procamp OBJECT-TYPE
        SYNTAX            INTEGER
        MAX-ACCESS        read-write
        STATUS            current
        DESCRIPTION
                "CMNT: - Disembed Proc Amp Gain
                 TYPE: - Number
                 PAGE: - AudioInput
                    Disembed2_2_procamp  cmdID= 40003
                    min= -801  max= 120  step= 1  format= %0.1f dB  div_scale= 10  preset= 0
                    Min = -80.1 dB  Max = 12.0 dB  Step = 0.1 dB  Preset = 0.0 dB  "
        ::= { iquav10CmdEntry 40003 }


    iquav10Disembed18Disembed2Mute21 OBJECT-TYPE
        SYNTAX            INTEGER { disable(0), enable(1)  }
        MAX-ACCESS        read-write
        STATUS            current
        DESCRIPTION
                "CMNT: - 
                 TYPE: - Checkbox
                 PAGE: - Disembed1-8
                    Mute2_1  cmdID= 40034  "
        ::= { iquav10CmdEntry 40034 }


    iquav10Disembed18Disembed2Mute22 OBJECT-TYPE
        SYNTAX            INTEGER { disable(0), enable(1)  }
        MAX-ACCESS        read-write
        STATUS            current
        DESCRIPTION
                "CMNT: - 
                 TYPE: - Checkbox
                 PAGE: - Disembed1-8
                    Mute2_2  cmdID= 40035  "
        ::= { iquav10CmdEntry 40035 }


    iquav10Disembed18Disembed2Stereo2 OBJECT-TYPE
        SYNTAX            INTEGER { disable(0), enable(1)  }
        MAX-ACCESS        read-write
        STATUS            current
        DESCRIPTION
                "CMNT: - 
                 TYPE: - Checkbox
                 PAGE: - Disembed1-8
                    Stereo2  cmdID= 40049  "
        ::= { iquav10CmdEntry 40049 }


    iquav10AudioInputDisembed18Disembed21invert OBJECT-TYPE
        SYNTAX            INTEGER { disable(0), enable(1)  }
        MAX-ACCESS        read-write
        STATUS            current
        DESCRIPTION
                "CMNT: - 
                 TYPE: - Checkbox
                 PAGE: - AudioInput
                    Disembed2_1_invert  cmdID= 40018  "
        ::= { iquav10CmdEntry 40018 }


    iquav10AudioInputDisembed18Disembed22invert OBJECT-TYPE
        SYNTAX            INTEGER { disable(0), enable(1)  }
        MAX-ACCESS        read-write
        STATUS            current
        DESCRIPTION
                "CMNT: - 
                 TYPE: - Checkbox
                 PAGE: - AudioInput
                    Disembed2_2_invert  cmdID= 40019  "
        ::= { iquav10CmdEntry 40019 }


    iquav10Disembed18Disembed2dolbyLine OBJECT-TYPE
        SYNTAX            RollCallString
        MAX-ACCESS        read-only
        STATUS            current
        DESCRIPTION
                "CMNT: - 
                 TYPE: - Display
                 PAGE: - Disembed1-8
                    dolbyLine  cmdID= 40074  "
        ::= { iquav10CmdEntry 40074 }


    iquav10AudioInputDisembed18Disembed31procamp OBJECT-TYPE
        SYNTAX            INTEGER
        MAX-ACCESS        read-write
        STATUS            current
        DESCRIPTION
                "CMNT: - Disembed Proc Amp Gain
                 TYPE: - Number
                 PAGE: - AudioInput
                    Disembed3_1_procamp  cmdID= 40004
                    min= -801  max= 120  step= 1  format= %0.1f dB  div_scale= 10  preset= 0
                    Min = -80.1 dB  Max = 12.0 dB  Step = 0.1 dB  Preset = 0.0 dB  "
        ::= { iquav10CmdEntry 40004 }


    iquav10AudioInputDisembed18Disembed32procamp OBJECT-TYPE
        SYNTAX            INTEGER
        MAX-ACCESS        read-write
        STATUS            current
        DESCRIPTION
                "CMNT: - Disembed Proc Amp Gain
                 TYPE: - Number
                 PAGE: - AudioInput
                    Disembed3_2_procamp  cmdID= 40005
                    min= -801  max= 120  step= 1  format= %0.1f dB  div_scale= 10  preset= 0
                    Min = -80.1 dB  Max = 12.0 dB  Step = 0.1 dB  Preset = 0.0 dB  "
        ::= { iquav10CmdEntry 40005 }


    iquav10Disembed18Disembed3Mute31 OBJECT-TYPE
        SYNTAX            INTEGER { disable(0), enable(1)  }
        MAX-ACCESS        read-write
        STATUS            current
        DESCRIPTION
                "CMNT: - 
                 TYPE: - Checkbox
                 PAGE: - Disembed1-8
                    Mute3_1  cmdID= 40036  "
        ::= { iquav10CmdEntry 40036 }


    iquav10Disembed18Disembed3Mute32 OBJECT-TYPE
        SYNTAX            INTEGER { disable(0), enable(1)  }
        MAX-ACCESS        read-write
        STATUS            current
        DESCRIPTION
                "CMNT: - 
                 TYPE: - Checkbox
                 PAGE: - Disembed1-8
                    Mute3_2  cmdID= 40037  "
        ::= { iquav10CmdEntry 40037 }


    iquav10Disembed18Disembed3Stereo3 OBJECT-TYPE
        SYNTAX            INTEGER { disable(0), enable(1)  }
        MAX-ACCESS        read-write
        STATUS            current
        DESCRIPTION
                "CMNT: - 
                 TYPE: - Checkbox
                 PAGE: - Disembed1-8
                    Stereo3  cmdID= 40050  "
        ::= { iquav10CmdEntry 40050 }


    iquav10AudioInputDisembed18Disembed31invert OBJECT-TYPE
        SYNTAX            INTEGER { disable(0), enable(1)  }
        MAX-ACCESS        read-write
        STATUS            current
        DESCRIPTION
                "CMNT: - 
                 TYPE: - Checkbox
                 PAGE: - AudioInput
                    Disembed3_1_invert  cmdID= 40020  "
        ::= { iquav10CmdEntry 40020 }


    iquav10AudioInputDisembed18Disembed32invert OBJECT-TYPE
        SYNTAX            INTEGER { disable(0), enable(1)  }
        MAX-ACCESS        read-write
        STATUS            current
        DESCRIPTION
                "CMNT: - 
                 TYPE: - Checkbox
                 PAGE: - AudioInput
                    Disembed3_2_invert  cmdID= 40021  "
        ::= { iquav10CmdEntry 40021 }


    iquav10Disembed18Disembed3dolbyLine OBJECT-TYPE
        SYNTAX            RollCallString
        MAX-ACCESS        read-only
        STATUS            current
        DESCRIPTION
                "CMNT: - 
                 TYPE: - Display
                 PAGE: - Disembed1-8
                    dolbyLine  cmdID= 40075  "
        ::= { iquav10CmdEntry 40075 }


    iquav10AudioInputDisembed18Disembed41procamp OBJECT-TYPE
        SYNTAX            INTEGER
        MAX-ACCESS        read-write
        STATUS            current
        DESCRIPTION
                "CMNT: - Disembed Proc Amp Gain
                 TYPE: - Number
                 PAGE: - AudioInput
                    Disembed4_1_procamp  cmdID= 40006
                    min= -801  max= 120  step= 1  format= %0.1f dB  div_scale= 10  preset= 0
                    Min = -80.1 dB  Max = 12.0 dB  Step = 0.1 dB  Preset = 0.0 dB  "
        ::= { iquav10CmdEntry 40006 }


    iquav10AudioInputDisembed18Disembed42procamp OBJECT-TYPE
        SYNTAX            INTEGER
        MAX-ACCESS        read-write
        STATUS            current
        DESCRIPTION
                "CMNT: - Disembed Proc Amp Gain
                 TYPE: - Number
                 PAGE: - AudioInput
                    Disembed4_2_procamp  cmdID= 40007
                    min= -801  max= 120  step= 1  format= %0.1f dB  div_scale= 10  preset= 0
                    Min = -80.1 dB  Max = 12.0 dB  Step = 0.1 dB  Preset = 0.0 dB  "
        ::= { iquav10CmdEntry 40007 }


    iquav10Disembed18Disembed4Mute41 OBJECT-TYPE
        SYNTAX            INTEGER { disable(0), enable(1)  }
        MAX-ACCESS        read-write
        STATUS            current
        DESCRIPTION
                "CMNT: - 
                 TYPE: - Checkbox
                 PAGE: - Disembed1-8
                    Mute4_1  cmdID= 40038  "
        ::= { iquav10CmdEntry 40038 }


    iquav10Disembed18Disembed4Mute42 OBJECT-TYPE
        SYNTAX            INTEGER { disable(0), enable(1)  }
        MAX-ACCESS        read-write
        STATUS            current
        DESCRIPTION
                "CMNT: - 
                 TYPE: - Checkbox
                 PAGE: - Disembed1-8
                    Mute4_2  cmdID= 40039  "
        ::= { iquav10CmdEntry 40039 }


    iquav10Disembed18Disembed4Stereo4 OBJECT-TYPE
        SYNTAX            INTEGER { disable(0), enable(1)  }
        MAX-ACCESS        read-write
        STATUS            current
        DESCRIPTION
                "CMNT: - 
                 TYPE: - Checkbox
                 PAGE: - Disembed1-8
                    Stereo4  cmdID= 40051  "
        ::= { iquav10CmdEntry 40051 }


    iquav10AudioInputDisembed18Disembed41invert OBJECT-TYPE
        SYNTAX            INTEGER { disable(0), enable(1)  }
        MAX-ACCESS        read-write
        STATUS            current
        DESCRIPTION
                "CMNT: - 
                 TYPE: - Checkbox
                 PAGE: - AudioInput
                    Disembed4_1_invert  cmdID= 40022  "
        ::= { iquav10CmdEntry 40022 }


    iquav10AudioInputDisembed18Disembed42invert OBJECT-TYPE
        SYNTAX            INTEGER { disable(0), enable(1)  }
        MAX-ACCESS        read-write
        STATUS            current
        DESCRIPTION
                "CMNT: - 
                 TYPE: - Checkbox
                 PAGE: - AudioInput
                    Disembed4_2_invert  cmdID= 40023  "
        ::= { iquav10CmdEntry 40023 }


    iquav10Disembed18Disembed4dolbyLine OBJECT-TYPE
        SYNTAX            RollCallString
        MAX-ACCESS        read-only
        STATUS            current
        DESCRIPTION
                "CMNT: - 
                 TYPE: - Display
                 PAGE: - Disembed1-8
                    dolbyLine  cmdID= 40076  "
        ::= { iquav10CmdEntry 40076 }


    iquav10AudioInputDisembed18Disembed51procamp OBJECT-TYPE
        SYNTAX            INTEGER
        MAX-ACCESS        read-write
        STATUS            current
        DESCRIPTION
                "CMNT: - Disembed Proc Amp Gain
                 TYPE: - Number
                 PAGE: - AudioInput
                    Disembed5_1_procamp  cmdID= 40008
                    min= -801  max= 120  step= 1  format= %0.1f dB  div_scale= 10  preset= 0
                    Min = -80.1 dB  Max = 12.0 dB  Step = 0.1 dB  Preset = 0.0 dB  "
        ::= { iquav10CmdEntry 40008 }


    iquav10AudioInputDisembed18Disembed52procamp OBJECT-TYPE
        SYNTAX            INTEGER
        MAX-ACCESS        read-write
        STATUS            current
        DESCRIPTION
                "CMNT: - Disembed Proc Amp Gain
                 TYPE: - Number
                 PAGE: - AudioInput
                    Disembed5_2_procamp  cmdID= 40009
                    min= -801  max= 120  step= 1  format= %0.1f dB  div_scale= 10  preset= 0
                    Min = -80.1 dB  Max = 12.0 dB  Step = 0.1 dB  Preset = 0.0 dB  "
        ::= { iquav10CmdEntry 40009 }


    iquav10Disembed18Disembed5Mute51 OBJECT-TYPE
        SYNTAX            INTEGER { disable(0), enable(1)  }
        MAX-ACCESS        read-write
        STATUS            current
        DESCRIPTION
                "CMNT: - 
                 TYPE: - Checkbox
                 PAGE: - Disembed1-8
                    Mute5_1  cmdID= 40040  "
        ::= { iquav10CmdEntry 40040 }


    iquav10Disembed18Disembed5Mute52 OBJECT-TYPE
        SYNTAX            INTEGER { disable(0), enable(1)  }
        MAX-ACCESS        read-write
        STATUS            current
        DESCRIPTION
                "CMNT: - 
                 TYPE: - Checkbox
                 PAGE: - Disembed1-8
                    Mute5_2  cmdID= 40041  "
        ::= { iquav10CmdEntry 40041 }


    iquav10Disembed18Disembed5Stereo5 OBJECT-TYPE
        SYNTAX            INTEGER { disable(0), enable(1)  }
        MAX-ACCESS        read-write
        STATUS            current
        DESCRIPTION
                "CMNT: - 
                 TYPE: - Checkbox
                 PAGE: - Disembed1-8
                    Stereo5  cmdID= 40052  "
        ::= { iquav10CmdEntry 40052 }


    iquav10AudioInputDisembed18Disembed51invert OBJECT-TYPE
        SYNTAX            INTEGER { disable(0), enable(1)  }
        MAX-ACCESS        read-write
        STATUS            current
        DESCRIPTION
                "CMNT: - 
                 TYPE: - Checkbox
                 PAGE: - AudioInput
                    Disembed5_1_invert  cmdID= 40024  "
        ::= { iquav10CmdEntry 40024 }


    iquav10AudioInputDisembed18Disembed52invert OBJECT-TYPE
        SYNTAX            INTEGER { disable(0), enable(1)  }
        MAX-ACCESS        read-write
        STATUS            current
        DESCRIPTION
                "CMNT: - 
                 TYPE: - Checkbox
                 PAGE: - AudioInput
                    Disembed5_2_invert  cmdID= 40025  "
        ::= { iquav10CmdEntry 40025 }


    iquav10Disembed18Disembed5dolbyLine OBJECT-TYPE
        SYNTAX            RollCallString
        MAX-ACCESS        read-only
        STATUS            current
        DESCRIPTION
                "CMNT: - 
                 TYPE: - Display
                 PAGE: - Disembed1-8
                    dolbyLine  cmdID= 40077  "
        ::= { iquav10CmdEntry 40077 }


    iquav10AudioInputDisembed18Disembed61procamp OBJECT-TYPE
        SYNTAX            INTEGER
        MAX-ACCESS        read-write
        STATUS            current
        DESCRIPTION
                "CMNT: - Disembed Proc Amp Gain
                 TYPE: - Number
                 PAGE: - AudioInput
                    Disembed6_1_procamp  cmdID= 40010
                    min= -801  max= 120  step= 1  format= %0.1f dB  div_scale= 10  preset= 0
                    Min = -80.1 dB  Max = 12.0 dB  Step = 0.1 dB  Preset = 0.0 dB  "
        ::= { iquav10CmdEntry 40010 }


    iquav10AudioInputDisembed18Disembed62procamp OBJECT-TYPE
        SYNTAX            INTEGER
        MAX-ACCESS        read-write
        STATUS            current
        DESCRIPTION
                "CMNT: - Disembed Proc Amp Gain
                 TYPE: - Number
                 PAGE: - AudioInput
                    Disembed6_2_procamp  cmdID= 40011
                    min= -801  max= 120  step= 1  format= %0.1f dB  div_scale= 10  preset= 0
                    Min = -80.1 dB  Max = 12.0 dB  Step = 0.1 dB  Preset = 0.0 dB  "
        ::= { iquav10CmdEntry 40011 }


    iquav10Disembed18Disembed6Mute61 OBJECT-TYPE
        SYNTAX            INTEGER { disable(0), enable(1)  }
        MAX-ACCESS        read-write
        STATUS            current
        DESCRIPTION
                "CMNT: - 
                 TYPE: - Checkbox
                 PAGE: - Disembed1-8
                    Mute6_1  cmdID= 40042  "
        ::= { iquav10CmdEntry 40042 }


    iquav10Disembed18Disembed6Mute62 OBJECT-TYPE
        SYNTAX            INTEGER { disable(0), enable(1)  }
        MAX-ACCESS        read-write
        STATUS            current
        DESCRIPTION
                "CMNT: - 
                 TYPE: - Checkbox
                 PAGE: - Disembed1-8
                    Mute6_2  cmdID= 40043  "
        ::= { iquav10CmdEntry 40043 }


    iquav10Disembed18Disembed6Stereo6 OBJECT-TYPE
        SYNTAX            INTEGER { disable(0), enable(1)  }
        MAX-ACCESS        read-write
        STATUS            current
        DESCRIPTION
                "CMNT: - 
                 TYPE: - Checkbox
                 PAGE: - Disembed1-8
                    Stereo6  cmdID= 40053  "
        ::= { iquav10CmdEntry 40053 }


    iquav10AudioInputDisembed18Disembed61invert OBJECT-TYPE
        SYNTAX            INTEGER { disable(0), enable(1)  }
        MAX-ACCESS        read-write
        STATUS            current
        DESCRIPTION
                "CMNT: - 
                 TYPE: - Checkbox
                 PAGE: - AudioInput
                    Disembed6_1_invert  cmdID= 40026  "
        ::= { iquav10CmdEntry 40026 }


    iquav10AudioInputDisembed18Disembed62invert OBJECT-TYPE
        SYNTAX            INTEGER { disable(0), enable(1)  }
        MAX-ACCESS        read-write
        STATUS            current
        DESCRIPTION
                "CMNT: - 
                 TYPE: - Checkbox
                 PAGE: - AudioInput
                    Disembed6_2_invert  cmdID= 40027  "
        ::= { iquav10CmdEntry 40027 }


    iquav10Disembed18Disembed6dolbyLine OBJECT-TYPE
        SYNTAX            RollCallString
        MAX-ACCESS        read-only
        STATUS            current
        DESCRIPTION
                "CMNT: - 
                 TYPE: - Display
                 PAGE: - Disembed1-8
                    dolbyLine  cmdID= 40078  "
        ::= { iquav10CmdEntry 40078 }


    iquav10AudioInputDisembed18Disembed71procamp OBJECT-TYPE
        SYNTAX            INTEGER
        MAX-ACCESS        read-write
        STATUS            current
        DESCRIPTION
                "CMNT: - Disembed Proc Amp Gain
                 TYPE: - Number
                 PAGE: - AudioInput
                    Disembed7_1_procamp  cmdID= 40012
                    min= -801  max= 120  step= 1  format= %0.1f dB  div_scale= 10  preset= 0
                    Min = -80.1 dB  Max = 12.0 dB  Step = 0.1 dB  Preset = 0.0 dB  "
        ::= { iquav10CmdEntry 40012 }


    iquav10AudioInputDisembed18Disembed72procamp OBJECT-TYPE
        SYNTAX            INTEGER
        MAX-ACCESS        read-write
        STATUS            current
        DESCRIPTION
                "CMNT: - Disembed Proc Amp Gain
                 TYPE: - Number
                 PAGE: - AudioInput
                    Disembed7_2_procamp  cmdID= 40013
                    min= -801  max= 120  step= 1  format= %0.1f dB  div_scale= 10  preset= 0
                    Min = -80.1 dB  Max = 12.0 dB  Step = 0.1 dB  Preset = 0.0 dB  "
        ::= { iquav10CmdEntry 40013 }


    iquav10Disembed18Disembed7Mute71 OBJECT-TYPE
        SYNTAX            INTEGER { disable(0), enable(1)  }
        MAX-ACCESS        read-write
        STATUS            current
        DESCRIPTION
                "CMNT: - 
                 TYPE: - Checkbox
                 PAGE: - Disembed1-8
                    Mute7_1  cmdID= 40044  "
        ::= { iquav10CmdEntry 40044 }


    iquav10Disembed18Disembed7Mute72 OBJECT-TYPE
        SYNTAX            INTEGER { disable(0), enable(1)  }
        MAX-ACCESS        read-write
        STATUS            current
        DESCRIPTION
                "CMNT: - 
                 TYPE: - Checkbox
                 PAGE: - Disembed1-8
                    Mute7_2  cmdID= 40045  "
        ::= { iquav10CmdEntry 40045 }


    iquav10Disembed18Disembed7Stereo7 OBJECT-TYPE
        SYNTAX            INTEGER { disable(0), enable(1)  }
        MAX-ACCESS        read-write
        STATUS            current
        DESCRIPTION
                "CMNT: - 
                 TYPE: - Checkbox
                 PAGE: - Disembed1-8
                    Stereo7  cmdID= 40054  "
        ::= { iquav10CmdEntry 40054 }


    iquav10AudioInputDisembed18Disembed71invert OBJECT-TYPE
        SYNTAX            INTEGER { disable(0), enable(1)  }
        MAX-ACCESS        read-write
        STATUS            current
        DESCRIPTION
                "CMNT: - 
                 TYPE: - Checkbox
                 PAGE: - AudioInput
                    Disembed7_1_invert  cmdID= 40028  "
        ::= { iquav10CmdEntry 40028 }


    iquav10AudioInputDisembed18Disembed72invert OBJECT-TYPE
        SYNTAX            INTEGER { disable(0), enable(1)  }
        MAX-ACCESS        read-write
        STATUS            current
        DESCRIPTION
                "CMNT: - 
                 TYPE: - Checkbox
                 PAGE: - AudioInput
                    Disembed7_2_invert  cmdID= 40029  "
        ::= { iquav10CmdEntry 40029 }


    iquav10Disembed18Disembed7dolbyLine OBJECT-TYPE
        SYNTAX            RollCallString
        MAX-ACCESS        read-only
        STATUS            current
        DESCRIPTION
                "CMNT: - 
                 TYPE: - Display
                 PAGE: - Disembed1-8
                    dolbyLine  cmdID= 40079  "
        ::= { iquav10CmdEntry 40079 }


    iquav10AudioInputDisembed18Disembed81procamp OBJECT-TYPE
        SYNTAX            INTEGER
        MAX-ACCESS        read-write
        STATUS            current
        DESCRIPTION
                "CMNT: - Disembed Proc Amp Gain
                 TYPE: - Number
                 PAGE: - AudioInput
                    Disembed8_1_procamp  cmdID= 40014
                    min= -801  max= 120  step= 1  format= %0.1f dB  div_scale= 10  preset= 0
                    Min = -80.1 dB  Max = 12.0 dB  Step = 0.1 dB  Preset = 0.0 dB  "
        ::= { iquav10CmdEntry 40014 }


    iquav10AudioInputDisembed18Disembed82procamp OBJECT-TYPE
        SYNTAX            INTEGER
        MAX-ACCESS        read-write
        STATUS            current
        DESCRIPTION
                "CMNT: - Disembed Proc Amp Gain
                 TYPE: - Number
                 PAGE: - AudioInput
                    Disembed8_2_procamp  cmdID= 40015
                    min= -801  max= 120  step= 1  format= %0.1f dB  div_scale= 10  preset= 0
                    Min = -80.1 dB  Max = 12.0 dB  Step = 0.1 dB  Preset = 0.0 dB  "
        ::= { iquav10CmdEntry 40015 }


    iquav10Disembed18Disembed8Mute81 OBJECT-TYPE
        SYNTAX            INTEGER { disable(0), enable(1)  }
        MAX-ACCESS        read-write
        STATUS            current
        DESCRIPTION
                "CMNT: - 
                 TYPE: - Checkbox
                 PAGE: - Disembed1-8
                    Mute8_1  cmdID= 40046  "
        ::= { iquav10CmdEntry 40046 }


    iquav10Disembed18Disembed8Mute82 OBJECT-TYPE
        SYNTAX            INTEGER { disable(0), enable(1)  }
        MAX-ACCESS        read-write
        STATUS            current
        DESCRIPTION
                "CMNT: - 
                 TYPE: - Checkbox
                 PAGE: - Disembed1-8
                    Mute8_2  cmdID= 40047  "
        ::= { iquav10CmdEntry 40047 }


    iquav10Disembed18Disembed8Stereo8 OBJECT-TYPE
        SYNTAX            INTEGER { disable(0), enable(1)  }
        MAX-ACCESS        read-write
        STATUS            current
        DESCRIPTION
                "CMNT: - 
                 TYPE: - Checkbox
                 PAGE: - Disembed1-8
                    Stereo8  cmdID= 40055  "
        ::= { iquav10CmdEntry 40055 }


    iquav10AudioInputDisembed18Disembed81invert OBJECT-TYPE
        SYNTAX            INTEGER { disable(0), enable(1)  }
        MAX-ACCESS        read-write
        STATUS            current
        DESCRIPTION
                "CMNT: - 
                 TYPE: - Checkbox
                 PAGE: - AudioInput
                    Disembed8_1_invert  cmdID= 40030  "
        ::= { iquav10CmdEntry 40030 }


    iquav10AudioInputDisembed18Disembed82invert OBJECT-TYPE
        SYNTAX            INTEGER { disable(0), enable(1)  }
        MAX-ACCESS        read-write
        STATUS            current
        DESCRIPTION
                "CMNT: - 
                 TYPE: - Checkbox
                 PAGE: - AudioInput
                    Disembed8_2_invert  cmdID= 40031  "
        ::= { iquav10CmdEntry 40031 }


    iquav10Disembed18Disembed8dolbyLine OBJECT-TYPE
        SYNTAX            RollCallString
        MAX-ACCESS        read-only
        STATUS            current
        DESCRIPTION
                "CMNT: - 
                 TYPE: - Display
                 PAGE: - Disembed1-8
                    dolbyLine  cmdID= 40080  "
        ::= { iquav10CmdEntry 40080 }


    iquav10AudioInputDisembed18ProcampSaveset OBJECT-TYPE
        SYNTAX            INTEGER
        MAX-ACCESS        read-write
        STATUS            current
        DESCRIPTION
                "CMNT: - Used to correctly restore stereo procamp and mute values.
                 TYPE: - Number
                 PAGE: - AudioInput
                    ProcampSaveset  cmdID= 40072
                    min= 0  max= 1  step= 1  format= %0.0f  div_scale= 1  preset= 0
                    Min = 0  Max = 1  Step = 1  Preset = 0  "
        ::= { iquav10CmdEntry 40072 }


    iquav10AudioInputAESInput18AESInput11procamp OBJECT-TYPE
        SYNTAX            INTEGER
        MAX-ACCESS        read-write
        STATUS            current
        DESCRIPTION
                "CMNT: - AESInput Proc Amp Gain
                 TYPE: - Number
                 PAGE: - AudioInput
                    AESInput1_1_procamp  cmdID= 40100
                    min= -801  max= 120  step= 1  format= %0.1f dB  div_scale= 10  preset= 0
                    Min = -80.1 dB  Max = 12.0 dB  Step = 0.1 dB  Preset = 0.0 dB  "
        ::= { iquav10CmdEntry 40100 }


    iquav10AudioInputAESInput18AESInput12procamp OBJECT-TYPE
        SYNTAX            INTEGER
        MAX-ACCESS        read-write
        STATUS            current
        DESCRIPTION
                "CMNT: - AESInput Proc Amp Gain
                 TYPE: - Number
                 PAGE: - AudioInput
                    AESInput1_2_procamp  cmdID= 40101
                    min= -801  max= 120  step= 1  format= %0.1f dB  div_scale= 10  preset= 0
                    Min = -80.1 dB  Max = 12.0 dB  Step = 0.1 dB  Preset = 0.0 dB  "
        ::= { iquav10CmdEntry 40101 }


    iquav10AESInput18AESInput1Mute11 OBJECT-TYPE
        SYNTAX            INTEGER { disable(0), enable(1)  }
        MAX-ACCESS        read-write
        STATUS            current
        DESCRIPTION
                "CMNT: - 
                 TYPE: - Checkbox
                 PAGE: - AESInput1-8
                    Mute1_1  cmdID= 40132  "
        ::= { iquav10CmdEntry 40132 }


    iquav10AESInput18AESInput1Mute12 OBJECT-TYPE
        SYNTAX            INTEGER { disable(0), enable(1)  }
        MAX-ACCESS        read-write
        STATUS            current
        DESCRIPTION
                "CMNT: - 
                 TYPE: - Checkbox
                 PAGE: - AESInput1-8
                    Mute1_2  cmdID= 40133  "
        ::= { iquav10CmdEntry 40133 }


    iquav10AESInput18AESInput1Stereo1 OBJECT-TYPE
        SYNTAX            INTEGER { disable(0), enable(1)  }
        MAX-ACCESS        read-write
        STATUS            current
        DESCRIPTION
                "CMNT: - 
                 TYPE: - Checkbox
                 PAGE: - AESInput1-8
                    Stereo1  cmdID= 40148  "
        ::= { iquav10CmdEntry 40148 }


    iquav10AudioInputAESInput18AESInput11invert OBJECT-TYPE
        SYNTAX            INTEGER { disable(0), enable(1)  }
        MAX-ACCESS        read-write
        STATUS            current
        DESCRIPTION
                "CMNT: - 
                 TYPE: - Checkbox
                 PAGE: - AudioInput
                    AESInput1_1_invert  cmdID= 40116  "
        ::= { iquav10CmdEntry 40116 }


    iquav10AudioInputAESInput18AESInput12invert OBJECT-TYPE
        SYNTAX            INTEGER { disable(0), enable(1)  }
        MAX-ACCESS        read-write
        STATUS            current
        DESCRIPTION
                "CMNT: - 
                 TYPE: - Checkbox
                 PAGE: - AudioInput
                    AESInput1_2_invert  cmdID= 40117  "
        ::= { iquav10CmdEntry 40117 }


    iquav10AESInput18AESInput1AESIO OBJECT-TYPE
        SYNTAX            INTEGER {
                            valSetOutput(0),
                            valSetInput(1)
                            }
        MAX-ACCESS        read-write
        STATUS            current
        DESCRIPTION
                "CMNT: - 
                 TYPE: - RadiobuttonList
                 PAGE: - AESInput1-8
                    AES I/O  cmdID= 40263
                    Set Output  value= 0
                    Set Input  value= 1  "
        ::= { iquav10CmdEntry 40263 }


    iquav10AudioInputAESInput18AESInput21procamp OBJECT-TYPE
        SYNTAX            INTEGER
        MAX-ACCESS        read-write
        STATUS            current
        DESCRIPTION
                "CMNT: - AESInput Proc Amp Gain
                 TYPE: - Number
                 PAGE: - AudioInput
                    AESInput2_1_procamp  cmdID= 40102
                    min= -801  max= 120  step= 1  format= %0.1f dB  div_scale= 10  preset= 0
                    Min = -80.1 dB  Max = 12.0 dB  Step = 0.1 dB  Preset = 0.0 dB  "
        ::= { iquav10CmdEntry 40102 }


    iquav10AudioInputAESInput18AESInput22procamp OBJECT-TYPE
        SYNTAX            INTEGER
        MAX-ACCESS        read-write
        STATUS            current
        DESCRIPTION
                "CMNT: - AESInput Proc Amp Gain
                 TYPE: - Number
                 PAGE: - AudioInput
                    AESInput2_2_procamp  cmdID= 40103
                    min= -801  max= 120  step= 1  format= %0.1f dB  div_scale= 10  preset= 0
                    Min = -80.1 dB  Max = 12.0 dB  Step = 0.1 dB  Preset = 0.0 dB  "
        ::= { iquav10CmdEntry 40103 }


    iquav10AESInput18AESInput2Mute21 OBJECT-TYPE
        SYNTAX            INTEGER { disable(0), enable(1)  }
        MAX-ACCESS        read-write
        STATUS            current
        DESCRIPTION
                "CMNT: - 
                 TYPE: - Checkbox
                 PAGE: - AESInput1-8
                    Mute2_1  cmdID= 40134  "
        ::= { iquav10CmdEntry 40134 }


    iquav10AESInput18AESInput2Mute22 OBJECT-TYPE
        SYNTAX            INTEGER { disable(0), enable(1)  }
        MAX-ACCESS        read-write
        STATUS            current
        DESCRIPTION
                "CMNT: - 
                 TYPE: - Checkbox
                 PAGE: - AESInput1-8
                    Mute2_2  cmdID= 40135  "
        ::= { iquav10CmdEntry 40135 }


    iquav10AESInput18AESInput2Stereo2 OBJECT-TYPE
        SYNTAX            INTEGER { disable(0), enable(1)  }
        MAX-ACCESS        read-write
        STATUS            current
        DESCRIPTION
                "CMNT: - 
                 TYPE: - Checkbox
                 PAGE: - AESInput1-8
                    Stereo2  cmdID= 40149  "
        ::= { iquav10CmdEntry 40149 }


    iquav10AudioInputAESInput18AESInput21invert OBJECT-TYPE
        SYNTAX            INTEGER { disable(0), enable(1)  }
        MAX-ACCESS        read-write
        STATUS            current
        DESCRIPTION
                "CMNT: - 
                 TYPE: - Checkbox
                 PAGE: - AudioInput
                    AESInput2_1_invert  cmdID= 40118  "
        ::= { iquav10CmdEntry 40118 }


    iquav10AudioInputAESInput18AESInput22invert OBJECT-TYPE
        SYNTAX            INTEGER { disable(0), enable(1)  }
        MAX-ACCESS        read-write
        STATUS            current
        DESCRIPTION
                "CMNT: - 
                 TYPE: - Checkbox
                 PAGE: - AudioInput
                    AESInput2_2_invert  cmdID= 40119  "
        ::= { iquav10CmdEntry 40119 }


    iquav10AESInput18AESInput2AESIO OBJECT-TYPE
        SYNTAX            INTEGER {
                            valSetOutput(0),
                            valSetInput(1)
                            }
        MAX-ACCESS        read-write
        STATUS            current
        DESCRIPTION
                "CMNT: - 
                 TYPE: - RadiobuttonList
                 PAGE: - AESInput1-8
                    AES I/O  cmdID= 40264
                    Set Output  value= 0
                    Set Input  value= 1  "
        ::= { iquav10CmdEntry 40264 }


    iquav10AudioInputAESInput18AESInput31procamp OBJECT-TYPE
        SYNTAX            INTEGER
        MAX-ACCESS        read-write
        STATUS            current
        DESCRIPTION
                "CMNT: - AESInput Proc Amp Gain
                 TYPE: - Number
                 PAGE: - AudioInput
                    AESInput3_1_procamp  cmdID= 40104
                    min= -801  max= 120  step= 1  format= %0.1f dB  div_scale= 10  preset= 0
                    Min = -80.1 dB  Max = 12.0 dB  Step = 0.1 dB  Preset = 0.0 dB  "
        ::= { iquav10CmdEntry 40104 }


    iquav10AudioInputAESInput18AESInput32procamp OBJECT-TYPE
        SYNTAX            INTEGER
        MAX-ACCESS        read-write
        STATUS            current
        DESCRIPTION
                "CMNT: - AESInput Proc Amp Gain
                 TYPE: - Number
                 PAGE: - AudioInput
                    AESInput3_2_procamp  cmdID= 40105
                    min= -801  max= 120  step= 1  format= %0.1f dB  div_scale= 10  preset= 0
                    Min = -80.1 dB  Max = 12.0 dB  Step = 0.1 dB  Preset = 0.0 dB  "
        ::= { iquav10CmdEntry 40105 }


    iquav10AESInput18AESInput3Mute31 OBJECT-TYPE
        SYNTAX            INTEGER { disable(0), enable(1)  }
        MAX-ACCESS        read-write
        STATUS            current
        DESCRIPTION
                "CMNT: - 
                 TYPE: - Checkbox
                 PAGE: - AESInput1-8
                    Mute3_1  cmdID= 40136  "
        ::= { iquav10CmdEntry 40136 }


    iquav10AESInput18AESInput3Mute32 OBJECT-TYPE
        SYNTAX            INTEGER { disable(0), enable(1)  }
        MAX-ACCESS        read-write
        STATUS            current
        DESCRIPTION
                "CMNT: - 
                 TYPE: - Checkbox
                 PAGE: - AESInput1-8
                    Mute3_2  cmdID= 40137  "
        ::= { iquav10CmdEntry 40137 }


    iquav10AESInput18AESInput3Stereo3 OBJECT-TYPE
        SYNTAX            INTEGER { disable(0), enable(1)  }
        MAX-ACCESS        read-write
        STATUS            current
        DESCRIPTION
                "CMNT: - 
                 TYPE: - Checkbox
                 PAGE: - AESInput1-8
                    Stereo3  cmdID= 40150  "
        ::= { iquav10CmdEntry 40150 }


    iquav10AudioInputAESInput18AESInput31invert OBJECT-TYPE
        SYNTAX            INTEGER { disable(0), enable(1)  }
        MAX-ACCESS        read-write
        STATUS            current
        DESCRIPTION
                "CMNT: - 
                 TYPE: - Checkbox
                 PAGE: - AudioInput
                    AESInput3_1_invert  cmdID= 40120  "
        ::= { iquav10CmdEntry 40120 }


    iquav10AudioInputAESInput18AESInput32invert OBJECT-TYPE
        SYNTAX            INTEGER { disable(0), enable(1)  }
        MAX-ACCESS        read-write
        STATUS            current
        DESCRIPTION
                "CMNT: - 
                 TYPE: - Checkbox
                 PAGE: - AudioInput
                    AESInput3_2_invert  cmdID= 40121  "
        ::= { iquav10CmdEntry 40121 }


    iquav10AESInput18AESInput3AESIO OBJECT-TYPE
        SYNTAX            INTEGER {
                            valSetOutput(0),
                            valSetInput(1)
                            }
        MAX-ACCESS        read-write
        STATUS            current
        DESCRIPTION
                "CMNT: - 
                 TYPE: - RadiobuttonList
                 PAGE: - AESInput1-8
                    AES I/O  cmdID= 40265
                    Set Output  value= 0
                    Set Input  value= 1  "
        ::= { iquav10CmdEntry 40265 }


    iquav10AudioInputAESInput18AESInput41procamp OBJECT-TYPE
        SYNTAX            INTEGER
        MAX-ACCESS        read-write
        STATUS            current
        DESCRIPTION
                "CMNT: - AESInput Proc Amp Gain
                 TYPE: - Number
                 PAGE: - AudioInput
                    AESInput4_1_procamp  cmdID= 40106
                    min= -801  max= 120  step= 1  format= %0.1f dB  div_scale= 10  preset= 0
                    Min = -80.1 dB  Max = 12.0 dB  Step = 0.1 dB  Preset = 0.0 dB  "
        ::= { iquav10CmdEntry 40106 }


    iquav10AudioInputAESInput18AESInput42procamp OBJECT-TYPE
        SYNTAX            INTEGER
        MAX-ACCESS        read-write
        STATUS            current
        DESCRIPTION
                "CMNT: - AESInput Proc Amp Gain
                 TYPE: - Number
                 PAGE: - AudioInput
                    AESInput4_2_procamp  cmdID= 40107
                    min= -801  max= 120  step= 1  format= %0.1f dB  div_scale= 10  preset= 0
                    Min = -80.1 dB  Max = 12.0 dB  Step = 0.1 dB  Preset = 0.0 dB  "
        ::= { iquav10CmdEntry 40107 }


    iquav10AESInput18AESInput4Mute41 OBJECT-TYPE
        SYNTAX            INTEGER { disable(0), enable(1)  }
        MAX-ACCESS        read-write
        STATUS            current
        DESCRIPTION
                "CMNT: - 
                 TYPE: - Checkbox
                 PAGE: - AESInput1-8
                    Mute4_1  cmdID= 40138  "
        ::= { iquav10CmdEntry 40138 }


    iquav10AESInput18AESInput4Mute42 OBJECT-TYPE
        SYNTAX            INTEGER { disable(0), enable(1)  }
        MAX-ACCESS        read-write
        STATUS            current
        DESCRIPTION
                "CMNT: - 
                 TYPE: - Checkbox
                 PAGE: - AESInput1-8
                    Mute4_2  cmdID= 40139  "
        ::= { iquav10CmdEntry 40139 }


    iquav10AESInput18AESInput4Stereo4 OBJECT-TYPE
        SYNTAX            INTEGER { disable(0), enable(1)  }
        MAX-ACCESS        read-write
        STATUS            current
        DESCRIPTION
                "CMNT: - 
                 TYPE: - Checkbox
                 PAGE: - AESInput1-8
                    Stereo4  cmdID= 40151  "
        ::= { iquav10CmdEntry 40151 }


    iquav10AudioInputAESInput18AESInput41invert OBJECT-TYPE
        SYNTAX            INTEGER { disable(0), enable(1)  }
        MAX-ACCESS        read-write
        STATUS            current
        DESCRIPTION
                "CMNT: - 
                 TYPE: - Checkbox
                 PAGE: - AudioInput
                    AESInput4_1_invert  cmdID= 40122  "
        ::= { iquav10CmdEntry 40122 }


    iquav10AudioInputAESInput18AESInput42invert OBJECT-TYPE
        SYNTAX            INTEGER { disable(0), enable(1)  }
        MAX-ACCESS        read-write
        STATUS            current
        DESCRIPTION
                "CMNT: - 
                 TYPE: - Checkbox
                 PAGE: - AudioInput
                    AESInput4_2_invert  cmdID= 40123  "
        ::= { iquav10CmdEntry 40123 }


    iquav10AESInput18AESInput4AESIO OBJECT-TYPE
        SYNTAX            INTEGER {
                            valSetOutput(0),
                            valSetInput(1)
                            }
        MAX-ACCESS        read-write
        STATUS            current
        DESCRIPTION
                "CMNT: - 
                 TYPE: - RadiobuttonList
                 PAGE: - AESInput1-8
                    AES I/O  cmdID= 40266
                    Set Output  value= 0
                    Set Input  value= 1  "
        ::= { iquav10CmdEntry 40266 }


    iquav10AudioInputAESInput18AESInput51procamp OBJECT-TYPE
        SYNTAX            INTEGER
        MAX-ACCESS        read-write
        STATUS            current
        DESCRIPTION
                "CMNT: - AESInput Proc Amp Gain
                 TYPE: - Number
                 PAGE: - AudioInput
                    AESInput5_1_procamp  cmdID= 40108
                    min= -801  max= 120  step= 1  format= %0.1f dB  div_scale= 10  preset= 0
                    Min = -80.1 dB  Max = 12.0 dB  Step = 0.1 dB  Preset = 0.0 dB  "
        ::= { iquav10CmdEntry 40108 }


    iquav10AudioInputAESInput18AESInput52procamp OBJECT-TYPE
        SYNTAX            INTEGER
        MAX-ACCESS        read-write
        STATUS            current
        DESCRIPTION
                "CMNT: - AESInput Proc Amp Gain
                 TYPE: - Number
                 PAGE: - AudioInput
                    AESInput5_2_procamp  cmdID= 40109
                    min= -801  max= 120  step= 1  format= %0.1f dB  div_scale= 10  preset= 0
                    Min = -80.1 dB  Max = 12.0 dB  Step = 0.1 dB  Preset = 0.0 dB  "
        ::= { iquav10CmdEntry 40109 }


    iquav10AESInput18AESInput5Mute51 OBJECT-TYPE
        SYNTAX            INTEGER { disable(0), enable(1)  }
        MAX-ACCESS        read-write
        STATUS            current
        DESCRIPTION
                "CMNT: - 
                 TYPE: - Checkbox
                 PAGE: - AESInput1-8
                    Mute5_1  cmdID= 40140  "
        ::= { iquav10CmdEntry 40140 }


    iquav10AESInput18AESInput5Mute52 OBJECT-TYPE
        SYNTAX            INTEGER { disable(0), enable(1)  }
        MAX-ACCESS        read-write
        STATUS            current
        DESCRIPTION
                "CMNT: - 
                 TYPE: - Checkbox
                 PAGE: - AESInput1-8
                    Mute5_2  cmdID= 40141  "
        ::= { iquav10CmdEntry 40141 }


    iquav10AESInput18AESInput5Stereo5 OBJECT-TYPE
        SYNTAX            INTEGER { disable(0), enable(1)  }
        MAX-ACCESS        read-write
        STATUS            current
        DESCRIPTION
                "CMNT: - 
                 TYPE: - Checkbox
                 PAGE: - AESInput1-8
                    Stereo5  cmdID= 40152  "
        ::= { iquav10CmdEntry 40152 }


    iquav10AudioInputAESInput18AESInput51invert OBJECT-TYPE
        SYNTAX            INTEGER { disable(0), enable(1)  }
        MAX-ACCESS        read-write
        STATUS            current
        DESCRIPTION
                "CMNT: - 
                 TYPE: - Checkbox
                 PAGE: - AudioInput
                    AESInput5_1_invert  cmdID= 40124  "
        ::= { iquav10CmdEntry 40124 }


    iquav10AudioInputAESInput18AESInput52invert OBJECT-TYPE
        SYNTAX            INTEGER { disable(0), enable(1)  }
        MAX-ACCESS        read-write
        STATUS            current
        DESCRIPTION
                "CMNT: - 
                 TYPE: - Checkbox
                 PAGE: - AudioInput
                    AESInput5_2_invert  cmdID= 40125  "
        ::= { iquav10CmdEntry 40125 }


    iquav10AESInput18AESInput5AESIO OBJECT-TYPE
        SYNTAX            INTEGER {
                            valSetOutput(0),
                            valSetInput(1)
                            }
        MAX-ACCESS        read-write
        STATUS            current
        DESCRIPTION
                "CMNT: - 
                 TYPE: - RadiobuttonList
                 PAGE: - AESInput1-8
                    AES I/O  cmdID= 40267
                    Set Output  value= 0
                    Set Input  value= 1  "
        ::= { iquav10CmdEntry 40267 }


    iquav10AudioInputAESInput18AESInput61procamp OBJECT-TYPE
        SYNTAX            INTEGER
        MAX-ACCESS        read-write
        STATUS            current
        DESCRIPTION
                "CMNT: - AESInput Proc Amp Gain
                 TYPE: - Number
                 PAGE: - AudioInput
                    AESInput6_1_procamp  cmdID= 40110
                    min= -801  max= 120  step= 1  format= %0.1f dB  div_scale= 10  preset= 0
                    Min = -80.1 dB  Max = 12.0 dB  Step = 0.1 dB  Preset = 0.0 dB  "
        ::= { iquav10CmdEntry 40110 }


    iquav10AudioInputAESInput18AESInput62procamp OBJECT-TYPE
        SYNTAX            INTEGER
        MAX-ACCESS        read-write
        STATUS            current
        DESCRIPTION
                "CMNT: - AESInput Proc Amp Gain
                 TYPE: - Number
                 PAGE: - AudioInput
                    AESInput6_2_procamp  cmdID= 40111
                    min= -801  max= 120  step= 1  format= %0.1f dB  div_scale= 10  preset= 0
                    Min = -80.1 dB  Max = 12.0 dB  Step = 0.1 dB  Preset = 0.0 dB  "
        ::= { iquav10CmdEntry 40111 }


    iquav10AESInput18AESInput6Mute61 OBJECT-TYPE
        SYNTAX            INTEGER { disable(0), enable(1)  }
        MAX-ACCESS        read-write
        STATUS            current
        DESCRIPTION
                "CMNT: - 
                 TYPE: - Checkbox
                 PAGE: - AESInput1-8
                    Mute6_1  cmdID= 40142  "
        ::= { iquav10CmdEntry 40142 }


    iquav10AESInput18AESInput6Mute62 OBJECT-TYPE
        SYNTAX            INTEGER { disable(0), enable(1)  }
        MAX-ACCESS        read-write
        STATUS            current
        DESCRIPTION
                "CMNT: - 
                 TYPE: - Checkbox
                 PAGE: - AESInput1-8
                    Mute6_2  cmdID= 40143  "
        ::= { iquav10CmdEntry 40143 }


    iquav10AESInput18AESInput6Stereo6 OBJECT-TYPE
        SYNTAX            INTEGER { disable(0), enable(1)  }
        MAX-ACCESS        read-write
        STATUS            current
        DESCRIPTION
                "CMNT: - 
                 TYPE: - Checkbox
                 PAGE: - AESInput1-8
                    Stereo6  cmdID= 40153  "
        ::= { iquav10CmdEntry 40153 }


    iquav10AudioInputAESInput18AESInput61invert OBJECT-TYPE
        SYNTAX            INTEGER { disable(0), enable(1)  }
        MAX-ACCESS        read-write
        STATUS            current
        DESCRIPTION
                "CMNT: - 
                 TYPE: - Checkbox
                 PAGE: - AudioInput
                    AESInput6_1_invert  cmdID= 40126  "
        ::= { iquav10CmdEntry 40126 }


    iquav10AudioInputAESInput18AESInput62invert OBJECT-TYPE
        SYNTAX            INTEGER { disable(0), enable(1)  }
        MAX-ACCESS        read-write
        STATUS            current
        DESCRIPTION
                "CMNT: - 
                 TYPE: - Checkbox
                 PAGE: - AudioInput
                    AESInput6_2_invert  cmdID= 40127  "
        ::= { iquav10CmdEntry 40127 }


    iquav10AESInput18AESInput6AESIO OBJECT-TYPE
        SYNTAX            INTEGER {
                            valSetOutput(0),
                            valSetInput(1)
                            }
        MAX-ACCESS        read-write
        STATUS            current
        DESCRIPTION
                "CMNT: - 
                 TYPE: - RadiobuttonList
                 PAGE: - AESInput1-8
                    AES I/O  cmdID= 40268
                    Set Output  value= 0
                    Set Input  value= 1  "
        ::= { iquav10CmdEntry 40268 }


    iquav10AudioInputAESInput18AESInput71procamp OBJECT-TYPE
        SYNTAX            INTEGER
        MAX-ACCESS        read-write
        STATUS            current
        DESCRIPTION
                "CMNT: - AESInput Proc Amp Gain
                 TYPE: - Number
                 PAGE: - AudioInput
                    AESInput7_1_procamp  cmdID= 40112
                    min= -801  max= 120  step= 1  format= %0.1f dB  div_scale= 10  preset= 0
                    Min = -80.1 dB  Max = 12.0 dB  Step = 0.1 dB  Preset = 0.0 dB  "
        ::= { iquav10CmdEntry 40112 }


    iquav10AudioInputAESInput18AESInput72procamp OBJECT-TYPE
        SYNTAX            INTEGER
        MAX-ACCESS        read-write
        STATUS            current
        DESCRIPTION
                "CMNT: - AESInput Proc Amp Gain
                 TYPE: - Number
                 PAGE: - AudioInput
                    AESInput7_2_procamp  cmdID= 40113
                    min= -801  max= 120  step= 1  format= %0.1f dB  div_scale= 10  preset= 0
                    Min = -80.1 dB  Max = 12.0 dB  Step = 0.1 dB  Preset = 0.0 dB  "
        ::= { iquav10CmdEntry 40113 }


    iquav10AESInput18AESInput7Mute71 OBJECT-TYPE
        SYNTAX            INTEGER { disable(0), enable(1)  }
        MAX-ACCESS        read-write
        STATUS            current
        DESCRIPTION
                "CMNT: - 
                 TYPE: - Checkbox
                 PAGE: - AESInput1-8
                    Mute7_1  cmdID= 40144  "
        ::= { iquav10CmdEntry 40144 }


    iquav10AESInput18AESInput7Mute72 OBJECT-TYPE
        SYNTAX            INTEGER { disable(0), enable(1)  }
        MAX-ACCESS        read-write
        STATUS            current
        DESCRIPTION
                "CMNT: - 
                 TYPE: - Checkbox
                 PAGE: - AESInput1-8
                    Mute7_2  cmdID= 40145  "
        ::= { iquav10CmdEntry 40145 }


    iquav10AESInput18AESInput7Stereo7 OBJECT-TYPE
        SYNTAX            INTEGER { disable(0), enable(1)  }
        MAX-ACCESS        read-write
        STATUS            current
        DESCRIPTION
                "CMNT: - 
                 TYPE: - Checkbox
                 PAGE: - AESInput1-8
                    Stereo7  cmdID= 40154  "
        ::= { iquav10CmdEntry 40154 }


    iquav10AudioInputAESInput18AESInput71invert OBJECT-TYPE
        SYNTAX            INTEGER { disable(0), enable(1)  }
        MAX-ACCESS        read-write
        STATUS            current
        DESCRIPTION
                "CMNT: - 
                 TYPE: - Checkbox
                 PAGE: - AudioInput
                    AESInput7_1_invert  cmdID= 40128  "
        ::= { iquav10CmdEntry 40128 }


    iquav10AudioInputAESInput18AESInput72invert OBJECT-TYPE
        SYNTAX            INTEGER { disable(0), enable(1)  }
        MAX-ACCESS        read-write
        STATUS            current
        DESCRIPTION
                "CMNT: - 
                 TYPE: - Checkbox
                 PAGE: - AudioInput
                    AESInput7_2_invert  cmdID= 40129  "
        ::= { iquav10CmdEntry 40129 }


    iquav10AESInput18AESInput7AESIO OBJECT-TYPE
        SYNTAX            INTEGER {
                            valSetOutput(0),
                            valSetInput(1)
                            }
        MAX-ACCESS        read-write
        STATUS            current
        DESCRIPTION
                "CMNT: - 
                 TYPE: - RadiobuttonList
                 PAGE: - AESInput1-8
                    AES I/O  cmdID= 40269
                    Set Output  value= 0
                    Set Input  value= 1  "
        ::= { iquav10CmdEntry 40269 }


    iquav10AudioInputAESInput18AESInput81procamp OBJECT-TYPE
        SYNTAX            INTEGER
        MAX-ACCESS        read-write
        STATUS            current
        DESCRIPTION
                "CMNT: - AESInput Proc Amp Gain
                 TYPE: - Number
                 PAGE: - AudioInput
                    AESInput8_1_procamp  cmdID= 40114
                    min= -801  max= 120  step= 1  format= %0.1f dB  div_scale= 10  preset= 0
                    Min = -80.1 dB  Max = 12.0 dB  Step = 0.1 dB  Preset = 0.0 dB  "
        ::= { iquav10CmdEntry 40114 }


    iquav10AudioInputAESInput18AESInput82procamp OBJECT-TYPE
        SYNTAX            INTEGER
        MAX-ACCESS        read-write
        STATUS            current
        DESCRIPTION
                "CMNT: - AESInput Proc Amp Gain
                 TYPE: - Number
                 PAGE: - AudioInput
                    AESInput8_2_procamp  cmdID= 40115
                    min= -801  max= 120  step= 1  format= %0.1f dB  div_scale= 10  preset= 0
                    Min = -80.1 dB  Max = 12.0 dB  Step = 0.1 dB  Preset = 0.0 dB  "
        ::= { iquav10CmdEntry 40115 }


    iquav10AESInput18AESInput8Mute81 OBJECT-TYPE
        SYNTAX            INTEGER { disable(0), enable(1)  }
        MAX-ACCESS        read-write
        STATUS            current
        DESCRIPTION
                "CMNT: - 
                 TYPE: - Checkbox
                 PAGE: - AESInput1-8
                    Mute8_1  cmdID= 40146  "
        ::= { iquav10CmdEntry 40146 }


    iquav10AESInput18AESInput8Mute82 OBJECT-TYPE
        SYNTAX            INTEGER { disable(0), enable(1)  }
        MAX-ACCESS        read-write
        STATUS            current
        DESCRIPTION
                "CMNT: - 
                 TYPE: - Checkbox
                 PAGE: - AESInput1-8
                    Mute8_2  cmdID= 40147  "
        ::= { iquav10CmdEntry 40147 }


    iquav10AESInput18AESInput8Stereo8 OBJECT-TYPE
        SYNTAX            INTEGER { disable(0), enable(1)  }
        MAX-ACCESS        read-write
        STATUS            current
        DESCRIPTION
                "CMNT: - 
                 TYPE: - Checkbox
                 PAGE: - AESInput1-8
                    Stereo8  cmdID= 40155  "
        ::= { iquav10CmdEntry 40155 }


    iquav10AudioInputAESInput18AESInput81invert OBJECT-TYPE
        SYNTAX            INTEGER { disable(0), enable(1)  }
        MAX-ACCESS        read-write
        STATUS            current
        DESCRIPTION
                "CMNT: - 
                 TYPE: - Checkbox
                 PAGE: - AudioInput
                    AESInput8_1_invert  cmdID= 40130  "
        ::= { iquav10CmdEntry 40130 }


    iquav10AudioInputAESInput18AESInput82invert OBJECT-TYPE
        SYNTAX            INTEGER { disable(0), enable(1)  }
        MAX-ACCESS        read-write
        STATUS            current
        DESCRIPTION
                "CMNT: - 
                 TYPE: - Checkbox
                 PAGE: - AudioInput
                    AESInput8_2_invert  cmdID= 40131  "
        ::= { iquav10CmdEntry 40131 }


    iquav10AESInput18AESInput8AESIO OBJECT-TYPE
        SYNTAX            INTEGER {
                            valSetOutput(0),
                            valSetInput(1)
                            }
        MAX-ACCESS        read-write
        STATUS            current
        DESCRIPTION
                "CMNT: - 
                 TYPE: - RadiobuttonList
                 PAGE: - AESInput1-8
                    AES I/O  cmdID= 40270
                    Set Output  value= 0
                    Set Input  value= 1  "
        ::= { iquav10CmdEntry 40270 }


    iquav10AudioInputAnalogInput12AnalogInput11procamp OBJECT-TYPE
        SYNTAX            INTEGER
        MAX-ACCESS        read-write
        STATUS            current
        DESCRIPTION
                "CMNT: - AnalogInput Proc Amp Gain
                 TYPE: - Number
                 PAGE: - AudioInput
                    AnalogInput1_1_procamp  cmdID= 40181
                    min= -801  max= 120  step= 1  format= %0.1f dB  div_scale= 10  preset= 0
                    Min = -80.1 dB  Max = 12.0 dB  Step = 0.1 dB  Preset = 0.0 dB  "
        ::= { iquav10CmdEntry 40181 }


    iquav10AudioInputAnalogInput12AnalogInput12procamp OBJECT-TYPE
        SYNTAX            INTEGER
        MAX-ACCESS        read-write
        STATUS            current
        DESCRIPTION
                "CMNT: - AnalogInput Proc Amp Gain
                 TYPE: - Number
                 PAGE: - AudioInput
                    AnalogInput1_2_procamp  cmdID= 40182
                    min= -801  max= 120  step= 1  format= %0.1f dB  div_scale= 10  preset= 0
                    Min = -80.1 dB  Max = 12.0 dB  Step = 0.1 dB  Preset = 0.0 dB  "
        ::= { iquav10CmdEntry 40182 }


    iquav10AnalogInput12AnalogInput1Mute11 OBJECT-TYPE
        SYNTAX            INTEGER { disable(0), enable(1)  }
        MAX-ACCESS        read-write
        STATUS            current
        DESCRIPTION
                "CMNT: - 
                 TYPE: - Checkbox
                 PAGE: - AnalogInput1-2
                    Mute1_1  cmdID= 40189  "
        ::= { iquav10CmdEntry 40189 }


    iquav10AnalogInput12AnalogInput1Mute12 OBJECT-TYPE
        SYNTAX            INTEGER { disable(0), enable(1)  }
        MAX-ACCESS        read-write
        STATUS            current
        DESCRIPTION
                "CMNT: - 
                 TYPE: - Checkbox
                 PAGE: - AnalogInput1-2
                    Mute1_2  cmdID= 40190  "
        ::= { iquav10CmdEntry 40190 }


    iquav10AnalogInput12AnalogInput1Stereo1 OBJECT-TYPE
        SYNTAX            INTEGER { disable(0), enable(1)  }
        MAX-ACCESS        read-write
        STATUS            current
        DESCRIPTION
                "CMNT: - 
                 TYPE: - Checkbox
                 PAGE: - AnalogInput1-2
                    Stereo1  cmdID= 40193  "
        ::= { iquav10CmdEntry 40193 }


    iquav10AudioInputAnalogInput12AnalogInput11invert OBJECT-TYPE
        SYNTAX            INTEGER { disable(0), enable(1)  }
        MAX-ACCESS        read-write
        STATUS            current
        DESCRIPTION
                "CMNT: - 
                 TYPE: - Checkbox
                 PAGE: - AudioInput
                    AnalogInput1_1_invert  cmdID= 40185  "
        ::= { iquav10CmdEntry 40185 }


    iquav10AudioInputAnalogInput12AnalogInput12invert OBJECT-TYPE
        SYNTAX            INTEGER { disable(0), enable(1)  }
        MAX-ACCESS        read-write
        STATUS            current
        DESCRIPTION
                "CMNT: - 
                 TYPE: - Checkbox
                 PAGE: - AudioInput
                    AnalogInput1_2_invert  cmdID= 40186  "
        ::= { iquav10CmdEntry 40186 }


    iquav10AudioInputAnalogInput12AnalogInput21procamp OBJECT-TYPE
        SYNTAX            INTEGER
        MAX-ACCESS        read-write
        STATUS            current
        DESCRIPTION
                "CMNT: - AnalogInput Proc Amp Gain
                 TYPE: - Number
                 PAGE: - AudioInput
                    AnalogInput2_1_procamp  cmdID= 40183
                    min= -801  max= 120  step= 1  format= %0.1f dB  div_scale= 10  preset= 0
                    Min = -80.1 dB  Max = 12.0 dB  Step = 0.1 dB  Preset = 0.0 dB  "
        ::= { iquav10CmdEntry 40183 }


    iquav10AudioInputAnalogInput12AnalogInput22procamp OBJECT-TYPE
        SYNTAX            INTEGER
        MAX-ACCESS        read-write
        STATUS            current
        DESCRIPTION
                "CMNT: - AnalogInput Proc Amp Gain
                 TYPE: - Number
                 PAGE: - AudioInput
                    AnalogInput2_2_procamp  cmdID= 40184
                    min= -801  max= 120  step= 1  format= %0.1f dB  div_scale= 10  preset= 0
                    Min = -80.1 dB  Max = 12.0 dB  Step = 0.1 dB  Preset = 0.0 dB  "
        ::= { iquav10CmdEntry 40184 }


    iquav10AnalogInput12AnalogInput2Mute21 OBJECT-TYPE
        SYNTAX            INTEGER { disable(0), enable(1)  }
        MAX-ACCESS        read-write
        STATUS            current
        DESCRIPTION
                "CMNT: - 
                 TYPE: - Checkbox
                 PAGE: - AnalogInput1-2
                    Mute2_1  cmdID= 40191  "
        ::= { iquav10CmdEntry 40191 }


    iquav10AnalogInput12AnalogInput2Mute22 OBJECT-TYPE
        SYNTAX            INTEGER { disable(0), enable(1)  }
        MAX-ACCESS        read-write
        STATUS            current
        DESCRIPTION
                "CMNT: - 
                 TYPE: - Checkbox
                 PAGE: - AnalogInput1-2
                    Mute2_2  cmdID= 40192  "
        ::= { iquav10CmdEntry 40192 }


    iquav10AnalogInput12AnalogInput2Stereo2 OBJECT-TYPE
        SYNTAX            INTEGER { disable(0), enable(1)  }
        MAX-ACCESS        read-write
        STATUS            current
        DESCRIPTION
                "CMNT: - 
                 TYPE: - Checkbox
                 PAGE: - AnalogInput1-2
                    Stereo2  cmdID= 40194  "
        ::= { iquav10CmdEntry 40194 }


    iquav10AudioInputAnalogInput12AnalogInput21invert OBJECT-TYPE
        SYNTAX            INTEGER { disable(0), enable(1)  }
        MAX-ACCESS        read-write
        STATUS            current
        DESCRIPTION
                "CMNT: - 
                 TYPE: - Checkbox
                 PAGE: - AudioInput
                    AnalogInput2_1_invert  cmdID= 40187  "
        ::= { iquav10CmdEntry 40187 }


    iquav10AudioInputAnalogInput12AnalogInput22invert OBJECT-TYPE
        SYNTAX            INTEGER { disable(0), enable(1)  }
        MAX-ACCESS        read-write
        STATUS            current
        DESCRIPTION
                "CMNT: - 
                 TYPE: - Checkbox
                 PAGE: - AudioInput
                    AnalogInput2_2_invert  cmdID= 40188  "
        ::= { iquav10CmdEntry 40188 }


    iquav10AudioOutputEmbed18Embed11procamp OBJECT-TYPE
        SYNTAX            INTEGER
        MAX-ACCESS        read-write
        STATUS            current
        DESCRIPTION
                "CMNT: - Embed Proc Amp Gain
                 TYPE: - Number
                 PAGE: - AudioOutput
                    Embed1_1_procamp  cmdID= 40400
                    min= -801  max= 120  step= 1  format= %0.1f dB  div_scale= 10  preset= 0
                    Min = -80.1 dB  Max = 12.0 dB  Step = 0.1 dB  Preset = 0.0 dB  "
        ::= { iquav10CmdEntry 40400 }


    iquav10AudioOutputEmbed18Embed12procamp OBJECT-TYPE
        SYNTAX            INTEGER
        MAX-ACCESS        read-write
        STATUS            current
        DESCRIPTION
                "CMNT: - Embed Proc Amp Gain
                 TYPE: - Number
                 PAGE: - AudioOutput
                    Embed1_2_procamp  cmdID= 40401
                    min= -801  max= 120  step= 1  format= %0.1f dB  div_scale= 10  preset= 0
                    Min = -80.1 dB  Max = 12.0 dB  Step = 0.1 dB  Preset = 0.0 dB  "
        ::= { iquav10CmdEntry 40401 }


    iquav10Embed18Embed1Mute11 OBJECT-TYPE
        SYNTAX            INTEGER { disable(0), enable(1)  }
        MAX-ACCESS        read-write
        STATUS            current
        DESCRIPTION
                "CMNT: - 
                 TYPE: - Checkbox
                 PAGE: - Embed1-8
                    Mute1_1  cmdID= 40432  "
        ::= { iquav10CmdEntry 40432 }


    iquav10Embed18Embed1Mute12 OBJECT-TYPE
        SYNTAX            INTEGER { disable(0), enable(1)  }
        MAX-ACCESS        read-write
        STATUS            current
        DESCRIPTION
                "CMNT: - 
                 TYPE: - Checkbox
                 PAGE: - Embed1-8
                    Mute1_2  cmdID= 40433  "
        ::= { iquav10CmdEntry 40433 }


    iquav10Embed18Embed1Stereo1 OBJECT-TYPE
        SYNTAX            INTEGER { disable(0), enable(1)  }
        MAX-ACCESS        read-write
        STATUS            current
        DESCRIPTION
                "CMNT: - 
                 TYPE: - Checkbox
                 PAGE: - Embed1-8
                    Stereo1  cmdID= 40448  "
        ::= { iquav10CmdEntry 40448 }


    iquav10Embed18Embed1dolbyLine OBJECT-TYPE
        SYNTAX            RollCallString
        MAX-ACCESS        read-only
        STATUS            current
        DESCRIPTION
                "CMNT: - 
                 TYPE: - Display
                 PAGE: - Embed1-8
                    dolbyLine  cmdID= 40081  "
        ::= { iquav10CmdEntry 40081 }


    iquav10AudioOutputEmbed18Embed21procamp OBJECT-TYPE
        SYNTAX            INTEGER
        MAX-ACCESS        read-write
        STATUS            current
        DESCRIPTION
                "CMNT: - Embed Proc Amp Gain
                 TYPE: - Number
                 PAGE: - AudioOutput
                    Embed2_1_procamp  cmdID= 40402
                    min= -801  max= 120  step= 1  format= %0.1f dB  div_scale= 10  preset= 0
                    Min = -80.1 dB  Max = 12.0 dB  Step = 0.1 dB  Preset = 0.0 dB  "
        ::= { iquav10CmdEntry 40402 }


    iquav10AudioOutputEmbed18Embed22procamp OBJECT-TYPE
        SYNTAX            INTEGER
        MAX-ACCESS        read-write
        STATUS            current
        DESCRIPTION
                "CMNT: - Embed Proc Amp Gain
                 TYPE: - Number
                 PAGE: - AudioOutput
                    Embed2_2_procamp  cmdID= 40403
                    min= -801  max= 120  step= 1  format= %0.1f dB  div_scale= 10  preset= 0
                    Min = -80.1 dB  Max = 12.0 dB  Step = 0.1 dB  Preset = 0.0 dB  "
        ::= { iquav10CmdEntry 40403 }


    iquav10Embed18Embed2Mute21 OBJECT-TYPE
        SYNTAX            INTEGER { disable(0), enable(1)  }
        MAX-ACCESS        read-write
        STATUS            current
        DESCRIPTION
                "CMNT: - 
                 TYPE: - Checkbox
                 PAGE: - Embed1-8
                    Mute2_1  cmdID= 40434  "
        ::= { iquav10CmdEntry 40434 }


    iquav10Embed18Embed2Mute22 OBJECT-TYPE
        SYNTAX            INTEGER { disable(0), enable(1)  }
        MAX-ACCESS        read-write
        STATUS            current
        DESCRIPTION
                "CMNT: - 
                 TYPE: - Checkbox
                 PAGE: - Embed1-8
                    Mute2_2  cmdID= 40435  "
        ::= { iquav10CmdEntry 40435 }


    iquav10Embed18Embed2Stereo2 OBJECT-TYPE
        SYNTAX            INTEGER { disable(0), enable(1)  }
        MAX-ACCESS        read-write
        STATUS            current
        DESCRIPTION
                "CMNT: - 
                 TYPE: - Checkbox
                 PAGE: - Embed1-8
                    Stereo2  cmdID= 40449  "
        ::= { iquav10CmdEntry 40449 }


    iquav10Embed18Embed2dolbyLine OBJECT-TYPE
        SYNTAX            RollCallString
        MAX-ACCESS        read-only
        STATUS            current
        DESCRIPTION
                "CMNT: - 
                 TYPE: - Display
                 PAGE: - Embed1-8
                    dolbyLine  cmdID= 40082  "
        ::= { iquav10CmdEntry 40082 }


    iquav10AudioOutputEmbed18Embed31procamp OBJECT-TYPE
        SYNTAX            INTEGER
        MAX-ACCESS        read-write
        STATUS            current
        DESCRIPTION
                "CMNT: - Embed Proc Amp Gain
                 TYPE: - Number
                 PAGE: - AudioOutput
                    Embed3_1_procamp  cmdID= 40404
                    min= -801  max= 120  step= 1  format= %0.1f dB  div_scale= 10  preset= 0
                    Min = -80.1 dB  Max = 12.0 dB  Step = 0.1 dB  Preset = 0.0 dB  "
        ::= { iquav10CmdEntry 40404 }


    iquav10AudioOutputEmbed18Embed32procamp OBJECT-TYPE
        SYNTAX            INTEGER
        MAX-ACCESS        read-write
        STATUS            current
        DESCRIPTION
                "CMNT: - Embed Proc Amp Gain
                 TYPE: - Number
                 PAGE: - AudioOutput
                    Embed3_2_procamp  cmdID= 40405
                    min= -801  max= 120  step= 1  format= %0.1f dB  div_scale= 10  preset= 0
                    Min = -80.1 dB  Max = 12.0 dB  Step = 0.1 dB  Preset = 0.0 dB  "
        ::= { iquav10CmdEntry 40405 }


    iquav10Embed18Embed3Mute31 OBJECT-TYPE
        SYNTAX            INTEGER { disable(0), enable(1)  }
        MAX-ACCESS        read-write
        STATUS            current
        DESCRIPTION
                "CMNT: - 
                 TYPE: - Checkbox
                 PAGE: - Embed1-8
                    Mute3_1  cmdID= 40436  "
        ::= { iquav10CmdEntry 40436 }


    iquav10Embed18Embed3Mute32 OBJECT-TYPE
        SYNTAX            INTEGER { disable(0), enable(1)  }
        MAX-ACCESS        read-write
        STATUS            current
        DESCRIPTION
                "CMNT: - 
                 TYPE: - Checkbox
                 PAGE: - Embed1-8
                    Mute3_2  cmdID= 40437  "
        ::= { iquav10CmdEntry 40437 }


    iquav10Embed18Embed3Stereo3 OBJECT-TYPE
        SYNTAX            INTEGER { disable(0), enable(1)  }
        MAX-ACCESS        read-write
        STATUS            current
        DESCRIPTION
                "CMNT: - 
                 TYPE: - Checkbox
                 PAGE: - Embed1-8
                    Stereo3  cmdID= 40450  "
        ::= { iquav10CmdEntry 40450 }


    iquav10Embed18Embed3dolbyLine OBJECT-TYPE
        SYNTAX            RollCallString
        MAX-ACCESS        read-only
        STATUS            current
        DESCRIPTION
                "CMNT: - 
                 TYPE: - Display
                 PAGE: - Embed1-8
                    dolbyLine  cmdID= 40083  "
        ::= { iquav10CmdEntry 40083 }


    iquav10AudioOutputEmbed18Embed41procamp OBJECT-TYPE
        SYNTAX            INTEGER
        MAX-ACCESS        read-write
        STATUS            current
        DESCRIPTION
                "CMNT: - Embed Proc Amp Gain
                 TYPE: - Number
                 PAGE: - AudioOutput
                    Embed4_1_procamp  cmdID= 40406
                    min= -801  max= 120  step= 1  format= %0.1f dB  div_scale= 10  preset= 0
                    Min = -80.1 dB  Max = 12.0 dB  Step = 0.1 dB  Preset = 0.0 dB  "
        ::= { iquav10CmdEntry 40406 }


    iquav10AudioOutputEmbed18Embed42procamp OBJECT-TYPE
        SYNTAX            INTEGER
        MAX-ACCESS        read-write
        STATUS            current
        DESCRIPTION
                "CMNT: - Embed Proc Amp Gain
                 TYPE: - Number
                 PAGE: - AudioOutput
                    Embed4_2_procamp  cmdID= 40407
                    min= -801  max= 120  step= 1  format= %0.1f dB  div_scale= 10  preset= 0
                    Min = -80.1 dB  Max = 12.0 dB  Step = 0.1 dB  Preset = 0.0 dB  "
        ::= { iquav10CmdEntry 40407 }


    iquav10Embed18Embed4Mute41 OBJECT-TYPE
        SYNTAX            INTEGER { disable(0), enable(1)  }
        MAX-ACCESS        read-write
        STATUS            current
        DESCRIPTION
                "CMNT: - 
                 TYPE: - Checkbox
                 PAGE: - Embed1-8
                    Mute4_1  cmdID= 40438  "
        ::= { iquav10CmdEntry 40438 }


    iquav10Embed18Embed4Mute42 OBJECT-TYPE
        SYNTAX            INTEGER { disable(0), enable(1)  }
        MAX-ACCESS        read-write
        STATUS            current
        DESCRIPTION
                "CMNT: - 
                 TYPE: - Checkbox
                 PAGE: - Embed1-8
                    Mute4_2  cmdID= 40439  "
        ::= { iquav10CmdEntry 40439 }


    iquav10Embed18Embed4Stereo4 OBJECT-TYPE
        SYNTAX            INTEGER { disable(0), enable(1)  }
        MAX-ACCESS        read-write
        STATUS            current
        DESCRIPTION
                "CMNT: - 
                 TYPE: - Checkbox
                 PAGE: - Embed1-8
                    Stereo4  cmdID= 40451  "
        ::= { iquav10CmdEntry 40451 }


    iquav10Embed18Embed4dolbyLine OBJECT-TYPE
        SYNTAX            RollCallString
        MAX-ACCESS        read-only
        STATUS            current
        DESCRIPTION
                "CMNT: - 
                 TYPE: - Display
                 PAGE: - Embed1-8
                    dolbyLine  cmdID= 40084  "
        ::= { iquav10CmdEntry 40084 }


    iquav10AudioOutputEmbed18Embed51procamp OBJECT-TYPE
        SYNTAX            INTEGER
        MAX-ACCESS        read-write
        STATUS            current
        DESCRIPTION
                "CMNT: - Embed Proc Amp Gain
                 TYPE: - Number
                 PAGE: - AudioOutput
                    Embed5_1_procamp  cmdID= 40408
                    min= -801  max= 120  step= 1  format= %0.1f dB  div_scale= 10  preset= 0
                    Min = -80.1 dB  Max = 12.0 dB  Step = 0.1 dB  Preset = 0.0 dB  "
        ::= { iquav10CmdEntry 40408 }


    iquav10AudioOutputEmbed18Embed52procamp OBJECT-TYPE
        SYNTAX            INTEGER
        MAX-ACCESS        read-write
        STATUS            current
        DESCRIPTION
                "CMNT: - Embed Proc Amp Gain
                 TYPE: - Number
                 PAGE: - AudioOutput
                    Embed5_2_procamp  cmdID= 40409
                    min= -801  max= 120  step= 1  format= %0.1f dB  div_scale= 10  preset= 0
                    Min = -80.1 dB  Max = 12.0 dB  Step = 0.1 dB  Preset = 0.0 dB  "
        ::= { iquav10CmdEntry 40409 }


    iquav10Embed18Embed5Mute51 OBJECT-TYPE
        SYNTAX            INTEGER { disable(0), enable(1)  }
        MAX-ACCESS        read-write
        STATUS            current
        DESCRIPTION
                "CMNT: - 
                 TYPE: - Checkbox
                 PAGE: - Embed1-8
                    Mute5_1  cmdID= 40440  "
        ::= { iquav10CmdEntry 40440 }


    iquav10Embed18Embed5Mute52 OBJECT-TYPE
        SYNTAX            INTEGER { disable(0), enable(1)  }
        MAX-ACCESS        read-write
        STATUS            current
        DESCRIPTION
                "CMNT: - 
                 TYPE: - Checkbox
                 PAGE: - Embed1-8
                    Mute5_2  cmdID= 40441  "
        ::= { iquav10CmdEntry 40441 }


    iquav10Embed18Embed5Stereo5 OBJECT-TYPE
        SYNTAX            INTEGER { disable(0), enable(1)  }
        MAX-ACCESS        read-write
        STATUS            current
        DESCRIPTION
                "CMNT: - 
                 TYPE: - Checkbox
                 PAGE: - Embed1-8
                    Stereo5  cmdID= 40452  "
        ::= { iquav10CmdEntry 40452 }


    iquav10Embed18Embed5dolbyLine OBJECT-TYPE
        SYNTAX            RollCallString
        MAX-ACCESS        read-only
        STATUS            current
        DESCRIPTION
                "CMNT: - 
                 TYPE: - Display
                 PAGE: - Embed1-8
                    dolbyLine  cmdID= 40085  "
        ::= { iquav10CmdEntry 40085 }


    iquav10AudioOutputEmbed18Embed61procamp OBJECT-TYPE
        SYNTAX            INTEGER
        MAX-ACCESS        read-write
        STATUS            current
        DESCRIPTION
                "CMNT: - Embed Proc Amp Gain
                 TYPE: - Number
                 PAGE: - AudioOutput
                    Embed6_1_procamp  cmdID= 40410
                    min= -801  max= 120  step= 1  format= %0.1f dB  div_scale= 10  preset= 0
                    Min = -80.1 dB  Max = 12.0 dB  Step = 0.1 dB  Preset = 0.0 dB  "
        ::= { iquav10CmdEntry 40410 }


    iquav10AudioOutputEmbed18Embed62procamp OBJECT-TYPE
        SYNTAX            INTEGER
        MAX-ACCESS        read-write
        STATUS            current
        DESCRIPTION
                "CMNT: - Embed Proc Amp Gain
                 TYPE: - Number
                 PAGE: - AudioOutput
                    Embed6_2_procamp  cmdID= 40411
                    min= -801  max= 120  step= 1  format= %0.1f dB  div_scale= 10  preset= 0
                    Min = -80.1 dB  Max = 12.0 dB  Step = 0.1 dB  Preset = 0.0 dB  "
        ::= { iquav10CmdEntry 40411 }


    iquav10Embed18Embed6Mute61 OBJECT-TYPE
        SYNTAX            INTEGER { disable(0), enable(1)  }
        MAX-ACCESS        read-write
        STATUS            current
        DESCRIPTION
                "CMNT: - 
                 TYPE: - Checkbox
                 PAGE: - Embed1-8
                    Mute6_1  cmdID= 40442  "
        ::= { iquav10CmdEntry 40442 }


    iquav10Embed18Embed6Mute62 OBJECT-TYPE
        SYNTAX            INTEGER { disable(0), enable(1)  }
        MAX-ACCESS        read-write
        STATUS            current
        DESCRIPTION
                "CMNT: - 
                 TYPE: - Checkbox
                 PAGE: - Embed1-8
                    Mute6_2  cmdID= 40443  "
        ::= { iquav10CmdEntry 40443 }


    iquav10Embed18Embed6Stereo6 OBJECT-TYPE
        SYNTAX            INTEGER { disable(0), enable(1)  }
        MAX-ACCESS        read-write
        STATUS            current
        DESCRIPTION
                "CMNT: - 
                 TYPE: - Checkbox
                 PAGE: - Embed1-8
                    Stereo6  cmdID= 40453  "
        ::= { iquav10CmdEntry 40453 }


    iquav10Embed18Embed6dolbyLine OBJECT-TYPE
        SYNTAX            RollCallString
        MAX-ACCESS        read-only
        STATUS            current
        DESCRIPTION
                "CMNT: - 
                 TYPE: - Display
                 PAGE: - Embed1-8
                    dolbyLine  cmdID= 40086  "
        ::= { iquav10CmdEntry 40086 }


    iquav10AudioOutputEmbed18Embed71procamp OBJECT-TYPE
        SYNTAX            INTEGER
        MAX-ACCESS        read-write
        STATUS            current
        DESCRIPTION
                "CMNT: - Embed Proc Amp Gain
                 TYPE: - Number
                 PAGE: - AudioOutput
                    Embed7_1_procamp  cmdID= 40412
                    min= -801  max= 120  step= 1  format= %0.1f dB  div_scale= 10  preset= 0
                    Min = -80.1 dB  Max = 12.0 dB  Step = 0.1 dB  Preset = 0.0 dB  "
        ::= { iquav10CmdEntry 40412 }


    iquav10AudioOutputEmbed18Embed72procamp OBJECT-TYPE
        SYNTAX            INTEGER
        MAX-ACCESS        read-write
        STATUS            current
        DESCRIPTION
                "CMNT: - Embed Proc Amp Gain
                 TYPE: - Number
                 PAGE: - AudioOutput
                    Embed7_2_procamp  cmdID= 40413
                    min= -801  max= 120  step= 1  format= %0.1f dB  div_scale= 10  preset= 0
                    Min = -80.1 dB  Max = 12.0 dB  Step = 0.1 dB  Preset = 0.0 dB  "
        ::= { iquav10CmdEntry 40413 }


    iquav10Embed18Embed7Mute71 OBJECT-TYPE
        SYNTAX            INTEGER { disable(0), enable(1)  }
        MAX-ACCESS        read-write
        STATUS            current
        DESCRIPTION
                "CMNT: - 
                 TYPE: - Checkbox
                 PAGE: - Embed1-8
                    Mute7_1  cmdID= 40444  "
        ::= { iquav10CmdEntry 40444 }


    iquav10Embed18Embed7Mute72 OBJECT-TYPE
        SYNTAX            INTEGER { disable(0), enable(1)  }
        MAX-ACCESS        read-write
        STATUS            current
        DESCRIPTION
                "CMNT: - 
                 TYPE: - Checkbox
                 PAGE: - Embed1-8
                    Mute7_2  cmdID= 40445  "
        ::= { iquav10CmdEntry 40445 }


    iquav10Embed18Embed7Stereo7 OBJECT-TYPE
        SYNTAX            INTEGER { disable(0), enable(1)  }
        MAX-ACCESS        read-write
        STATUS            current
        DESCRIPTION
                "CMNT: - 
                 TYPE: - Checkbox
                 PAGE: - Embed1-8
                    Stereo7  cmdID= 40454  "
        ::= { iquav10CmdEntry 40454 }


    iquav10Embed18Embed7dolbyLine OBJECT-TYPE
        SYNTAX            RollCallString
        MAX-ACCESS        read-only
        STATUS            current
        DESCRIPTION
                "CMNT: - 
                 TYPE: - Display
                 PAGE: - Embed1-8
                    dolbyLine  cmdID= 40087  "
        ::= { iquav10CmdEntry 40087 }


    iquav10AudioOutputEmbed18Embed81procamp OBJECT-TYPE
        SYNTAX            INTEGER
        MAX-ACCESS        read-write
        STATUS            current
        DESCRIPTION
                "CMNT: - Embed Proc Amp Gain
                 TYPE: - Number
                 PAGE: - AudioOutput
                    Embed8_1_procamp  cmdID= 40414
                    min= -801  max= 120  step= 1  format= %0.1f dB  div_scale= 10  preset= 0
                    Min = -80.1 dB  Max = 12.0 dB  Step = 0.1 dB  Preset = 0.0 dB  "
        ::= { iquav10CmdEntry 40414 }


    iquav10AudioOutputEmbed18Embed82procamp OBJECT-TYPE
        SYNTAX            INTEGER
        MAX-ACCESS        read-write
        STATUS            current
        DESCRIPTION
                "CMNT: - Embed Proc Amp Gain
                 TYPE: - Number
                 PAGE: - AudioOutput
                    Embed8_2_procamp  cmdID= 40415
                    min= -801  max= 120  step= 1  format= %0.1f dB  div_scale= 10  preset= 0
                    Min = -80.1 dB  Max = 12.0 dB  Step = 0.1 dB  Preset = 0.0 dB  "
        ::= { iquav10CmdEntry 40415 }


    iquav10Embed18Embed8Mute81 OBJECT-TYPE
        SYNTAX            INTEGER { disable(0), enable(1)  }
        MAX-ACCESS        read-write
        STATUS            current
        DESCRIPTION
                "CMNT: - 
                 TYPE: - Checkbox
                 PAGE: - Embed1-8
                    Mute8_1  cmdID= 40446  "
        ::= { iquav10CmdEntry 40446 }


    iquav10Embed18Embed8Mute82 OBJECT-TYPE
        SYNTAX            INTEGER { disable(0), enable(1)  }
        MAX-ACCESS        read-write
        STATUS            current
        DESCRIPTION
                "CMNT: - 
                 TYPE: - Checkbox
                 PAGE: - Embed1-8
                    Mute8_2  cmdID= 40447  "
        ::= { iquav10CmdEntry 40447 }


    iquav10Embed18Embed8Stereo8 OBJECT-TYPE
        SYNTAX            INTEGER { disable(0), enable(1)  }
        MAX-ACCESS        read-write
        STATUS            current
        DESCRIPTION
                "CMNT: - 
                 TYPE: - Checkbox
                 PAGE: - Embed1-8
                    Stereo8  cmdID= 40455  "
        ::= { iquav10CmdEntry 40455 }


    iquav10Embed18Embed8dolbyLine OBJECT-TYPE
        SYNTAX            RollCallString
        MAX-ACCESS        read-only
        STATUS            current
        DESCRIPTION
                "CMNT: - 
                 TYPE: - Display
                 PAGE: - Embed1-8
                    dolbyLine  cmdID= 40088  "
        ::= { iquav10CmdEntry 40088 }


    iquav10Embed18GroupEmbGroup1 OBJECT-TYPE
        SYNTAX            INTEGER { disable(0), enable(1)  }
        MAX-ACCESS        read-write
        STATUS            current
        DESCRIPTION
                "CMNT: - Audio group 1 enable
                 TYPE: - Checkbox
                 PAGE: - Embed1-8
                    EmbGroup1  cmdID= 36139  "
        ::= { iquav10CmdEntry 36139 }


    iquav10Embed18GroupEmbGroup2 OBJECT-TYPE
        SYNTAX            INTEGER { disable(0), enable(1)  }
        MAX-ACCESS        read-write
        STATUS            current
        DESCRIPTION
                "CMNT: - Audio group 2 enable
                 TYPE: - Checkbox
                 PAGE: - Embed1-8
                    EmbGroup2  cmdID= 36140  "
        ::= { iquav10CmdEntry 36140 }


    iquav10Embed18GroupEmbGroup3 OBJECT-TYPE
        SYNTAX            INTEGER { disable(0), enable(1)  }
        MAX-ACCESS        read-write
        STATUS            current
        DESCRIPTION
                "CMNT: - Audio group 3 enable
                 TYPE: - Checkbox
                 PAGE: - Embed1-8
                    EmbGroup3  cmdID= 36141  "
        ::= { iquav10CmdEntry 36141 }


    iquav10Embed18GroupEmbGroup4 OBJECT-TYPE
        SYNTAX            INTEGER { disable(0), enable(1)  }
        MAX-ACCESS        read-write
        STATUS            current
        DESCRIPTION
                "CMNT: - Audio group 4 enable
                 TYPE: - Checkbox
                 PAGE: - Embed1-8
                    EmbGroup4  cmdID= 36142  "
        ::= { iquav10CmdEntry 36142 }


    iquav10AudioOutputAESOutput18AESOutput11procamp OBJECT-TYPE
        SYNTAX            INTEGER
        MAX-ACCESS        read-write
        STATUS            current
        DESCRIPTION
                "CMNT: - AESOutput Proc Amp Gain
                 TYPE: - Number
                 PAGE: - AudioOutput
                    AESOutput1_1_procamp  cmdID= 40500
                    min= -801  max= 120  step= 1  format= %0.1f dB  div_scale= 10  preset= 0
                    Min = -80.1 dB  Max = 12.0 dB  Step = 0.1 dB  Preset = 0.0 dB  "
        ::= { iquav10CmdEntry 40500 }


    iquav10AudioOutputAESOutput18AESOutput12procamp OBJECT-TYPE
        SYNTAX            INTEGER
        MAX-ACCESS        read-write
        STATUS            current
        DESCRIPTION
                "CMNT: - AESOutput Proc Amp Gain
                 TYPE: - Number
                 PAGE: - AudioOutput
                    AESOutput1_2_procamp  cmdID= 40501
                    min= -801  max= 120  step= 1  format= %0.1f dB  div_scale= 10  preset= 0
                    Min = -80.1 dB  Max = 12.0 dB  Step = 0.1 dB  Preset = 0.0 dB  "
        ::= { iquav10CmdEntry 40501 }


    iquav10AESOutput18AESOutput1Mute11 OBJECT-TYPE
        SYNTAX            INTEGER { disable(0), enable(1)  }
        MAX-ACCESS        read-write
        STATUS            current
        DESCRIPTION
                "CMNT: - 
                 TYPE: - Checkbox
                 PAGE: - AESOutput1-8
                    Mute1_1  cmdID= 40532  "
        ::= { iquav10CmdEntry 40532 }


    iquav10AESOutput18AESOutput1Mute12 OBJECT-TYPE
        SYNTAX            INTEGER { disable(0), enable(1)  }
        MAX-ACCESS        read-write
        STATUS            current
        DESCRIPTION
                "CMNT: - 
                 TYPE: - Checkbox
                 PAGE: - AESOutput1-8
                    Mute1_2  cmdID= 40533  "
        ::= { iquav10CmdEntry 40533 }


    iquav10AESOutput18AESOutput1Stereo1 OBJECT-TYPE
        SYNTAX            INTEGER { disable(0), enable(1)  }
        MAX-ACCESS        read-write
        STATUS            current
        DESCRIPTION
                "CMNT: - 
                 TYPE: - Checkbox
                 PAGE: - AESOutput1-8
                    Stereo1  cmdID= 40548  "
        ::= { iquav10CmdEntry 40548 }


    iquav10AudioOutputAESOutput18AESOutput21procamp OBJECT-TYPE
        SYNTAX            INTEGER
        MAX-ACCESS        read-write
        STATUS            current
        DESCRIPTION
                "CMNT: - AESOutput Proc Amp Gain
                 TYPE: - Number
                 PAGE: - AudioOutput
                    AESOutput2_1_procamp  cmdID= 40502
                    min= -801  max= 120  step= 1  format= %0.1f dB  div_scale= 10  preset= 0
                    Min = -80.1 dB  Max = 12.0 dB  Step = 0.1 dB  Preset = 0.0 dB  "
        ::= { iquav10CmdEntry 40502 }


    iquav10AudioOutputAESOutput18AESOutput22procamp OBJECT-TYPE
        SYNTAX            INTEGER
        MAX-ACCESS        read-write
        STATUS            current
        DESCRIPTION
                "CMNT: - AESOutput Proc Amp Gain
                 TYPE: - Number
                 PAGE: - AudioOutput
                    AESOutput2_2_procamp  cmdID= 40503
                    min= -801  max= 120  step= 1  format= %0.1f dB  div_scale= 10  preset= 0
                    Min = -80.1 dB  Max = 12.0 dB  Step = 0.1 dB  Preset = 0.0 dB  "
        ::= { iquav10CmdEntry 40503 }


    iquav10AESOutput18AESOutput2Mute21 OBJECT-TYPE
        SYNTAX            INTEGER { disable(0), enable(1)  }
        MAX-ACCESS        read-write
        STATUS            current
        DESCRIPTION
                "CMNT: - 
                 TYPE: - Checkbox
                 PAGE: - AESOutput1-8
                    Mute2_1  cmdID= 40534  "
        ::= { iquav10CmdEntry 40534 }


    iquav10AESOutput18AESOutput2Mute22 OBJECT-TYPE
        SYNTAX            INTEGER { disable(0), enable(1)  }
        MAX-ACCESS        read-write
        STATUS            current
        DESCRIPTION
                "CMNT: - 
                 TYPE: - Checkbox
                 PAGE: - AESOutput1-8
                    Mute2_2  cmdID= 40535  "
        ::= { iquav10CmdEntry 40535 }


    iquav10AESOutput18AESOutput2Stereo2 OBJECT-TYPE
        SYNTAX            INTEGER { disable(0), enable(1)  }
        MAX-ACCESS        read-write
        STATUS            current
        DESCRIPTION
                "CMNT: - 
                 TYPE: - Checkbox
                 PAGE: - AESOutput1-8
                    Stereo2  cmdID= 40549  "
        ::= { iquav10CmdEntry 40549 }


    iquav10AudioOutputAESOutput18AESOutput31procamp OBJECT-TYPE
        SYNTAX            INTEGER
        MAX-ACCESS        read-write
        STATUS            current
        DESCRIPTION
                "CMNT: - AESOutput Proc Amp Gain
                 TYPE: - Number
                 PAGE: - AudioOutput
                    AESOutput3_1_procamp  cmdID= 40504
                    min= -801  max= 120  step= 1  format= %0.1f dB  div_scale= 10  preset= 0
                    Min = -80.1 dB  Max = 12.0 dB  Step = 0.1 dB  Preset = 0.0 dB  "
        ::= { iquav10CmdEntry 40504 }


    iquav10AudioOutputAESOutput18AESOutput32procamp OBJECT-TYPE
        SYNTAX            INTEGER
        MAX-ACCESS        read-write
        STATUS            current
        DESCRIPTION
                "CMNT: - AESOutput Proc Amp Gain
                 TYPE: - Number
                 PAGE: - AudioOutput
                    AESOutput3_2_procamp  cmdID= 40505
                    min= -801  max= 120  step= 1  format= %0.1f dB  div_scale= 10  preset= 0
                    Min = -80.1 dB  Max = 12.0 dB  Step = 0.1 dB  Preset = 0.0 dB  "
        ::= { iquav10CmdEntry 40505 }


    iquav10AESOutput18AESOutput3Mute31 OBJECT-TYPE
        SYNTAX            INTEGER { disable(0), enable(1)  }
        MAX-ACCESS        read-write
        STATUS            current
        DESCRIPTION
                "CMNT: - 
                 TYPE: - Checkbox
                 PAGE: - AESOutput1-8
                    Mute3_1  cmdID= 40536  "
        ::= { iquav10CmdEntry 40536 }


    iquav10AESOutput18AESOutput3Mute32 OBJECT-TYPE
        SYNTAX            INTEGER { disable(0), enable(1)  }
        MAX-ACCESS        read-write
        STATUS            current
        DESCRIPTION
                "CMNT: - 
                 TYPE: - Checkbox
                 PAGE: - AESOutput1-8
                    Mute3_2  cmdID= 40537  "
        ::= { iquav10CmdEntry 40537 }


    iquav10AESOutput18AESOutput3Stereo3 OBJECT-TYPE
        SYNTAX            INTEGER { disable(0), enable(1)  }
        MAX-ACCESS        read-write
        STATUS            current
        DESCRIPTION
                "CMNT: - 
                 TYPE: - Checkbox
                 PAGE: - AESOutput1-8
                    Stereo3  cmdID= 40550  "
        ::= { iquav10CmdEntry 40550 }


    iquav10AudioOutputAESOutput18AESOutput41procamp OBJECT-TYPE
        SYNTAX            INTEGER
        MAX-ACCESS        read-write
        STATUS            current
        DESCRIPTION
                "CMNT: - AESOutput Proc Amp Gain
                 TYPE: - Number
                 PAGE: - AudioOutput
                    AESOutput4_1_procamp  cmdID= 40506
                    min= -801  max= 120  step= 1  format= %0.1f dB  div_scale= 10  preset= 0
                    Min = -80.1 dB  Max = 12.0 dB  Step = 0.1 dB  Preset = 0.0 dB  "
        ::= { iquav10CmdEntry 40506 }


    iquav10AudioOutputAESOutput18AESOutput42procamp OBJECT-TYPE
        SYNTAX            INTEGER
        MAX-ACCESS        read-write
        STATUS            current
        DESCRIPTION
                "CMNT: - AESOutput Proc Amp Gain
                 TYPE: - Number
                 PAGE: - AudioOutput
                    AESOutput4_2_procamp  cmdID= 40507
                    min= -801  max= 120  step= 1  format= %0.1f dB  div_scale= 10  preset= 0
                    Min = -80.1 dB  Max = 12.0 dB  Step = 0.1 dB  Preset = 0.0 dB  "
        ::= { iquav10CmdEntry 40507 }


    iquav10AESOutput18AESOutput4Mute41 OBJECT-TYPE
        SYNTAX            INTEGER { disable(0), enable(1)  }
        MAX-ACCESS        read-write
        STATUS            current
        DESCRIPTION
                "CMNT: - 
                 TYPE: - Checkbox
                 PAGE: - AESOutput1-8
                    Mute4_1  cmdID= 40538  "
        ::= { iquav10CmdEntry 40538 }


    iquav10AESOutput18AESOutput4Mute42 OBJECT-TYPE
        SYNTAX            INTEGER { disable(0), enable(1)  }
        MAX-ACCESS        read-write
        STATUS            current
        DESCRIPTION
                "CMNT: - 
                 TYPE: - Checkbox
                 PAGE: - AESOutput1-8
                    Mute4_2  cmdID= 40539  "
        ::= { iquav10CmdEntry 40539 }


    iquav10AESOutput18AESOutput4Stereo4 OBJECT-TYPE
        SYNTAX            INTEGER { disable(0), enable(1)  }
        MAX-ACCESS        read-write
        STATUS            current
        DESCRIPTION
                "CMNT: - 
                 TYPE: - Checkbox
                 PAGE: - AESOutput1-8
                    Stereo4  cmdID= 40551  "
        ::= { iquav10CmdEntry 40551 }


    iquav10AudioOutputAESOutput18AESOutput51procamp OBJECT-TYPE
        SYNTAX            INTEGER
        MAX-ACCESS        read-write
        STATUS            current
        DESCRIPTION
                "CMNT: - AESOutput Proc Amp Gain
                 TYPE: - Number
                 PAGE: - AudioOutput
                    AESOutput5_1_procamp  cmdID= 40508
                    min= -801  max= 120  step= 1  format= %0.1f dB  div_scale= 10  preset= 0
                    Min = -80.1 dB  Max = 12.0 dB  Step = 0.1 dB  Preset = 0.0 dB  "
        ::= { iquav10CmdEntry 40508 }


    iquav10AudioOutputAESOutput18AESOutput52procamp OBJECT-TYPE
        SYNTAX            INTEGER
        MAX-ACCESS        read-write
        STATUS            current
        DESCRIPTION
                "CMNT: - AESOutput Proc Amp Gain
                 TYPE: - Number
                 PAGE: - AudioOutput
                    AESOutput5_2_procamp  cmdID= 40509
                    min= -801  max= 120  step= 1  format= %0.1f dB  div_scale= 10  preset= 0
                    Min = -80.1 dB  Max = 12.0 dB  Step = 0.1 dB  Preset = 0.0 dB  "
        ::= { iquav10CmdEntry 40509 }


    iquav10AESOutput18AESOutput5Mute51 OBJECT-TYPE
        SYNTAX            INTEGER { disable(0), enable(1)  }
        MAX-ACCESS        read-write
        STATUS            current
        DESCRIPTION
                "CMNT: - 
                 TYPE: - Checkbox
                 PAGE: - AESOutput1-8
                    Mute5_1  cmdID= 40540  "
        ::= { iquav10CmdEntry 40540 }


    iquav10AESOutput18AESOutput5Mute52 OBJECT-TYPE
        SYNTAX            INTEGER { disable(0), enable(1)  }
        MAX-ACCESS        read-write
        STATUS            current
        DESCRIPTION
                "CMNT: - 
                 TYPE: - Checkbox
                 PAGE: - AESOutput1-8
                    Mute5_2  cmdID= 40541  "
        ::= { iquav10CmdEntry 40541 }


    iquav10AESOutput18AESOutput5Stereo5 OBJECT-TYPE
        SYNTAX            INTEGER { disable(0), enable(1)  }
        MAX-ACCESS        read-write
        STATUS            current
        DESCRIPTION
                "CMNT: - 
                 TYPE: - Checkbox
                 PAGE: - AESOutput1-8
                    Stereo5  cmdID= 40552  "
        ::= { iquav10CmdEntry 40552 }


    iquav10AudioOutputAESOutput18AESOutput61procamp OBJECT-TYPE
        SYNTAX            INTEGER
        MAX-ACCESS        read-write
        STATUS            current
        DESCRIPTION
                "CMNT: - AESOutput Proc Amp Gain
                 TYPE: - Number
                 PAGE: - AudioOutput
                    AESOutput6_1_procamp  cmdID= 40510
                    min= -801  max= 120  step= 1  format= %0.1f dB  div_scale= 10  preset= 0
                    Min = -80.1 dB  Max = 12.0 dB  Step = 0.1 dB  Preset = 0.0 dB  "
        ::= { iquav10CmdEntry 40510 }


    iquav10AudioOutputAESOutput18AESOutput62procamp OBJECT-TYPE
        SYNTAX            INTEGER
        MAX-ACCESS        read-write
        STATUS            current
        DESCRIPTION
                "CMNT: - AESOutput Proc Amp Gain
                 TYPE: - Number
                 PAGE: - AudioOutput
                    AESOutput6_2_procamp  cmdID= 40511
                    min= -801  max= 120  step= 1  format= %0.1f dB  div_scale= 10  preset= 0
                    Min = -80.1 dB  Max = 12.0 dB  Step = 0.1 dB  Preset = 0.0 dB  "
        ::= { iquav10CmdEntry 40511 }


    iquav10AESOutput18AESOutput6Mute61 OBJECT-TYPE
        SYNTAX            INTEGER { disable(0), enable(1)  }
        MAX-ACCESS        read-write
        STATUS            current
        DESCRIPTION
                "CMNT: - 
                 TYPE: - Checkbox
                 PAGE: - AESOutput1-8
                    Mute6_1  cmdID= 40542  "
        ::= { iquav10CmdEntry 40542 }


    iquav10AESOutput18AESOutput6Mute62 OBJECT-TYPE
        SYNTAX            INTEGER { disable(0), enable(1)  }
        MAX-ACCESS        read-write
        STATUS            current
        DESCRIPTION
                "CMNT: - 
                 TYPE: - Checkbox
                 PAGE: - AESOutput1-8
                    Mute6_2  cmdID= 40543  "
        ::= { iquav10CmdEntry 40543 }


    iquav10AESOutput18AESOutput6Stereo6 OBJECT-TYPE
        SYNTAX            INTEGER { disable(0), enable(1)  }
        MAX-ACCESS        read-write
        STATUS            current
        DESCRIPTION
                "CMNT: - 
                 TYPE: - Checkbox
                 PAGE: - AESOutput1-8
                    Stereo6  cmdID= 40553  "
        ::= { iquav10CmdEntry 40553 }


    iquav10AudioOutputAESOutput18AESOutput71procamp OBJECT-TYPE
        SYNTAX            INTEGER
        MAX-ACCESS        read-write
        STATUS            current
        DESCRIPTION
                "CMNT: - AESOutput Proc Amp Gain
                 TYPE: - Number
                 PAGE: - AudioOutput
                    AESOutput7_1_procamp  cmdID= 40512
                    min= -801  max= 120  step= 1  format= %0.1f dB  div_scale= 10  preset= 0
                    Min = -80.1 dB  Max = 12.0 dB  Step = 0.1 dB  Preset = 0.0 dB  "
        ::= { iquav10CmdEntry 40512 }


    iquav10AudioOutputAESOutput18AESOutput72procamp OBJECT-TYPE
        SYNTAX            INTEGER
        MAX-ACCESS        read-write
        STATUS            current
        DESCRIPTION
                "CMNT: - AESOutput Proc Amp Gain
                 TYPE: - Number
                 PAGE: - AudioOutput
                    AESOutput7_2_procamp  cmdID= 40513
                    min= -801  max= 120  step= 1  format= %0.1f dB  div_scale= 10  preset= 0
                    Min = -80.1 dB  Max = 12.0 dB  Step = 0.1 dB  Preset = 0.0 dB  "
        ::= { iquav10CmdEntry 40513 }


    iquav10AESOutput18AESOutput7Mute71 OBJECT-TYPE
        SYNTAX            INTEGER { disable(0), enable(1)  }
        MAX-ACCESS        read-write
        STATUS            current
        DESCRIPTION
                "CMNT: - 
                 TYPE: - Checkbox
                 PAGE: - AESOutput1-8
                    Mute7_1  cmdID= 40544  "
        ::= { iquav10CmdEntry 40544 }


    iquav10AESOutput18AESOutput7Mute72 OBJECT-TYPE
        SYNTAX            INTEGER { disable(0), enable(1)  }
        MAX-ACCESS        read-write
        STATUS            current
        DESCRIPTION
                "CMNT: - 
                 TYPE: - Checkbox
                 PAGE: - AESOutput1-8
                    Mute7_2  cmdID= 40545  "
        ::= { iquav10CmdEntry 40545 }


    iquav10AESOutput18AESOutput7Stereo7 OBJECT-TYPE
        SYNTAX            INTEGER { disable(0), enable(1)  }
        MAX-ACCESS        read-write
        STATUS            current
        DESCRIPTION
                "CMNT: - 
                 TYPE: - Checkbox
                 PAGE: - AESOutput1-8
                    Stereo7  cmdID= 40554  "
        ::= { iquav10CmdEntry 40554 }


    iquav10AudioOutputAESOutput18AESOutput81procamp OBJECT-TYPE
        SYNTAX            INTEGER
        MAX-ACCESS        read-write
        STATUS            current
        DESCRIPTION
                "CMNT: - AESOutput Proc Amp Gain
                 TYPE: - Number
                 PAGE: - AudioOutput
                    AESOutput8_1_procamp  cmdID= 40514
                    min= -801  max= 120  step= 1  format= %0.1f dB  div_scale= 10  preset= 0
                    Min = -80.1 dB  Max = 12.0 dB  Step = 0.1 dB  Preset = 0.0 dB  "
        ::= { iquav10CmdEntry 40514 }


    iquav10AudioOutputAESOutput18AESOutput82procamp OBJECT-TYPE
        SYNTAX            INTEGER
        MAX-ACCESS        read-write
        STATUS            current
        DESCRIPTION
                "CMNT: - AESOutput Proc Amp Gain
                 TYPE: - Number
                 PAGE: - AudioOutput
                    AESOutput8_2_procamp  cmdID= 40515
                    min= -801  max= 120  step= 1  format= %0.1f dB  div_scale= 10  preset= 0
                    Min = -80.1 dB  Max = 12.0 dB  Step = 0.1 dB  Preset = 0.0 dB  "
        ::= { iquav10CmdEntry 40515 }


    iquav10AESOutput18AESOutput8Mute81 OBJECT-TYPE
        SYNTAX            INTEGER { disable(0), enable(1)  }
        MAX-ACCESS        read-write
        STATUS            current
        DESCRIPTION
                "CMNT: - 
                 TYPE: - Checkbox
                 PAGE: - AESOutput1-8
                    Mute8_1  cmdID= 40546  "
        ::= { iquav10CmdEntry 40546 }


    iquav10AESOutput18AESOutput8Mute82 OBJECT-TYPE
        SYNTAX            INTEGER { disable(0), enable(1)  }
        MAX-ACCESS        read-write
        STATUS            current
        DESCRIPTION
                "CMNT: - 
                 TYPE: - Checkbox
                 PAGE: - AESOutput1-8
                    Mute8_2  cmdID= 40547  "
        ::= { iquav10CmdEntry 40547 }


    iquav10AESOutput18AESOutput8Stereo8 OBJECT-TYPE
        SYNTAX            INTEGER { disable(0), enable(1)  }
        MAX-ACCESS        read-write
        STATUS            current
        DESCRIPTION
                "CMNT: - 
                 TYPE: - Checkbox
                 PAGE: - AESOutput1-8
                    Stereo8  cmdID= 40555  "
        ::= { iquav10CmdEntry 40555 }


    iquav10AudioOutputAnalogOutput12AnalogOutput11procamp OBJECT-TYPE
        SYNTAX            INTEGER
        MAX-ACCESS        read-write
        STATUS            current
        DESCRIPTION
                "CMNT: - AnalogOutput Proc Amp Gain
                 TYPE: - Number
                 PAGE: - AudioOutput
                    AnalogOutput1_1_procamp  cmdID= 40572
                    min= -801  max= 120  step= 1  format= %0.1f dB  div_scale= 10  preset= 0
                    Min = -80.1 dB  Max = 12.0 dB  Step = 0.1 dB  Preset = 0.0 dB  "
        ::= { iquav10CmdEntry 40572 }


    iquav10AudioOutputAnalogOutput12AnalogOutput12procamp OBJECT-TYPE
        SYNTAX            INTEGER
        MAX-ACCESS        read-write
        STATUS            current
        DESCRIPTION
                "CMNT: - AnalogOutput Proc Amp Gain
                 TYPE: - Number
                 PAGE: - AudioOutput
                    AnalogOutput1_2_procamp  cmdID= 40573
                    min= -801  max= 120  step= 1  format= %0.1f dB  div_scale= 10  preset= 0
                    Min = -80.1 dB  Max = 12.0 dB  Step = 0.1 dB  Preset = 0.0 dB  "
        ::= { iquav10CmdEntry 40573 }


    iquav10AnalogOutput12AnalogOutput1Mute11 OBJECT-TYPE
        SYNTAX            INTEGER { disable(0), enable(1)  }
        MAX-ACCESS        read-write
        STATUS            current
        DESCRIPTION
                "CMNT: - 
                 TYPE: - Checkbox
                 PAGE: - AnalogOutput1-2
                    Mute1_1  cmdID= 40576  "
        ::= { iquav10CmdEntry 40576 }


    iquav10AnalogOutput12AnalogOutput1Mute12 OBJECT-TYPE
        SYNTAX            INTEGER { disable(0), enable(1)  }
        MAX-ACCESS        read-write
        STATUS            current
        DESCRIPTION
                "CMNT: - 
                 TYPE: - Checkbox
                 PAGE: - AnalogOutput1-2
                    Mute1_2  cmdID= 40577  "
        ::= { iquav10CmdEntry 40577 }


    iquav10AnalogOutput12AnalogOutput1Stereo1 OBJECT-TYPE
        SYNTAX            INTEGER { disable(0), enable(1)  }
        MAX-ACCESS        read-write
        STATUS            current
        DESCRIPTION
                "CMNT: - 
                 TYPE: - Checkbox
                 PAGE: - AnalogOutput1-2
                    Stereo1  cmdID= 40580  "
        ::= { iquav10CmdEntry 40580 }


    iquav10AudioOutputAnalogOutput12AnalogOutput21procamp OBJECT-TYPE
        SYNTAX            INTEGER
        MAX-ACCESS        read-write
        STATUS            current
        DESCRIPTION
                "CMNT: - AnalogOutput Proc Amp Gain
                 TYPE: - Number
                 PAGE: - AudioOutput
                    AnalogOutput2_1_procamp  cmdID= 40574
                    min= -801  max= 120  step= 1  format= %0.1f dB  div_scale= 10  preset= 0
                    Min = -80.1 dB  Max = 12.0 dB  Step = 0.1 dB  Preset = 0.0 dB  "
        ::= { iquav10CmdEntry 40574 }


    iquav10AudioOutputAnalogOutput12AnalogOutput22procamp OBJECT-TYPE
        SYNTAX            INTEGER
        MAX-ACCESS        read-write
        STATUS            current
        DESCRIPTION
                "CMNT: - AnalogOutput Proc Amp Gain
                 TYPE: - Number
                 PAGE: - AudioOutput
                    AnalogOutput2_2_procamp  cmdID= 40575
                    min= -801  max= 120  step= 1  format= %0.1f dB  div_scale= 10  preset= 0
                    Min = -80.1 dB  Max = 12.0 dB  Step = 0.1 dB  Preset = 0.0 dB  "
        ::= { iquav10CmdEntry 40575 }


    iquav10AnalogOutput12AnalogOutput2Mute21 OBJECT-TYPE
        SYNTAX            INTEGER { disable(0), enable(1)  }
        MAX-ACCESS        read-write
        STATUS            current
        DESCRIPTION
                "CMNT: - 
                 TYPE: - Checkbox
                 PAGE: - AnalogOutput1-2
                    Mute2_1  cmdID= 40578  "
        ::= { iquav10CmdEntry 40578 }


    iquav10AnalogOutput12AnalogOutput2Mute22 OBJECT-TYPE
        SYNTAX            INTEGER { disable(0), enable(1)  }
        MAX-ACCESS        read-write
        STATUS            current
        DESCRIPTION
                "CMNT: - 
                 TYPE: - Checkbox
                 PAGE: - AnalogOutput1-2
                    Mute2_2  cmdID= 40579  "
        ::= { iquav10CmdEntry 40579 }


    iquav10AnalogOutput12AnalogOutput2Stereo2 OBJECT-TYPE
        SYNTAX            INTEGER { disable(0), enable(1)  }
        MAX-ACCESS        read-write
        STATUS            current
        DESCRIPTION
                "CMNT: - 
                 TYPE: - Checkbox
                 PAGE: - AnalogOutput1-2
                    Stereo2  cmdID= 40581  "
        ::= { iquav10CmdEntry 40581 }


    iquav10AudSetupDelaySelectTotalDelayBus1 OBJECT-TYPE
        SYNTAX            RollCallString
        MAX-ACCESS        read-only
        STATUS            current
        DESCRIPTION
                "CMNT: - Set Manual delay
                 TYPE: - Display
                 PAGE: - AudSetup
                    TotalDelayBus1  cmdID= 40656  "
        ::= { iquav10CmdEntry 40656 }


    iquav10AudSetupDelaySelectTotalDelayBus2 OBJECT-TYPE
        SYNTAX            RollCallString
        MAX-ACCESS        read-only
        STATUS            current
        DESCRIPTION
                "CMNT: - Set Manual delay
                 TYPE: - Display
                 PAGE: - AudSetup
                    TotalDelayBus2  cmdID= 40657  "
        ::= { iquav10CmdEntry 40657 }


    iquav10AudSetupDelaySelectTotalDelayBus3 OBJECT-TYPE
        SYNTAX            RollCallString
        MAX-ACCESS        read-only
        STATUS            current
        DESCRIPTION
                "CMNT: - Set Manual delay
                 TYPE: - Display
                 PAGE: - AudSetup
                    TotalDelayBus3  cmdID= 40658  "
        ::= { iquav10CmdEntry 40658 }


    iquav10AudSetupDelaySelectTotalDelayBus4 OBJECT-TYPE
        SYNTAX            RollCallString
        MAX-ACCESS        read-only
        STATUS            current
        DESCRIPTION
                "CMNT: - Set Manual delay
                 TYPE: - Display
                 PAGE: - AudSetup
                    TotalDelayBus4  cmdID= 40659  "
        ::= { iquav10CmdEntry 40659 }


    iquav10AudSetupDelaySelectTotalDelayBus5 OBJECT-TYPE
        SYNTAX            RollCallString
        MAX-ACCESS        read-only
        STATUS            current
        DESCRIPTION
                "CMNT: - Set Manual delay
                 TYPE: - Display
                 PAGE: - AudSetup
                    TotalDelayBus5  cmdID= 40660  "
        ::= { iquav10CmdEntry 40660 }


    iquav10AudSetupDelaySelectTotalDelayBus6 OBJECT-TYPE
        SYNTAX            RollCallString
        MAX-ACCESS        read-only
        STATUS            current
        DESCRIPTION
                "CMNT: - Set Manual delay
                 TYPE: - Display
                 PAGE: - AudSetup
                    TotalDelayBus6  cmdID= 40661  "
        ::= { iquav10CmdEntry 40661 }


    iquav10AudSetupDelaySelectTotalDelayBus7 OBJECT-TYPE
        SYNTAX            RollCallString
        MAX-ACCESS        read-only
        STATUS            current
        DESCRIPTION
                "CMNT: - Set Manual delay
                 TYPE: - Display
                 PAGE: - AudSetup
                    TotalDelayBus7  cmdID= 40662  "
        ::= { iquav10CmdEntry 40662 }


    iquav10AudSetupDelaySelectTotalDelayBus8 OBJECT-TYPE
        SYNTAX            RollCallString
        MAX-ACCESS        read-only
        STATUS            current
        DESCRIPTION
                "CMNT: - Set Manual delay
                 TYPE: - Display
                 PAGE: - AudSetup
                    TotalDelayBus8  cmdID= 40663  "
        ::= { iquav10CmdEntry 40663 }


    iquav10AudSetupDelaySelectBus1Delay OBJECT-TYPE
        SYNTAX            INTEGER
        MAX-ACCESS        read-write
        STATUS            current
        DESCRIPTION
                "CMNT: - Set Manual delay
                 TYPE: - Number
                 PAGE: - AudSetup
                    Bus 1 Delay  cmdID= 40648
                    min= -1995  max= 1995  step= 1  format= %d  div_scale= 1  preset= 0
                    Min = 0  Max = 0  Step = 0  Preset = 0  "
        ::= { iquav10CmdEntry 40648 }


    iquav10AudSetupDelaySelectBus2Delay OBJECT-TYPE
        SYNTAX            INTEGER
        MAX-ACCESS        read-write
        STATUS            current
        DESCRIPTION
                "CMNT: - Set Manual delay
                 TYPE: - Number
                 PAGE: - AudSetup
                    Bus 2 Delay  cmdID= 40649
                    min= -1995  max= 1995  step= 1  format= %d  div_scale= 1  preset= 0
                    Min = 0  Max = 0  Step = 0  Preset = 0  "
        ::= { iquav10CmdEntry 40649 }


    iquav10AudSetupDelaySelectBus3Delay OBJECT-TYPE
        SYNTAX            INTEGER
        MAX-ACCESS        read-write
        STATUS            current
        DESCRIPTION
                "CMNT: - Set Manual delay
                 TYPE: - Number
                 PAGE: - AudSetup
                    Bus 3 Delay  cmdID= 40650
                    min= -1995  max= 1995  step= 1  format= %d  div_scale= 1  preset= 0
                    Min = 0  Max = 0  Step = 0  Preset = 0  "
        ::= { iquav10CmdEntry 40650 }


    iquav10AudSetupDelaySelectBus4Delay OBJECT-TYPE
        SYNTAX            INTEGER
        MAX-ACCESS        read-write
        STATUS            current
        DESCRIPTION
                "CMNT: - Set Manual delay
                 TYPE: - Number
                 PAGE: - AudSetup
                    Bus 4 Delay  cmdID= 40651
                    min= -1995  max= 1995  step= 1  format= %d  div_scale= 1  preset= 0
                    Min = 0  Max = 0  Step = 0  Preset = 0  "
        ::= { iquav10CmdEntry 40651 }


    iquav10AudSetupDelaySelectBus5Delay OBJECT-TYPE
        SYNTAX            INTEGER
        MAX-ACCESS        read-write
        STATUS            current
        DESCRIPTION
                "CMNT: - Set Manual delay
                 TYPE: - Number
                 PAGE: - AudSetup
                    Bus 5 Delay  cmdID= 40652
                    min= -1995  max= 1995  step= 1  format= %d  div_scale= 1  preset= 0
                    Min = 0  Max = 0  Step = 0  Preset = 0  "
        ::= { iquav10CmdEntry 40652 }


    iquav10AudSetupDelaySelectBus6Delay OBJECT-TYPE
        SYNTAX            INTEGER
        MAX-ACCESS        read-write
        STATUS            current
        DESCRIPTION
                "CMNT: - Set Manual delay
                 TYPE: - Number
                 PAGE: - AudSetup
                    Bus 6 Delay  cmdID= 40653
                    min= -1995  max= 1995  step= 1  format= %d  div_scale= 1  preset= 0
                    Min = 0  Max = 0  Step = 0  Preset = 0  "
        ::= { iquav10CmdEntry 40653 }


    iquav10AudSetupDelaySelectBus7Delay OBJECT-TYPE
        SYNTAX            INTEGER
        MAX-ACCESS        read-write
        STATUS            current
        DESCRIPTION
                "CMNT: - Set Manual delay
                 TYPE: - Number
                 PAGE: - AudSetup
                    Bus 7 Delay  cmdID= 40654
                    min= -1995  max= 1995  step= 1  format= %d  div_scale= 1  preset= 0
                    Min = 0  Max = 0  Step = 0  Preset = 0  "
        ::= { iquav10CmdEntry 40654 }


    iquav10AudSetupDelaySelectBus8Delay OBJECT-TYPE
        SYNTAX            INTEGER
        MAX-ACCESS        read-write
        STATUS            current
        DESCRIPTION
                "CMNT: - Set Manual delay
                 TYPE: - Number
                 PAGE: - AudSetup
                    Bus 8 Delay  cmdID= 40655
                    min= -1995  max= 1995  step= 1  format= %d  div_scale= 1  preset= 0
                    Min = 0  Max = 0  Step = 0  Preset = 0  "
        ::= { iquav10CmdEntry 40655 }


    iquav10AudSetupDelaySelectBus1Fine OBJECT-TYPE
        SYNTAX            INTEGER
        MAX-ACCESS        read-write
        STATUS            current
        DESCRIPTION
                "CMNT: - Set Manual delay
                 TYPE: - Number
                 PAGE: - AudSetup
                    Bus 1 Fine  cmdID= 36165
                    min= -240  max= 240  step= 1  format= %d  div_scale= 1  preset= 0
                    Min = 0  Max = 0  Step = 0  Preset = 0  "
        ::= { iquav10CmdEntry 36165 }


    iquav10AudSetupDelaySelectBus2Fine OBJECT-TYPE
        SYNTAX            INTEGER
        MAX-ACCESS        read-write
        STATUS            current
        DESCRIPTION
                "CMNT: - Set Manual delay
                 TYPE: - Number
                 PAGE: - AudSetup
                    Bus 2 Fine  cmdID= 36166
                    min= -240  max= 240  step= 1  format= %d  div_scale= 1  preset= 0
                    Min = 0  Max = 0  Step = 0  Preset = 0  "
        ::= { iquav10CmdEntry 36166 }


    iquav10AudSetupDelaySelectBus3Fine OBJECT-TYPE
        SYNTAX            INTEGER
        MAX-ACCESS        read-write
        STATUS            current
        DESCRIPTION
                "CMNT: - Set Manual delay
                 TYPE: - Number
                 PAGE: - AudSetup
                    Bus 3 Fine  cmdID= 36167
                    min= -240  max= 240  step= 1  format= %d  div_scale= 1  preset= 0
                    Min = 0  Max = 0  Step = 0  Preset = 0  "
        ::= { iquav10CmdEntry 36167 }


    iquav10AudSetupDelaySelectBus4Fine OBJECT-TYPE
        SYNTAX            INTEGER
        MAX-ACCESS        read-write
        STATUS            current
        DESCRIPTION
                "CMNT: - Set Manual delay
                 TYPE: - Number
                 PAGE: - AudSetup
                    Bus 4 Fine  cmdID= 36168
                    min= -240  max= 240  step= 1  format= %d  div_scale= 1  preset= 0
                    Min = 0  Max = 0  Step = 0  Preset = 0  "
        ::= { iquav10CmdEntry 36168 }


    iquav10AudSetupDelaySelectBus5Fine OBJECT-TYPE
        SYNTAX            INTEGER
        MAX-ACCESS        read-write
        STATUS            current
        DESCRIPTION
                "CMNT: - Set Manual delay
                 TYPE: - Number
                 PAGE: - AudSetup
                    Bus 5 Fine  cmdID= 36169
                    min= -240  max= 240  step= 1  format= %d  div_scale= 1  preset= 0
                    Min = 0  Max = 0  Step = 0  Preset = 0  "
        ::= { iquav10CmdEntry 36169 }


    iquav10AudSetupDelaySelectBus6Fine OBJECT-TYPE
        SYNTAX            INTEGER
        MAX-ACCESS        read-write
        STATUS            current
        DESCRIPTION
                "CMNT: - Set Manual delay
                 TYPE: - Number
                 PAGE: - AudSetup
                    Bus 6 Fine  cmdID= 36170
                    min= -240  max= 240  step= 1  format= %d  div_scale= 1  preset= 0
                    Min = 0  Max = 0  Step = 0  Preset = 0  "
        ::= { iquav10CmdEntry 36170 }


    iquav10AudSetupDelaySelectBus7Fine OBJECT-TYPE
        SYNTAX            INTEGER
        MAX-ACCESS        read-write
        STATUS            current
        DESCRIPTION
                "CMNT: - Set Manual delay
                 TYPE: - Number
                 PAGE: - AudSetup
                    Bus 7 Fine  cmdID= 36171
                    min= -240  max= 240  step= 1  format= %d  div_scale= 1  preset= 0
                    Min = 0  Max = 0  Step = 0  Preset = 0  "
        ::= { iquav10CmdEntry 36171 }


    iquav10AudSetupDelaySelectBus8Fine OBJECT-TYPE
        SYNTAX            INTEGER
        MAX-ACCESS        read-write
        STATUS            current
        DESCRIPTION
                "CMNT: - Set Manual delay
                 TYPE: - Number
                 PAGE: - AudSetup
                    Bus 8 Fine  cmdID= 36172
                    min= -240  max= 240  step= 1  format= %d  div_scale= 1  preset= 0
                    Min = 0  Max = 0  Step = 0  Preset = 0  "
        ::= { iquav10CmdEntry 36172 }


    iquav10AudSetupDelaySelectBusBulkDelay OBJECT-TYPE
        SYNTAX            INTEGER
        MAX-ACCESS        read-write
        STATUS            current
        DESCRIPTION
                "CMNT: - Set Bulk delay
                 TYPE: - Number
                 PAGE: - AudSetup
                    Bus Bulk Delay  cmdID= 40647
                    min= -3210  max= 12000  step= 1  format= %d  div_scale= 1  preset= 0
                    Min = 0  Max = 0  Step = 0  Preset = 0  "
        ::= { iquav10CmdEntry 40647 }


    iquav10AudSetupDelaySelectThreshold OBJECT-TYPE
        SYNTAX            INTEGER
        MAX-ACCESS        read-write
        STATUS            current
        DESCRIPTION
                "CMNT: - Set DELAY Threshold
                 TYPE: - Number
                 PAGE: - AudSetup
                    Threshold  cmdID= 40646
                    min= 240  max= 3840  step= 1  format= %d  div_scale= 1  preset= 3840
                    Min = 0  Max = 0  Step = 0  Preset = 0  "
        ::= { iquav10CmdEntry 40646 }


    iquav10AudSetupDelaySelectRtrack14 OBJECT-TYPE
        SYNTAX            INTEGER { disable(0), enable(1)  }
        MAX-ACCESS        read-write
        STATUS            current
        DESCRIPTION
                "CMNT: - Use rolltrack14 data for delay
                 TYPE: - Checkbox
                 PAGE: - AudSetup
                    Rtrack14  cmdID= 40600  "
        ::= { iquav10CmdEntry 40600 }


    iquav10AudSetupDelaySelectRtrack15 OBJECT-TYPE
        SYNTAX            INTEGER { disable(0), enable(1)  }
        MAX-ACCESS        read-write
        STATUS            current
        DESCRIPTION
                "CMNT: - Use rolltrack15 data for delay
                 TYPE: - Checkbox
                 PAGE: - AudSetup
                    Rtrack15  cmdID= 40608  "
        ::= { iquav10CmdEntry 40608 }


    iquav10AudSetupDelaySelectRtrack16 OBJECT-TYPE
        SYNTAX            INTEGER { disable(0), enable(1)  }
        MAX-ACCESS        read-write
        STATUS            current
        DESCRIPTION
                "CMNT: - Use rolltrack16 data for delay
                 TYPE: - Checkbox
                 PAGE: - AudSetup
                    Rtrack16  cmdID= 40616  "
        ::= { iquav10CmdEntry 40616 }


    iquav10AudSetupDelaySelectRtrack17 OBJECT-TYPE
        SYNTAX            INTEGER { disable(0), enable(1)  }
        MAX-ACCESS        read-write
        STATUS            current
        DESCRIPTION
                "CMNT: - Use rolltrack17 data for delay
                 TYPE: - Checkbox
                 PAGE: - AudSetup
                    Rtrack17  cmdID= 40624  "
        ::= { iquav10CmdEntry 40624 }


    iquav10AudSetupDelaySelectEnableBulk OBJECT-TYPE
        SYNTAX            INTEGER { disable(0), enable(1)  }
        MAX-ACCESS        read-write
        STATUS            current
        DESCRIPTION
                "CMNT: - Use BULK data for delay
                 TYPE: - Checkbox
                 PAGE: - AudSetup
                    EnableBulk  cmdID= 40625  "
        ::= { iquav10CmdEntry 40625 }


    iquav10AudSetupDelaySelectEnableVideo OBJECT-TYPE
        SYNTAX            INTEGER { disable(0), enable(1)  }
        MAX-ACCESS        read-write
        STATUS            current
        DESCRIPTION
                "CMNT: - Use BULK data for delay
                 TYPE: - Checkbox
                 PAGE: - AudSetup
                    EnableVideo  cmdID= 40632  "
        ::= { iquav10CmdEntry 40632 }


    iquav10AudioAudSetupRollTrack14 OBJECT-TYPE
        SYNTAX            RollCallString
        MAX-ACCESS        read-only
        STATUS            current
        DESCRIPTION
                "CMNT: - Rolltrack input command for delays
                 TYPE: - Display
                 PAGE: - Audio
                    RollTrack14  cmdID= 14  "
        ::= { iquav10CmdEntry 14 }


    iquav10AudioAudSetupRollTrack15 OBJECT-TYPE
        SYNTAX            RollCallString
        MAX-ACCESS        read-only
        STATUS            current
        DESCRIPTION
                "CMNT: - Rolltrack input command for delays
                 TYPE: - Display
                 PAGE: - Audio
                    RollTrack15  cmdID= 15  "
        ::= { iquav10CmdEntry 15 }


    iquav10AudioAudSetupRollTrack16 OBJECT-TYPE
        SYNTAX            RollCallString
        MAX-ACCESS        read-only
        STATUS            current
        DESCRIPTION
                "CMNT: - Rolltrack input command for delays
                 TYPE: - Display
                 PAGE: - Audio
                    RollTrack16  cmdID= 16  "
        ::= { iquav10CmdEntry 16 }


    iquav10AudioAudSetupRollTrack17 OBJECT-TYPE
        SYNTAX            RollCallString
        MAX-ACCESS        read-only
        STATUS            current
        DESCRIPTION
                "CMNT: - Rolltrack input command for delays
                 TYPE: - Display
                 PAGE: - Audio
                    RollTrack17  cmdID= 17  "
        ::= { iquav10CmdEntry 17 }


    iquav10AudioAudSetupCurrentVidDelay OBJECT-TYPE
        SYNTAX            RollCallString
        MAX-ACCESS        read-only
        STATUS            current
        DESCRIPTION
                "CMNT: - Internal Video Delay for Synchroniser modules
                 TYPE: - Display
                 PAGE: - Audio
                    CurrentVidDelay  cmdID= 33030  "
        ::= { iquav10CmdEntry 33030 }


    iquav10AudioAudSetupMinVidAudDelay OBJECT-TYPE
        SYNTAX            RollCallString
        MAX-ACCESS        read-only
        STATUS            current
        DESCRIPTION
                "CMNT: - Internal Video Delay for Synchroniser modules
                 TYPE: - Display
                 PAGE: - Audio
                    MinVidAudDelay  cmdID= 33043  "
        ::= { iquav10CmdEntry 33043 }


    iquav10AudioAudSetupCurrRTrack14Delay OBJECT-TYPE
        SYNTAX            RollCallString
        MAX-ACCESS        read-only
        STATUS            current
        DESCRIPTION
                "CMNT: - Current Delay for Rolltrack 14
                 TYPE: - Display
                 PAGE: - Audio
                    CurrRTrack14Delay  cmdID= 40665  "
        ::= { iquav10CmdEntry 40665 }


    iquav10AudioAudSetupCurrRlTrack15Delay OBJECT-TYPE
        SYNTAX            RollCallString
        MAX-ACCESS        read-only
        STATUS            current
        DESCRIPTION
                "CMNT: - Current Delay for Rolltrack 15
                 TYPE: - Display
                 PAGE: - Audio
                    CurrRlTrack15Delay  cmdID= 40666  "
        ::= { iquav10CmdEntry 40666 }


    iquav10AudioAudSetupCurrRTrack16Delay OBJECT-TYPE
        SYNTAX            RollCallString
        MAX-ACCESS        read-only
        STATUS            current
        DESCRIPTION
                "CMNT: - Current Delay for Rolltrack 16
                 TYPE: - Display
                 PAGE: - Audio
                    CurrRTrack16Delay  cmdID= 40667  "
        ::= { iquav10CmdEntry 40667 }


    iquav10AudioAudSetupCurrRTrack17Delay OBJECT-TYPE
        SYNTAX            RollCallString
        MAX-ACCESS        read-only
        STATUS            current
        DESCRIPTION
                "CMNT: - Current Delay for Rolltrack 17
                 TYPE: - Display
                 PAGE: - Audio
                    CurrRTrack17Delay  cmdID= 40668  "
        ::= { iquav10CmdEntry 40668 }


    iquav10AudSetupTonesFreq0 OBJECT-TYPE
        SYNTAX            INTEGER
        MAX-ACCESS        read-write
        STATUS            current
        DESCRIPTION
                "CMNT: - 
                 TYPE: - Number
                 PAGE: - AudSetup
                    Freq0  cmdID= 42600
                    min= 1  max= 160  step= 1  format= %d  div_scale= 1  preset= 4
                    Min = 0  Max = 0  Step = 0  Preset = 0  "
        ::= { iquav10CmdEntry 42600 }


    iquav10AudSetupTonesFreq1 OBJECT-TYPE
        SYNTAX            INTEGER
        MAX-ACCESS        read-write
        STATUS            current
        DESCRIPTION
                "CMNT: - 
                 TYPE: - Number
                 PAGE: - AudSetup
                    Freq1  cmdID= 42601
                    min= 1  max= 160  step= 1  format= %d  div_scale= 1  preset= 8
                    Min = 0  Max = 0  Step = 0  Preset = 0  "
        ::= { iquav10CmdEntry 42601 }


    iquav10AudSetupTonesFreq2 OBJECT-TYPE
        SYNTAX            INTEGER
        MAX-ACCESS        read-write
        STATUS            current
        DESCRIPTION
                "CMNT: - 
                 TYPE: - Number
                 PAGE: - AudSetup
                    Freq2  cmdID= 42602
                    min= 1  max= 160  step= 1  format= %d  div_scale= 1  preset= 16
                    Min = 0  Max = 0  Step = 0  Preset = 0  "
        ::= { iquav10CmdEntry 42602 }


    iquav10AudSetupTonesFreq3 OBJECT-TYPE
        SYNTAX            INTEGER
        MAX-ACCESS        read-write
        STATUS            current
        DESCRIPTION
                "CMNT: - 
                 TYPE: - Number
                 PAGE: - AudSetup
                    Freq3  cmdID= 42603
                    min= 1  max= 160  step= 1  format= %d  div_scale= 1  preset= 32
                    Min = 0  Max = 0  Step = 0  Preset = 0  "
        ::= { iquav10CmdEntry 42603 }


    iquav10AudSetupTonesFreq4 OBJECT-TYPE
        SYNTAX            INTEGER
        MAX-ACCESS        read-write
        STATUS            current
        DESCRIPTION
                "CMNT: - 
                 TYPE: - Number
                 PAGE: - AudSetup
                    Freq4  cmdID= 42604
                    min= 1  max= 160  step= 1  format= %d  div_scale= 1  preset= 6
                    Min = 0  Max = 0  Step = 0  Preset = 0  "
        ::= { iquav10CmdEntry 42604 }


    iquav10AudSetupTonesFreq5 OBJECT-TYPE
        SYNTAX            INTEGER
        MAX-ACCESS        read-write
        STATUS            current
        DESCRIPTION
                "CMNT: - 
                 TYPE: - Number
                 PAGE: - AudSetup
                    Freq5  cmdID= 42605
                    min= 1  max= 160  step= 1  format= %d  div_scale= 1  preset= 12
                    Min = 0  Max = 0  Step = 0  Preset = 0  "
        ::= { iquav10CmdEntry 42605 }


    iquav10AudSetupTonesFreq6 OBJECT-TYPE
        SYNTAX            INTEGER
        MAX-ACCESS        read-write
        STATUS            current
        DESCRIPTION
                "CMNT: - 
                 TYPE: - Number
                 PAGE: - AudSetup
                    Freq6  cmdID= 42606
                    min= 1  max= 160  step= 1  format= %d  div_scale= 1  preset= 24
                    Min = 0  Max = 0  Step = 0  Preset = 0  "
        ::= { iquav10CmdEntry 42606 }


    iquav10AudSetupTonesFreq7 OBJECT-TYPE
        SYNTAX            INTEGER
        MAX-ACCESS        read-write
        STATUS            current
        DESCRIPTION
                "CMNT: - 
                 TYPE: - Number
                 PAGE: - AudSetup
                    Freq7  cmdID= 42607
                    min= 1  max= 160  step= 1  format= %d  div_scale= 1  preset= 48
                    Min = 0  Max = 0  Step = 0  Preset = 0  "
        ::= { iquav10CmdEntry 42607 }


    iquav10AudSetupTonesIdent0 OBJECT-TYPE
        SYNTAX            INTEGER { disable(0), enable(1)  }
        MAX-ACCESS        read-write
        STATUS            current
        DESCRIPTION
                "CMNT: - 
                 TYPE: - Checkbox
                 PAGE: - AudSetup
                    Ident0  cmdID= 42610  "
        ::= { iquav10CmdEntry 42610 }


    iquav10AudSetupTonesIdent1 OBJECT-TYPE
        SYNTAX            INTEGER { disable(0), enable(1)  }
        MAX-ACCESS        read-write
        STATUS            current
        DESCRIPTION
                "CMNT: - 
                 TYPE: - Checkbox
                 PAGE: - AudSetup
                    Ident1  cmdID= 42611  "
        ::= { iquav10CmdEntry 42611 }


    iquav10AudSetupTonesIdent2 OBJECT-TYPE
        SYNTAX            INTEGER { disable(0), enable(1)  }
        MAX-ACCESS        read-write
        STATUS            current
        DESCRIPTION
                "CMNT: - 
                 TYPE: - Checkbox
                 PAGE: - AudSetup
                    Ident2  cmdID= 42612  "
        ::= { iquav10CmdEntry 42612 }


    iquav10AudSetupTonesIdent3 OBJECT-TYPE
        SYNTAX            INTEGER { disable(0), enable(1)  }
        MAX-ACCESS        read-write
        STATUS            current
        DESCRIPTION
                "CMNT: - 
                 TYPE: - Checkbox
                 PAGE: - AudSetup
                    Ident3  cmdID= 42613  "
        ::= { iquav10CmdEntry 42613 }


    iquav10AudSetupTonesIdent4 OBJECT-TYPE
        SYNTAX            INTEGER { disable(0), enable(1)  }
        MAX-ACCESS        read-write
        STATUS            current
        DESCRIPTION
                "CMNT: - 
                 TYPE: - Checkbox
                 PAGE: - AudSetup
                    Ident4  cmdID= 42614  "
        ::= { iquav10CmdEntry 42614 }


    iquav10AudSetupTonesIdent5 OBJECT-TYPE
        SYNTAX            INTEGER { disable(0), enable(1)  }
        MAX-ACCESS        read-write
        STATUS            current
        DESCRIPTION
                "CMNT: - 
                 TYPE: - Checkbox
                 PAGE: - AudSetup
                    Ident5  cmdID= 42615  "
        ::= { iquav10CmdEntry 42615 }


    iquav10AudSetupTonesIdent6 OBJECT-TYPE
        SYNTAX            INTEGER { disable(0), enable(1)  }
        MAX-ACCESS        read-write
        STATUS            current
        DESCRIPTION
                "CMNT: - 
                 TYPE: - Checkbox
                 PAGE: - AudSetup
                    Ident6  cmdID= 42616  "
        ::= { iquav10CmdEntry 42616 }


    iquav10AudSetupTonesIdent7 OBJECT-TYPE
        SYNTAX            INTEGER { disable(0), enable(1)  }
        MAX-ACCESS        read-write
        STATUS            current
        DESCRIPTION
                "CMNT: - 
                 TYPE: - Checkbox
                 PAGE: - AudSetup
                    Ident7  cmdID= 42617  "
        ::= { iquav10CmdEntry 42617 }


    iquav10AudioAudSetupNeg1Frame OBJECT-TYPE
        SYNTAX            INTEGER { noAction(0),valNeg1Frame(1) }
        MAX-ACCESS        read-write
        STATUS            current
        DESCRIPTION
                "CMNT: - 
                 TYPE: - Button
                 PAGE: - Audio
                    Neg1Frame  cmdID= 40626
                    value= 1  "
        ::= { iquav10CmdEntry 40626 }


    iquav10AudioAudSetupNeg1ms OBJECT-TYPE
        SYNTAX            INTEGER { noAction(0),valNeg1ms(1) }
        MAX-ACCESS        read-write
        STATUS            current
        DESCRIPTION
                "CMNT: - 
                 TYPE: - Button
                 PAGE: - Audio
                    Neg1ms  cmdID= 40627
                    value= 1  "
        ::= { iquav10CmdEntry 40627 }


    iquav10AudioAudSetupNeg4samp OBJECT-TYPE
        SYNTAX            INTEGER { noAction(0),valNeg4samp(1) }
        MAX-ACCESS        read-write
        STATUS            current
        DESCRIPTION
                "CMNT: - 
                 TYPE: - Button
                 PAGE: - Audio
                    Neg4samp  cmdID= 40628
                    value= 1  "
        ::= { iquav10CmdEntry 40628 }


    iquav10AudioAudSetupPos4samp OBJECT-TYPE
        SYNTAX            INTEGER { noAction(0),valPos4samp(1) }
        MAX-ACCESS        read-write
        STATUS            current
        DESCRIPTION
                "CMNT: - 
                 TYPE: - Button
                 PAGE: - Audio
                    Pos4samp  cmdID= 40629
                    value= 1  "
        ::= { iquav10CmdEntry 40629 }


    iquav10AudioAudSetupPos1ms OBJECT-TYPE
        SYNTAX            INTEGER { noAction(0),valPos1ms(1) }
        MAX-ACCESS        read-write
        STATUS            current
        DESCRIPTION
                "CMNT: - 
                 TYPE: - Button
                 PAGE: - Audio
                    Pos1ms  cmdID= 40630
                    value= 1  "
        ::= { iquav10CmdEntry 40630 }


    iquav10AudioAudSetupPos1Frame OBJECT-TYPE
        SYNTAX            INTEGER { noAction(0),valPos1Frame(1) }
        MAX-ACCESS        read-write
        STATUS            current
        DESCRIPTION
                "CMNT: - 
                 TYPE: - Button
                 PAGE: - Audio
                    Pos1Frame  cmdID= 40631
                    value= 1  "
        ::= { iquav10CmdEntry 40631 }


    iquav10AudioAudSetupSilentLevel OBJECT-TYPE
        SYNTAX            INTEGER
        MAX-ACCESS        read-write
        STATUS            current
        DESCRIPTION
                "CMNT: - Set Audio Silent level
                 TYPE: - Number
                 PAGE: - Audio
                    SilentLevel  cmdID= 3061
                    min= -100  max= -2  step= 1  format= %0.0f dBFS  div_scale= 1  preset= -70
                    Min = -100 dBFS  Max = -2 dBFS  Step = 1 dBFS  Preset = -70 dBFS  "
        ::= { iquav10CmdEntry 3061 }


    iquav10AudioAudSetupOverloadLevel OBJECT-TYPE
        SYNTAX            INTEGER
        MAX-ACCESS        read-write
        STATUS            current
        DESCRIPTION
                "CMNT: - Set Audio Overload level
                 TYPE: - Number
                 PAGE: - Audio
                    OverloadLevel  cmdID= 3064
                    min= -99  max= -1  step= 1  format= %0.0f dBFS  div_scale= 1  preset= -1
                    Min = -99 dBFS  Max = -1 dBFS  Step = 1 dBFS  Preset = -1 dBFS  "
        ::= { iquav10CmdEntry 3064 }


    iquav10AudioAudSetupLevelTimeout OBJECT-TYPE
        SYNTAX            INTEGER
        MAX-ACCESS        read-write
        STATUS            current
        DESCRIPTION
                "CMNT: - Set Audio level timeout
                 TYPE: - Number
                 PAGE: - Audio
                    LevelTimeout  cmdID= 3065
                    min= 1  max= 20  step= 1  format= %d  div_scale= 1  preset= 10
                    Min = 0  Max = 0  Step = 0  Preset = 0  "
        ::= { iquav10CmdEntry 3065 }


    iquav10AudioAudSetupLevelUpdateEnb OBJECT-TYPE
        SYNTAX            INTEGER { disable(0), enable(1)  }
        MAX-ACCESS        read-write
        STATUS            current
        DESCRIPTION
                "CMNT: - Enable Audio level updates to rollmap
                 TYPE: - Checkbox
                 PAGE: - Audio
                    LevelUpdateEnb  cmdID= 38275  "
        ::= { iquav10CmdEntry 38275 }


    iquav10AudioAudSetupAudLevel OBJECT-TYPE
        SYNTAX            RollCallString
        MAX-ACCESS        read-only
        STATUS            current
        DESCRIPTION
                "CMNT: - Audio level updates to rollmap
                 TYPE: - Display
                 PAGE: - Audio
                    AudLevel  cmdID= 38276  "
        ::= { iquav10CmdEntry 38276 }


    iquav10AudioAudSetupHeadroomIn OBJECT-TYPE
        SYNTAX            INTEGER
        MAX-ACCESS        read-write
        STATUS            current
        DESCRIPTION
                "CMNT: - Set Audio level Headroom
                 TYPE: - Number
                 PAGE: - Audio
                    HeadroomIn  cmdID= 3066
                    min= 4  max= 24  step= 1  format= %0.0fdB  div_scale= 1  preset= 18
                    Min = 4dB  Max = 24dB  Step = 1dB  Preset = 18dB  "
        ::= { iquav10CmdEntry 3066 }


    iquav10AudioAudSetupLineupIn OBJECT-TYPE
        SYNTAX            INTEGER
        MAX-ACCESS        read-write
        STATUS            current
        DESCRIPTION
                "CMNT: - Set Audio level Lineup
                 TYPE: - Number
                 PAGE: - Audio
                    LineupIn  cmdID= 3067
                    min= -20  max= 20  step= 1  format= %0.0fdBu  div_scale= 1  preset= 0
                    Min = -20dBu  Max = 20dBu  Step = 1dBu  Preset = 0dBu  "
        ::= { iquav10CmdEntry 3067 }


    iquav10AudioAudSetupHeadroomOut OBJECT-TYPE
        SYNTAX            INTEGER
        MAX-ACCESS        read-write
        STATUS            current
        DESCRIPTION
                "CMNT: - Set Audio level Headroom
                 TYPE: - Number
                 PAGE: - Audio
                    HeadroomOut  cmdID= 3068
                    min= 4  max= 24  step= 1  format= %0.0fdB  div_scale= 1  preset= 18
                    Min = 4dB  Max = 24dB  Step = 1dB  Preset = 18dB  "
        ::= { iquav10CmdEntry 3068 }


    iquav10AudioAudSetupLineupOut OBJECT-TYPE
        SYNTAX            INTEGER
        MAX-ACCESS        read-write
        STATUS            current
        DESCRIPTION
                "CMNT: - Set Audio level Lineup
                 TYPE: - Number
                 PAGE: - Audio
                    LineupOut  cmdID= 3069
                    min= -20  max= 20  step= 1  format= %0.0fdBu  div_scale= 1  preset= 0
                    Min = -20dBu  Max = 20dBu  Step = 1dBu  Preset = 0dBu  "
        ::= { iquav10CmdEntry 3069 }


    iquav10AudioRoutingInputRouteDest1 OBJECT-TYPE
        SYNTAX            INTEGER
        MAX-ACCESS        read-write
        STATUS            current
        DESCRIPTION
                "CMNT: - 
                 TYPE: - Number
                 PAGE: - Audio
                    Input Route Dest 1  cmdID= 40223
                    min= 0  max= 22  step= 1  format= 0  div_scale= 1  preset= 0
                    Min = 0  Max = 0  Step = 0  Preset = 0  "
        ::= { iquav10CmdEntry 40223 }


    iquav10AudioRoutingInputRouteDest2 OBJECT-TYPE
        SYNTAX            INTEGER
        MAX-ACCESS        read-write
        STATUS            current
        DESCRIPTION
                "CMNT: - 
                 TYPE: - Number
                 PAGE: - Audio
                    Input Route Dest 2  cmdID= 40224
                    min= 0  max= 22  step= 1  format= 0  div_scale= 1  preset= 1
                    Min = 0  Max = 0  Step = 0  Preset = 0  "
        ::= { iquav10CmdEntry 40224 }


    iquav10AudioRoutingInputRouteDest3 OBJECT-TYPE
        SYNTAX            INTEGER
        MAX-ACCESS        read-write
        STATUS            current
        DESCRIPTION
                "CMNT: - 
                 TYPE: - Number
                 PAGE: - Audio
                    Input Route Dest 3  cmdID= 40225
                    min= 0  max= 22  step= 1  format= 0  div_scale= 1  preset= 2
                    Min = 0  Max = 0  Step = 0  Preset = 0  "
        ::= { iquav10CmdEntry 40225 }


    iquav10AudioRoutingInputRouteDest4 OBJECT-TYPE
        SYNTAX            INTEGER
        MAX-ACCESS        read-write
        STATUS            current
        DESCRIPTION
                "CMNT: - 
                 TYPE: - Number
                 PAGE: - Audio
                    Input Route Dest 4  cmdID= 40226
                    min= 0  max= 22  step= 1  format= 0  div_scale= 1  preset= 3
                    Min = 0  Max = 0  Step = 0  Preset = 0  "
        ::= { iquav10CmdEntry 40226 }


    iquav10AudioRoutingInputRouteDest5 OBJECT-TYPE
        SYNTAX            INTEGER
        MAX-ACCESS        read-write
        STATUS            current
        DESCRIPTION
                "CMNT: - 
                 TYPE: - Number
                 PAGE: - Audio
                    Input Route Dest 5  cmdID= 40227
                    min= 0  max= 22  step= 1  format= 0  div_scale= 1  preset= 4
                    Min = 0  Max = 0  Step = 0  Preset = 0  "
        ::= { iquav10CmdEntry 40227 }


    iquav10AudioRoutingInputRouteDest6 OBJECT-TYPE
        SYNTAX            INTEGER
        MAX-ACCESS        read-write
        STATUS            current
        DESCRIPTION
                "CMNT: - 
                 TYPE: - Number
                 PAGE: - Audio
                    Input Route Dest 6  cmdID= 40228
                    min= 0  max= 22  step= 1  format= 0  div_scale= 1  preset= 5
                    Min = 0  Max = 0  Step = 0  Preset = 0  "
        ::= { iquav10CmdEntry 40228 }


    iquav10AudioRoutingInputRouteDest7 OBJECT-TYPE
        SYNTAX            INTEGER
        MAX-ACCESS        read-write
        STATUS            current
        DESCRIPTION
                "CMNT: - 
                 TYPE: - Number
                 PAGE: - Audio
                    Input Route Dest 7  cmdID= 40229
                    min= 0  max= 22  step= 1  format= 0  div_scale= 1  preset= 6
                    Min = 0  Max = 0  Step = 0  Preset = 0  "
        ::= { iquav10CmdEntry 40229 }


    iquav10AudioRoutingInputRouteDest8 OBJECT-TYPE
        SYNTAX            INTEGER
        MAX-ACCESS        read-write
        STATUS            current
        DESCRIPTION
                "CMNT: - 
                 TYPE: - Number
                 PAGE: - Audio
                    Input Route Dest 8  cmdID= 40230
                    min= 0  max= 22  step= 1  format= 0  div_scale= 1  preset= 7
                    Min = 0  Max = 0  Step = 0  Preset = 0  "
        ::= { iquav10CmdEntry 40230 }


    iquav10AudioRoutingInputNameAnalog OBJECT-TYPE
        SYNTAX            RollCallString
        MAX-ACCESS        read-only
        STATUS            current
        DESCRIPTION
                "CMNT: - 
                 TYPE: - Display
                 PAGE: - Audio
                    Input Name Analog  cmdID= 40216  "
        ::= { iquav10CmdEntry 40216 }


    iquav10AudioRoutingInputNameDlby1 OBJECT-TYPE
        SYNTAX            RollCallString
        MAX-ACCESS        read-only
        STATUS            current
        DESCRIPTION
                "CMNT: - 
                 TYPE: - Display
                 PAGE: - Audio
                    Input Name Dlby 1  cmdID= 40218  "
        ::= { iquav10CmdEntry 40218 }


    iquav10AudioRoutingInputNameDlby2 OBJECT-TYPE
        SYNTAX            RollCallString
        MAX-ACCESS        read-only
        STATUS            current
        DESCRIPTION
                "CMNT: - 
                 TYPE: - Display
                 PAGE: - Audio
                    Input Name Dlby 2  cmdID= 40219  "
        ::= { iquav10CmdEntry 40219 }


    iquav10AudioRoutingInputNameDlby3 OBJECT-TYPE
        SYNTAX            RollCallString
        MAX-ACCESS        read-only
        STATUS            current
        DESCRIPTION
                "CMNT: - 
                 TYPE: - Display
                 PAGE: - Audio
                    Input Name Dlby 3  cmdID= 40220  "
        ::= { iquav10CmdEntry 40220 }


    iquav10AudioRoutingInputNameDlby4 OBJECT-TYPE
        SYNTAX            RollCallString
        MAX-ACCESS        read-only
        STATUS            current
        DESCRIPTION
                "CMNT: - 
                 TYPE: - Display
                 PAGE: - Audio
                    Input Name Dlby 4  cmdID= 40221  "
        ::= { iquav10CmdEntry 40221 }


    iquav10AudioRoutingInputNameDlby5 OBJECT-TYPE
        SYNTAX            RollCallString
        MAX-ACCESS        read-only
        STATUS            current
        DESCRIPTION
                "CMNT: - 
                 TYPE: - Display
                 PAGE: - Audio
                    Input Name Dlby 5  cmdID= 40222  "
        ::= { iquav10CmdEntry 40222 }


    iquav10AudioRoutingInputHideAES1 OBJECT-TYPE
        SYNTAX            RollCallString
        MAX-ACCESS        read-only
        STATUS            current
        DESCRIPTION
                "CMNT: - 
                 TYPE: - Display
                 PAGE: - Audio
                    Input Hide AES 1  cmdID= 40233  "
        ::= { iquav10CmdEntry 40233 }


    iquav10AudioRoutingInputHideAES2 OBJECT-TYPE
        SYNTAX            RollCallString
        MAX-ACCESS        read-only
        STATUS            current
        DESCRIPTION
                "CMNT: - 
                 TYPE: - Display
                 PAGE: - Audio
                    Input Hide AES 2  cmdID= 40234  "
        ::= { iquav10CmdEntry 40234 }


    iquav10AudioRoutingInputHideAES3 OBJECT-TYPE
        SYNTAX            RollCallString
        MAX-ACCESS        read-only
        STATUS            current
        DESCRIPTION
                "CMNT: - 
                 TYPE: - Display
                 PAGE: - Audio
                    Input Hide AES 3  cmdID= 40235  "
        ::= { iquav10CmdEntry 40235 }


    iquav10AudioRoutingInputHideAES4 OBJECT-TYPE
        SYNTAX            RollCallString
        MAX-ACCESS        read-only
        STATUS            current
        DESCRIPTION
                "CMNT: - 
                 TYPE: - Display
                 PAGE: - Audio
                    Input Hide AES 4  cmdID= 40236  "
        ::= { iquav10CmdEntry 40236 }


    iquav10AudioRoutingInputHideAES5 OBJECT-TYPE
        SYNTAX            RollCallString
        MAX-ACCESS        read-only
        STATUS            current
        DESCRIPTION
                "CMNT: - 
                 TYPE: - Display
                 PAGE: - Audio
                    Input Hide AES 5  cmdID= 40237  "
        ::= { iquav10CmdEntry 40237 }


    iquav10AudioRoutingInputHideAES6 OBJECT-TYPE
        SYNTAX            RollCallString
        MAX-ACCESS        read-only
        STATUS            current
        DESCRIPTION
                "CMNT: - 
                 TYPE: - Display
                 PAGE: - Audio
                    Input Hide AES 6  cmdID= 40238  "
        ::= { iquav10CmdEntry 40238 }


    iquav10AudioRoutingInputHideAES7 OBJECT-TYPE
        SYNTAX            RollCallString
        MAX-ACCESS        read-only
        STATUS            current
        DESCRIPTION
                "CMNT: - 
                 TYPE: - Display
                 PAGE: - Audio
                    Input Hide AES 7  cmdID= 40239  "
        ::= { iquav10CmdEntry 40239 }


    iquav10AudioRoutingInputHideAES8 OBJECT-TYPE
        SYNTAX            RollCallString
        MAX-ACCESS        read-only
        STATUS            current
        DESCRIPTION
                "CMNT: - 
                 TYPE: - Display
                 PAGE: - Audio
                    Input Hide AES 8  cmdID= 40240  "
        ::= { iquav10CmdEntry 40240 }


    iquav10AudioRoutingOutputHideAES1 OBJECT-TYPE
        SYNTAX            RollCallString
        MAX-ACCESS        read-only
        STATUS            current
        DESCRIPTION
                "CMNT: - 
                 TYPE: - Display
                 PAGE: - Audio
                    Output Hide AES 1  cmdID= 40250  "
        ::= { iquav10CmdEntry 40250 }


    iquav10AudioRoutingOutputHideAES2 OBJECT-TYPE
        SYNTAX            RollCallString
        MAX-ACCESS        read-only
        STATUS            current
        DESCRIPTION
                "CMNT: - 
                 TYPE: - Display
                 PAGE: - Audio
                    Output Hide AES 2  cmdID= 40251  "
        ::= { iquav10CmdEntry 40251 }


    iquav10AudioRoutingOutputHideAES3 OBJECT-TYPE
        SYNTAX            RollCallString
        MAX-ACCESS        read-only
        STATUS            current
        DESCRIPTION
                "CMNT: - 
                 TYPE: - Display
                 PAGE: - Audio
                    Output Hide AES 3  cmdID= 40252  "
        ::= { iquav10CmdEntry 40252 }


    iquav10AudioRoutingOutputHideAES4 OBJECT-TYPE
        SYNTAX            RollCallString
        MAX-ACCESS        read-only
        STATUS            current
        DESCRIPTION
                "CMNT: - 
                 TYPE: - Display
                 PAGE: - Audio
                    Output Hide AES 4  cmdID= 40253  "
        ::= { iquav10CmdEntry 40253 }


    iquav10AudioRoutingOutputHideAES5 OBJECT-TYPE
        SYNTAX            RollCallString
        MAX-ACCESS        read-only
        STATUS            current
        DESCRIPTION
                "CMNT: - 
                 TYPE: - Display
                 PAGE: - Audio
                    Output Hide AES 5  cmdID= 40254  "
        ::= { iquav10CmdEntry 40254 }


    iquav10AudioRoutingOutputHideAES6 OBJECT-TYPE
        SYNTAX            RollCallString
        MAX-ACCESS        read-only
        STATUS            current
        DESCRIPTION
                "CMNT: - 
                 TYPE: - Display
                 PAGE: - Audio
                    Output Hide AES 6  cmdID= 40255  "
        ::= { iquav10CmdEntry 40255 }


    iquav10AudioRoutingOutputHideAES7 OBJECT-TYPE
        SYNTAX            RollCallString
        MAX-ACCESS        read-only
        STATUS            current
        DESCRIPTION
                "CMNT: - 
                 TYPE: - Display
                 PAGE: - Audio
                    Output Hide AES 7  cmdID= 40256  "
        ::= { iquav10CmdEntry 40256 }


    iquav10AudioRoutingOutputHideAES8 OBJECT-TYPE
        SYNTAX            RollCallString
        MAX-ACCESS        read-only
        STATUS            current
        DESCRIPTION
                "CMNT: - 
                 TYPE: - Display
                 PAGE: - Audio
                    Output Hide AES 8  cmdID= 40257  "
        ::= { iquav10CmdEntry 40257 }


    iquav10AudioRoutingDolbyDecodeSource OBJECT-TYPE
        SYNTAX            INTEGER {
                            valDisembed1(0),
                            valDisembed2(1),
                            valDisembed3(2),
                            valDisembed4(3),
                            valDisembed5(4),
                            valDisembed6(5),
                            valDisembed7(6),
                            valDisembed8(7),
                            valAes1(8),
                            valAes2(9),
                            valAes3(10),
                            valAes4(11),
                            valAes5(12),
                            valAes6(13),
                            valAes7(14),
                            valAes8(15)
                            }
        MAX-ACCESS        read-write
        STATUS            current
        DESCRIPTION
                "CMNT: - 
                 TYPE: - RadiobuttonList
                 PAGE: - Audio
                    DolbyDecode Source  cmdID= 40241
                    Disembed 1  value= 0
                    Disembed 2  value= 1
                    Disembed 3  value= 2
                    Disembed 4  value= 3
                    Disembed 5  value= 4
                    Disembed 6  value= 5
                    Disembed 7  value= 6
                    Disembed 8  value= 7
                    Aes 1  value= 8
                    Aes 2  value= 9
                    Aes 3  value= 10
                    Aes 4  value= 11
                    Aes 5  value= 12
                    Aes 6  value= 13
                    Aes 7  value= 14
                    Aes 8  value= 15  "
        ::= { iquav10CmdEntry 40241 }


    iquav10AudioRoutingDolbyDecodeNum OBJECT-TYPE
        SYNTAX            INTEGER
        MAX-ACCESS        read-write
        STATUS            current
        DESCRIPTION
                "CMNT: - 
                 TYPE: - Number
                 PAGE: - Audio
                    DolbyDecodeNum  cmdID= 40242
                    min= 0  max= 1  step= 1  format= 0  div_scale= 1  preset= 0
                    Min = 0  Max = 0  Step = 0  Preset = 0  "
        ::= { iquav10CmdEntry 40242 }


    iquav10AudioOutputRoutingOutDest1 OBJECT-TYPE
        SYNTAX            INTEGER
        MAX-ACCESS        read-write
        STATUS            current
        DESCRIPTION
                "CMNT: - 
                 TYPE: - Number
                 PAGE: - Audio
                    OutDest1  cmdID= 40293
                    min= 0  max= 47  step= 1  format= %d  div_scale= 1  preset= 0
                    Min = 0  Max = 0  Step = 0  Preset = 0  "
        ::= { iquav10CmdEntry 40293 }


    iquav10AudioOutputRoutingOutDest2 OBJECT-TYPE
        SYNTAX            INTEGER
        MAX-ACCESS        read-write
        STATUS            current
        DESCRIPTION
                "CMNT: - 
                 TYPE: - Number
                 PAGE: - Audio
                    OutDest2  cmdID= 40294
                    min= 0  max= 47  step= 1  format= %d  div_scale= 1  preset= 1
                    Min = 0  Max = 0  Step = 0  Preset = 0  "
        ::= { iquav10CmdEntry 40294 }


    iquav10AudioOutputRoutingOutDest3 OBJECT-TYPE
        SYNTAX            INTEGER
        MAX-ACCESS        read-write
        STATUS            current
        DESCRIPTION
                "CMNT: - 
                 TYPE: - Number
                 PAGE: - Audio
                    OutDest3  cmdID= 40295
                    min= 0  max= 47  step= 1  format= %d  div_scale= 1  preset= 2
                    Min = 0  Max = 0  Step = 0  Preset = 0  "
        ::= { iquav10CmdEntry 40295 }


    iquav10AudioOutputRoutingOutDest4 OBJECT-TYPE
        SYNTAX            INTEGER
        MAX-ACCESS        read-write
        STATUS            current
        DESCRIPTION
                "CMNT: - 
                 TYPE: - Number
                 PAGE: - Audio
                    OutDest4  cmdID= 40296
                    min= 0  max= 47  step= 1  format= %d  div_scale= 1  preset= 3
                    Min = 0  Max = 0  Step = 0  Preset = 0  "
        ::= { iquav10CmdEntry 40296 }


    iquav10AudioOutputRoutingOutDest5 OBJECT-TYPE
        SYNTAX            INTEGER
        MAX-ACCESS        read-write
        STATUS            current
        DESCRIPTION
                "CMNT: - 
                 TYPE: - Number
                 PAGE: - Audio
                    OutDest5  cmdID= 40297
                    min= 0  max= 47  step= 1  format= %d  div_scale= 1  preset= 4
                    Min = 0  Max = 0  Step = 0  Preset = 0  "
        ::= { iquav10CmdEntry 40297 }


    iquav10AudioOutputRoutingOutDest6 OBJECT-TYPE
        SYNTAX            INTEGER
        MAX-ACCESS        read-write
        STATUS            current
        DESCRIPTION
                "CMNT: - 
                 TYPE: - Number
                 PAGE: - Audio
                    OutDest6  cmdID= 40298
                    min= 0  max= 47  step= 1  format= %d  div_scale= 1  preset= 5
                    Min = 0  Max = 0  Step = 0  Preset = 0  "
        ::= { iquav10CmdEntry 40298 }


    iquav10AudioOutputRoutingOutDest7 OBJECT-TYPE
        SYNTAX            INTEGER
        MAX-ACCESS        read-write
        STATUS            current
        DESCRIPTION
                "CMNT: - 
                 TYPE: - Number
                 PAGE: - Audio
                    OutDest7  cmdID= 40299
                    min= 0  max= 47  step= 1  format= %d  div_scale= 1  preset= 6
                    Min = 0  Max = 0  Step = 0  Preset = 0  "
        ::= { iquav10CmdEntry 40299 }


    iquav10AudioOutputRoutingOutDest8 OBJECT-TYPE
        SYNTAX            INTEGER
        MAX-ACCESS        read-write
        STATUS            current
        DESCRIPTION
                "CMNT: - 
                 TYPE: - Number
                 PAGE: - Audio
                    OutDest8  cmdID= 40300
                    min= 0  max= 47  step= 1  format= %d  div_scale= 1  preset= 7
                    Min = 0  Max = 0  Step = 0  Preset = 0  "
        ::= { iquav10CmdEntry 40300 }


    iquav10AudioOutputRoutingOutDest9 OBJECT-TYPE
        SYNTAX            INTEGER
        MAX-ACCESS        read-write
        STATUS            current
        DESCRIPTION
                "CMNT: - 
                 TYPE: - Number
                 PAGE: - Audio
                    OutDest9  cmdID= 40301
                    min= 0  max= 47  step= 1  format= %d  div_scale= 1  preset= 8
                    Min = 0  Max = 0  Step = 0  Preset = 0  "
        ::= { iquav10CmdEntry 40301 }


    iquav10AudioOutputRoutingOutDest10 OBJECT-TYPE
        SYNTAX            INTEGER
        MAX-ACCESS        read-write
        STATUS            current
        DESCRIPTION
                "CMNT: - 
                 TYPE: - Number
                 PAGE: - Audio
                    OutDest10  cmdID= 40302
                    min= 0  max= 47  step= 1  format= %d  div_scale= 1  preset= 9
                    Min = 0  Max = 0  Step = 0  Preset = 0  "
        ::= { iquav10CmdEntry 40302 }


    iquav10AudioOutputRoutingOutDest11 OBJECT-TYPE
        SYNTAX            INTEGER
        MAX-ACCESS        read-write
        STATUS            current
        DESCRIPTION
                "CMNT: - 
                 TYPE: - Number
                 PAGE: - Audio
                    OutDest11  cmdID= 40303
                    min= 0  max= 47  step= 1  format= %d  div_scale= 1  preset= 10
                    Min = 0  Max = 0  Step = 0  Preset = 0  "
        ::= { iquav10CmdEntry 40303 }


    iquav10AudioOutputRoutingOutDest12 OBJECT-TYPE
        SYNTAX            INTEGER
        MAX-ACCESS        read-write
        STATUS            current
        DESCRIPTION
                "CMNT: - 
                 TYPE: - Number
                 PAGE: - Audio
                    OutDest12  cmdID= 40304
                    min= 0  max= 47  step= 1  format= %d  div_scale= 1  preset= 11
                    Min = 0  Max = 0  Step = 0  Preset = 0  "
        ::= { iquav10CmdEntry 40304 }


    iquav10AudioOutputRoutingOutDest13 OBJECT-TYPE
        SYNTAX            INTEGER
        MAX-ACCESS        read-write
        STATUS            current
        DESCRIPTION
                "CMNT: - 
                 TYPE: - Number
                 PAGE: - Audio
                    OutDest13  cmdID= 40305
                    min= 0  max= 47  step= 1  format= %d  div_scale= 1  preset= 12
                    Min = 0  Max = 0  Step = 0  Preset = 0  "
        ::= { iquav10CmdEntry 40305 }


    iquav10AudioOutputRoutingOutDest14 OBJECT-TYPE
        SYNTAX            INTEGER
        MAX-ACCESS        read-write
        STATUS            current
        DESCRIPTION
                "CMNT: - 
                 TYPE: - Number
                 PAGE: - Audio
                    OutDest14  cmdID= 40306
                    min= 0  max= 47  step= 1  format= %d  div_scale= 1  preset= 13
                    Min = 0  Max = 0  Step = 0  Preset = 0  "
        ::= { iquav10CmdEntry 40306 }


    iquav10AudioOutputRoutingOutDest15 OBJECT-TYPE
        SYNTAX            INTEGER
        MAX-ACCESS        read-write
        STATUS            current
        DESCRIPTION
                "CMNT: - 
                 TYPE: - Number
                 PAGE: - Audio
                    OutDest15  cmdID= 40307
                    min= 0  max= 47  step= 1  format= %d  div_scale= 1  preset= 14
                    Min = 0  Max = 0  Step = 0  Preset = 0  "
        ::= { iquav10CmdEntry 40307 }


    iquav10AudioOutputRoutingOutDest16 OBJECT-TYPE
        SYNTAX            INTEGER
        MAX-ACCESS        read-write
        STATUS            current
        DESCRIPTION
                "CMNT: - 
                 TYPE: - Number
                 PAGE: - Audio
                    OutDest16  cmdID= 40308
                    min= 0  max= 47  step= 1  format= %d  div_scale= 1  preset= 15
                    Min = 0  Max = 0  Step = 0  Preset = 0  "
        ::= { iquav10CmdEntry 40308 }


    iquav10AudioOutputRoutingOutDest17 OBJECT-TYPE
        SYNTAX            INTEGER
        MAX-ACCESS        read-write
        STATUS            current
        DESCRIPTION
                "CMNT: - 
                 TYPE: - Number
                 PAGE: - Audio
                    OutDest17  cmdID= 40309
                    min= 0  max= 47  step= 1  format= %d  div_scale= 1  preset= 34
                    Min = 0  Max = 0  Step = 0  Preset = 0  "
        ::= { iquav10CmdEntry 40309 }


    iquav10AudioOutputRoutingOutDest18 OBJECT-TYPE
        SYNTAX            INTEGER
        MAX-ACCESS        read-write
        STATUS            current
        DESCRIPTION
                "CMNT: - 
                 TYPE: - Number
                 PAGE: - Audio
                    OutDest18  cmdID= 40310
                    min= 0  max= 47  step= 1  format= %d  div_scale= 1  preset= 34
                    Min = 0  Max = 0  Step = 0  Preset = 0  "
        ::= { iquav10CmdEntry 40310 }


    iquav10AudioOutputRoutingOutDest19 OBJECT-TYPE
        SYNTAX            INTEGER
        MAX-ACCESS        read-write
        STATUS            current
        DESCRIPTION
                "CMNT: - 
                 TYPE: - Number
                 PAGE: - Audio
                    OutDest19  cmdID= 40311
                    min= 0  max= 47  step= 1  format= %d  div_scale= 1  preset= 34
                    Min = 0  Max = 0  Step = 0  Preset = 0  "
        ::= { iquav10CmdEntry 40311 }


    iquav10AudioOutputRoutingOutDest20 OBJECT-TYPE
        SYNTAX            INTEGER
        MAX-ACCESS        read-write
        STATUS            current
        DESCRIPTION
                "CMNT: - 
                 TYPE: - Number
                 PAGE: - Audio
                    OutDest20  cmdID= 40312
                    min= 0  max= 47  step= 1  format= %d  div_scale= 1  preset= 34
                    Min = 0  Max = 0  Step = 0  Preset = 0  "
        ::= { iquav10CmdEntry 40312 }


    iquav10AudioOutputRoutingOutDest21 OBJECT-TYPE
        SYNTAX            INTEGER
        MAX-ACCESS        read-write
        STATUS            current
        DESCRIPTION
                "CMNT: - 
                 TYPE: - Number
                 PAGE: - Audio
                    OutDest21  cmdID= 40313
                    min= 0  max= 47  step= 1  format= %d  div_scale= 1  preset= 34
                    Min = 0  Max = 0  Step = 0  Preset = 0  "
        ::= { iquav10CmdEntry 40313 }


    iquav10AudioOutputRoutingOutDest22 OBJECT-TYPE
        SYNTAX            INTEGER
        MAX-ACCESS        read-write
        STATUS            current
        DESCRIPTION
                "CMNT: - 
                 TYPE: - Number
                 PAGE: - Audio
                    OutDest22  cmdID= 40314
                    min= 0  max= 47  step= 1  format= %d  div_scale= 1  preset= 34
                    Min = 0  Max = 0  Step = 0  Preset = 0  "
        ::= { iquav10CmdEntry 40314 }


    iquav10AudioOutputRoutingOutDest23 OBJECT-TYPE
        SYNTAX            INTEGER
        MAX-ACCESS        read-write
        STATUS            current
        DESCRIPTION
                "CMNT: - 
                 TYPE: - Number
                 PAGE: - Audio
                    OutDest23  cmdID= 40315
                    min= 0  max= 47  step= 1  format= %d  div_scale= 1  preset= 34
                    Min = 0  Max = 0  Step = 0  Preset = 0  "
        ::= { iquav10CmdEntry 40315 }


    iquav10AudioOutputRoutingOutDest24 OBJECT-TYPE
        SYNTAX            INTEGER
        MAX-ACCESS        read-write
        STATUS            current
        DESCRIPTION
                "CMNT: - 
                 TYPE: - Number
                 PAGE: - Audio
                    OutDest24  cmdID= 40316
                    min= 0  max= 47  step= 1  format= %d  div_scale= 1  preset= 34
                    Min = 0  Max = 0  Step = 0  Preset = 0  "
        ::= { iquav10CmdEntry 40316 }


    iquav10AudioOutputRoutingOutDest25 OBJECT-TYPE
        SYNTAX            INTEGER
        MAX-ACCESS        read-write
        STATUS            current
        DESCRIPTION
                "CMNT: - 
                 TYPE: - Number
                 PAGE: - Audio
                    OutDest25  cmdID= 40317
                    min= 0  max= 47  step= 1  format= %d  div_scale= 1  preset= 34
                    Min = 0  Max = 0  Step = 0  Preset = 0  "
        ::= { iquav10CmdEntry 40317 }


    iquav10AudioOutputRoutingOutDest26 OBJECT-TYPE
        SYNTAX            INTEGER
        MAX-ACCESS        read-write
        STATUS            current
        DESCRIPTION
                "CMNT: - 
                 TYPE: - Number
                 PAGE: - Audio
                    OutDest26  cmdID= 40318
                    min= 0  max= 47  step= 1  format= %d  div_scale= 1  preset= 34
                    Min = 0  Max = 0  Step = 0  Preset = 0  "
        ::= { iquav10CmdEntry 40318 }


    iquav10AudioOutputRoutingOutDest27 OBJECT-TYPE
        SYNTAX            INTEGER
        MAX-ACCESS        read-write
        STATUS            current
        DESCRIPTION
                "CMNT: - 
                 TYPE: - Number
                 PAGE: - Audio
                    OutDest27  cmdID= 40319
                    min= 0  max= 47  step= 1  format= %d  div_scale= 1  preset= 34
                    Min = 0  Max = 0  Step = 0  Preset = 0  "
        ::= { iquav10CmdEntry 40319 }


    iquav10AudioOutputRoutingOutDest28 OBJECT-TYPE
        SYNTAX            INTEGER
        MAX-ACCESS        read-write
        STATUS            current
        DESCRIPTION
                "CMNT: - 
                 TYPE: - Number
                 PAGE: - Audio
                    OutDest28  cmdID= 40320
                    min= 0  max= 47  step= 1  format= %d  div_scale= 1  preset= 34
                    Min = 0  Max = 0  Step = 0  Preset = 0  "
        ::= { iquav10CmdEntry 40320 }


    iquav10AudioOutputRoutingOutDest29 OBJECT-TYPE
        SYNTAX            INTEGER
        MAX-ACCESS        read-write
        STATUS            current
        DESCRIPTION
                "CMNT: - 
                 TYPE: - Number
                 PAGE: - Audio
                    OutDest29  cmdID= 40321
                    min= 0  max= 47  step= 1  format= %d  div_scale= 1  preset= 34
                    Min = 0  Max = 0  Step = 0  Preset = 0  "
        ::= { iquav10CmdEntry 40321 }


    iquav10AudioOutputRoutingOutDest30 OBJECT-TYPE
        SYNTAX            INTEGER
        MAX-ACCESS        read-write
        STATUS            current
        DESCRIPTION
                "CMNT: - 
                 TYPE: - Number
                 PAGE: - Audio
                    OutDest30  cmdID= 40322
                    min= 0  max= 47  step= 1  format= %d  div_scale= 1  preset= 34
                    Min = 0  Max = 0  Step = 0  Preset = 0  "
        ::= { iquav10CmdEntry 40322 }


    iquav10AudioOutputRoutingOutDest31 OBJECT-TYPE
        SYNTAX            INTEGER
        MAX-ACCESS        read-write
        STATUS            current
        DESCRIPTION
                "CMNT: - 
                 TYPE: - Number
                 PAGE: - Audio
                    OutDest31  cmdID= 40323
                    min= 0  max= 47  step= 1  format= %d  div_scale= 1  preset= 34
                    Min = 0  Max = 0  Step = 0  Preset = 0  "
        ::= { iquav10CmdEntry 40323 }


    iquav10AudioOutputRoutingOutDest32 OBJECT-TYPE
        SYNTAX            INTEGER
        MAX-ACCESS        read-write
        STATUS            current
        DESCRIPTION
                "CMNT: - 
                 TYPE: - Number
                 PAGE: - Audio
                    OutDest32  cmdID= 40324
                    min= 0  max= 47  step= 1  format= %d  div_scale= 1  preset= 34
                    Min = 0  Max = 0  Step = 0  Preset = 0  "
        ::= { iquav10CmdEntry 40324 }


    iquav10AudioOutputRoutingOutDest33 OBJECT-TYPE
        SYNTAX            INTEGER
        MAX-ACCESS        read-write
        STATUS            current
        DESCRIPTION
                "CMNT: - 
                 TYPE: - Number
                 PAGE: - Audio
                    OutDest33  cmdID= 40325
                    min= 0  max= 47  step= 1  format= %d  div_scale= 1  preset= 34
                    Min = 0  Max = 0  Step = 0  Preset = 0  "
        ::= { iquav10CmdEntry 40325 }


    iquav10AudioOutputRoutingOutDest34 OBJECT-TYPE
        SYNTAX            INTEGER
        MAX-ACCESS        read-write
        STATUS            current
        DESCRIPTION
                "CMNT: - 
                 TYPE: - Number
                 PAGE: - Audio
                    OutDest34  cmdID= 40326
                    min= 0  max= 47  step= 1  format= %d  div_scale= 1  preset= 34
                    Min = 0  Max = 0  Step = 0  Preset = 0  "
        ::= { iquav10CmdEntry 40326 }


    iquav10AudioOutputRoutingOutDest35 OBJECT-TYPE
        SYNTAX            INTEGER
        MAX-ACCESS        read-write
        STATUS            current
        DESCRIPTION
                "CMNT: - 
                 TYPE: - Number
                 PAGE: - Audio
                    OutDest35  cmdID= 40327
                    min= 0  max= 47  step= 1  format= %d  div_scale= 1  preset= 34
                    Min = 0  Max = 0  Step = 0  Preset = 0  "
        ::= { iquav10CmdEntry 40327 }


    iquav10AudioOutputRoutingOutDest36 OBJECT-TYPE
        SYNTAX            INTEGER
        MAX-ACCESS        read-write
        STATUS            current
        DESCRIPTION
                "CMNT: - 
                 TYPE: - Number
                 PAGE: - Audio
                    OutDest36  cmdID= 40328
                    min= 0  max= 47  step= 1  format= %d  div_scale= 1  preset= 34
                    Min = 0  Max = 0  Step = 0  Preset = 0  "
        ::= { iquav10CmdEntry 40328 }


    iquav10AudioOutputRoutingDolbyEncEnb OBJECT-TYPE
        SYNTAX            RollCallString
        MAX-ACCESS        read-only
        STATUS            current
        DESCRIPTION
                "CMNT: - 
                 TYPE: - Display
                 PAGE: - Audio
                    DolbyEncEnb  cmdID= 40214  "
        ::= { iquav10CmdEntry 40214 }


    iquav10AudioOutputRoutingUpmixEnb OBJECT-TYPE
        SYNTAX            RollCallString
        MAX-ACCESS        read-only
        STATUS            current
        DESCRIPTION
                "CMNT: - 
                 TYPE: - Display
                 PAGE: - Audio
                    UpmixEnb  cmdID= 40213  "
        ::= { iquav10CmdEntry 40213 }


    iquav10AudioProcDefaultEmbed OBJECT-TYPE
        SYNTAX            INTEGER {
                            valCustom(3),
                            valRampp2dB(0),
                            valRampn2dB(1),
                            valLevel0dB(2)
                            }
        MAX-ACCESS        read-write
        STATUS            current
        DESCRIPTION
                "CMNT: - Procamp default
                 TYPE: - RadiobuttonList
                 PAGE: - Audio
                    Embed  cmdID= 43105
                    Custom  value= 3
                    Ramp +2dB  value= 0
                    Ramp -2dB  value= 1
                    Level 0dB  value= 2  "
        ::= { iquav10CmdEntry 43105 }


    iquav10AudioProcDefaultAesOut OBJECT-TYPE
        SYNTAX            INTEGER {
                            valCustom(3),
                            valRampp2dB(0),
                            valRampn2dB(1),
                            valLevel0dB(2)
                            }
        MAX-ACCESS        read-write
        STATUS            current
        DESCRIPTION
                "CMNT: - Procamp default
                 TYPE: - RadiobuttonList
                 PAGE: - Audio
                    AesOut  cmdID= 43106
                    Custom  value= 3
                    Ramp +2dB  value= 0
                    Ramp -2dB  value= 1
                    Level 0dB  value= 2  "
        ::= { iquav10CmdEntry 43106 }


    iquav10AudioProcDefaultAnlgOut OBJECT-TYPE
        SYNTAX            INTEGER {
                            valCustom(3),
                            valRampp2dB(0),
                            valRampn2dB(1),
                            valLevel0dB(2)
                            }
        MAX-ACCESS        read-write
        STATUS            current
        DESCRIPTION
                "CMNT: - Procamp default
                 TYPE: - RadiobuttonList
                 PAGE: - Audio
                    AnlgOut  cmdID= 43107
                    Custom  value= 3
                    Ramp +2dB  value= 0
                    Ramp -2dB  value= 1
                    Level 0dB  value= 2  "
        ::= { iquav10CmdEntry 43107 }


    iquav10AudioRoutingMatrixBus1audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 1 aud sel  cmdID= 40200
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iquav10CmdEntry 40200 }


    iquav10AudioRoutingMatrixBus2audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 2 aud sel  cmdID= 40201
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iquav10CmdEntry 40201 }


    iquav10AudioRoutingMatrixBus3audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 3 aud sel  cmdID= 40202
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iquav10CmdEntry 40202 }


    iquav10AudioRoutingMatrixBus4audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 4 aud sel  cmdID= 40203
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iquav10CmdEntry 40203 }


    iquav10AudioRoutingMatrixBus5audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 5 aud sel  cmdID= 40204
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iquav10CmdEntry 40204 }


    iquav10AudioRoutingMatrixBus6audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 6 aud sel  cmdID= 40205
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iquav10CmdEntry 40205 }


    iquav10AudioRoutingMatrixBus7audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 7 aud sel  cmdID= 40206
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iquav10CmdEntry 40206 }


    iquav10AudioRoutingMatrixBus8audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 8 aud sel  cmdID= 40207
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iquav10CmdEntry 40207 }


    iquav10AudioOutRouteMatrixEmbed12MatrixEmbed11audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed1_1 aud sel  cmdID= 40329
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40329 }


    iquav10AudioOutRouteMatrixEmbed12MatrixEmbed12audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed1_2 aud sel  cmdID= 40330
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40330 }


    iquav10AudioOutRouteMatrixEmbed12MatrixEmbed21audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed2_1 aud sel  cmdID= 40331
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40331 }


    iquav10AudioOutRouteMatrixEmbed12MatrixEmbed22audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed2_2 aud sel  cmdID= 40332
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40332 }


    iquav10AudioOutRouteMatrixEmbed34MatrixEmbed31audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed3_1 aud sel  cmdID= 40333
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40333 }


    iquav10AudioOutRouteMatrixEmbed34MatrixEmbed32audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed3_2 aud sel  cmdID= 40334
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40334 }


    iquav10AudioOutRouteMatrixEmbed34MatrixEmbed41audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed4_1 aud sel  cmdID= 40335
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40335 }


    iquav10AudioOutRouteMatrixEmbed34MatrixEmbed42audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed4_2 aud sel  cmdID= 40336
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40336 }


    iquav10AudioOutRouteMatrixEmbed56MatrixEmbed51audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed5_1 aud sel  cmdID= 40337
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40337 }


    iquav10AudioOutRouteMatrixEmbed56MatrixEmbed52audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed5_2 aud sel  cmdID= 40338
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40338 }


    iquav10AudioOutRouteMatrixEmbed56MatrixEmbed61audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed6_1 aud sel  cmdID= 40339
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40339 }


    iquav10AudioOutRouteMatrixEmbed56MatrixEmbed62audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed6_2 aud sel  cmdID= 40340
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40340 }


    iquav10AudioOutRouteMatrixEmbed78MatrixEmbed71audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed7_1 aud sel  cmdID= 40341
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40341 }


    iquav10AudioOutRouteMatrixEmbed78MatrixEmbed72audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed7_2 aud sel  cmdID= 40342
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40342 }


    iquav10AudioOutRouteMatrixEmbed78MatrixEmbed81audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed8_1 aud sel  cmdID= 40343
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40343 }


    iquav10AudioOutRouteMatrixEmbed78MatrixEmbed82audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed8_2 aud sel  cmdID= 40344
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40344 }


    iquav10AudioOutRouteMatrixAES12MatrixAES11audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES1_1 aud sel  cmdID= 40345
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40345 }


    iquav10AudioOutRouteMatrixAES12MatrixAES12audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES1_2 aud sel  cmdID= 40346
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40346 }


    iquav10AudioOutRouteMatrixAES12MatrixAES21audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES2_1 aud sel  cmdID= 40347
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40347 }


    iquav10AudioOutRouteMatrixAES12MatrixAES22audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES2_2 aud sel  cmdID= 40348
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40348 }


    iquav10AudioOutRouteMatrixAES34MatrixAES31audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES3_1 aud sel  cmdID= 40349
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40349 }


    iquav10AudioOutRouteMatrixAES34MatrixAES32audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES3_2 aud sel  cmdID= 40350
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40350 }


    iquav10AudioOutRouteMatrixAES34MatrixAES41audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES4_1 aud sel  cmdID= 40351
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40351 }


    iquav10AudioOutRouteMatrixAES34MatrixAES42audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES4_2 aud sel  cmdID= 40352
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40352 }


    iquav10AudioOutRouteMatrixAES56MatrixAES51audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES5_1 aud sel  cmdID= 40353
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40353 }


    iquav10AudioOutRouteMatrixAES56MatrixAES52audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES5_2 aud sel  cmdID= 40354
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40354 }


    iquav10AudioOutRouteMatrixAES56MatrixAES61audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES6_1 aud sel  cmdID= 40355
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40355 }


    iquav10AudioOutRouteMatrixAES56MatrixAES62audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES6_2 aud sel  cmdID= 40356
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40356 }


    iquav10AudioOutRouteMatrixAES78MatrixAES71audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES7_1 aud sel  cmdID= 40357
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40357 }


    iquav10AudioOutRouteMatrixAES78MatrixAES72audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES7_2 aud sel  cmdID= 40358
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40358 }


    iquav10AudioOutRouteMatrixAES78MatrixAES81audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES8_1 aud sel  cmdID= 40359
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40359 }


    iquav10AudioOutRouteMatrixAES78MatrixAES82audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    AES8_2 aud sel  cmdID= 40360
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40360 }


    iquav10AudioOutRouteMatrixAnlg12MatrixAnlg11audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Anlg1_1 aud sel  cmdID= 40361
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40361 }


    iquav10AudioOutRouteMatrixAnlg12MatrixAnlg12audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Anlg1_2 aud sel  cmdID= 40362
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40362 }


    iquav10AudioOutRouteMatrixAnlg12MatrixAnlg21audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Anlg2_1 aud sel  cmdID= 40363
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40363 }


    iquav10AudioOutRouteMatrixAnlg12MatrixAnlg22audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Anlg2_2 aud sel  cmdID= 40364
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iquav10CmdEntry 40364 }


    iquav10AudioOutRouteMatrixDefaultsEmbOut OBJECT-TYPE
        SYNTAX            INTEGER {
                            valCustom(10),
                            valEmbedPassthrough(0),
                            valAESPassthrough(1),
                            valDisEm1n4(2),
                            valDisEm1n4AESin1n4(3),
                            valDisEm1n4AESin5n8(4),
                            valAESin1n4(5),
                            valAESin5n8(6),
                            valAnlgin1n2(7),
                            valTone1n2(8),
                            valSilent(9)
                            }
        MAX-ACCESS        read-write
        STATUS            current
        DESCRIPTION
                "CMNT: - 
                 TYPE: - RadiobuttonList
                 PAGE: - AudioOut RouteMatrix
                    Emb Out  cmdID= 40365
                    Custom  value= 10
                    Embed Passthrough  value= 0
                    AES Passthrough  value= 1
                    DisEm1-4  value= 2
                    DisEm1-4 & AESin1-4  value= 3
                    DisEm1-4 & AESin5-8  value= 4
                    AESin1-4  value= 5
                    AESin5-8  value= 6
                    Anlg in 1-2  value= 7
                    Tone 1-2  value= 8
                    Silent  value= 9  "
        ::= { iquav10CmdEntry 40365 }


    iquav10AudioOutRouteMatrixDefaultsAESOut OBJECT-TYPE
        SYNTAX            INTEGER {
                            valCustom(8),
                            valEmbedPassthrough(0),
                            valDisEm1n4nAESout1n4(1),
                            valDisEm1n4nAESout5n8(4),
                            valAESin5n8nAESout1n4(2),
                            valAESin1n4nAESout5n8(3),
                            valAnlgin1n2(5),
                            valTone1n2(6),
                            valSilent(7)
                            }
        MAX-ACCESS        read-write
        STATUS            current
        DESCRIPTION
                "CMNT: - 
                 TYPE: - RadiobuttonList
                 PAGE: - AudioOut RouteMatrix
                    AES Out  cmdID= 40366
                    Custom  value= 8
                    Embed Passthrough  value= 0
                    DisEm1-4->AESout1-4  value= 1
                    DisEm1-4->AESout5-8  value= 4
                    AESin5-8->AESout1-4  value= 2
                    AESin1-4->AESout5-8  value= 3
                    Anlg in 1-2  value= 5
                    Tone 1-2  value= 6
                    Silent  value= 7  "
        ::= { iquav10CmdEntry 40366 }


    iquav10AudioOutRouteMatrixDefaultsAnlgOut OBJECT-TYPE
        SYNTAX            INTEGER {
                            valCustom(5),
                            valDisEmb1n2(0),
                            valAESin1n2(1),
                            valAnlgin1n2(2),
                            valTone1n2(3),
                            valSilent(4)
                            }
        MAX-ACCESS        read-write
        STATUS            current
        DESCRIPTION
                "CMNT: - 
                 TYPE: - RadiobuttonList
                 PAGE: - AudioOut RouteMatrix
                    Anlg Out  cmdID= 40367
                    Custom  value= 5
                    DisEmb1-2  value= 0
                    AES in 1-2  value= 1
                    Anlg in 1-2  value= 2
                    Tone 1-2  value= 3
                    Silent  value= 4  "
        ::= { iquav10CmdEntry 40367 }


    iquav10UpMixerLoud14Source1ProcGain OBJECT-TYPE
        SYNTAX            INTEGER
        MAX-ACCESS        read-write
        STATUS            current
        DESCRIPTION
                "CMNT: - Mix_1 Proc Amp Gain
                 TYPE: - Number
                 PAGE: - UpMixerLoud1_4
                    ProcGain  cmdID= 40834
                    min= -801  max= 120  step= 1  format= %0.1f dB  div_scale= 10  preset= 0
                    Min = -80.1 dB  Max = 12.0 dB  Step = 0.1 dB  Preset = 0.0 dB  "
        ::= { iquav10CmdEntry 40834 }


    iquav10UpMixerLoud14Source1Mute OBJECT-TYPE
        SYNTAX            INTEGER { disable(0), enable(1)  }
        MAX-ACCESS        read-write
        STATUS            current
        DESCRIPTION
                "CMNT: - Mix_1 Mute
                 TYPE: - Checkbox
                 PAGE: - UpMixerLoud1_4
                    Mute  cmdID= 40840  "
        ::= { iquav10CmdEntry 40840 }


    iquav10UpMixerLoud14Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_1 source
                 TYPE: - RadiobuttonList
                 PAGE: - UpMixerLoud1_4
                    Src  cmdID= 40846
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iquav10CmdEntry 40846 }


    iquav10UpMixerLoud14Source2ProcGain OBJECT-TYPE
        SYNTAX            INTEGER
        MAX-ACCESS        read-write
        STATUS            current
        DESCRIPTION
                "CMNT: - Mix_2 Proc Amp Gain
                 TYPE: - Number
                 PAGE: - UpMixerLoud1_4
                    ProcGain  cmdID= 40835
                    min= -801  max= 120  step= 1  format= %0.1f dB  div_scale= 10  preset= 0
                    Min = -80.1 dB  Max = 12.0 dB  Step = 0.1 dB  Preset = 0.0 dB  "
        ::= { iquav10CmdEntry 40835 }


    iquav10UpMixerLoud14Source2Mute OBJECT-TYPE
        SYNTAX            INTEGER { disable(0), enable(1)  }
        MAX-ACCESS        read-write
        STATUS            current
        DESCRIPTION
                "CMNT: - Mix_2 Mute
                 TYPE: - Checkbox
                 PAGE: - UpMixerLoud1_4
                    Mute  cmdID= 40841  "
        ::= { iquav10CmdEntry 40841 }


    iquav10UpMixerLoud14Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_2 source
                 TYPE: - RadiobuttonList
                 PAGE: - UpMixerLoud1_4
                    Src  cmdID= 40847
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iquav10CmdEntry 40847 }


    iquav10UpMixerLoud14Source3ProcGain OBJECT-TYPE
        SYNTAX            INTEGER
        MAX-ACCESS        read-write
        STATUS            current
        DESCRIPTION
                "CMNT: - Mix_3 Proc Amp Gain
                 TYPE: - Number
                 PAGE: - UpMixerLoud1_4
                    ProcGain  cmdID= 40836
                    min= -801  max= 120  step= 1  format= %0.1f dB  div_scale= 10  preset= 0
                    Min = -80.1 dB  Max = 12.0 dB  Step = 0.1 dB  Preset = 0.0 dB  "
        ::= { iquav10CmdEntry 40836 }


    iquav10UpMixerLoud14Source3Mute OBJECT-TYPE
        SYNTAX            INTEGER { disable(0), enable(1)  }
        MAX-ACCESS        read-write
        STATUS            current
        DESCRIPTION
                "CMNT: - Mix_3 Mute
                 TYPE: - Checkbox
                 PAGE: - UpMixerLoud1_4
                    Mute  cmdID= 40842  "
        ::= { iquav10CmdEntry 40842 }


    iquav10UpMixerLoud14Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_3 source
                 TYPE: - RadiobuttonList
                 PAGE: - UpMixerLoud1_4
                    Src  cmdID= 40848
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iquav10CmdEntry 40848 }


    iquav10UpMixerLoud14Source4ProcGain OBJECT-TYPE
        SYNTAX            INTEGER
        MAX-ACCESS        read-write
        STATUS            current
        DESCRIPTION
                "CMNT: - Mix_4 Proc Amp Gain
                 TYPE: - Number
                 PAGE: - UpMixerLoud1_4
                    ProcGain  cmdID= 40837
                    min= -801  max= 120  step= 1  format= %0.1f dB  div_scale= 10  preset= 0
                    Min = -80.1 dB  Max = 12.0 dB  Step = 0.1 dB  Preset = 0.0 dB  "
        ::= { iquav10CmdEntry 40837 }


    iquav10UpMixerLoud14Source4Mute OBJECT-TYPE
        SYNTAX            INTEGER { disable(0), enable(1)  }
        MAX-ACCESS        read-write
        STATUS            current
        DESCRIPTION
                "CMNT: - Mix_4 Mute
                 TYPE: - Checkbox
                 PAGE: - UpMixerLoud1_4
                    Mute  cmdID= 40843  "
        ::= { iquav10CmdEntry 40843 }


    iquav10UpMixerLoud14Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_4 source
                 TYPE: - RadiobuttonList
                 PAGE: - UpMixerLoud1_4
                    Src  cmdID= 40849
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iquav10CmdEntry 40849 }


    iquav10UpMixerLoud14Mode OBJECT-TYPE
        SYNTAX            INTEGER {
                            valAuto(0),
                            valAlwaysUpmix(1),
                            valBypass(2)
                            }
        MAX-ACCESS        read-write
        STATUS            current
        DESCRIPTION
                "CMNT: - UpMixer mode
                 TYPE: - RadiobuttonList
                 PAGE: - UpMixerLoud1_4
                    Mode  cmdID= 40854
                    Auto  value= 0
                    Always Upmix  value= 1
                    Bypass  value= 2  "
        ::= { iquav10CmdEntry 40854 }


    iquav10UpMixerLoud14Status OBJECT-TYPE
        SYNTAX            RollCallString
        MAX-ACCESS        read-only
        STATUS            current
        DESCRIPTION
                "CMNT: - UpMixer status
                 TYPE: - Display
                 PAGE: - UpMixerLoud1_4
                    Status  cmdID= 40855  "
        ::= { iquav10CmdEntry 40855 }


    iquav10UpMixerLoud14XfadeBypass OBJECT-TYPE
        SYNTAX            INTEGER {
                            valVerySlow(0),
                            valSlow(1),
                            valMedium(2),
                            valFast(3),
                            valVeryFast(4),
                            valInstant(5)
                            }
        MAX-ACCESS        read-write
        STATUS            current
        DESCRIPTION
                "CMNT: - UpMixer Xfade to bypass
                 TYPE: - RadiobuttonList
                 PAGE: - UpMixerLoud1_4
                    XfadeBypass  cmdID= 40856
                    Very Slow  value= 0
                    Slow  value= 1
                    Medium  value= 2
                    Fast  value= 3
                    Very Fast  value= 4
                    Instant  value= 5  "
        ::= { iquav10CmdEntry 40856 }


    iquav10UpMixerLoud14XfadeUpmix OBJECT-TYPE
        SYNTAX            INTEGER {
                            valVerySlow(0),
                            valSlow(1),
                            valMedium(2),
                            valFast(3),
                            valVeryFast(4),
                            valInstant(5)
                            }
        MAX-ACCESS        read-write
        STATUS            current
        DESCRIPTION
                "CMNT: - UpMixer Xfade to upmix
                 TYPE: - RadiobuttonList
                 PAGE: - UpMixerLoud1_4
                    XfadeUpmix  cmdID= 40857
                    Very Slow  value= 0
                    Slow  value= 1
                    Medium  value= 2
                    Fast  value= 3
                    Very Fast  value= 4
                    Instant  value= 5  "
        ::= { iquav10CmdEntry 40857 }


    iquav10UpMixerLoud14Detect OBJECT-TYPE
        SYNTAX            INTEGER
        MAX-ACCESS        read-write
        STATUS            current
        DESCRIPTION
                "CMNT: - UpMixer Detection threshold
                 TYPE: - Number
                 PAGE: - UpMixerLoud1_4
                    Detect  cmdID= 40858
                    min= -1500  max= 0  step= 1  format= %0.1f dB  div_scale= 10  preset= -600
                    Min = -150.0 dB  Max = 0.0 dB  Step = 0.1 dB  Preset = -60.0 dB  "
        ::= { iquav10CmdEntry 40858 }


    iquav10UpMixerLoud14CenterWidth OBJECT-TYPE
        SYNTAX            INTEGER
        MAX-ACCESS        read-write
        STATUS            current
        DESCRIPTION
                "CMNT: - UpMixer Center width
                 TYPE: - Number
                 PAGE: - UpMixerLoud1_4
                    CenterWidth  cmdID= 40859
                    min= 0  max= 1000  step= 1  format= %0.1f%%  div_scale= 10  preset= 0
                    Min = 0.0%  Max = 100.0%  Step = 0.1%  Preset = 0.0%  "
        ::= { iquav10CmdEntry 40859 }


    iquav10UpMixerLoud14Surround OBJECT-TYPE
        SYNTAX            INTEGER
        MAX-ACCESS        read-write
        STATUS            current
        DESCRIPTION
                "CMNT: - UpMixer Surround Depth
                 TYPE: - Number
                 PAGE: - UpMixerLoud1_4
                    Surround  cmdID= 40860
                    min= 0  max= 1000  step= 1  format= %0.1f%%  div_scale= 10  preset= 1000
                    Min = 0.0%  Max = 100.0%  Step = 0.1%  Preset = 100.0%  "
        ::= { iquav10CmdEntry 40860 }


    iquav10UpMixerLoud14AlgorithmType OBJECT-TYPE
        SYNTAX            INTEGER {
                            valUpmix(0),
                            valLoudness51(1),
                            valLoudness1p2(2),
                            valLoudness1(3),
                            valUpmixLoudA(5)
                            }
        MAX-ACCESS        read-write
        STATUS            current
        DESCRIPTION
                "CMNT: - Linear Acoustic Algorithm Type
                 TYPE: - RadiobuttonList
                 PAGE: - UpMixerLoud1_4
                    Algorithm Type  cmdID= 36148
                    Upmix  value= 0
                    Loudness5.1  value= 1
                    Loudness1+2  value= 2
                    Loudness1  value= 3
                    UpmixLoudA  value= 5  "
        ::= { iquav10CmdEntry 36148 }


    iquav10UpMixerLoud58LoudnessPreset1 OBJECT-TYPE
        SYNTAX            INTEGER {
                            valGeneral(0),
                            valLight(1),
                            valHeavy(2),
                            valLoud(3),
                            valLoudLimit(4),
                            valProtectionLimit(5),
                            valCustom1(6),
                            valCustom2(7)
                            }
        MAX-ACCESS        read-write
        STATUS            current
        DESCRIPTION
                "CMNT: - Linear Acoustic Preset 1
                 TYPE: - RadiobuttonList
                 PAGE: - UpMixerLoud5_8
                    Preset1  cmdID= 36151
                    General  value= 0
                    Light  value= 1
                    Heavy  value= 2
                    Loud  value= 3
                    Loud Limit  value= 4
                    Protection Limit  value= 5
                    Custom 1  value= 6
                    Custom 2  value= 7  "
        ::= { iquav10CmdEntry 36151 }


    iquav10UpMixerLoud58LoudnessMasterLevel1 OBJECT-TYPE
        SYNTAX            INTEGER
        MAX-ACCESS        read-write
        STATUS            current
        DESCRIPTION
                "CMNT: - Linear Acoustic Master level 1
                 TYPE: - Number
                 PAGE: - UpMixerLoud5_8
                    MasterLevel1  cmdID= 36149
                    min= -310  max= 0  step= 1  format= %0.1f dB  div_scale= 10  preset= -110
                    Min = -31.0 dB  Max = 0.0 dB  Step = 0.1 dB  Preset = -11.0 dB  "
        ::= { iquav10CmdEntry 36149 }


    iquav10UpMixerLoud58LoudnessName1 OBJECT-TYPE
        SYNTAX            RollCallString
        MAX-ACCESS        read-only
        STATUS            current
        DESCRIPTION
                "CMNT: - Linear Acoustic Name 1
                 TYPE: - Display
                 PAGE: - UpMixerLoud5_8
                    Name1  cmdID= 36153  "
        ::= { iquav10CmdEntry 36153 }


    iquav10UpMixerLoud58LoudnessBypass1 OBJECT-TYPE
        SYNTAX            INTEGER { disable(0), enable(1)  }
        MAX-ACCESS        read-write
        STATUS            current
        DESCRIPTION
                "CMNT: - Linear Acoustic Bypass 1
                 TYPE: - Checkbox
                 PAGE: - UpMixerLoud5_8
                    Bypass 1  cmdID= 36173  "
        ::= { iquav10CmdEntry 36173 }


    iquav10UpMixerLoud58LoudnessPreset2 OBJECT-TYPE
        SYNTAX            INTEGER {
                            valGeneral(0),
                            valLight(1),
                            valHeavy(2),
                            valLoud(3),
                            valLoudLimit(4),
                            valProtectionLimit(5),
                            valCustom1(6),
                            valCustom2(7)
                            }
        MAX-ACCESS        read-write
        STATUS            current
        DESCRIPTION
                "CMNT: - Linear Acoustic Preset 2
                 TYPE: - RadiobuttonList
                 PAGE: - UpMixerLoud5_8
                    Preset2  cmdID= 36152
                    General  value= 0
                    Light  value= 1
                    Heavy  value= 2
                    Loud  value= 3
                    Loud Limit  value= 4
                    Protection Limit  value= 5
                    Custom 1  value= 6
                    Custom 2  value= 7  "
        ::= { iquav10CmdEntry 36152 }


    iquav10UpMixerLoud58LoudnessMasterLevel2 OBJECT-TYPE
        SYNTAX            INTEGER
        MAX-ACCESS        read-write
        STATUS            current
        DESCRIPTION
                "CMNT: - Linear Acoustic Master level 2
                 TYPE: - Number
                 PAGE: - UpMixerLoud5_8
                    MasterLevel2  cmdID= 36150
                    min= -310  max= 0  step= 1  format= %0.1f dB  div_scale= 10  preset= -110
                    Min = -31.0 dB  Max = 0.0 dB  Step = 0.1 dB  Preset = -11.0 dB  "
        ::= { iquav10CmdEntry 36150 }


    iquav10UpMixerLoud58LoudnessName2 OBJECT-TYPE
        SYNTAX            RollCallString
        MAX-ACCESS        read-only
        STATUS            current
        DESCRIPTION
                "CMNT: - Linear Acoustic Name 2
                 TYPE: - Display
                 PAGE: - UpMixerLoud5_8
                    Name2  cmdID= 36154  "
        ::= { iquav10CmdEntry 36154 }


    iquav10UpMixerLoud58LoudnessBypass2 OBJECT-TYPE
        SYNTAX            INTEGER { disable(0), enable(1)  }
        MAX-ACCESS        read-write
        STATUS            current
        DESCRIPTION
                "CMNT: - Linear Acoustic Bypass 2
                 TYPE: - Checkbox
                 PAGE: - UpMixerLoud5_8
                    Bypass 2  cmdID= 36174  "
        ::= { iquav10CmdEntry 36174 }


    iquav10UpMixerLoud58Source5ProcGain OBJECT-TYPE
        SYNTAX            INTEGER
        MAX-ACCESS        read-write
        STATUS            current
        DESCRIPTION
                "CMNT: - Mix_5 Proc Amp Gain
                 TYPE: - Number
                 PAGE: - UpMixerLoud5_8
                    ProcGain  cmdID= 40838
                    min= -801  max= 120  step= 1  format= %0.1f dB  div_scale= 10  preset= 0
                    Min = -80.1 dB  Max = 12.0 dB  Step = 0.1 dB  Preset = 0.0 dB  "
        ::= { iquav10CmdEntry 40838 }


    iquav10UpMixerLoud58Source5Mute OBJECT-TYPE
        SYNTAX            INTEGER { disable(0), enable(1)  }
        MAX-ACCESS        read-write
        STATUS            current
        DESCRIPTION
                "CMNT: - Mix_5 Mute
                 TYPE: - Checkbox
                 PAGE: - UpMixerLoud5_8
                    Mute  cmdID= 40844  "
        ::= { iquav10CmdEntry 40844 }


    iquav10UpMixerLoud58Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_5 source
                 TYPE: - RadiobuttonList
                 PAGE: - UpMixerLoud5_8
                    Src  cmdID= 40850
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iquav10CmdEntry 40850 }


    iquav10UpMixerLoud58Source6ProcGain OBJECT-TYPE
        SYNTAX            INTEGER
        MAX-ACCESS        read-write
        STATUS            current
        DESCRIPTION
                "CMNT: - Mix_6 Proc Amp Gain
                 TYPE: - Number
                 PAGE: - UpMixerLoud5_8
                    ProcGain  cmdID= 40839
                    min= -801  max= 120  step= 1  format= %0.1f dB  div_scale= 10  preset= 0
                    Min = -80.1 dB  Max = 12.0 dB  Step = 0.1 dB  Preset = 0.0 dB  "
        ::= { iquav10CmdEntry 40839 }


    iquav10UpMixerLoud58Source6Mute OBJECT-TYPE
        SYNTAX            INTEGER { disable(0), enable(1)  }
        MAX-ACCESS        read-write
        STATUS            current
        DESCRIPTION
                "CMNT: - Mix_6 Mute
                 TYPE: - Checkbox
                 PAGE: - UpMixerLoud5_8
                    Mute  cmdID= 40845  "
        ::= { iquav10CmdEntry 40845 }


    iquav10UpMixerLoud58Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_6 source
                 TYPE: - RadiobuttonList
                 PAGE: - UpMixerLoud5_8
                    Src  cmdID= 40851
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iquav10CmdEntry 40851 }


    iquav10UpMixerLoud58Source7ProcGain OBJECT-TYPE
        SYNTAX            INTEGER
        MAX-ACCESS        read-write
        STATUS            current
        DESCRIPTION
                "CMNT: - Mix_7 Proc Amp Gain
                 TYPE: - Number
                 PAGE: - UpMixerLoud5_8
                    ProcGain  cmdID= 40873
                    min= -801  max= 120  step= 1  format= %0.1f dB  div_scale= 10  preset= 0
                    Min = -80.1 dB  Max = 12.0 dB  Step = 0.1 dB  Preset = 0.0 dB  "
        ::= { iquav10CmdEntry 40873 }


    iquav10UpMixerLoud58Source7Mute OBJECT-TYPE
        SYNTAX            INTEGER { disable(0), enable(1)  }
        MAX-ACCESS        read-write
        STATUS            current
        DESCRIPTION
                "CMNT: - Mix_7 Mute
                 TYPE: - Checkbox
                 PAGE: - UpMixerLoud5_8
                    Mute  cmdID= 40875  "
        ::= { iquav10CmdEntry 40875 }


    iquav10UpMixerLoud58Source7Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_7 source
                 TYPE: - RadiobuttonList
                 PAGE: - UpMixerLoud5_8
                    Src  cmdID= 40877
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iquav10CmdEntry 40877 }


    iquav10UpMixerLoud58Source8ProcGain OBJECT-TYPE
        SYNTAX            INTEGER
        MAX-ACCESS        read-write
        STATUS            current
        DESCRIPTION
                "CMNT: - Mix_8 Proc Amp Gain
                 TYPE: - Number
                 PAGE: - UpMixerLoud5_8
                    ProcGain  cmdID= 40874
                    min= -801  max= 120  step= 1  format= %0.1f dB  div_scale= 10  preset= 0
                    Min = -80.1 dB  Max = 12.0 dB  Step = 0.1 dB  Preset = 0.0 dB  "
        ::= { iquav10CmdEntry 40874 }


    iquav10UpMixerLoud58Source8Mute OBJECT-TYPE
        SYNTAX            INTEGER { disable(0), enable(1)  }
        MAX-ACCESS        read-write
        STATUS            current
        DESCRIPTION
                "CMNT: - Mix_8 Mute
                 TYPE: - Checkbox
                 PAGE: - UpMixerLoud5_8
                    Mute  cmdID= 40876  "
        ::= { iquav10CmdEntry 40876 }


    iquav10UpMixerLoud58Source8Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_8 source
                 TYPE: - RadiobuttonList
                 PAGE: - UpMixerLoud5_8
                    Src  cmdID= 40878
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iquav10CmdEntry 40878 }


    iquav10UpMixerLoud58UpmixHide OBJECT-TYPE
        SYNTAX            RollCallString
        MAX-ACCESS        read-only
        STATUS            current
        DESCRIPTION
                "CMNT: - Hide Upmix
                 TYPE: - Display
                 PAGE: - UpMixerLoud5_8
                    UpmixHide  cmdID= 36155  "
        ::= { iquav10CmdEntry 36155 }


    iquav10UpMixerLoud58Chan1Name OBJECT-TYPE
        SYNTAX            RollCallString
        MAX-ACCESS        read-only
        STATUS            current
        DESCRIPTION
                "CMNT: - Linear Acoustic Chan Name 1
                 TYPE: - Display
                 PAGE: - UpMixerLoud5_8
                    Chan1Name  cmdID= 36158  "
        ::= { iquav10CmdEntry 36158 }


    iquav10UpMixerLoud58Chan2Name OBJECT-TYPE
        SYNTAX            RollCallString
        MAX-ACCESS        read-only
        STATUS            current
        DESCRIPTION
                "CMNT: - Linear Acoustic Chan Name 2
                 TYPE: - Display
                 PAGE: - UpMixerLoud5_8
                    Chan2Name  cmdID= 36159  "
        ::= { iquav10CmdEntry 36159 }


    iquav10UpMixerLoud58Chan3Name OBJECT-TYPE
        SYNTAX            RollCallString
        MAX-ACCESS        read-only
        STATUS            current
        DESCRIPTION
                "CMNT: - Linear Acoustic Chan Name 3
                 TYPE: - Display
                 PAGE: - UpMixerLoud5_8
                    Chan3Name  cmdID= 36160  "
        ::= { iquav10CmdEntry 36160 }


    iquav10UpMixerLoud58Chan4Name OBJECT-TYPE
        SYNTAX            RollCallString
        MAX-ACCESS        read-only
        STATUS            current
        DESCRIPTION
                "CMNT: - Linear Acoustic Chan Name 4
                 TYPE: - Display
                 PAGE: - UpMixerLoud5_8
                    Chan4Name  cmdID= 36161  "
        ::= { iquav10CmdEntry 36161 }


    iquav10UpMixerLoud58Chan5Name OBJECT-TYPE
        SYNTAX            RollCallString
        MAX-ACCESS        read-only
        STATUS            current
        DESCRIPTION
                "CMNT: - Linear Acoustic Chan Name 5
                 TYPE: - Display
                 PAGE: - UpMixerLoud5_8
                    Chan5Name  cmdID= 36162  "
        ::= { iquav10CmdEntry 36162 }


    iquav10UpMixerLoud58Chan6Name OBJECT-TYPE
        SYNTAX            RollCallString
        MAX-ACCESS        read-only
        STATUS            current
        DESCRIPTION
                "CMNT: - Linear Acoustic Chan Name 6
                 TYPE: - Display
                 PAGE: - UpMixerLoud5_8
                    Chan6Name  cmdID= 36163  "
        ::= { iquav10CmdEntry 36163 }


    iquav10UpMixerLoud58Chan7Name OBJECT-TYPE
        SYNTAX            RollCallString
        MAX-ACCESS        read-only
        STATUS            current
        DESCRIPTION
                "CMNT: - Linear Acoustic Chan Name 7
                 TYPE: - Display
                 PAGE: - UpMixerLoud5_8
                    Chan7Name  cmdID= 36183  "
        ::= { iquav10CmdEntry 36183 }


    iquav10UpMixerLoud58Chan8Name OBJECT-TYPE
        SYNTAX            RollCallString
        MAX-ACCESS        read-only
        STATUS            current
        DESCRIPTION
                "CMNT: - Linear Acoustic Chan Name 8
                 TYPE: - Display
                 PAGE: - UpMixerLoud5_8
                    Chan8Name  cmdID= 36184  "
        ::= { iquav10CmdEntry 36184 }


    iquav10UpMixerLoud58Chan1NameIn OBJECT-TYPE
        SYNTAX            RollCallString
        MAX-ACCESS        read-only
        STATUS            current
        DESCRIPTION
                "CMNT: - Linear Acoustic Chan Name 1
                 TYPE: - Display
                 PAGE: - UpMixerLoud5_8
                    Chan1NameIn  cmdID= 36175  "
        ::= { iquav10CmdEntry 36175 }


    iquav10UpMixerLoud58Chan2NameIn OBJECT-TYPE
        SYNTAX            RollCallString
        MAX-ACCESS        read-only
        STATUS            current
        DESCRIPTION
                "CMNT: - Linear Acoustic Chan Name 2
                 TYPE: - Display
                 PAGE: - UpMixerLoud5_8
                    Chan2NameIn  cmdID= 36176  "
        ::= { iquav10CmdEntry 36176 }


    iquav10UpMixerLoud58Chan3NameIn OBJECT-TYPE
        SYNTAX            RollCallString
        MAX-ACCESS        read-only
        STATUS            current
        DESCRIPTION
                "CMNT: - Linear Acoustic Chan Name 3
                 TYPE: - Display
                 PAGE: - UpMixerLoud5_8
                    Chan3NameIn  cmdID= 36177  "
        ::= { iquav10CmdEntry 36177 }


    iquav10UpMixerLoud58Chan4NameIn OBJECT-TYPE
        SYNTAX            RollCallString
        MAX-ACCESS        read-only
        STATUS            current
        DESCRIPTION
                "CMNT: - Linear Acoustic Chan Name 4
                 TYPE: - Display
                 PAGE: - UpMixerLoud5_8
                    Chan4NameIn  cmdID= 36178  "
        ::= { iquav10CmdEntry 36178 }


    iquav10UpMixerLoud58Chan5NameIn OBJECT-TYPE
        SYNTAX            RollCallString
        MAX-ACCESS        read-only
        STATUS            current
        DESCRIPTION
                "CMNT: - Linear Acoustic Chan Name 5
                 TYPE: - Display
                 PAGE: - UpMixerLoud5_8
                    Chan5NameIn  cmdID= 36179  "
        ::= { iquav10CmdEntry 36179 }


    iquav10UpMixerLoud58Chan6NameIn OBJECT-TYPE
        SYNTAX            RollCallString
        MAX-ACCESS        read-only
        STATUS            current
        DESCRIPTION
                "CMNT: - Linear Acoustic Chan Name 6
                 TYPE: - Display
                 PAGE: - UpMixerLoud5_8
                    Chan6NameIn  cmdID= 36180  "
        ::= { iquav10CmdEntry 36180 }


    iquav10UpMixerLoud58Chan7NameIn OBJECT-TYPE
        SYNTAX            RollCallString
        MAX-ACCESS        read-only
        STATUS            current
        DESCRIPTION
                "CMNT: - Linear Acoustic Chan Name 7
                 TYPE: - Display
                 PAGE: - UpMixerLoud5_8
                    Chan7NameIn  cmdID= 36181  "
        ::= { iquav10CmdEntry 36181 }


    iquav10UpMixerLoud58Chan8NameIn OBJECT-TYPE
        SYNTAX            RollCallString
        MAX-ACCESS        read-only
        STATUS            current
        DESCRIPTION
                "CMNT: - Linear Acoustic Chan Name 8
                 TYPE: - Display
                 PAGE: - UpMixerLoud5_8
                    Chan8NameIn  cmdID= 36182  "
        ::= { iquav10CmdEntry 36182 }


    iquav10UpMixerLoud58DialogHide OBJECT-TYPE
        SYNTAX            RollCallString
        MAX-ACCESS        read-only
        STATUS            current
        DESCRIPTION
                "CMNT: - Hide Upmix DIALOG
                 TYPE: - Display
                 PAGE: - UpMixerLoud5_8
                    DialogHide  cmdID= 36164  "
        ::= { iquav10CmdEntry 36164 }


    iquav10LoudCustomBlock1Name OBJECT-TYPE
        SYNTAX            RollCallString
        MAX-ACCESS        read-write
        STATUS            current
        DESCRIPTION
                "CMNT: - Linear Acoustic MB Block1 Name
                 TYPE: - Editstring
                 PAGE: - LoudCustom
                    Name  cmdID= 36304
                    preset= Custom Block 1"
        ::= { iquav10CmdEntry 36304 }


    iquav10LoudCustomBlock1inagcfreeze OBJECT-TYPE
        SYNTAX            INTEGER
        MAX-ACCESS        read-write
        STATUS            current
        DESCRIPTION
                "CMNT: - Linear Acoustic InAGC Block1 Freeze Threshold
                 TYPE: - Number
                 PAGE: - LoudCustom
                    inagc freeze  cmdID= 36200
                    min= -180  max= 0  step= 1  format= %0.1f dBFS  div_scale= 2  preset= -62
                    Min = -90.0 dBFS  Max = 0.0 dBFS  Step = 0.5 dBFS  Preset = -31.0 dBFS  "
        ::= { iquav10CmdEntry 36200 }


    iquav10LoudCustomBlock1inagcgate OBJECT-TYPE
        SYNTAX            INTEGER
        MAX-ACCESS        read-write
        STATUS            current
        DESCRIPTION
                "CMNT: - Linear Acoustic InAGC Block1 Gate Threshold
                 TYPE: - Number
                 PAGE: - LoudCustom
                    inagc gate  cmdID= 36202
                    min= -180  max= 0  step= 1  format= %0.1f dBFS  div_scale= 2  preset= -42
                    Min = -90.0 dBFS  Max = 0.0 dBFS  Step = 0.5 dBFS  Preset = -21.0 dBFS  "
        ::= { iquav10CmdEntry 36202 }


    iquav10LoudCustomBlock1inagcratio OBJECT-TYPE
        SYNTAX            INTEGER
        MAX-ACCESS        read-write
        STATUS            current
        DESCRIPTION
                "CMNT: - Linear Acoustic InAGC Block1 Ratio
                 TYPE: - Number
                 PAGE: - LoudCustom
                    inagc ratio  cmdID= 36208
                    min= 0  max= 100  step= 1  format= %0.0f  div_scale= 1  preset= 91
                    Min = 0  Max = 100  Step = 1  Preset = 91  "
        ::= { iquav10CmdEntry 36208 }


    iquav10LoudCustomBlock1inagcrange OBJECT-TYPE
        SYNTAX            INTEGER
        MAX-ACCESS        read-write
        STATUS            current
        DESCRIPTION
                "CMNT: - Linear Acoustic InAGC Block1 Range
                 TYPE: - Number
                 PAGE: - LoudCustom
                    inagc range  cmdID= 36206
                    min= 0  max= 180  step= 1  format= %0.1f dB  div_scale= 5  preset= 125
                    Min = 0.0 dB  Max = 36.0 dB  Step = 0.2 dB  Preset = 25.0 dB  "
        ::= { iquav10CmdEntry 36206 }


    iquav10LoudCustomBlock1inagcthresh OBJECT-TYPE
        SYNTAX            INTEGER
        MAX-ACCESS        read-write
        STATUS            current
        DESCRIPTION
                "CMNT: - Linear Acoustic InAGC Block1 Threshold
                 TYPE: - Number
                 PAGE: - LoudCustom
                    inagc thresh  cmdID= 36204
                    min= -180  max= 0  step= 1  format= %0.1f dBFS  div_scale= 10  preset= -140
                    Min = -18.0 dBFS  Max = 0.0 dBFS  Step = 0.1 dBFS  Preset = -14.0 dBFS  "
        ::= { iquav10CmdEntry 36204 }


    iquav10LoudCustomBlock1inagcattack OBJECT-TYPE
        SYNTAX            INTEGER
        MAX-ACCESS        read-write
        STATUS            current
        DESCRIPTION
                "CMNT: - Linear Acoustic InAGC Block1 Attack
                 TYPE: - Number
                 PAGE: - LoudCustom
                    inagc attack  cmdID= 36210
                    min= 1  max= 100  step= 1  format= %0.0f  div_scale= 1  preset= 24
                    Min = 1  Max = 100  Step = 1  Preset = 24  "
        ::= { iquav10CmdEntry 36210 }


    iquav10LoudCustomBlock1inagcrelease OBJECT-TYPE
        SYNTAX            INTEGER
        MAX-ACCESS        read-write
        STATUS            current
        DESCRIPTION
                "CMNT: - Linear Acoustic InAGC Block1 Release
                 TYPE: - Number
                 PAGE: - LoudCustom
                    inagc release  cmdID= 36212
                    min= 1  max= 100  step= 1  format= %0.0f  div_scale= 1  preset= 42
                    Min = 1  Max = 100  Step = 1  Preset = 42  "
        ::= { iquav10CmdEntry 36212 }


    iquav10LoudCustomBlock1peqfreq1 OBJECT-TYPE
        SYNTAX            INTEGER
        MAX-ACCESS        read-write
        STATUS            current
        DESCRIPTION
                "CMNT: - Linear Acoustic PEQ Block1 Index 1 Frequency
                 TYPE: - Number
                 PAGE: - LoudCustom
                    peq freq 1  cmdID= 36276
                    min= 20  max= 20000  step= 1  format= %0.0f Hz  div_scale= 1  preset= 1000
                    Min = 20 Hz  Max = 20000 Hz  Step = 1 Hz  Preset = 1000 Hz  "
        ::= { iquav10CmdEntry 36276 }


    iquav10LoudCustomBlock1peqq1 OBJECT-TYPE
        SYNTAX            INTEGER
        MAX-ACCESS        read-write
        STATUS            current
        DESCRIPTION
                "CMNT: - Linear Acoustic PEQ Block1 Index 1 Q
                 TYPE: - Number
                 PAGE: - LoudCustom
                    peq q 1  cmdID= 36282
                    min= 1  max= 200  step= 1  format= %0.2f  div_scale= 20  preset= 20
                    Min = 0.05  Max = 10.00  Step = 0.05  Preset = 1.00  "
        ::= { iquav10CmdEntry 36282 }


    iquav10LoudCustomBlock1peqlevel1 OBJECT-TYPE
        SYNTAX            INTEGER
        MAX-ACCESS        read-write
        STATUS            current
        DESCRIPTION
                "CMNT: - Linear Acoustic PEQ Block1 Index 1 Level
                 TYPE: - Number
                 PAGE: - LoudCustom
                    peq level 1  cmdID= 36288
                    min= -90  max= 90  step= 1  format= %0.1f dB  div_scale= 5  preset= 0
                    Min = -18.0 dB  Max = 18.0 dB  Step = 0.2 dB  Preset = 0.0 dB  "
        ::= { iquav10CmdEntry 36288 }


    iquav10LoudCustomBlock1peqfreq2 OBJECT-TYPE
        SYNTAX            INTEGER
        MAX-ACCESS        read-write
        STATUS            current
        DESCRIPTION
                "CMNT: - Linear Acoustic PEQ Block1 Index 2 Frequency
                 TYPE: - Number
                 PAGE: - LoudCustom
                    peq freq 2  cmdID= 36277
                    min= 20  max= 20000  step= 1  format= %0.0f Hz  div_scale= 1  preset= 1000
                    Min = 20 Hz  Max = 20000 Hz  Step = 1 Hz  Preset = 1000 Hz  "
        ::= { iquav10CmdEntry 36277 }


    iquav10LoudCustomBlock1peqq2 OBJECT-TYPE
        SYNTAX            INTEGER
        MAX-ACCESS        read-write
        STATUS            current
        DESCRIPTION
                "CMNT: - Linear Acoustic PEQ Block1 Index 2 Q
                 TYPE: - Number
                 PAGE: - LoudCustom
                    peq q 2  cmdID= 36283
                    min= 1  max= 200  step= 1  format= %0.2f  div_scale= 20  preset= 20
                    Min = 0.05  Max = 10.00  Step = 0.05  Preset = 1.00  "
        ::= { iquav10CmdEntry 36283 }


    iquav10LoudCustomBlock1peqlevel2 OBJECT-TYPE
        SYNTAX            INTEGER
        MAX-ACCESS        read-write
        STATUS            current
        DESCRIPTION
                "CMNT: - Linear Acoustic PEQ Block1 Index 2 Level
                 TYPE: - Number
                 PAGE: - LoudCustom
                    peq level 2  cmdID= 36289
                    min= -90  max= 90  step= 1  format= %0.1f dB  div_scale= 5  preset= 0
                    Min = -18.0 dB  Max = 18.0 dB  Step = 0.2 dB  Preset = 0.0 dB  "
        ::= { iquav10CmdEntry 36289 }


    iquav10LoudCustomBlock1peqfreq3 OBJECT-TYPE
        SYNTAX            INTEGER
        MAX-ACCESS        read-write
        STATUS            current
        DESCRIPTION
                "CMNT: - Linear Acoustic PEQ Block1 Index 3 Frequency
                 TYPE: - Number
                 PAGE: - LoudCustom
                    peq freq 3  cmdID= 36278
                    min= 20  max= 20000  step= 1  format= %0.0f Hz  div_scale= 1  preset= 1000
                    Min = 20 Hz  Max = 20000 Hz  Step = 1 Hz  Preset = 1000 Hz  "
        ::= { iquav10CmdEntry 36278 }


    iquav10LoudCustomBlock1peqq3 OBJECT-TYPE
        SYNTAX            INTEGER
        MAX-ACCESS        read-write
        STATUS            current
        DESCRIPTION
                "CMNT: - Linear Acoustic PEQ Block1 Index 3 Q
                 TYPE: - Number
                 PAGE: - LoudCustom
                    peq q 3  cmdID= 36284
                    min= 1  max= 200  step= 1  format= %0.2f  div_scale= 20  preset= 20
                    Min = 0.05  Max = 10.00  Step = 0.05  Preset = 1.00  "
        ::= { iquav10CmdEntry 36284 }


    iquav10LoudCustomBlock1peqlevel3 OBJECT-TYPE
        SYNTAX            INTEGER
        MAX-ACCESS        read-write
        STATUS            current
        DESCRIPTION
                "CMNT: - Linear Acoustic PEQ Block1 Index 3 Level
                 TYPE: - Number
                 PAGE: - LoudCustom
                    peq level 3  cmdID= 36290
                    min= -90  max= 90  step= 1  format= %0.1f dB  div_scale= 5  preset= 0
                    Min = -18.0 dB  Max = 18.0 dB  Step = 0.2 dB  Preset = 0.0 dB  "
        ::= { iquav10CmdEntry 36290 }


    iquav10LoudCustomBlock1mbagcatk1 OBJECT-TYPE
        SYNTAX            INTEGER
        MAX-ACCESS        read-write
        STATUS            current
        DESCRIPTION
                "CMNT: - Linear Acoustic MBAGC Block1 Index 1 Attack
                 TYPE: - Number
                 PAGE: - LoudCustom
                    mbagc atk 1  cmdID= 36236
                    min= 0  max= 100  step= 1  format= %0.0f  div_scale= 1  preset= 24
                    Min = 0  Max = 100  Step = 1  Preset = 24  "
        ::= { iquav10CmdEntry 36236 }


    iquav10LoudCustomBlock1mbagcrel1 OBJECT-TYPE
        SYNTAX            INTEGER
        MAX-ACCESS        read-write
        STATUS            current
        DESCRIPTION
                "CMNT: - Linear Acoustic MBAGC Block1 Index 1 Release
                 TYPE: - Number
                 PAGE: - LoudCustom
                    mbagc rel 1  cmdID= 36226
                    min= 0  max= 100  step= 1  format= %0.0f  div_scale= 1  preset= 42
                    Min = 0  Max = 100  Step = 1  Preset = 42  "
        ::= { iquav10CmdEntry 36226 }


    iquav10LoudCustomBlock1mbagcthresh1 OBJECT-TYPE
        SYNTAX            INTEGER
        MAX-ACCESS        read-write
        STATUS            current
        DESCRIPTION
                "CMNT: - Linear Acoustic MBAGC Block1 Index 1 Threshold
                 TYPE: - Number
                 PAGE: - LoudCustom
                    mbagc thresh 1  cmdID= 36246
                    min= -120  max= 120  step= 1  format= %0.1f dB  div_scale= 10  preset= 0
                    Min = -12.0 dB  Max = 12.0 dB  Step = 0.1 dB  Preset = 0.0 dB  "
        ::= { iquav10CmdEntry 36246 }


    iquav10LoudCustomBlock1mbagcoutlev1 OBJECT-TYPE
        SYNTAX            INTEGER
        MAX-ACCESS        read-write
        STATUS            current
        DESCRIPTION
                "CMNT: - Linear Acoustic MBAGC Block1 Index 1 OutLevel
                 TYPE: - Number
                 PAGE: - LoudCustom
                    mbagc outlev 1  cmdID= 36266
                    min= -120  max= 120  step= 1  format= %0.1f dB  div_scale= 10  preset= 0
                    Min = -12.0 dB  Max = 12.0 dB  Step = 0.1 dB  Preset = 0.0 dB  "
        ::= { iquav10CmdEntry 36266 }


    iquav10LoudCustomBlock1mbagclimthresh1 OBJECT-TYPE
        SYNTAX            INTEGER
        MAX-ACCESS        read-write
        STATUS            current
        DESCRIPTION
                "CMNT: - Linear Acoustic MBAGC Block1 Index 1 Limit Threshold
                 TYPE: - Number
                 PAGE: - LoudCustom
                    mbagc limthresh 1  cmdID= 36256
                    min= 0  max= 180  step= 1  format= %0.1f dB  div_scale= 10  preset= 0
                    Min = 0.0 dB  Max = 18.0 dB  Step = 0.1 dB  Preset = 0.0 dB  "
        ::= { iquav10CmdEntry 36256 }


    iquav10LoudCustomBlock1mbagcinfthr1 OBJECT-TYPE
        SYNTAX            INTEGER { disable(0), enable(1)  }
        MAX-ACCESS        read-write
        STATUS            current
        DESCRIPTION
                "CMNT: - Linear Acoustic MBAGC Block1 Index 1 InfThr
                 TYPE: - Checkbox
                 PAGE: - LoudCustom
                    mbagc infthr 1  cmdID= 36294  "
        ::= { iquav10CmdEntry 36294 }


    iquav10LoudCustomBlock1mbagcatk2 OBJECT-TYPE
        SYNTAX            INTEGER
        MAX-ACCESS        read-write
        STATUS            current
        DESCRIPTION
                "CMNT: - Linear Acoustic MBAGC Block1 Index 2 Attack
                 TYPE: - Number
                 PAGE: - LoudCustom
                    mbagc atk 2  cmdID= 36237
                    min= 0  max= 100  step= 1  format= %0.0f  div_scale= 1  preset= 24
                    Min = 0  Max = 100  Step = 1  Preset = 24  "
        ::= { iquav10CmdEntry 36237 }


    iquav10LoudCustomBlock1mbagcrel2 OBJECT-TYPE
        SYNTAX            INTEGER
        MAX-ACCESS        read-write
        STATUS            current
        DESCRIPTION
                "CMNT: - Linear Acoustic MBAGC Block1 Index 2 Release
                 TYPE: - Number
                 PAGE: - LoudCustom
                    mbagc rel 2  cmdID= 36227
                    min= 0  max= 100  step= 1  format= %0.0f  div_scale= 1  preset= 42
                    Min = 0  Max = 100  Step = 1  Preset = 42  "
        ::= { iquav10CmdEntry 36227 }


    iquav10LoudCustomBlock1mbagcthresh2 OBJECT-TYPE
        SYNTAX            INTEGER
        MAX-ACCESS        read-write
        STATUS            current
        DESCRIPTION
                "CMNT: - Linear Acoustic MBAGC Block1 Index 2 Threshold
                 TYPE: - Number
                 PAGE: - LoudCustom
                    mbagc thresh 2  cmdID= 36247
                    min= -120  max= 120  step= 1  format= %0.1f dB  div_scale= 10  preset= 0
                    Min = -12.0 dB  Max = 12.0 dB  Step = 0.1 dB  Preset = 0.0 dB  "
        ::= { iquav10CmdEntry 36247 }


    iquav10LoudCustomBlock1mbagcoutlev2 OBJECT-TYPE
        SYNTAX            INTEGER
        MAX-ACCESS        read-write
        STATUS            current
        DESCRIPTION
                "CMNT: - Linear Acoustic MBAGC Block1 Index 2 OutLevel
                 TYPE: - Number
                 PAGE: - LoudCustom
                    mbagc outlev 2  cmdID= 36267
                    min= -120  max= 120  step= 1  format= %0.1f dB  div_scale= 10  preset= 0
                    Min = -12.0 dB  Max = 12.0 dB  Step = 0.1 dB  Preset = 0.0 dB  "
        ::= { iquav10CmdEntry 36267 }


    iquav10LoudCustomBlock1mbagclimthresh2 OBJECT-TYPE
        SYNTAX            INTEGER
        MAX-ACCESS        read-write
        STATUS            current
        DESCRIPTION
                "CMNT: - Linear Acoustic MBAGC Block1 Index 2 Limit Threshold
                 TYPE: - Number
                 PAGE: - LoudCustom
                    mbagc limthresh 2  cmdID= 36257
                    min= 0  max= 180  step= 1  format= %0.1f dB  div_scale= 10  preset= 0
                    Min = 0.0 dB  Max = 18.0 dB  Step = 0.1 dB  Preset = 0.0 dB  "
        ::= { iquav10CmdEntry 36257 }


    iquav10LoudCustomBlock1mbagcinfthr2 OBJECT-TYPE
        SYNTAX            INTEGER { disable(0), enable(1)  }
        MAX-ACCESS        read-write
        STATUS            current
        DESCRIPTION
                "CMNT: - Linear Acoustic MBAGC Block1 Index 2 InfThr
                 TYPE: - Checkbox
                 PAGE: - LoudCustom
                    mbagc infthr 2  cmdID= 36295  "
        ::= { iquav10CmdEntry 36295 }


    iquav10LoudCustomBlock1mbagcatk3 OBJECT-TYPE
        SYNTAX            INTEGER
        MAX-ACCESS        read-write
        STATUS            current
        DESCRIPTION
                "CMNT: - Linear Acoustic MBAGC Block1 Index 3 Attack
                 TYPE: - Number
                 PAGE: - LoudCustom
                    mbagc atk 3  cmdID= 36238
                    min= 0  max= 100  step= 1  format= %0.0f  div_scale= 1  preset= 24
                    Min = 0  Max = 100  Step = 1  Preset = 24  "
        ::= { iquav10CmdEntry 36238 }


    iquav10LoudCustomBlock1mbagcrel3 OBJECT-TYPE
        SYNTAX            INTEGER
        MAX-ACCESS        read-write
        STATUS            current
        DESCRIPTION
                "CMNT: - Linear Acoustic MBAGC Block1 Index 3 Release
                 TYPE: - Number
                 PAGE: - LoudCustom
                    mbagc rel 3  cmdID= 36228
                    min= 0  max= 100  step= 1  format= %0.0f  div_scale= 1  preset= 42
                    Min = 0  Max = 100  Step = 1  Preset = 42  "
        ::= { iquav10CmdEntry 36228 }


    iquav10LoudCustomBlock1mbagcthresh3 OBJECT-TYPE
        SYNTAX            INTEGER
        MAX-ACCESS        read-write
        STATUS            current
        DESCRIPTION
                "CMNT: - Linear Acoustic MBAGC Block1 Index 3 Threshold
                 TYPE: - Number
                 PAGE: - LoudCustom
                    mbagc thresh 3  cmdID= 36248
                    min= -120  max= 120  step= 1  format= %0.1f dB  div_scale= 10  preset= 0
                    Min = -12.0 dB  Max = 12.0 dB  Step = 0.1 dB  Preset = 0.0 dB  "
        ::= { iquav10CmdEntry 36248 }


    iquav10LoudCustomBlock1mbagcoutlev3 OBJECT-TYPE
        SYNTAX            INTEGER
        MAX-ACCESS        read-write
        STATUS            current
        DESCRIPTION
                "CMNT: - Linear Acoustic MBAGC Block1 Index 3 OutLevel
                 TYPE: - Number
                 PAGE: - LoudCustom
                    mbagc outlev 3  cmdID= 36268
                    min= -120  max= 120  step= 1  format= %0.1f dB  div_scale= 10  preset= 0
                    Min = -12.0 dB  Max = 12.0 dB  Step = 0.1 dB  Preset = 0.0 dB  "
        ::= { iquav10CmdEntry 36268 }


    iquav10LoudCustomBlock1mbagclimthresh3 OBJECT-TYPE
        SYNTAX            INTEGER
        MAX-ACCESS        read-write
        STATUS            current
        DESCRIPTION
                "CMNT: - Linear Acoustic MBAGC Block1 Index 3 Limit Threshold
                 TYPE: - Number
                 PAGE: - LoudCustom
                    mbagc limthresh 3  cmdID= 36258
                    min= 0  max= 180  step= 1  format= %0.1f dB  div_scale= 10  preset= 0
                    Min = 0.0 dB  Max = 18.0 dB  Step = 0.1 dB  Preset = 0.0 dB  "
        ::= { iquav10CmdEntry 36258 }


    iquav10LoudCustomBlock1mbagcinfthr3 OBJECT-TYPE
        SYNTAX            INTEGER { disable(0), enable(1)  }
        MAX-ACCESS        read-write
        STATUS            current
        DESCRIPTION
                "CMNT: - Linear Acoustic MBAGC Block1 Index 3 InfThr
                 TYPE: - Checkbox
                 PAGE: - LoudCustom
                    mbagc infthr 3  cmdID= 36296  "
        ::= { iquav10CmdEntry 36296 }


    iquav10LoudCustomBlock1mbagcatk4 OBJECT-TYPE
        SYNTAX            INTEGER
        MAX-ACCESS        read-write
        STATUS            current
        DESCRIPTION
                "CMNT: - Linear Acoustic MBAGC Block1 Index 4 Attack
                 TYPE: - Number
                 PAGE: - LoudCustom
                    mbagc atk 4  cmdID= 36239
                    min= 0  max= 100  step= 1  format= %0.0f  div_scale= 1  preset= 24
                    Min = 0  Max = 100  Step = 1  Preset = 24  "
        ::= { iquav10CmdEntry 36239 }


    iquav10LoudCustomBlock1mbagcrel4 OBJECT-TYPE
        SYNTAX            INTEGER
        MAX-ACCESS        read-write
        STATUS            current
        DESCRIPTION
                "CMNT: - Linear Acoustic MBAGC Block1 Index 4 Release
                 TYPE: - Number
                 PAGE: - LoudCustom
                    mbagc rel 4  cmdID= 36229
                    min= 0  max= 100  step= 1  format= %0.0f  div_scale= 1  preset= 42
                    Min = 0  Max = 100  Step = 1  Preset = 42  "
        ::= { iquav10CmdEntry 36229 }


    iquav10LoudCustomBlock1mbagcthresh4 OBJECT-TYPE
        SYNTAX            INTEGER
        MAX-ACCESS        read-write
        STATUS            current
        DESCRIPTION
                "CMNT: - Linear Acoustic MBAGC Block1 Index 4 Threshold
                 TYPE: - Number
                 PAGE: - LoudCustom
                    mbagc thresh 4  cmdID= 36249
                    min= -120  max= 120  step= 1  format= %0.1f dB  div_scale= 10  preset= 0
                    Min = -12.0 dB  Max = 12.0 dB  Step = 0.1 dB  Preset = 0.0 dB  "
        ::= { iquav10CmdEntry 36249 }


    iquav10LoudCustomBlock1mbagcoutlev4 OBJECT-TYPE
        SYNTAX            INTEGER
        MAX-ACCESS        read-write
        STATUS            current
        DESCRIPTION
                "CMNT: - Linear Acoustic MBAGC Block1 Index 4 OutLevel
                 TYPE: - Number
                 PAGE: - LoudCustom
                    mbagc outlev 4  cmdID= 36269
                    min= -120  max= 120  step= 1  format= %0.1f dB  div_scale= 10  preset= 0
                    Min = -12.0 dB  Max = 12.0 dB  Step = 0.1 dB  Preset = 0.0 dB  "
        ::= { iquav10CmdEntry 36269 }


    iquav10LoudCustomBlock1mbagclimthresh4 OBJECT-TYPE
        SYNTAX            INTEGER
        MAX-ACCESS        read-write
        STATUS            current
        DESCRIPTION
                "CMNT: - Linear Acoustic MBAGC Block1 Index 4 Limit Threshold
                 TYPE: - Number
                 PAGE: - LoudCustom
                    mbagc limthresh 4  cmdID= 36259
                    min= 0  max= 180  step= 1  format= %0.1f dB  div_scale= 10  preset= 0
                    Min = 0.0 dB  Max = 18.0 dB  Step = 0.1 dB  Preset = 0.0 dB  "
        ::= { iquav10CmdEntry 36259 }


    iquav10LoudCustomBlock1mbagcinfthr4 OBJECT-TYPE
        SYNTAX            INTEGER { disable(0), enable(1)  }
        MAX-ACCESS        read-write
        STATUS            current
        DESCRIPTION
                "CMNT: - Linear Acoustic MBAGC Block1 Index 4 InfThr
                 TYPE: - Checkbox
                 PAGE: - LoudCustom
                    mbagc infthr 4  cmdID= 36297  "
        ::= { iquav10CmdEntry 36297 }


    iquav10LoudCustomBlock1mbagcatk5 OBJECT-TYPE
        SYNTAX            INTEGER
        MAX-ACCESS        read-write
        STATUS            current
        DESCRIPTION
                "CMNT: - Linear Acoustic MBAGC Block1 Index 5 Attack
                 TYPE: - Number
                 PAGE: - LoudCustom
                    mbagc atk 5  cmdID= 36240
                    min= 0  max= 100  step= 1  format= %0.0f  div_scale= 1  preset= 24
                    Min = 0  Max = 100  Step = 1  Preset = 24  "
        ::= { iquav10CmdEntry 36240 }


    iquav10LoudCustomBlock1mbagcrel5 OBJECT-TYPE
        SYNTAX            INTEGER
        MAX-ACCESS        read-write
        STATUS            current
        DESCRIPTION
                "CMNT: - Linear Acoustic MBAGC Block1 Index 5 Release
                 TYPE: - Number
                 PAGE: - LoudCustom
                    mbagc rel 5  cmdID= 36230
                    min= 0  max= 100  step= 1  format= %0.0f  div_scale= 1  preset= 42
                    Min = 0  Max = 100  Step = 1  Preset = 42  "
        ::= { iquav10CmdEntry 36230 }


    iquav10LoudCustomBlock1mbagcthresh5 OBJECT-TYPE
        SYNTAX            INTEGER
        MAX-ACCESS        read-write
        STATUS            current
        DESCRIPTION
                "CMNT: - Linear Acoustic MBAGC Block1 Index 5 Threshold
                 TYPE: - Number
                 PAGE: - LoudCustom
                    mbagc thresh 5  cmdID= 36250
                    min= -120  max= 120  step= 1  format= %0.1f dB  div_scale= 10  preset= 0
                    Min = -12.0 dB  Max = 12.0 dB  Step = 0.1 dB  Preset = 0.0 dB  "
        ::= { iquav10CmdEntry 36250 }


    iquav10LoudCustomBlock1mbagcoutlev5 OBJECT-TYPE
        SYNTAX            INTEGER
        MAX-ACCESS        read-write
        STATUS            current
        DESCRIPTION
                "CMNT: - Linear Acoustic MBAGC Block1 Index 5 OutLevel
                 TYPE: - Number
                 PAGE: - LoudCustom
                    mbagc outlev 5  cmdID= 36270
                    min= -120  max= 120  step= 1  format= %0.1f dB  div_scale= 10  preset= 0
                    Min = -12.0 dB  Max = 12.0 dB  Step = 0.1 dB  Preset = 0.0 dB  "
        ::= { iquav10CmdEntry 36270 }


    iquav10LoudCustomBlock1mbagclimthresh5 OBJECT-TYPE
        SYNTAX            INTEGER
        MAX-ACCESS        read-write
        STATUS            current
        DESCRIPTION
                "CMNT: - Linear Acoustic MBAGC Block1 Index 5 Limit Threshold
                 TYPE: - Number
                 PAGE: - LoudCustom
                    mbagc limthresh 5  cmdID= 36260
                    min= 0  max= 180  step= 1  format= %0.1f dB  div_scale= 10  preset= 0
                    Min = 0.0 dB  Max = 18.0 dB  Step = 0.1 dB  Preset = 0.0 dB  "
        ::= { iquav10CmdEntry 36260 }


    iquav10LoudCustomBlock1mbagcinfthr5 OBJECT-TYPE
        SYNTAX            INTEGER { disable(0), enable(1)  }
        MAX-ACCESS        read-write
        STATUS            current
        DESCRIPTION
                "CMNT: - Linear Acoustic MBAGC Block1 Index 5 InfThr
                 TYPE: - Checkbox
                 PAGE: - LoudCustom
                    mbagc infthr 5  cmdID= 36298  "
        ::= { iquav10CmdEntry 36298 }


    iquav10LoudCustomBlock1mbrange OBJECT-TYPE
        SYNTAX            INTEGER
        MAX-ACCESS        read-write
        STATUS            current
        DESCRIPTION
                "CMNT: - Linear Acoustic MB Block1 Range
                 TYPE: - Number
                 PAGE: - LoudCustom
                    mb range  cmdID= 36216
                    min= 0  max= 180  step= 1  format= %0.1f dB  div_scale= 5  preset= 90
                    Min = 0.0 dB  Max = 36.0 dB  Step = 0.2 dB  Preset = 18.0 dB  "
        ::= { iquav10CmdEntry 36216 }


    iquav10LoudCustomBlock1mbprogrise OBJECT-TYPE
        SYNTAX            INTEGER
        MAX-ACCESS        read-write
        STATUS            current
        DESCRIPTION
                "CMNT: - Linear Acoustic MB Block1 Progressive Rise
                 TYPE: - Number
                 PAGE: - LoudCustom
                    mb progrise  cmdID= 36214
                    min= 0  max= 100  step= 1  format= %0.0f  div_scale= 1  preset= 1
                    Min = 0  Max = 100  Step = 1  Preset = 1  "
        ::= { iquav10CmdEntry 36214 }


    iquav10LoudCustomBlock1mbsoftclip1 OBJECT-TYPE
        SYNTAX            INTEGER
        MAX-ACCESS        read-write
        STATUS            current
        DESCRIPTION
                "CMNT: - Linear Acoustic MB Block1 SoftClip1
                 TYPE: - Number
                 PAGE: - LoudCustom
                    mb softclip1  cmdID= 36218
                    min= 0  max= 180  step= 1  format= %0.1f dB  div_scale= 10  preset= 180
                    Min = 0.0 dB  Max = 18.0 dB  Step = 0.1 dB  Preset = 18.0 dB  "
        ::= { iquav10CmdEntry 36218 }


    iquav10LoudCustomBlock1mbsoftclip2 OBJECT-TYPE
        SYNTAX            INTEGER
        MAX-ACCESS        read-write
        STATUS            current
        DESCRIPTION
                "CMNT: - Linear Acoustic MB Block1 SoftClip2
                 TYPE: - Number
                 PAGE: - LoudCustom
                    mb softclip2  cmdID= 36220
                    min= 0  max= 180  step= 1  format= %0.1f dB  div_scale= 10  preset= 180
                    Min = 0.0 dB  Max = 18.0 dB  Step = 0.1 dB  Preset = 18.0 dB  "
        ::= { iquav10CmdEntry 36220 }


    iquav10LoudCustomBlock1mbratio OBJECT-TYPE
        SYNTAX            INTEGER
        MAX-ACCESS        read-write
        STATUS            current
        DESCRIPTION
                "CMNT: - Linear Acoustic MB Block1 Ratio
                 TYPE: - Number
                 PAGE: - LoudCustom
                    mb ratio  cmdID= 36222
                    min= 0  max= 100  step= 1  format= %0.0f  div_scale= 1  preset= 63
                    Min = 0  Max = 100  Step = 1  Preset = 63  "
        ::= { iquav10CmdEntry 36222 }


    iquav10LoudCustomBlock1mblimdrive OBJECT-TYPE
        SYNTAX            INTEGER
        MAX-ACCESS        read-write
        STATUS            current
        DESCRIPTION
                "CMNT: - Linear Acoustic MB Block1 OutLimDrive
                 TYPE: - Number
                 PAGE: - LoudCustom
                    mb lim drive  cmdID= 36224
                    min= -60  max= 60  step= 1  format= %0.1f dB  div_scale= 10  preset= -50
                    Min = -6.0 dB  Max = 6.0 dB  Step = 0.1 dB  Preset = -5.0 dB  "
        ::= { iquav10CmdEntry 36224 }


    iquav10LoudCustomBlock1CustomPreset OBJECT-TYPE
        SYNTAX            INTEGER {
                            valGeneral(0),
                            valLight(1),
                            valHeavy(2),
                            valLoud(3),
                            valLoudLimit(4),
                            valProtectionLimit(5),
                            valDefaults(6),
                            valCustom(7)
                            }
        MAX-ACCESS        read-write
        STATUS            current
        DESCRIPTION
                "CMNT: - Linear Acoustic Cust Preset 1
                 TYPE: - RadiobuttonList
                 PAGE: - LoudCustom
                    CustomPreset  cmdID= 36306
                    General  value= 0
                    Light  value= 1
                    Heavy  value= 2
                    Loud  value= 3
                    LoudLimit  value= 4
                    ProtectionLimit  value= 5
                    Defaults  value= 6
                    Custom  value= 7  "
        ::= { iquav10CmdEntry 36306 }


    iquav10LoudCustomBlock1Copyto2 OBJECT-TYPE
        SYNTAX            INTEGER { noAction(0),valCopyto2(1) }
        MAX-ACCESS        read-write
        STATUS            current
        DESCRIPTION
                "CMNT: - Linear Acoustic Cust Preset COPY 1 to 2
                 TYPE: - Button
                 PAGE: - LoudCustom
                    Copy to 2  cmdID= 36309
                    value= 1  "
        ::= { iquav10CmdEntry 36309 }


    iquav10LoudCustomBlock2Name OBJECT-TYPE
        SYNTAX            RollCallString
        MAX-ACCESS        read-write
        STATUS            current
        DESCRIPTION
                "CMNT: - Linear Acoustic MB Block2 Name
                 TYPE: - Editstring
                 PAGE: - LoudCustom
                    Name  cmdID= 36305
                    preset= Custom Block 2"
        ::= { iquav10CmdEntry 36305 }


    iquav10LoudCustomBlock2inagcfreeze OBJECT-TYPE
        SYNTAX            INTEGER
        MAX-ACCESS        read-write
        STATUS            current
        DESCRIPTION
                "CMNT: - Linear Acoustic InAGC Block2 Freeze Threshold
                 TYPE: - Number
                 PAGE: - LoudCustom
                    inagc freeze  cmdID= 36201
                    min= -180  max= 0  step= 1  format= %0.1f dBFS  div_scale= 2  preset= -62
                    Min = -90.0 dBFS  Max = 0.0 dBFS  Step = 0.5 dBFS  Preset = -31.0 dBFS  "
        ::= { iquav10CmdEntry 36201 }


    iquav10LoudCustomBlock2inagcgate OBJECT-TYPE
        SYNTAX            INTEGER
        MAX-ACCESS        read-write
        STATUS            current
        DESCRIPTION
                "CMNT: - Linear Acoustic InAGC Block2 Gate Threshold
                 TYPE: - Number
                 PAGE: - LoudCustom
                    inagc gate  cmdID= 36203
                    min= -180  max= 0  step= 1  format= %0.1f dBFS  div_scale= 2  preset= -42
                    Min = -90.0 dBFS  Max = 0.0 dBFS  Step = 0.5 dBFS  Preset = -21.0 dBFS  "
        ::= { iquav10CmdEntry 36203 }


    iquav10LoudCustomBlock2inagcratio OBJECT-TYPE
        SYNTAX            INTEGER
        MAX-ACCESS        read-write
        STATUS            current
        DESCRIPTION
                "CMNT: - Linear Acoustic InAGC Block2 Ratio
                 TYPE: - Number
                 PAGE: - LoudCustom
                    inagc ratio  cmdID= 36209
                    min= 0  max= 100  step= 1  format= %0.0f  div_scale= 1  preset= 91
                    Min = 0  Max = 100  Step = 1  Preset = 91  "
        ::= { iquav10CmdEntry 36209 }


    iquav10LoudCustomBlock2inagcrange OBJECT-TYPE
        SYNTAX            INTEGER
        MAX-ACCESS        read-write
        STATUS            current
        DESCRIPTION
                "CMNT: - Linear Acoustic InAGC Block2 Range
                 TYPE: - Number
                 PAGE: - LoudCustom
                    inagc range  cmdID= 36207
                    min= 0  max= 180  step= 1  format= %0.1f dB  div_scale= 5  preset= 125
                    Min = 0.0 dB  Max = 36.0 dB  Step = 0.2 dB  Preset = 25.0 dB  "
        ::= { iquav10CmdEntry 36207 }


    iquav10LoudCustomBlock2inagcthresh OBJECT-TYPE
        SYNTAX            INTEGER
        MAX-ACCESS        read-write
        STATUS            current
        DESCRIPTION
                "CMNT: - Linear Acoustic InAGC Block2 Threshold
                 TYPE: - Number
                 PAGE: - LoudCustom
                    inagc thresh  cmdID= 36205
                    min= -180  max= 0  step= 1  format= %0.1f dBFS  div_scale= 10  preset= -140
                    Min = -18.0 dBFS  Max = 0.0 dBFS  Step = 0.1 dBFS  Preset = -14.0 dBFS  "
        ::= { iquav10CmdEntry 36205 }


    iquav10LoudCustomBlock2inagcattack OBJECT-TYPE
        SYNTAX            INTEGER
        MAX-ACCESS        read-write
        STATUS            current
        DESCRIPTION
                "CMNT: - Linear Acoustic InAGC Block2 Attack
                 TYPE: - Number
                 PAGE: - LoudCustom
                    inagc attack  cmdID= 36211
                    min= 1  max= 100  step= 1  format= %0.0f  div_scale= 1  preset= 24
                    Min = 1  Max = 100  Step = 1  Preset = 24  "
        ::= { iquav10CmdEntry 36211 }


    iquav10LoudCustomBlock2inagcrelease OBJECT-TYPE
        SYNTAX            INTEGER
        MAX-ACCESS        read-write
        STATUS            current
        DESCRIPTION
                "CMNT: - Linear Acoustic InAGC Block2 Release
                 TYPE: - Number
                 PAGE: - LoudCustom
                    inagc release  cmdID= 36213
                    min= 1  max= 100  step= 1  format= %0.0f  div_scale= 1  preset= 42
                    Min = 1  Max = 100  Step = 1  Preset = 42  "
        ::= { iquav10CmdEntry 36213 }


    iquav10LoudCustomBlock2peqfreq1 OBJECT-TYPE
        SYNTAX            INTEGER
        MAX-ACCESS        read-write
        STATUS            current
        DESCRIPTION
                "CMNT: - Linear Acoustic PEQ Block2 Index 1 Frequency
                 TYPE: - Number
                 PAGE: - LoudCustom
                    peq freq 1  cmdID= 36279
                    min= 20  max= 20000  step= 1  format= %0.0f Hz  div_scale= 1  preset= 1000
                    Min = 20 Hz  Max = 20000 Hz  Step = 1 Hz  Preset = 1000 Hz  "
        ::= { iquav10CmdEntry 36279 }


    iquav10LoudCustomBlock2peqq1 OBJECT-TYPE
        SYNTAX            INTEGER
        MAX-ACCESS        read-write
        STATUS            current
        DESCRIPTION
                "CMNT: - Linear Acoustic PEQ Block2 Index 1 Q
                 TYPE: - Number
                 PAGE: - LoudCustom
                    peq q 1  cmdID= 36285
                    min= 1  max= 200  step= 1  format= %0.2f  div_scale= 20  preset= 20
                    Min = 0.05  Max = 10.00  Step = 0.05  Preset = 1.00  "
        ::= { iquav10CmdEntry 36285 }


    iquav10LoudCustomBlock2peqlevel1 OBJECT-TYPE
        SYNTAX            INTEGER
        MAX-ACCESS        read-write
        STATUS            current
        DESCRIPTION
                "CMNT: - Linear Acoustic PEQ Block2 Index 1 Level
                 TYPE: - Number
                 PAGE: - LoudCustom
                    peq level 1  cmdID= 36291
                    min= -90  max= 90  step= 1  format= %0.1f dB  div_scale= 5  preset= 0
                    Min = -18.0 dB  Max = 18.0 dB  Step = 0.2 dB  Preset = 0.0 dB  "
        ::= { iquav10CmdEntry 36291 }


    iquav10LoudCustomBlock2peqfreq2 OBJECT-TYPE
        SYNTAX            INTEGER
        MAX-ACCESS        read-write
        STATUS            current
        DESCRIPTION
                "CMNT: - Linear Acoustic PEQ Block2 Index 2 Frequency
                 TYPE: - Number
                 PAGE: - LoudCustom
                    peq freq 2  cmdID= 36280
                    min= 20  max= 20000  step= 1  format= %0.0f Hz  div_scale= 1  preset= 1000
                    Min = 20 Hz  Max = 20000 Hz  Step = 1 Hz  Preset = 1000 Hz  "
        ::= { iquav10CmdEntry 36280 }


    iquav10LoudCustomBlock2peqq2 OBJECT-TYPE
        SYNTAX            INTEGER
        MAX-ACCESS        read-write
        STATUS            current
        DESCRIPTION
                "CMNT: - Linear Acoustic PEQ Block2 Index 2 Q
                 TYPE: - Number
                 PAGE: - LoudCustom
                    peq q 2  cmdID= 36286
                    min= 1  max= 200  step= 1  format= %0.2f  div_scale= 20  preset= 20
                    Min = 0.05  Max = 10.00  Step = 0.05  Preset = 1.00  "
        ::= { iquav10CmdEntry 36286 }


    iquav10LoudCustomBlock2peqlevel2 OBJECT-TYPE
        SYNTAX            INTEGER
        MAX-ACCESS        read-write
        STATUS            current
        DESCRIPTION
                "CMNT: - Linear Acoustic PEQ Block2 Index 2 Level
                 TYPE: - Number
                 PAGE: - LoudCustom
                    peq level 2  cmdID= 36292
                    min= -90  max= 90  step= 1  format= %0.1f dB  div_scale= 5  preset= 0
                    Min = -18.0 dB  Max = 18.0 dB  Step = 0.2 dB  Preset = 0.0 dB  "
        ::= { iquav10CmdEntry 36292 }


    iquav10LoudCustomBlock2peqfreq3 OBJECT-TYPE
        SYNTAX            INTEGER
        MAX-ACCESS        read-write
        STATUS            current
        DESCRIPTION
                "CMNT: - Linear Acoustic PEQ Block2 Index 3 Frequency
                 TYPE: - Number
                 PAGE: - LoudCustom
                    peq freq 3  cmdID= 36281
                    min= 20  max= 20000  step= 1  format= %0.0f Hz  div_scale= 1  preset= 1000
                    Min = 20 Hz  Max = 20000 Hz  Step = 1 Hz  Preset = 1000 Hz  "
        ::= { iquav10CmdEntry 36281 }


    iquav10LoudCustomBlock2peqq3 OBJECT-TYPE
        SYNTAX            INTEGER
        MAX-ACCESS        read-write
        STATUS            current
        DESCRIPTION
                "CMNT: - Linear Acoustic PEQ Block2 Index 3 Q
                 TYPE: - Number
                 PAGE: - LoudCustom
                    peq q 3  cmdID= 36287
                    min= 1  max= 200  step= 1  format= %0.2f  div_scale= 20  preset= 20
                    Min = 0.05  Max = 10.00  Step = 0.05  Preset = 1.00  "
        ::= { iquav10CmdEntry 36287 }


    iquav10LoudCustomBlock2peqlevel3 OBJECT-TYPE
        SYNTAX            INTEGER
        MAX-ACCESS        read-write
        STATUS            current
        DESCRIPTION
                "CMNT: - Linear Acoustic PEQ Block2 Index 3 Level
                 TYPE: - Number
                 PAGE: - LoudCustom
                    peq level 3  cmdID= 36293
                    min= -90  max= 90  step= 1  format= %0.1f dB  div_scale= 5  preset= 0
                    Min = -18.0 dB  Max = 18.0 dB  Step = 0.2 dB  Preset = 0.0 dB  "
        ::= { iquav10CmdEntry 36293 }


    iquav10LoudCustomBlock2mbagcatk1 OBJECT-TYPE
        SYNTAX            INTEGER
        MAX-ACCESS        read-write
        STATUS            current
        DESCRIPTION
                "CMNT: - Linear Acoustic MBAGC Block2 Index 1 Attack
                 TYPE: - Number
                 PAGE: - LoudCustom
                    mbagc atk 1  cmdID= 36241
                    min= 0  max= 100  step= 1  format= %0.0f  div_scale= 1  preset= 24
                    Min = 0  Max = 100  Step = 1  Preset = 24  "
        ::= { iquav10CmdEntry 36241 }


    iquav10LoudCustomBlock2mbagcrel1 OBJECT-TYPE
        SYNTAX            INTEGER
        MAX-ACCESS        read-write
        STATUS            current
        DESCRIPTION
                "CMNT: - Linear Acoustic MBAGC Block2 Index 1 Release
                 TYPE: - Number
                 PAGE: - LoudCustom
                    mbagc rel 1  cmdID= 36231
                    min= 0  max= 100  step= 1  format= %0.0f  div_scale= 1  preset= 42
                    Min = 0  Max = 100  Step = 1  Preset = 42  "
        ::= { iquav10CmdEntry 36231 }


    iquav10LoudCustomBlock2mbagcthresh1 OBJECT-TYPE
        SYNTAX            INTEGER
        MAX-ACCESS        read-write
        STATUS            current
        DESCRIPTION
                "CMNT: - Linear Acoustic MBAGC Block2 Index 1 Threshold
                 TYPE: - Number
                 PAGE: - LoudCustom
                    mbagc thresh 1  cmdID= 36251
                    min= -120  max= 120  step= 1  format= %0.1f dB  div_scale= 10  preset= 0
                    Min = -12.0 dB  Max = 12.0 dB  Step = 0.1 dB  Preset = 0.0 dB  "
        ::= { iquav10CmdEntry 36251 }


    iquav10LoudCustomBlock2mbagcoutlev1 OBJECT-TYPE
        SYNTAX            INTEGER
        MAX-ACCESS        read-write
        STATUS            current
        DESCRIPTION
                "CMNT: - Linear Acoustic MBAGC Block2 Index 1 OutLevel
                 TYPE: - Number
                 PAGE: - LoudCustom
                    mbagc outlev 1  cmdID= 36271
                    min= -120  max= 120  step= 1  format= %0.1f dB  div_scale= 10  preset= 0
                    Min = -12.0 dB  Max = 12.0 dB  Step = 0.1 dB  Preset = 0.0 dB  "
        ::= { iquav10CmdEntry 36271 }


    iquav10LoudCustomBlock2mbagclimthresh1 OBJECT-TYPE
        SYNTAX            INTEGER
        MAX-ACCESS        read-write
        STATUS            current
        DESCRIPTION
                "CMNT: - Linear Acoustic MBAGC Block2 Index 1 Limit Threshold
                 TYPE: - Number
                 PAGE: - LoudCustom
                    mbagc limthresh 1  cmdID= 36261
                    min= 0  max= 180  step= 1  format= %0.1f dB  div_scale= 10  preset= 0
                    Min = 0.0 dB  Max = 18.0 dB  Step = 0.1 dB  Preset = 0.0 dB  "
        ::= { iquav10CmdEntry 36261 }


    iquav10LoudCustomBlock2mbagcinfthr1 OBJECT-TYPE
        SYNTAX            INTEGER { disable(0), enable(1)  }
        MAX-ACCESS        read-write
        STATUS            current
        DESCRIPTION
                "CMNT: - Linear Acoustic MBAGC Block2 Index 1 InfThr
                 TYPE: - Checkbox
                 PAGE: - LoudCustom
                    mbagc infthr 1  cmdID= 36299  "
        ::= { iquav10CmdEntry 36299 }


    iquav10LoudCustomBlock2mbagcatk2 OBJECT-TYPE
        SYNTAX            INTEGER
        MAX-ACCESS        read-write
        STATUS            current
        DESCRIPTION
                "CMNT: - Linear Acoustic MBAGC Block2 Index 2 Attack
                 TYPE: - Number
                 PAGE: - LoudCustom
                    mbagc atk 2  cmdID= 36242
                    min= 0  max= 100  step= 1  format= %0.0f  div_scale= 1  preset= 24
                    Min = 0  Max = 100  Step = 1  Preset = 24  "
        ::= { iquav10CmdEntry 36242 }


    iquav10LoudCustomBlock2mbagcrel2 OBJECT-TYPE
        SYNTAX            INTEGER
        MAX-ACCESS        read-write
        STATUS            current
        DESCRIPTION
                "CMNT: - Linear Acoustic MBAGC Block2 Index 2 Release
                 TYPE: - Number
                 PAGE: - LoudCustom
                    mbagc rel 2  cmdID= 36232
                    min= 0  max= 100  step= 1  format= %0.0f  div_scale= 1  preset= 42
                    Min = 0  Max = 100  Step = 1  Preset = 42  "
        ::= { iquav10CmdEntry 36232 }


    iquav10LoudCustomBlock2mbagcthresh2 OBJECT-TYPE
        SYNTAX            INTEGER
        MAX-ACCESS        read-write
        STATUS            current
        DESCRIPTION
                "CMNT: - Linear Acoustic MBAGC Block2 Index 2 Threshold
                 TYPE: - Number
                 PAGE: - LoudCustom
                    mbagc thresh 2  cmdID= 36252
                    min= -120  max= 120  step= 1  format= %0.1f dB  div_scale= 10  preset= 0
                    Min = -12.0 dB  Max = 12.0 dB  Step = 0.1 dB  Preset = 0.0 dB  "
        ::= { iquav10CmdEntry 36252 }


    iquav10LoudCustomBlock2mbagcoutlev2 OBJECT-TYPE
        SYNTAX            INTEGER
        MAX-ACCESS        read-write
        STATUS            current
        DESCRIPTION
                "CMNT: - Linear Acoustic MBAGC Block2 Index 2 OutLevel
                 TYPE: - Number
                 PAGE: - LoudCustom
                    mbagc outlev 2  cmdID= 36272
                    min= -120  max= 120  step= 1  format= %0.1f dB  div_scale= 10  preset= 0
                    Min = -12.0 dB  Max = 12.0 dB  Step = 0.1 dB  Preset = 0.0 dB  "
        ::= { iquav10CmdEntry 36272 }


    iquav10LoudCustomBlock2mbagclimthresh2 OBJECT-TYPE
        SYNTAX            INTEGER
        MAX-ACCESS        read-write
        STATUS            current
        DESCRIPTION
                "CMNT: - Linear Acoustic MBAGC Block2 Index 2 Limit Threshold
                 TYPE: - Number
                 PAGE: - LoudCustom
                    mbagc limthresh 2  cmdID= 36262
                    min= 0  max= 180  step= 1  format= %0.1f dB  div_scale= 10  preset= 0
                    Min = 0.0 dB  Max = 18.0 dB  Step = 0.1 dB  Preset = 0.0 dB  "
        ::= { iquav10CmdEntry 36262 }


    iquav10LoudCustomBlock2mbagcinfthr2 OBJECT-TYPE
        SYNTAX            INTEGER { disable(0), enable(1)  }
        MAX-ACCESS        read-write
        STATUS            current
        DESCRIPTION
                "CMNT: - Linear Acoustic MBAGC Block2 Index 2 InfThr
                 TYPE: - Checkbox
                 PAGE: - LoudCustom
                    mbagc infthr 2  cmdID= 36300  "
        ::= { iquav10CmdEntry 36300 }


    iquav10LoudCustomBlock2mbagcatk3 OBJECT-TYPE
        SYNTAX            INTEGER
        MAX-ACCESS        read-write
        STATUS            current
        DESCRIPTION
                "CMNT: - Linear Acoustic MBAGC Block2 Index 3 Attack
                 TYPE: - Number
                 PAGE: - LoudCustom
                    mbagc atk 3  cmdID= 36243
                    min= 0  max= 100  step= 1  format= %0.0f  div_scale= 1  preset= 24
                    Min = 0  Max = 100  Step = 1  Preset = 24  "
        ::= { iquav10CmdEntry 36243 }


    iquav10LoudCustomBlock2mbagcrel3 OBJECT-TYPE
        SYNTAX            INTEGER
        MAX-ACCESS        read-write
        STATUS            current
        DESCRIPTION
                "CMNT: - Linear Acoustic MBAGC Block2 Index 3 Release
                 TYPE: - Number
                 PAGE: - LoudCustom
                    mbagc rel 3  cmdID= 36233
                    min= 0  max= 100  step= 1  format= %0.0f  div_scale= 1  preset= 42
                    Min = 0  Max = 100  Step = 1  Preset = 42  "
        ::= { iquav10CmdEntry 36233 }


    iquav10LoudCustomBlock2mbagcthresh3 OBJECT-TYPE
        SYNTAX            INTEGER
        MAX-ACCESS        read-write
        STATUS            current
        DESCRIPTION
                "CMNT: - Linear Acoustic MBAGC Block2 Index 3 Threshold
                 TYPE: - Number
                 PAGE: - LoudCustom
                    mbagc thresh 3  cmdID= 36253
                    min= -120  max= 120  step= 1  format= %0.1f dB  div_scale= 10  preset= 0
                    Min = -12.0 dB  Max = 12.0 dB  Step = 0.1 dB  Preset = 0.0 dB  "
        ::= { iquav10CmdEntry 36253 }


    iquav10LoudCustomBlock2mbagcoutlev3 OBJECT-TYPE
        SYNTAX            INTEGER
        MAX-ACCESS        read-write
        STATUS            current
        DESCRIPTION
                "CMNT: - Linear Acoustic MBAGC Block2 Index 3 OutLevel
                 TYPE: - Number
                 PAGE: - LoudCustom
                    mbagc outlev 3  cmdID= 36273
                    min= -120  max= 120  step= 1  format= %0.1f dB  div_scale= 10  preset= 0
                    Min = -12.0 dB  Max = 12.0 dB  Step = 0.1 dB  Preset = 0.0 dB  "
        ::= { iquav10CmdEntry 36273 }


    iquav10LoudCustomBlock2mbagclimthresh3 OBJECT-TYPE
        SYNTAX            INTEGER
        MAX-ACCESS        read-write
        STATUS            current
        DESCRIPTION
                "CMNT: - Linear Acoustic MBAGC Block2 Index 3 Limit Threshold
                 TYPE: - Number
                 PAGE: - LoudCustom
                    mbagc limthresh 3  cmdID= 36263
                    min= 0  max= 180  step= 1  format= %0.1f dB  div_scale= 10  preset= 0
                    Min = 0.0 dB  Max = 18.0 dB  Step = 0.1 dB  Preset = 0.0 dB  "
        ::= { iquav10CmdEntry 36263 }


    iquav10LoudCustomBlock2mbagcinfthr3 OBJECT-TYPE
        SYNTAX            INTEGER { disable(0), enable(1)  }
        MAX-ACCESS        read-write
        STATUS            current
        DESCRIPTION
                "CMNT: - Linear Acoustic MBAGC Block2 Index 3 InfThr
                 TYPE: - Checkbox
                 PAGE: - LoudCustom
                    mbagc infthr 3  cmdID= 36301  "
        ::= { iquav10CmdEntry 36301 }


    iquav10LoudCustomBlock2mbagcatk4 OBJECT-TYPE
        SYNTAX            INTEGER
        MAX-ACCESS        read-write
        STATUS            current
        DESCRIPTION
                "CMNT: - Linear Acoustic MBAGC Block2 Index 4 Attack
                 TYPE: - Number
                 PAGE: - LoudCustom
                    mbagc atk 4  cmdID= 36244
                    min= 0  max= 100  step= 1  format= %0.0f  div_scale= 1  preset= 24
                    Min = 0  Max = 100  Step = 1  Preset = 24  "
        ::= { iquav10CmdEntry 36244 }


    iquav10LoudCustomBlock2mbagcrel4 OBJECT-TYPE
        SYNTAX            INTEGER
        MAX-ACCESS        read-write
        STATUS            current
        DESCRIPTION
                "CMNT: - Linear Acoustic MBAGC Block2 Index 4 Release
                 TYPE: - Number
                 PAGE: - LoudCustom
                    mbagc rel 4  cmdID= 36234
                    min= 0  max= 100  step= 1  format= %0.0f  div_scale= 1  preset= 42
                    Min = 0  Max = 100  Step = 1  Preset = 42  "
        ::= { iquav10CmdEntry 36234 }


    iquav10LoudCustomBlock2mbagcthresh4 OBJECT-TYPE
        SYNTAX            INTEGER
        MAX-ACCESS        read-write
        STATUS            current
        DESCRIPTION
                "CMNT: - Linear Acoustic MBAGC Block2 Index 4 Threshold
                 TYPE: - Number
                 PAGE: - LoudCustom
                    mbagc thresh 4  cmdID= 36254
                    min= -120  max= 120  step= 1  format= %0.1f dB  div_scale= 10  preset= 0
                    Min = -12.0 dB  Max = 12.0 dB  Step = 0.1 dB  Preset = 0.0 dB  "
        ::= { iquav10CmdEntry 36254 }


    iquav10LoudCustomBlock2mbagcoutlev4 OBJECT-TYPE
        SYNTAX            INTEGER
        MAX-ACCESS        read-write
        STATUS            current
        DESCRIPTION
                "CMNT: - Linear Acoustic MBAGC Block2 Index 4 OutLevel
                 TYPE: - Number
                 PAGE: - LoudCustom
                    mbagc outlev 4  cmdID= 36274
                    min= -120  max= 120  step= 1  format= %0.1f dB  div_scale= 10  preset= 0
                    Min = -12.0 dB  Max = 12.0 dB  Step = 0.1 dB  Preset = 0.0 dB  "
        ::= { iquav10CmdEntry 36274 }


    iquav10LoudCustomBlock2mbagclimthresh4 OBJECT-TYPE
        SYNTAX            INTEGER
        MAX-ACCESS        read-write
        STATUS            current
        DESCRIPTION
                "CMNT: - Linear Acoustic MBAGC Block2 Index 4 Limit Threshold
                 TYPE: - Number
                 PAGE: - LoudCustom
                    mbagc limthresh 4  cmdID= 36264
                    min= 0  max= 180  step= 1  format= %0.1f dB  div_scale= 10  preset= 0
                    Min = 0.0 dB  Max = 18.0 dB  Step = 0.1 dB  Preset = 0.0 dB  "
        ::= { iquav10CmdEntry 36264 }


    iquav10LoudCustomBlock2mbagcinfthr4 OBJECT-TYPE
        SYNTAX            INTEGER { disable(0), enable(1)  }
        MAX-ACCESS        read-write
        STATUS            current
        DESCRIPTION
                "CMNT: - Linear Acoustic MBAGC Block2 Index 4 InfThr
                 TYPE: - Checkbox
                 PAGE: - LoudCustom
                    mbagc infthr 4  cmdID= 36302  "
        ::= { iquav10CmdEntry 36302 }


    iquav10LoudCustomBlock2mbagcatk5 OBJECT-TYPE
        SYNTAX            INTEGER
        MAX-ACCESS        read-write
        STATUS            current
        DESCRIPTION
                "CMNT: - Linear Acoustic MBAGC Block2 Index 5 Attack
                 TYPE: - Number
                 PAGE: - LoudCustom
                    mbagc atk 5  cmdID= 36245
                    min= 0  max= 100  step= 1  format= %0.0f  div_scale= 1  preset= 24
                    Min = 0  Max = 100  Step = 1  Preset = 24  "
        ::= { iquav10CmdEntry 36245 }


    iquav10LoudCustomBlock2mbagcrel5 OBJECT-TYPE
        SYNTAX            INTEGER
        MAX-ACCESS        read-write
        STATUS            current
        DESCRIPTION
                "CMNT: - Linear Acoustic MBAGC Block2 Index 5 Release
                 TYPE: - Number
                 PAGE: - LoudCustom
                    mbagc rel 5  cmdID= 36235
                    min= 0  max= 100  step= 1  format= %0.0f  div_scale= 1  preset= 42
                    Min = 0  Max = 100  Step = 1  Preset = 42  "
        ::= { iquav10CmdEntry 36235 }


    iquav10LoudCustomBlock2mbagcthresh5 OBJECT-TYPE
        SYNTAX            INTEGER
        MAX-ACCESS        read-write
        STATUS            current
        DESCRIPTION
                "CMNT: - Linear Acoustic MBAGC Block2 Index 5 Threshold
                 TYPE: - Number
                 PAGE: - LoudCustom
                    mbagc thresh 5  cmdID= 36255
                    min= -120  max= 120  step= 1  format= %0.1f dB  div_scale= 10  preset= 0
                    Min = -12.0 dB  Max = 12.0 dB  Step = 0.1 dB  Preset = 0.0 dB  "
        ::= { iquav10CmdEntry 36255 }


    iquav10LoudCustomBlock2mbagcoutlev5 OBJECT-TYPE
        SYNTAX            INTEGER
        MAX-ACCESS        read-write
        STATUS            current
        DESCRIPTION
                "CMNT: - Linear Acoustic MBAGC Block2 Index 5 OutLevel
                 TYPE: - Number
                 PAGE: - LoudCustom
                    mbagc outlev 5  cmdID= 36275
                    min= -120  max= 120  step= 1  format= %0.1f dB  div_scale= 10  preset= 0
                    Min = -12.0 dB  Max = 12.0 dB  Step = 0.1 dB  Preset = 0.0 dB  "
        ::= { iquav10CmdEntry 36275 }


    iquav10LoudCustomBlock2mbagclimthresh5 OBJECT-TYPE
        SYNTAX            INTEGER
        MAX-ACCESS        read-write
        STATUS            current
        DESCRIPTION
                "CMNT: - Linear Acoustic MBAGC Block2 Index 5 Limit Threshold
                 TYPE: - Number
                 PAGE: - LoudCustom
                    mbagc limthresh 5  cmdID= 36265
                    min= 0  max= 180  step= 1  format= %0.1f dB  div_scale= 10  preset= 0
                    Min = 0.0 dB  Max = 18.0 dB  Step = 0.1 dB  Preset = 0.0 dB  "
        ::= { iquav10CmdEntry 36265 }


    iquav10LoudCustomBlock2mbagcinfthr5 OBJECT-TYPE
        SYNTAX            INTEGER { disable(0), enable(1)  }
        MAX-ACCESS        read-write
        STATUS            current
        DESCRIPTION
                "CMNT: - Linear Acoustic MBAGC Block2 Index 5 InfThr
                 TYPE: - Checkbox
                 PAGE: - LoudCustom
                    mbagc infthr 5  cmdID= 36303  "
        ::= { iquav10CmdEntry 36303 }


    iquav10LoudCustomBlock2mbrange OBJECT-TYPE
        SYNTAX            INTEGER
        MAX-ACCESS        read-write
        STATUS            current
        DESCRIPTION
                "CMNT: - Linear Acoustic MB Block2 Range
                 TYPE: - Number
                 PAGE: - LoudCustom
                    mb range  cmdID= 36217
                    min= 0  max= 180  step= 1  format= %0.1f dB  div_scale= 5  preset= 90
                    Min = 0.0 dB  Max = 36.0 dB  Step = 0.2 dB  Preset = 18.0 dB  "
        ::= { iquav10CmdEntry 36217 }


    iquav10LoudCustomBlock2mbprogrise OBJECT-TYPE
        SYNTAX            INTEGER
        MAX-ACCESS        read-write
        STATUS            current
        DESCRIPTION
                "CMNT: - Linear Acoustic MB Block2 Progressive Rise
                 TYPE: - Number
                 PAGE: - LoudCustom
                    mb progrise  cmdID= 36215
                    min= 0  max= 100  step= 1  format= %0.0f  div_scale= 1  preset= 1
                    Min = 0  Max = 100  Step = 1  Preset = 1  "
        ::= { iquav10CmdEntry 36215 }


    iquav10LoudCustomBlock2mbsoftclip1 OBJECT-TYPE
        SYNTAX            INTEGER
        MAX-ACCESS        read-write
        STATUS            current
        DESCRIPTION
                "CMNT: - Linear Acoustic MB Block2 SoftClip1
                 TYPE: - Number
                 PAGE: - LoudCustom
                    mb softclip1  cmdID= 36219
                    min= 0  max= 180  step= 1  format= %0.1f dB  div_scale= 10  preset= 180
                    Min = 0.0 dB  Max = 18.0 dB  Step = 0.1 dB  Preset = 18.0 dB  "
        ::= { iquav10CmdEntry 36219 }


    iquav10LoudCustomBlock2mbsoftclip2 OBJECT-TYPE
        SYNTAX            INTEGER
        MAX-ACCESS        read-write
        STATUS            current
        DESCRIPTION
                "CMNT: - Linear Acoustic MB Block2 SoftClip2
                 TYPE: - Number
                 PAGE: - LoudCustom
                    mb softclip2  cmdID= 36221
                    min= 0  max= 180  step= 1  format= %0.1f dB  div_scale= 10  preset= 180
                    Min = 0.0 dB  Max = 18.0 dB  Step = 0.1 dB  Preset = 18.0 dB  "
        ::= { iquav10CmdEntry 36221 }


    iquav10LoudCustomBlock2mbratio OBJECT-TYPE
        SYNTAX            INTEGER
        MAX-ACCESS        read-write
        STATUS            current
        DESCRIPTION
                "CMNT: - Linear Acoustic MB Block2 Ratio
                 TYPE: - Number
                 PAGE: - LoudCustom
                    mb ratio  cmdID= 36223
                    min= 0  max= 100  step= 1  format= %0.0f  div_scale= 1  preset= 63
                    Min = 0  Max = 100  Step = 1  Preset = 63  "
        ::= { iquav10CmdEntry 36223 }


    iquav10LoudCustomBlock2mblimdrive OBJECT-TYPE
        SYNTAX            INTEGER
        MAX-ACCESS        read-write
        STATUS            current
        DESCRIPTION
                "CMNT: - Linear Acoustic MB Block2 OutLimDrive
                 TYPE: - Number
                 PAGE: - LoudCustom
                    mb lim drive  cmdID= 36225
                    min= -60  max= 60  step= 1  format= %0.1f dB  div_scale= 10  preset= -50
                    Min = -6.0 dB  Max = 6.0 dB  Step = 0.1 dB  Preset = -5.0 dB  "
        ::= { iquav10CmdEntry 36225 }


    iquav10LoudCustomBlock2CustomPreset OBJECT-TYPE
        SYNTAX            INTEGER {
                            valGeneral(0),
                            valLight(1),
                            valHeavy(2),
                            valLoud(3),
                            valLoudLimit(4),
                            valProtectionLimit(5),
                            valDefaults(6),
                            valCustom(7)
                            }
        MAX-ACCESS        read-write
        STATUS            current
        DESCRIPTION
                "CMNT: - Linear Acoustic Cust Preset 2
                 TYPE: - RadiobuttonList
                 PAGE: - LoudCustom
                    CustomPreset  cmdID= 36307
                    General  value= 0
                    Light  value= 1
                    Heavy  value= 2
                    Loud  value= 3
                    LoudLimit  value= 4
                    ProtectionLimit  value= 5
                    Defaults  value= 6
                    Custom  value= 7  "
        ::= { iquav10CmdEntry 36307 }


    iquav10LoudCustomBlock2Copyto1 OBJECT-TYPE
        SYNTAX            INTEGER { noAction(0),valCopyto1(1) }
        MAX-ACCESS        read-write
        STATUS            current
        DESCRIPTION
                "CMNT: - Linear Acoustic Cust Preset COPY 2 to 1
                 TYPE: - Button
                 PAGE: - LoudCustom
                    Copy to 1  cmdID= 36308
                    value= 1  "
        ::= { iquav10CmdEntry 36308 }


    iquav10LoudCustomMasterLevelCustom1 OBJECT-TYPE
        SYNTAX            INTEGER
        MAX-ACCESS        read-write
        STATUS            current
        DESCRIPTION
                "CMNT: - Linear Acoustic CUSTOM1 Master Level 
                 TYPE: - Number
                 PAGE: - LoudCustom
                    Custom1  cmdID= 36328
                    min= -310  max= 0  step= 1  format= %0.1f dB  div_scale= 10  preset= -110
                    Min = -31.0 dB  Max = 0.0 dB  Step = 0.1 dB  Preset = -11.0 dB  "
        ::= { iquav10CmdEntry 36328 }


    iquav10LoudCustomMasterLevelCustom2 OBJECT-TYPE
        SYNTAX            INTEGER
        MAX-ACCESS        read-write
        STATUS            current
        DESCRIPTION
                "CMNT: - Linear Acoustic CUSTOM2 Master Level 
                 TYPE: - Number
                 PAGE: - LoudCustom
                    Custom2  cmdID= 36329
                    min= -310  max= 0  step= 1  format= %0.1f dB  div_scale= 10  preset= -110
                    Min = -31.0 dB  Max = 0.0 dB  Step = 0.1 dB  Preset = -11.0 dB  "
        ::= { iquav10CmdEntry 36329 }


    iquav10LoudCustomMasterLevelGen51 OBJECT-TYPE
        SYNTAX            INTEGER
        MAX-ACCESS        read-write
        STATUS            current
        DESCRIPTION
                "CMNT: - Linear Acoustic 5.1 Master Level General
                 TYPE: - Number
                 PAGE: - LoudCustom
                    Gen_51  cmdID= 36310
                    min= -310  max= 0  step= 1  format= %0.1f dB  div_scale= 10  preset= -110
                    Min = -31.0 dB  Max = 0.0 dB  Step = 0.1 dB  Preset = -11.0 dB  "
        ::= { iquav10CmdEntry 36310 }


    iquav10LoudCustomMasterLevelLight51 OBJECT-TYPE
        SYNTAX            INTEGER
        MAX-ACCESS        read-write
        STATUS            current
        DESCRIPTION
                "CMNT: - Linear Acoustic 5.1 Master Level Light
                 TYPE: - Number
                 PAGE: - LoudCustom
                    Light_51  cmdID= 36311
                    min= -310  max= 0  step= 1  format= %0.1f dB  div_scale= 10  preset= -110
                    Min = -31.0 dB  Max = 0.0 dB  Step = 0.1 dB  Preset = -11.0 dB  "
        ::= { iquav10CmdEntry 36311 }


    iquav10LoudCustomMasterLevelHeavy51 OBJECT-TYPE
        SYNTAX            INTEGER
        MAX-ACCESS        read-write
        STATUS            current
        DESCRIPTION
                "CMNT: - Linear Acoustic 5.1 Master Level Heavy
                 TYPE: - Number
                 PAGE: - LoudCustom
                    Heavy_51  cmdID= 36312
                    min= -310  max= 0  step= 1  format= %0.1f dB  div_scale= 10  preset= -110
                    Min = -31.0 dB  Max = 0.0 dB  Step = 0.1 dB  Preset = -11.0 dB  "
        ::= { iquav10CmdEntry 36312 }


    iquav10LoudCustomMasterLevelLoud51 OBJECT-TYPE
        SYNTAX            INTEGER
        MAX-ACCESS        read-write
        STATUS            current
        DESCRIPTION
                "CMNT: - Linear Acoustic 5.1 Master Level Loud
                 TYPE: - Number
                 PAGE: - LoudCustom
                    Loud_51  cmdID= 36313
                    min= -310  max= 0  step= 1  format= %0.1f dB  div_scale= 10  preset= -110
                    Min = -31.0 dB  Max = 0.0 dB  Step = 0.1 dB  Preset = -11.0 dB  "
        ::= { iquav10CmdEntry 36313 }


    iquav10LoudCustomMasterLevelLoudLimit51 OBJECT-TYPE
        SYNTAX            INTEGER
        MAX-ACCESS        read-write
        STATUS            current
        DESCRIPTION
                "CMNT: - Linear Acoustic 5.1 Master Level LoudLimit
                 TYPE: - Number
                 PAGE: - LoudCustom
                    LoudLimit_51  cmdID= 36314
                    min= -310  max= 0  step= 1  format= %0.1f dB  div_scale= 10  preset= -60
                    Min = -31.0 dB  Max = 0.0 dB  Step = 0.1 dB  Preset = -6.0 dB  "
        ::= { iquav10CmdEntry 36314 }


    iquav10LoudCustomMasterLevelProtect51 OBJECT-TYPE
        SYNTAX            INTEGER
        MAX-ACCESS        read-write
        STATUS            current
        DESCRIPTION
                "CMNT: - Linear Acoustic 5.1 Master Level Protection
                 TYPE: - Number
                 PAGE: - LoudCustom
                    Protect_51  cmdID= 36315
                    min= -310  max= 0  step= 1  format= %0.1f dB  div_scale= 10  preset= -30
                    Min = -31.0 dB  Max = 0.0 dB  Step = 0.1 dB  Preset = -3.0 dB  "
        ::= { iquav10CmdEntry 36315 }


    iquav10LoudCustomMasterLevelGenSterA OBJECT-TYPE
        SYNTAX            INTEGER
        MAX-ACCESS        read-write
        STATUS            current
        DESCRIPTION
                "CMNT: - Linear Acoustic StereoA Master Level General
                 TYPE: - Number
                 PAGE: - LoudCustom
                    Gen_SterA  cmdID= 36316
                    min= -310  max= 0  step= 1  format= %0.1f dB  div_scale= 10  preset= -110
                    Min = -31.0 dB  Max = 0.0 dB  Step = 0.1 dB  Preset = -11.0 dB  "
        ::= { iquav10CmdEntry 36316 }


    iquav10LoudCustomMasterLevelLightSterA OBJECT-TYPE
        SYNTAX            INTEGER
        MAX-ACCESS        read-write
        STATUS            current
        DESCRIPTION
                "CMNT: - Linear Acoustic StereoA Master Level Light
                 TYPE: - Number
                 PAGE: - LoudCustom
                    Light_SterA  cmdID= 36317
                    min= -310  max= 0  step= 1  format= %0.1f dB  div_scale= 10  preset= -110
                    Min = -31.0 dB  Max = 0.0 dB  Step = 0.1 dB  Preset = -11.0 dB  "
        ::= { iquav10CmdEntry 36317 }


    iquav10LoudCustomMasterLevelHeavySterA OBJECT-TYPE
        SYNTAX            INTEGER
        MAX-ACCESS        read-write
        STATUS            current
        DESCRIPTION
                "CMNT: - Linear Acoustic StereoA Master Level Heavy
                 TYPE: - Number
                 PAGE: - LoudCustom
                    Heavy_SterA  cmdID= 36318
                    min= -310  max= 0  step= 1  format= %0.1f dB  div_scale= 10  preset= -110
                    Min = -31.0 dB  Max = 0.0 dB  Step = 0.1 dB  Preset = -11.0 dB  "
        ::= { iquav10CmdEntry 36318 }


    iquav10LoudCustomMasterLevelLoudSterA OBJECT-TYPE
        SYNTAX            INTEGER
        MAX-ACCESS        read-write
        STATUS            current
        DESCRIPTION
                "CMNT: - Linear Acoustic StereoA Master Level Loud
                 TYPE: - Number
                 PAGE: - LoudCustom
                    Loud_SterA  cmdID= 36319
                    min= -310  max= 0  step= 1  format= %0.1f dB  div_scale= 10  preset= -110
                    Min = -31.0 dB  Max = 0.0 dB  Step = 0.1 dB  Preset = -11.0 dB  "
        ::= { iquav10CmdEntry 36319 }


    iquav10LoudCustomMasterLevelLoudLimitSterA OBJECT-TYPE
        SYNTAX            INTEGER
        MAX-ACCESS        read-write
        STATUS            current
        DESCRIPTION
                "CMNT: - Linear Acoustic StereoA Master Level LoudLimit
                 TYPE: - Number
                 PAGE: - LoudCustom
                    LoudLimit_SterA  cmdID= 36320
                    min= -310  max= 0  step= 1  format= %0.1f dB  div_scale= 10  preset= -60
                    Min = -31.0 dB  Max = 0.0 dB  Step = 0.1 dB  Preset = -6.0 dB  "
        ::= { iquav10CmdEntry 36320 }


    iquav10LoudCustomMasterLevelProtectSterA OBJECT-TYPE
        SYNTAX            INTEGER
        MAX-ACCESS        read-write
        STATUS            current
        DESCRIPTION
                "CMNT: - Linear Acoustic StereoA Master Level Protection
                 TYPE: - Number
                 PAGE: - LoudCustom
                    Protect_SterA  cmdID= 36321
                    min= -310  max= 0  step= 1  format= %0.1f dB  div_scale= 10  preset= -30
                    Min = -31.0 dB  Max = 0.0 dB  Step = 0.1 dB  Preset = -3.0 dB  "
        ::= { iquav10CmdEntry 36321 }


    iquav10LoudCustomMasterLevelGenSterB OBJECT-TYPE
        SYNTAX            INTEGER
        MAX-ACCESS        read-write
        STATUS            current
        DESCRIPTION
                "CMNT: - Linear Acoustic StereoB Master Level General
                 TYPE: - Number
                 PAGE: - LoudCustom
                    Gen_SterB  cmdID= 36322
                    min= -310  max= 0  step= 1  format= %0.1f dB  div_scale= 10  preset= -110
                    Min = -31.0 dB  Max = 0.0 dB  Step = 0.1 dB  Preset = -11.0 dB  "
        ::= { iquav10CmdEntry 36322 }


    iquav10LoudCustomMasterLevelLightSterB OBJECT-TYPE
        SYNTAX            INTEGER
        MAX-ACCESS        read-write
        STATUS            current
        DESCRIPTION
                "CMNT: - Linear Acoustic StereoB Master Level Light
                 TYPE: - Number
                 PAGE: - LoudCustom
                    Light_SterB  cmdID= 36323
                    min= -310  max= 0  step= 1  format= %0.1f dB  div_scale= 10  preset= -110
                    Min = -31.0 dB  Max = 0.0 dB  Step = 0.1 dB  Preset = -11.0 dB  "
        ::= { iquav10CmdEntry 36323 }


    iquav10LoudCustomMasterLevelHeavySterB OBJECT-TYPE
        SYNTAX            INTEGER
        MAX-ACCESS        read-write
        STATUS            current
        DESCRIPTION
                "CMNT: - Linear Acoustic StereoB Master Level Heavy
                 TYPE: - Number
                 PAGE: - LoudCustom
                    Heavy_SterB  cmdID= 36324
                    min= -310  max= 0  step= 1  format= %0.1f dB  div_scale= 10  preset= -110
                    Min = -31.0 dB  Max = 0.0 dB  Step = 0.1 dB  Preset = -11.0 dB  "
        ::= { iquav10CmdEntry 36324 }


    iquav10LoudCustomMasterLevelLoudSterB OBJECT-TYPE
        SYNTAX            INTEGER
        MAX-ACCESS        read-write
        STATUS            current
        DESCRIPTION
                "CMNT: - Linear Acoustic StereoB Master Level Loud
                 TYPE: - Number
                 PAGE: - LoudCustom
                    Loud_SterB  cmdID= 36325
                    min= -310  max= 0  step= 1  format= %0.1f dB  div_scale= 10  preset= -110
                    Min = -31.0 dB  Max = 0.0 dB  Step = 0.1 dB  Preset = -11.0 dB  "
        ::= { iquav10CmdEntry 36325 }


    iquav10LoudCustomMasterLevelLoudLimitSterB OBJECT-TYPE
        SYNTAX            INTEGER
        MAX-ACCESS        read-write
        STATUS            current
        DESCRIPTION
                "CMNT: - Linear Acoustic StereoB Master Level LoudLimit
                 TYPE: - Number
                 PAGE: - LoudCustom
                    LoudLimit_SterB  cmdID= 36326
                    min= -310  max= 0  step= 1  format= %0.1f dB  div_scale= 10  preset= -60
                    Min = -31.0 dB  Max = 0.0 dB  Step = 0.1 dB  Preset = -6.0 dB  "
        ::= { iquav10CmdEntry 36326 }


    iquav10LoudCustomMasterLevelProtectSterB OBJECT-TYPE
        SYNTAX            INTEGER
        MAX-ACCESS        read-write
        STATUS            current
        DESCRIPTION
                "CMNT: - Linear Acoustic StereoB Master Level Protection
                 TYPE: - Number
                 PAGE: - LoudCustom
                    Protect_SterB  cmdID= 36327
                    min= -310  max= 0  step= 1  format= %0.1f dB  div_scale= 10  preset= -30
                    Min = -31.0 dB  Max = 0.0 dB  Step = 0.1 dB  Preset = -3.0 dB  "
        ::= { iquav10CmdEntry 36327 }


    iquav10Mixers13Select OBJECT-TYPE
        SYNTAX            INTEGER {
                            valMixer1(0),
                            valMixer2(1),
                            valMixer3(2),
                            valMixer4(3),
                            valDownmix1n1(4),
                            valDownmix1n2(5)
                            }
        MAX-ACCESS        read-write
        STATUS            current
        DESCRIPTION
                "CMNT: - Mixer select
                 TYPE: - RadiobuttonList
                 PAGE: - Mixers1_3
                    Select  cmdID= 40825
                    Mixer1  value= 0
                    Mixer2  value= 1
                    Mixer3  value= 2
                    Mixer4  value= 3
                    Downmix1-1  value= 4
                    Downmix1-2  value= 5  "
        ::= { iquav10CmdEntry 40825 }


    iquav10Mixers13Source1ProcGain OBJECT-TYPE
        SYNTAX            INTEGER
        MAX-ACCESS        read-write
        STATUS            current
        DESCRIPTION
                "CMNT: - Mix_1 Proc Amp Gain
                 TYPE: - Number
                 PAGE: - Mixers1_3
                    ProcGain  cmdID= 40800
                    min= -801  max= 120  step= 1  format= %0.1f dB  div_scale= 10  preset= 0
                    Min = -80.1 dB  Max = 12.0 dB  Step = 0.1 dB  Preset = 0.0 dB  "
        ::= { iquav10CmdEntry 40800 }


    iquav10Mixers13Source1Invert OBJECT-TYPE
        SYNTAX            INTEGER { disable(0), enable(1)  }
        MAX-ACCESS        read-write
        STATUS            current
        DESCRIPTION
                "CMNT: - Mix_1 Invert
                 TYPE: - Checkbox
                 PAGE: - Mixers1_3
                    Invert  cmdID= 40806  "
        ::= { iquav10CmdEntry 40806 }


    iquav10Mixers13Source1Mute OBJECT-TYPE
        SYNTAX            INTEGER { disable(0), enable(1)  }
        MAX-ACCESS        read-write
        STATUS            current
        DESCRIPTION
                "CMNT: - Mix_1 Mute
                 TYPE: - Checkbox
                 PAGE: - Mixers1_3
                    Mute  cmdID= 40812  "
        ::= { iquav10CmdEntry 40812 }


    iquav10Mixers13Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_1 source
                 TYPE: - RadiobuttonList
                 PAGE: - Mixers1_3
                    Src  cmdID= 40818
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iquav10CmdEntry 40818 }


    iquav10Mixers13Source1Name OBJECT-TYPE
        SYNTAX            RollCallString
        MAX-ACCESS        read-only
        STATUS            current
        DESCRIPTION
                "CMNT: - Mix_1 name
                 TYPE: - Display
                 PAGE: - Mixers1_3
                    Name  cmdID= 40826  "
        ::= { iquav10CmdEntry 40826 }


    iquav10Mixers13Source2ProcGain OBJECT-TYPE
        SYNTAX            INTEGER
        MAX-ACCESS        read-write
        STATUS            current
        DESCRIPTION
                "CMNT: - Mix_2 Proc Amp Gain
                 TYPE: - Number
                 PAGE: - Mixers1_3
                    ProcGain  cmdID= 40801
                    min= -801  max= 120  step= 1  format= %0.1f dB  div_scale= 10  preset= 0
                    Min = -80.1 dB  Max = 12.0 dB  Step = 0.1 dB  Preset = 0.0 dB  "
        ::= { iquav10CmdEntry 40801 }


    iquav10Mixers13Source2Invert OBJECT-TYPE
        SYNTAX            INTEGER { disable(0), enable(1)  }
        MAX-ACCESS        read-write
        STATUS            current
        DESCRIPTION
                "CMNT: - Mix_2 Invert
                 TYPE: - Checkbox
                 PAGE: - Mixers1_3
                    Invert  cmdID= 40807  "
        ::= { iquav10CmdEntry 40807 }


    iquav10Mixers13Source2Mute OBJECT-TYPE
        SYNTAX            INTEGER { disable(0), enable(1)  }
        MAX-ACCESS        read-write
        STATUS            current
        DESCRIPTION
                "CMNT: - Mix_2 Mute
                 TYPE: - Checkbox
                 PAGE: - Mixers1_3
                    Mute  cmdID= 40813  "
        ::= { iquav10CmdEntry 40813 }


    iquav10Mixers13Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_2 source
                 TYPE: - RadiobuttonList
                 PAGE: - Mixers1_3
                    Src  cmdID= 40819
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iquav10CmdEntry 40819 }


    iquav10Mixers13Source2Name OBJECT-TYPE
        SYNTAX            RollCallString
        MAX-ACCESS        read-only
        STATUS            current
        DESCRIPTION
                "CMNT: - Mix_2 name
                 TYPE: - Display
                 PAGE: - Mixers1_3
                    Name  cmdID= 40827  "
        ::= { iquav10CmdEntry 40827 }


    iquav10Mixers13Source3ProcGain OBJECT-TYPE
        SYNTAX            INTEGER
        MAX-ACCESS        read-write
        STATUS            current
        DESCRIPTION
                "CMNT: - Mix_3 Proc Amp Gain
                 TYPE: - Number
                 PAGE: - Mixers1_3
                    ProcGain  cmdID= 40802
                    min= -801  max= 120  step= 1  format= %0.1f dB  div_scale= 10  preset= 0
                    Min = -80.1 dB  Max = 12.0 dB  Step = 0.1 dB  Preset = 0.0 dB  "
        ::= { iquav10CmdEntry 40802 }


    iquav10Mixers13Source3Invert OBJECT-TYPE
        SYNTAX            INTEGER { disable(0), enable(1)  }
        MAX-ACCESS        read-write
        STATUS            current
        DESCRIPTION
                "CMNT: - Mix_3 Invert
                 TYPE: - Checkbox
                 PAGE: - Mixers1_3
                    Invert  cmdID= 40808  "
        ::= { iquav10CmdEntry 40808 }


    iquav10Mixers13Source3Mute OBJECT-TYPE
        SYNTAX            INTEGER { disable(0), enable(1)  }
        MAX-ACCESS        read-write
        STATUS            current
        DESCRIPTION
                "CMNT: - Mix_3 Mute
                 TYPE: - Checkbox
                 PAGE: - Mixers1_3
                    Mute  cmdID= 40814  "
        ::= { iquav10CmdEntry 40814 }


    iquav10Mixers13Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_3 source
                 TYPE: - RadiobuttonList
                 PAGE: - Mixers1_3
                    Src  cmdID= 40820
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iquav10CmdEntry 40820 }


    iquav10Mixers13Source3Name OBJECT-TYPE
        SYNTAX            RollCallString
        MAX-ACCESS        read-only
        STATUS            current
        DESCRIPTION
                "CMNT: - Mix_3 name
                 TYPE: - Display
                 PAGE: - Mixers1_3
                    Name  cmdID= 40828  "
        ::= { iquav10CmdEntry 40828 }


    iquav10Mixers13MixerLoRo OBJECT-TYPE
        SYNTAX            INTEGER {
                            valCustom(0),
                            valn3dBCpLsRs(1),
                            valn3dBCn3dBLsRs(2),
                            valn3dBCn6dBLsRs(3),
                            valn3dBCn9dBLsRs(4)
                            }
        MAX-ACCESS        read-write
        STATUS            current
        DESCRIPTION
                "CMNT: - DownMixLoRo
                 TYPE: - RadiobuttonList
                 PAGE: - Mixers1_3
                    MixerLoRo  cmdID= 40832
                    Custom  value= 0
                    -3dB C + Ls/Rs  value= 1
                    -3dB C -3dB Ls/Rs  value= 2
                    -3dB C -6dB Ls/Rs  value= 3
                    -3dB C -9dB Ls/Rs  value= 4  "
        ::= { iquav10CmdEntry 40832 }


    iquav10Mixers46Source4ProcGain OBJECT-TYPE
        SYNTAX            INTEGER
        MAX-ACCESS        read-write
        STATUS            current
        DESCRIPTION
                "CMNT: - Mix_4 Proc Amp Gain
                 TYPE: - Number
                 PAGE: - Mixers4_6
                    ProcGain  cmdID= 40803
                    min= -801  max= 120  step= 1  format= %0.1f dB  div_scale= 10  preset= 0
                    Min = -80.1 dB  Max = 12.0 dB  Step = 0.1 dB  Preset = 0.0 dB  "
        ::= { iquav10CmdEntry 40803 }


    iquav10Mixers46Source4Invert OBJECT-TYPE
        SYNTAX            INTEGER { disable(0), enable(1)  }
        MAX-ACCESS        read-write
        STATUS            current
        DESCRIPTION
                "CMNT: - Mix_4 Invert
                 TYPE: - Checkbox
                 PAGE: - Mixers4_6
                    Invert  cmdID= 40809  "
        ::= { iquav10CmdEntry 40809 }


    iquav10Mixers46Source4Mute OBJECT-TYPE
        SYNTAX            INTEGER { disable(0), enable(1)  }
        MAX-ACCESS        read-write
        STATUS            current
        DESCRIPTION
                "CMNT: - Mix_4 Mute
                 TYPE: - Checkbox
                 PAGE: - Mixers4_6
                    Mute  cmdID= 40815  "
        ::= { iquav10CmdEntry 40815 }


    iquav10Mixers46Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_4 source
                 TYPE: - RadiobuttonList
                 PAGE: - Mixers4_6
                    Src  cmdID= 40821
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iquav10CmdEntry 40821 }


    iquav10Mixers46Source4Name OBJECT-TYPE
        SYNTAX            RollCallString
        MAX-ACCESS        read-only
        STATUS            current
        DESCRIPTION
                "CMNT: - Mix_4 name
                 TYPE: - Display
                 PAGE: - Mixers4_6
                    Name  cmdID= 40829  "
        ::= { iquav10CmdEntry 40829 }


    iquav10Mixers46Source5ProcGain OBJECT-TYPE
        SYNTAX            INTEGER
        MAX-ACCESS        read-write
        STATUS            current
        DESCRIPTION
                "CMNT: - Mix_5 Proc Amp Gain
                 TYPE: - Number
                 PAGE: - Mixers4_6
                    ProcGain  cmdID= 40804
                    min= -801  max= 120  step= 1  format= %0.1f dB  div_scale= 10  preset= 0
                    Min = -80.1 dB  Max = 12.0 dB  Step = 0.1 dB  Preset = 0.0 dB  "
        ::= { iquav10CmdEntry 40804 }


    iquav10Mixers46Source5Invert OBJECT-TYPE
        SYNTAX            INTEGER { disable(0), enable(1)  }
        MAX-ACCESS        read-write
        STATUS            current
        DESCRIPTION
                "CMNT: - Mix_5 Invert
                 TYPE: - Checkbox
                 PAGE: - Mixers4_6
                    Invert  cmdID= 40810  "
        ::= { iquav10CmdEntry 40810 }


    iquav10Mixers46Source5Mute OBJECT-TYPE
        SYNTAX            INTEGER { disable(0), enable(1)  }
        MAX-ACCESS        read-write
        STATUS            current
        DESCRIPTION
                "CMNT: - Mix_5 Mute
                 TYPE: - Checkbox
                 PAGE: - Mixers4_6
                    Mute  cmdID= 40816  "
        ::= { iquav10CmdEntry 40816 }


    iquav10Mixers46Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_5 source
                 TYPE: - RadiobuttonList
                 PAGE: - Mixers4_6
                    Src  cmdID= 40822
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iquav10CmdEntry 40822 }


    iquav10Mixers46Source5Name OBJECT-TYPE
        SYNTAX            RollCallString
        MAX-ACCESS        read-only
        STATUS            current
        DESCRIPTION
                "CMNT: - Mix_5 name
                 TYPE: - Display
                 PAGE: - Mixers4_6
                    Name  cmdID= 40830  "
        ::= { iquav10CmdEntry 40830 }


    iquav10Mixers46Source6ProcGain OBJECT-TYPE
        SYNTAX            INTEGER
        MAX-ACCESS        read-write
        STATUS            current
        DESCRIPTION
                "CMNT: - Mix_6 Proc Amp Gain
                 TYPE: - Number
                 PAGE: - Mixers4_6
                    ProcGain  cmdID= 40805
                    min= -801  max= 120  step= 1  format= %0.1f dB  div_scale= 10  preset= 0
                    Min = -80.1 dB  Max = 12.0 dB  Step = 0.1 dB  Preset = 0.0 dB  "
        ::= { iquav10CmdEntry 40805 }


    iquav10Mixers46Source6Invert OBJECT-TYPE
        SYNTAX            INTEGER { disable(0), enable(1)  }
        MAX-ACCESS        read-write
        STATUS            current
        DESCRIPTION
                "CMNT: - Mix_6 Invert
                 TYPE: - Checkbox
                 PAGE: - Mixers4_6
                    Invert  cmdID= 40811  "
        ::= { iquav10CmdEntry 40811 }


    iquav10Mixers46Source6Mute OBJECT-TYPE
        SYNTAX            INTEGER { disable(0), enable(1)  }
        MAX-ACCESS        read-write
        STATUS            current
        DESCRIPTION
                "CMNT: - Mix_6 Mute
                 TYPE: - Checkbox
                 PAGE: - Mixers4_6
                    Mute  cmdID= 40817  "
        ::= { iquav10CmdEntry 40817 }


    iquav10Mixers46Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_6 source
                 TYPE: - RadiobuttonList
                 PAGE: - Mixers4_6
                    Src  cmdID= 40823
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iquav10CmdEntry 40823 }


    iquav10Mixers46Source6Name OBJECT-TYPE
        SYNTAX            RollCallString
        MAX-ACCESS        read-only
        STATUS            current
        DESCRIPTION
                "CMNT: - Mix_6 name
                 TYPE: - Display
                 PAGE: - Mixers4_6
                    Name  cmdID= 40831  "
        ::= { iquav10CmdEntry 40831 }


    iquav10DolbyDecodeDolbyDecoderDetectMode OBJECT-TYPE
        SYNTAX            INTEGER {
                            valAuto(0),
                            valDolbyEorMute(1),
                            valDolbyDigitalorMute(2),
                            valMute(3)
                            }
        MAX-ACCESS        read-write
        STATUS            current
        DESCRIPTION
                "CMNT: - Dolby decoder detect mode
                 TYPE: - RadiobuttonList
                 PAGE: - DolbyDecode
                    Detect Mode  cmdID= 42401
                    Auto  value= 0
                    Dolby E or Mute  value= 1
                    Dolby Digital or Mute  value= 2
                    Mute  value= 3  "
        ::= { iquav10CmdEntry 42401 }


    iquav10DolbyDecodeDolbyDecoderAESChannelSelect OBJECT-TYPE
        SYNTAX            INTEGER {
                            valChannel1(0),
                            valChannel2(1)
                            }
        MAX-ACCESS        read-write
        STATUS            current
        DESCRIPTION
                "CMNT: - Dolby Digital Pro 16 AES channel select
                 TYPE: - RadiobuttonList
                 PAGE: - DolbyDecode
                    AES Channel Select  cmdID= 42402
                    Channel 1  value= 0
                    Channel 2  value= 1  "
        ::= { iquav10CmdEntry 42402 }


    iquav10DolbyDecodeDolbyDecoderPCMLatency OBJECT-TYPE
        SYNTAX            INTEGER {
                            valSingleVideoFrame(0),
                            valMinimum(1)
                            }
        MAX-ACCESS        read-write
        STATUS            current
        DESCRIPTION
                "CMNT: - Dolby decoder PCM latency
                 TYPE: - RadiobuttonList
                 PAGE: - DolbyDecode
                    PCM Latency  cmdID= 42403
                    Single Video Frame  value= 0
                    Minimum  value= 1  "
        ::= { iquav10CmdEntry 42403 }


    iquav10DolbyDecodeDolbyDecoderListeningModeDolbyD OBJECT-TYPE
        SYNTAX            INTEGER {
                            valFull(0),
                            valEX(1),
                            val3Stereo(2),
                            valPhantom(3),
                            valStereo(4),
                            valMono(5)
                            }
        MAX-ACCESS        read-write
        STATUS            current
        DESCRIPTION
                "CMNT: - Dolby decoder listening mode
                 TYPE: - RadiobuttonList
                 PAGE: - DolbyDecode
                    Listening Mode Dolby D  cmdID= 42404
                    Full  value= 0
                    EX  value= 1
                    3 Stereo  value= 2
                    Phantom  value= 3
                    Stereo  value= 4
                    Mono  value= 5  "
        ::= { iquav10CmdEntry 42404 }


    iquav10DolbyDecodeDolbyDecoderDynamicRange OBJECT-TYPE
        SYNTAX            INTEGER {
                            valLineMode(0),
                            valRFMode(1),
                            valBypassMode(3)
                            }
        MAX-ACCESS        read-write
        STATUS            current
        DESCRIPTION
                "CMNT: - Dolby decoder dynamic range
                 TYPE: - RadiobuttonList
                 PAGE: - DolbyDecode
                    Dynamic Range   cmdID= 42405
                    Line Mode  value= 0
                    RF Mode  value= 1
                    Bypass Mode  value= 3  "
        ::= { iquav10CmdEntry 42405 }


    iquav10DolbyDecoderAuxChannelProgramSelect OBJECT-TYPE
        SYNTAX            INTEGER {
                            valProgram1(0),
                            valProgram2(1),
                            valProgram3(2),
                            valProgram4(3),
                            valProgram5(4),
                            valProgram6(5),
                            valProgram7(6),
                            valProgram8(7)
                            }
        MAX-ACCESS        read-write
        STATUS            current
        DESCRIPTION
                "CMNT: - Dolby decoder auxiliary channel program select
                 TYPE: - RadiobuttonList
                 PAGE: - Dolby Decoder
                    Program Select  cmdID= 42406
                    Program 1  value= 0
                    Program 2  value= 1
                    Program 3  value= 2
                    Program 4  value= 3
                    Program 5  value= 4
                    Program 6  value= 5
                    Program 7  value= 6
                    Program 8  value= 7  "
        ::= { iquav10CmdEntry 42406 }


    iquav10DolbyDecoderAuxChannelDynamicRange OBJECT-TYPE
        SYNTAX            INTEGER {
                            valLineMode(0),
                            valRFMode(1)
                            }
        MAX-ACCESS        read-write
        STATUS            current
        DESCRIPTION
                "CMNT: - Dolby decoder auxiliary channel dynamic range
                 TYPE: - RadiobuttonList
                 PAGE: - Dolby Decoder
                    Dynamic Range  cmdID= 42407
                    Line Mode  value= 0
                    RF Mode  value= 1  "
        ::= { iquav10CmdEntry 42407 }


    iquav10DolbyDecoderAuxChannelOutputMode OBJECT-TYPE
        SYNTAX            INTEGER {
                            valLtRt(0),
                            valLoRo(1),
                            valMono(2),
                            valMute(3)
                            }
        MAX-ACCESS        read-write
        STATUS            current
        DESCRIPTION
                "CMNT: - Dolby decoder auxiliary channel output mode
                 TYPE: - RadiobuttonList
                 PAGE: - Dolby Decoder
                    Output Mode  cmdID= 42408
                    Lt/Rt  value= 0
                    Lo/Ro  value= 1
                    Mono  value= 2
                    Mute  value= 3  "
        ::= { iquav10CmdEntry 42408 }


    iquav10DolbyDecoderDecoderStatusBitstreamFormat OBJECT-TYPE
        SYNTAX            RollCallString
        MAX-ACCESS        read-only
        STATUS            current
        DESCRIPTION
                "CMNT: - Dolby decoder I/P bitstream format
                 TYPE: - Display
                 PAGE: - Dolby Decoder
                    Bitstream Format  cmdID= 42409  "
        ::= { iquav10CmdEntry 42409 }


    iquav10DolbyDecoderDecoderStatusBitstreamStatus OBJECT-TYPE
        SYNTAX            RollCallString
        MAX-ACCESS        read-only
        STATUS            current
        DESCRIPTION
                "CMNT: - Dolby decoder I/P bitstream status
                 TYPE: - Display
                 PAGE: - Dolby Decoder
                    Bitstream Status  cmdID= 42410  "
        ::= { iquav10CmdEntry 42410 }


    iquav10DolbyDecoderDecoderStatusDCRCErrorCount OBJECT-TYPE
        SYNTAX            RollCallString
        MAX-ACCESS        read-only
        STATUS            current
        DESCRIPTION
                "CMNT: - Dolby D decoder CRC error count
                 TYPE: - Display
                 PAGE: - Dolby Decoder
                    D CRC Error Count  cmdID= 42505  "
        ::= { iquav10CmdEntry 42505 }


    iquav10DolbyDecoderDecoderStatusDCRCErrorTime OBJECT-TYPE
        SYNTAX            RollCallString
        MAX-ACCESS        read-only
        STATUS            current
        DESCRIPTION
                "CMNT: - Dolby D decoder CRC error time
                 TYPE: - Display
                 PAGE: - Dolby Decoder
                    D CRC Error Time  cmdID= 42504  "
        ::= { iquav10CmdEntry 42504 }


    iquav10DolbyDecoderDecoderStatusECRCErrorCount OBJECT-TYPE
        SYNTAX            RollCallString
        MAX-ACCESS        read-only
        STATUS            current
        DESCRIPTION
                "CMNT: - Dolby E decoder CRC error count
                 TYPE: - Display
                 PAGE: - Dolby Decoder
                    E CRC Error Count  cmdID= 42507  "
        ::= { iquav10CmdEntry 42507 }


    iquav10DolbyDecoderDecoderStatusECRCErrorTime OBJECT-TYPE
        SYNTAX            RollCallString
        MAX-ACCESS        read-only
        STATUS            current
        DESCRIPTION
                "CMNT: - Dolby E decoder CRC error time
                 TYPE: - Display
                 PAGE: - Dolby Decoder
                    E CRC Error Time  cmdID= 42506  "
        ::= { iquav10CmdEntry 42506 }


    iquav10DolbyDecoderDecoderStatusResetErrors OBJECT-TYPE
        SYNTAX            INTEGER { noAction(0),valResetErrors(1) }
        MAX-ACCESS        read-write
        STATUS            current
        DESCRIPTION
                "CMNT: - Dolby decoder CRC error reset
                 TYPE: - Button
                 PAGE: - Dolby Decoder
                    Reset Errors  cmdID= 42502
                    value= 1  "
        ::= { iquav10CmdEntry 42502 }


    iquav10DolbyDecoderDecoderStatusResetTime OBJECT-TYPE
        SYNTAX            RollCallString
        MAX-ACCESS        read-only
        STATUS            current
        DESCRIPTION
                "CMNT: - Dolby decoder CRC error reset time
                 TYPE: - Display
                 PAGE: - Dolby Decoder
                    Reset Time  cmdID= 42503  "
        ::= { iquav10CmdEntry 42503 }


    iquav10DolbyDecoderOutputsA1A2A1Gain OBJECT-TYPE
        SYNTAX            INTEGER
        MAX-ACCESS        read-write
        STATUS            current
        DESCRIPTION
                "CMNT: - Dolby decoder O/P A1 gain
                 TYPE: - Number
                 PAGE: - Dolby Decoder Outputs
                    A1 Gain  cmdID= 42558
                    min= -801  max= 120  step= 1  format= %0.1f dB  div_scale= 10  preset= 0
                    Min = -80.1 dB  Max = 12.0 dB  Step = 0.1 dB  Preset = 0.0 dB  "
        ::= { iquav10CmdEntry 42558 }


    iquav10DolbyDecoderOutputsA1A2A2Gain OBJECT-TYPE
        SYNTAX            INTEGER
        MAX-ACCESS        read-write
        STATUS            current
        DESCRIPTION
                "CMNT: - Dolby decoder O/P A2 gain
                 TYPE: - Number
                 PAGE: - Dolby Decoder Outputs
                    A2 Gain  cmdID= 42559
                    min= -801  max= 120  step= 1  format= %0.1f dB  div_scale= 10  preset= 0
                    Min = -80.1 dB  Max = 12.0 dB  Step = 0.1 dB  Preset = 0.0 dB  "
        ::= { iquav10CmdEntry 42559 }


    iquav10DolbyDecoderOutputsA1A2MuteA1 OBJECT-TYPE
        SYNTAX            INTEGER { disable(0), enable(1)  }
        MAX-ACCESS        read-write
        STATUS            current
        DESCRIPTION
                "CMNT: - Dolby decoder O/P A1 mute
                 TYPE: - Checkbox
                 PAGE: - Dolby Decoder Outputs
                    Mute A1  cmdID= 42568  "
        ::= { iquav10CmdEntry 42568 }


    iquav10DolbyDecoderOutputsA1A2MuteA2 OBJECT-TYPE
        SYNTAX            INTEGER { disable(0), enable(1)  }
        MAX-ACCESS        read-write
        STATUS            current
        DESCRIPTION
                "CMNT: - Dolby decoder O/P A2 mute
                 TYPE: - Checkbox
                 PAGE: - Dolby Decoder Outputs
                    Mute A2  cmdID= 42569  "
        ::= { iquav10CmdEntry 42569 }


    iquav10DolbyDecoderOutputsA1A2StereoA OBJECT-TYPE
        SYNTAX            INTEGER { disable(0), enable(1)  }
        MAX-ACCESS        read-write
        STATUS            current
        DESCRIPTION
                "CMNT: - Dolby decoder O/P A stereo
                 TYPE: - Checkbox
                 PAGE: - Dolby Decoder Outputs
                    Stereo A  cmdID= 42578  "
        ::= { iquav10CmdEntry 42578 }


    iquav10DolbyDecoderOutputsB3B4B3Gain OBJECT-TYPE
        SYNTAX            INTEGER
        MAX-ACCESS        read-write
        STATUS            current
        DESCRIPTION
                "CMNT: - Dolby decoder O/P B3 gain
                 TYPE: - Number
                 PAGE: - Dolby Decoder Outputs
                    B3 Gain  cmdID= 42560
                    min= -801  max= 120  step= 1  format= %0.1f dB  div_scale= 10  preset= 0
                    Min = -80.1 dB  Max = 12.0 dB  Step = 0.1 dB  Preset = 0.0 dB  "
        ::= { iquav10CmdEntry 42560 }


    iquav10DolbyDecoderOutputsB3B4B4Gain OBJECT-TYPE
        SYNTAX            INTEGER
        MAX-ACCESS        read-write
        STATUS            current
        DESCRIPTION
                "CMNT: - Dolby decoder O/P B4 gain
                 TYPE: - Number
                 PAGE: - Dolby Decoder Outputs
                    B4 Gain  cmdID= 42561
                    min= -801  max= 120  step= 1  format= %0.1f dB  div_scale= 10  preset= 0
                    Min = -80.1 dB  Max = 12.0 dB  Step = 0.1 dB  Preset = 0.0 dB  "
        ::= { iquav10CmdEntry 42561 }


    iquav10DolbyDecoderOutputsB3B4MuteB3 OBJECT-TYPE
        SYNTAX            INTEGER { disable(0), enable(1)  }
        MAX-ACCESS        read-write
        STATUS            current
        DESCRIPTION
                "CMNT: - Dolby decoder O/P B3 mute
                 TYPE: - Checkbox
                 PAGE: - Dolby Decoder Outputs
                    Mute B3  cmdID= 42570  "
        ::= { iquav10CmdEntry 42570 }


    iquav10DolbyDecoderOutputsB3B4MuteB4 OBJECT-TYPE
        SYNTAX            INTEGER { disable(0), enable(1)  }
        MAX-ACCESS        read-write
        STATUS            current
        DESCRIPTION
                "CMNT: - Dolby decoder O/P B4 mute
                 TYPE: - Checkbox
                 PAGE: - Dolby Decoder Outputs
                    Mute B4  cmdID= 42571  "
        ::= { iquav10CmdEntry 42571 }


    iquav10DolbyDecoderOutputsB3B4StereoB OBJECT-TYPE
        SYNTAX            INTEGER { disable(0), enable(1)  }
        MAX-ACCESS        read-write
        STATUS            current
        DESCRIPTION
                "CMNT: - Dolby decoder O/P B stereo
                 TYPE: - Checkbox
                 PAGE: - Dolby Decoder Outputs
                    Stereo B  cmdID= 42579  "
        ::= { iquav10CmdEntry 42579 }


    iquav10DolbyDecoderOutputsC5C6C5Gain OBJECT-TYPE
        SYNTAX            INTEGER
        MAX-ACCESS        read-write
        STATUS            current
        DESCRIPTION
                "CMNT: - Dolby decoder O/P C5 gain
                 TYPE: - Number
                 PAGE: - Dolby Decoder Outputs
                    C5 Gain  cmdID= 42562
                    min= -801  max= 120  step= 1  format= %0.1f dB  div_scale= 10  preset= 0
                    Min = -80.1 dB  Max = 12.0 dB  Step = 0.1 dB  Preset = 0.0 dB  "
        ::= { iquav10CmdEntry 42562 }


    iquav10DolbyDecoderOutputsC5C6C6Gain OBJECT-TYPE
        SYNTAX            INTEGER
        MAX-ACCESS        read-write
        STATUS            current
        DESCRIPTION
                "CMNT: - Dolby decoder O/P C6 gain
                 TYPE: - Number
                 PAGE: - Dolby Decoder Outputs
                    C6 Gain  cmdID= 42563
                    min= -801  max= 120  step= 1  format= %0.1f dB  div_scale= 10  preset= 0
                    Min = -80.1 dB  Max = 12.0 dB  Step = 0.1 dB  Preset = 0.0 dB  "
        ::= { iquav10CmdEntry 42563 }


    iquav10DolbyDecoderOutputsC5C6MuteC5 OBJECT-TYPE
        SYNTAX            INTEGER { disable(0), enable(1)  }
        MAX-ACCESS        read-write
        STATUS            current
        DESCRIPTION
                "CMNT: - Dolby decoder O/P C5 mute
                 TYPE: - Checkbox
                 PAGE: - Dolby Decoder Outputs
                    Mute C5  cmdID= 42572  "
        ::= { iquav10CmdEntry 42572 }


    iquav10DolbyDecoderOutputsC5C6MuteC6 OBJECT-TYPE
        SYNTAX            INTEGER { disable(0), enable(1)  }
        MAX-ACCESS        read-write
        STATUS            current
        DESCRIPTION
                "CMNT: - Dolby decoder O/P C6 mute
                 TYPE: - Checkbox
                 PAGE: - Dolby Decoder Outputs
                    Mute C6  cmdID= 42573  "
        ::= { iquav10CmdEntry 42573 }


    iquav10DolbyDecoderOutputsC5C6StereoC OBJECT-TYPE
        SYNTAX            INTEGER { disable(0), enable(1)  }
        MAX-ACCESS        read-write
        STATUS            current
        DESCRIPTION
                "CMNT: - Dolby decoder O/P C stereo
                 TYPE: - Checkbox
                 PAGE: - Dolby Decoder Outputs
                    Stereo C  cmdID= 42580  "
        ::= { iquav10CmdEntry 42580 }


    iquav10DolbyDecoderOutputsD7D8D7Gain OBJECT-TYPE
        SYNTAX            INTEGER
        MAX-ACCESS        read-write
        STATUS            current
        DESCRIPTION
                "CMNT: - Dolby decoder O/P D7 gain
                 TYPE: - Number
                 PAGE: - Dolby Decoder Outputs
                    D7 Gain  cmdID= 42564
                    min= -801  max= 120  step= 1  format= %0.1f dB  div_scale= 10  preset= 0
                    Min = -80.1 dB  Max = 12.0 dB  Step = 0.1 dB  Preset = 0.0 dB  "
        ::= { iquav10CmdEntry 42564 }


    iquav10DolbyDecoderOutputsD7D8D8Gain OBJECT-TYPE
        SYNTAX            INTEGER
        MAX-ACCESS        read-write
        STATUS            current
        DESCRIPTION
                "CMNT: - Dolby decoder O/P D8 gain
                 TYPE: - Number
                 PAGE: - Dolby Decoder Outputs
                    D8 Gain  cmdID= 42565
                    min= -801  max= 120  step= 1  format= %0.1f dB  div_scale= 10  preset= 0
                    Min = -80.1 dB  Max = 12.0 dB  Step = 0.1 dB  Preset = 0.0 dB  "
        ::= { iquav10CmdEntry 42565 }


    iquav10DolbyDecoderOutputsD7D8MuteD7 OBJECT-TYPE
        SYNTAX            INTEGER { disable(0), enable(1)  }
        MAX-ACCESS        read-write
        STATUS            current
        DESCRIPTION
                "CMNT: - Dolby decoder O/P D7 mute
                 TYPE: - Checkbox
                 PAGE: - Dolby Decoder Outputs
                    Mute D7  cmdID= 42574  "
        ::= { iquav10CmdEntry 42574 }


    iquav10DolbyDecoderOutputsD7D8MuteD8 OBJECT-TYPE
        SYNTAX            INTEGER { disable(0), enable(1)  }
        MAX-ACCESS        read-write
        STATUS            current
        DESCRIPTION
                "CMNT: - Dolby decoder O/P D8 mute
                 TYPE: - Checkbox
                 PAGE: - Dolby Decoder Outputs
                    Mute D8  cmdID= 42575  "
        ::= { iquav10CmdEntry 42575 }


    iquav10DolbyDecoderOutputsD7D8StereoD OBJECT-TYPE
        SYNTAX            INTEGER { disable(0), enable(1)  }
        MAX-ACCESS        read-write
        STATUS            current
        DESCRIPTION
                "CMNT: - Dolby decoder O/P D stereo
                 TYPE: - Checkbox
                 PAGE: - Dolby Decoder Outputs
                    Stereo D  cmdID= 42581  "
        ::= { iquav10CmdEntry 42581 }


    iquav10DolbyDecoderOutputsMLMRMLGain OBJECT-TYPE
        SYNTAX            INTEGER
        MAX-ACCESS        read-write
        STATUS            current
        DESCRIPTION
                "CMNT: - Dolby decoder downmix O/P L gain
                 TYPE: - Number
                 PAGE: - Dolby Decoder Outputs
                    ML Gain  cmdID= 42566
                    min= -801  max= 120  step= 1  format= %0.1f dB  div_scale= 10  preset= 0
                    Min = -80.1 dB  Max = 12.0 dB  Step = 0.1 dB  Preset = 0.0 dB  "
        ::= { iquav10CmdEntry 42566 }


    iquav10DolbyDecoderOutputsMLMRMRGain OBJECT-TYPE
        SYNTAX            INTEGER
        MAX-ACCESS        read-write
        STATUS            current
        DESCRIPTION
                "CMNT: - Dolby decoder downmix O/P R gain
                 TYPE: - Number
                 PAGE: - Dolby Decoder Outputs
                    MR Gain  cmdID= 42567
                    min= -801  max= 120  step= 1  format= %0.1f dB  div_scale= 10  preset= 0
                    Min = -80.1 dB  Max = 12.0 dB  Step = 0.1 dB  Preset = 0.0 dB  "
        ::= { iquav10CmdEntry 42567 }


    iquav10DolbyDecoderOutputsMLMRMuteML OBJECT-TYPE
        SYNTAX            INTEGER { disable(0), enable(1)  }
        MAX-ACCESS        read-write
        STATUS            current
        DESCRIPTION
                "CMNT: - Dolby decoder downmix O/P L mute
                 TYPE: - Checkbox
                 PAGE: - Dolby Decoder Outputs
                    Mute ML  cmdID= 42576  "
        ::= { iquav10CmdEntry 42576 }


    iquav10DolbyDecoderOutputsMLMRMuteMR OBJECT-TYPE
        SYNTAX            INTEGER { disable(0), enable(1)  }
        MAX-ACCESS        read-write
        STATUS            current
        DESCRIPTION
                "CMNT: - Dolby decoder downmix O/P R mute
                 TYPE: - Checkbox
                 PAGE: - Dolby Decoder Outputs
                    Mute MR  cmdID= 42577  "
        ::= { iquav10CmdEntry 42577 }


    iquav10DolbyDecoderOutputsMLMRStereoM OBJECT-TYPE
        SYNTAX            INTEGER { disable(0), enable(1)  }
        MAX-ACCESS        read-write
        STATUS            current
        DESCRIPTION
                "CMNT: - Dolby decoder downmix O/P stereo
                 TYPE: - Checkbox
                 PAGE: - Dolby Decoder Outputs
                    Stereo M  cmdID= 42582  "
        ::= { iquav10CmdEntry 42582 }


    iquav10DolbyDecodeDolbyDecoderOutputsMasterGain OBJECT-TYPE
        SYNTAX            INTEGER
        MAX-ACCESS        read-write
        STATUS            current
        DESCRIPTION
                "CMNT: - Dolby decoder O/P master gain
                 TYPE: - Number
                 PAGE: - DolbyDecode
                    Master Gain  cmdID= 42556
                    min= -801  max= 120  step= 1  format= %0.1f dB  div_scale= 10  preset= 0
                    Min = -80.1 dB  Max = 12.0 dB  Step = 0.1 dB  Preset = 0.0 dB  "
        ::= { iquav10CmdEntry 42556 }


    iquav10DolbyDecodeDolbyDecoderOutputsMasterMute OBJECT-TYPE
        SYNTAX            INTEGER { disable(0), enable(1)  }
        MAX-ACCESS        read-write
        STATUS            current
        DESCRIPTION
                "CMNT: - Dolby decoder O/P master mute
                 TYPE: - Checkbox
                 PAGE: - DolbyDecode
                    Master Mute  cmdID= 42557  "
        ::= { iquav10CmdEntry 42557 }


    iquav10DolbyEncInp14Source1ProcGain OBJECT-TYPE
        SYNTAX            INTEGER
        MAX-ACCESS        read-write
        STATUS            current
        DESCRIPTION
                "CMNT: - Dolby encoder A1 input gain
                 TYPE: - Number
                 PAGE: - Dolby Enc Inp1_4
                    ProcGain  cmdID= 42520
                    min= -801  max= 120  step= 1  format= %0.1f dB  div_scale= 10  preset= 0
                    Min = -80.1 dB  Max = 12.0 dB  Step = 0.1 dB  Preset = 0.0 dB  "
        ::= { iquav10CmdEntry 42520 }


    iquav10DolbyEncInp14Source1Mute OBJECT-TYPE
        SYNTAX            INTEGER { disable(0), enable(1)  }
        MAX-ACCESS        read-write
        STATUS            current
        DESCRIPTION
                "CMNT: - Dolby encoder A1 input mute
                 TYPE: - Checkbox
                 PAGE: - Dolby Enc Inp1_4
                    Mute  cmdID= 42528  "
        ::= { iquav10CmdEntry 42528 }


    iquav10DolbyEncInp14Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder A1 input source
                 TYPE: - RadiobuttonList
                 PAGE: - Dolby Enc Inp1_4
                    Src  cmdID= 42536
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iquav10CmdEntry 42536 }


    iquav10DolbyEncInp14Source2ProcGain OBJECT-TYPE
        SYNTAX            INTEGER
        MAX-ACCESS        read-write
        STATUS            current
        DESCRIPTION
                "CMNT: - Dolby encoder A2 input gain
                 TYPE: - Number
                 PAGE: - Dolby Enc Inp1_4
                    ProcGain  cmdID= 42521
                    min= -801  max= 120  step= 1  format= %0.1f dB  div_scale= 10  preset= 0
                    Min = -80.1 dB  Max = 12.0 dB  Step = 0.1 dB  Preset = 0.0 dB  "
        ::= { iquav10CmdEntry 42521 }


    iquav10DolbyEncInp14Source2Mute OBJECT-TYPE
        SYNTAX            INTEGER { disable(0), enable(1)  }
        MAX-ACCESS        read-write
        STATUS            current
        DESCRIPTION
                "CMNT: - Dolby encoder A2 input mute
                 TYPE: - Checkbox
                 PAGE: - Dolby Enc Inp1_4
                    Mute  cmdID= 42529  "
        ::= { iquav10CmdEntry 42529 }


    iquav10DolbyEncInp14Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder A2 input source
                 TYPE: - RadiobuttonList
                 PAGE: - Dolby Enc Inp1_4
                    Src  cmdID= 42537
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iquav10CmdEntry 42537 }


    iquav10DolbyEncInp14Source3ProcGain OBJECT-TYPE
        SYNTAX            INTEGER
        MAX-ACCESS        read-write
        STATUS            current
        DESCRIPTION
                "CMNT: - Dolby encoder B3 input gain
                 TYPE: - Number
                 PAGE: - Dolby Enc Inp1_4
                    ProcGain  cmdID= 42522
                    min= -801  max= 120  step= 1  format= %0.1f dB  div_scale= 10  preset= 0
                    Min = -80.1 dB  Max = 12.0 dB  Step = 0.1 dB  Preset = 0.0 dB  "
        ::= { iquav10CmdEntry 42522 }


    iquav10DolbyEncInp14Source3Mute OBJECT-TYPE
        SYNTAX            INTEGER { disable(0), enable(1)  }
        MAX-ACCESS        read-write
        STATUS            current
        DESCRIPTION
                "CMNT: - Dolby encoder B3 input mute
                 TYPE: - Checkbox
                 PAGE: - Dolby Enc Inp1_4
                    Mute  cmdID= 42530  "
        ::= { iquav10CmdEntry 42530 }


    iquav10DolbyEncInp14Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder B3 input source
                 TYPE: - RadiobuttonList
                 PAGE: - Dolby Enc Inp1_4
                    Src  cmdID= 42538
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iquav10CmdEntry 42538 }


    iquav10DolbyEncInp14Source4ProcGain OBJECT-TYPE
        SYNTAX            INTEGER
        MAX-ACCESS        read-write
        STATUS            current
        DESCRIPTION
                "CMNT: - Dolby encoder B4 input gain
                 TYPE: - Number
                 PAGE: - Dolby Enc Inp1_4
                    ProcGain  cmdID= 42523
                    min= -801  max= 120  step= 1  format= %0.1f dB  div_scale= 10  preset= 0
                    Min = -80.1 dB  Max = 12.0 dB  Step = 0.1 dB  Preset = 0.0 dB  "
        ::= { iquav10CmdEntry 42523 }


    iquav10DolbyEncInp14Source4Mute OBJECT-TYPE
        SYNTAX            INTEGER { disable(0), enable(1)  }
        MAX-ACCESS        read-write
        STATUS            current
        DESCRIPTION
                "CMNT: - Dolby encoder B4 input mute
                 TYPE: - Checkbox
                 PAGE: - Dolby Enc Inp1_4
                    Mute  cmdID= 42531  "
        ::= { iquav10CmdEntry 42531 }


    iquav10DolbyEncInp14Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder B4 input source
                 TYPE: - RadiobuttonList
                 PAGE: - Dolby Enc Inp1_4
                    Src  cmdID= 42539
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iquav10CmdEntry 42539 }


    iquav10DolbyEncInp58Source5ProcGain OBJECT-TYPE
        SYNTAX            INTEGER
        MAX-ACCESS        read-write
        STATUS            current
        DESCRIPTION
                "CMNT: - Dolby encoder C5 input gain
                 TYPE: - Number
                 PAGE: - Dolby Enc Inp5_8
                    ProcGain  cmdID= 42524
                    min= -801  max= 120  step= 1  format= %0.1f dB  div_scale= 10  preset= 0
                    Min = -80.1 dB  Max = 12.0 dB  Step = 0.1 dB  Preset = 0.0 dB  "
        ::= { iquav10CmdEntry 42524 }


    iquav10DolbyEncInp58Source5Mute OBJECT-TYPE
        SYNTAX            INTEGER { disable(0), enable(1)  }
        MAX-ACCESS        read-write
        STATUS            current
        DESCRIPTION
                "CMNT: - Dolby encoder C5 input mute
                 TYPE: - Checkbox
                 PAGE: - Dolby Enc Inp5_8
                    Mute  cmdID= 42532  "
        ::= { iquav10CmdEntry 42532 }


    iquav10DolbyEncInp58Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder C5 input source
                 TYPE: - RadiobuttonList
                 PAGE: - Dolby Enc Inp5_8
                    Src  cmdID= 42540
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iquav10CmdEntry 42540 }


    iquav10DolbyEncInp58Source6ProcGain OBJECT-TYPE
        SYNTAX            INTEGER
        MAX-ACCESS        read-write
        STATUS            current
        DESCRIPTION
                "CMNT: - Dolby encoder C6 input gain
                 TYPE: - Number
                 PAGE: - Dolby Enc Inp5_8
                    ProcGain  cmdID= 42525
                    min= -801  max= 120  step= 1  format= %0.1f dB  div_scale= 10  preset= 0
                    Min = -80.1 dB  Max = 12.0 dB  Step = 0.1 dB  Preset = 0.0 dB  "
        ::= { iquav10CmdEntry 42525 }


    iquav10DolbyEncInp58Source6Mute OBJECT-TYPE
        SYNTAX            INTEGER { disable(0), enable(1)  }
        MAX-ACCESS        read-write
        STATUS            current
        DESCRIPTION
                "CMNT: - Dolby encoder C6 input mute
                 TYPE: - Checkbox
                 PAGE: - Dolby Enc Inp5_8
                    Mute  cmdID= 42533  "
        ::= { iquav10CmdEntry 42533 }


    iquav10DolbyEncInp58Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder C6 input source
                 TYPE: - RadiobuttonList
                 PAGE: - Dolby Enc Inp5_8
                    Src  cmdID= 42541
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iquav10CmdEntry 42541 }


    iquav10DolbyEncInp58Source7ProcGain OBJECT-TYPE
        SYNTAX            INTEGER
        MAX-ACCESS        read-write
        STATUS            current
        DESCRIPTION
                "CMNT: - Dolby encoder D7 input gain
                 TYPE: - Number
                 PAGE: - Dolby Enc Inp5_8
                    ProcGain  cmdID= 42526
                    min= -801  max= 120  step= 1  format= %0.1f dB  div_scale= 10  preset= 0
                    Min = -80.1 dB  Max = 12.0 dB  Step = 0.1 dB  Preset = 0.0 dB  "
        ::= { iquav10CmdEntry 42526 }


    iquav10DolbyEncInp58Source7Mute OBJECT-TYPE
        SYNTAX            INTEGER { disable(0), enable(1)  }
        MAX-ACCESS        read-write
        STATUS            current
        DESCRIPTION
                "CMNT: - Dolby encoder D7 input mute
                 TYPE: - Checkbox
                 PAGE: - Dolby Enc Inp5_8
                    Mute  cmdID= 42534  "
        ::= { iquav10CmdEntry 42534 }


    iquav10DolbyEncInp58Source7Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder D7 input source
                 TYPE: - RadiobuttonList
                 PAGE: - Dolby Enc Inp5_8
                    Src  cmdID= 42542
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iquav10CmdEntry 42542 }


    iquav10DolbyEncInp58Source8ProcGain OBJECT-TYPE
        SYNTAX            INTEGER
        MAX-ACCESS        read-write
        STATUS            current
        DESCRIPTION
                "CMNT: - Dolby encoder D8 input gain
                 TYPE: - Number
                 PAGE: - Dolby Enc Inp5_8
                    ProcGain  cmdID= 42527
                    min= -801  max= 120  step= 1  format= %0.1f dB  div_scale= 10  preset= 0
                    Min = -80.1 dB  Max = 12.0 dB  Step = 0.1 dB  Preset = 0.0 dB  "
        ::= { iquav10CmdEntry 42527 }


    iquav10DolbyEncInp58Source8Mute OBJECT-TYPE
        SYNTAX            INTEGER { disable(0), enable(1)  }
        MAX-ACCESS        read-write
        STATUS            current
        DESCRIPTION
                "CMNT: - Dolby encoder D8 input mute
                 TYPE: - Checkbox
                 PAGE: - Dolby Enc Inp5_8
                    Mute  cmdID= 42535  "
        ::= { iquav10CmdEntry 42535 }


    iquav10DolbyEncInp58Source8Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder D8 input source
                 TYPE: - RadiobuttonList
                 PAGE: - Dolby Enc Inp5_8
                    Src  cmdID= 42543
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iquav10CmdEntry 42543 }


    iquav10DolbyControlDolbyEncoderControlSampleRateConversion OBJECT-TYPE
        SYNTAX            INTEGER {
                            valEnabled(0),
                            valDisabled(1)
                            }
        MAX-ACCESS        read-write
        STATUS            current
        DESCRIPTION
                "CMNT: - Dolby encoder sample rate converter
                 TYPE: - RadiobuttonList
                 PAGE: - DolbyControl
                    Sample Rate Conversion  cmdID= 42451
                    Enabled  value= 0
                    Disabled  value= 1  "
        ::= { iquav10CmdEntry 42451 }


    iquav10DolbyControlDolbyEncoderControlMetaRevertMode OBJECT-TYPE
        SYNTAX            INTEGER {
                            valLastused(0),
                            valInternal(1)
                            }
        MAX-ACCESS        read-write
        STATUS            current
        DESCRIPTION
                "CMNT: - Dolby encoder metadata revert mode
                 TYPE: - RadiobuttonList
                 PAGE: - DolbyControl
                    Meta Revert Mode  cmdID= 42452
                    Last used  value= 0
                    Internal  value= 1  "
        ::= { iquav10CmdEntry 42452 }


    iquav10DolbyControlDolbyEncoderControlEncodingMode OBJECT-TYPE
        SYNTAX            INTEGER {
                            valEncode(0),
                            valPassThrough(1)
                            }
        MAX-ACCESS        read-write
        STATUS            current
        DESCRIPTION
                "CMNT: - Dolby encoding mode
                 TYPE: - RadiobuttonList
                 PAGE: - DolbyControl
                    Encoding Mode  cmdID= 42450
                    Encode  value= 0
                    Pass Through  value= 1  "
        ::= { iquav10CmdEntry 42450 }


    iquav10DolbyControlDolbyEEncoderCntrlBitDepth OBJECT-TYPE
        SYNTAX            INTEGER {
                            val20bit(0),
                            val16bit(1)
                            }
        MAX-ACCESS        read-write
        STATUS            current
        DESCRIPTION
                "CMNT: - Dolby E encoder bit depth
                 TYPE: - RadiobuttonList
                 PAGE: - DolbyControl
                    Bit Depth  cmdID= 42453
                    20 bit  value= 0
                    16 bit  value= 1  "
        ::= { iquav10CmdEntry 42453 }


    iquav10DolbyControlDolbyEEncoderCntrlMetadataSource OBJECT-TYPE
        SYNTAX            INTEGER {
                            valExternal(0),
                            valInternal(1)
                            }
        MAX-ACCESS        read-write
        STATUS            current
        DESCRIPTION
                "CMNT: - Dolby E encoder metadata sample rate converter
                 TYPE: - RadiobuttonList
                 PAGE: - DolbyControl
                    Metadata Source  cmdID= 42456
                    External  value= 0
                    Internal  value= 1  "
        ::= { iquav10CmdEntry 42456 }


    iquav10DolbyControlDolbyEEncoderCntrlInternalConfig OBJECT-TYPE
        SYNTAX            INTEGER {
                            val51p2(0),
                            val51p2x1(1),
                            val4p4(2),
                            val4p2x2(3),
                            val4p2p2x1(4),
                            val4p4x1(5),
                            val4x2(6),
                            val3x2p2x1(7),
                            val2x2p4x1(8),
                            val2p6x1(9),
                            val8x1(10),
                            val51(11),
                            val4p2(12),
                            val4p2x1(13),
                            val3x2(14),
                            val2x2p2x1(15),
                            val2p4x1(16),
                            val6x1(17),
                            val4(18),
                            val2p2(19),
                            val2p2x1(20),
                            val4x1(21),
                            val71(22),
                            val71Screen(23)
                            }
        MAX-ACCESS        read-write
        STATUS            current
        DESCRIPTION
                "CMNT: - Dolby E encoder internal program configuration
                 TYPE: - RadiobuttonList
                 PAGE: - DolbyControl
                    Internal Config  cmdID= 42455
                    5.1+2  value= 0
                    5.1+2x1  value= 1
                    4+4  value= 2
                    4+2x2  value= 3
                    4+2+2x1  value= 4
                    4+4x1  value= 5
                    4x2  value= 6
                    3x2+2x1  value= 7
                    2x2+4x1  value= 8
                    2+6x1  value= 9
                    8x1  value= 10
                    5.1  value= 11
                    4+2  value= 12
                    4+2x1  value= 13
                    3x2  value= 14
                    2x2+2x1  value= 15
                    2+4x1  value= 16
                    6x1  value= 17
                    4  value= 18
                    2+2  value= 19
                    2+2x1  value= 20
                    4x1  value= 21
                    7.1  value= 22
                    7.1 Screen  value= 23  "
        ::= { iquav10CmdEntry 42455 }


    iquav10DolbyControlDolbyEEncoderCntrlDefaultAllMeta OBJECT-TYPE
        SYNTAX            INTEGER { noAction(0),valDefaultAllMeta(3) }
        MAX-ACCESS        read-write
        STATUS            current
        DESCRIPTION
                "CMNT: - Dolby encoder default all internal metadata
                 TYPE: - Button
                 PAGE: - DolbyControl
                    Default All Meta  cmdID= 42514
                    value= 3  "
        ::= { iquav10CmdEntry 42514 }


    iquav10DolbyControlDolbyIntMetaCntrlCopyExtMetadata OBJECT-TYPE
        SYNTAX            INTEGER { noAction(0),valCopyExtMetadata(1) }
        MAX-ACCESS        read-write
        STATUS            current
        DESCRIPTION
                "CMNT: - Dolby encoder copy external metadata to internal
                 TYPE: - Button
                 PAGE: - DolbyControl
                    Copy Ext Metadata  cmdID= 42512
                    value= 1  "
        ::= { iquav10CmdEntry 42512 }


    iquav10DolbyControlDolbyIntMetaCntrlDefaultProgramMeta OBJECT-TYPE
        SYNTAX            INTEGER { noAction(0),valDefaultProgramMeta(2) }
        MAX-ACCESS        read-write
        STATUS            current
        DESCRIPTION
                "CMNT: - Dolby encoder default internal metadata
                 TYPE: - Button
                 PAGE: - DolbyControl
                    Default Program Meta  cmdID= 42513
                    value= 2  "
        ::= { iquav10CmdEntry 42513 }


    iquav10DolbyControlDolbyIntMetaCntrlDialogueNorm OBJECT-TYPE
        SYNTAX            INTEGER
        MAX-ACCESS        read-write
        STATUS            current
        DESCRIPTION
                "CMNT: - Dolby encoder internal metadata AC-3 dialogue normalisation
                 TYPE: - Number
                 PAGE: - DolbyControl
                    Dialogue Norm  cmdID= 42468
                    min= 1  max= 31  step= 1  format= -%0.0f dBFS  div_scale= 1  preset= 27
                    Min = -1 dBFS  Max = -31 dBFS  Step = -1 dBFS  Preset = -27 dBFS  "
        ::= { iquav10CmdEntry 42468 }


    iquav10DolbyControlDolbyIntMetaCntrlChannelMode OBJECT-TYPE
        SYNTAX            INTEGER {
                            val10C(1),
                            val20LR(2),
                            val30LCR(3),
                            val21LRS(4),
                            val31LCRS(5),
                            val22LRSLSR(6),
                            val32LCRSLSR(7)
                            }
        MAX-ACCESS        read-write
        STATUS            current
        DESCRIPTION
                "CMNT: - Dolby encoder internal metadata AC-3 channel (coding) mode
                 TYPE: - RadiobuttonList
                 PAGE: - DolbyControl
                    Channel Mode  cmdID= 42461
                    1/0 (C)  value= 1
                    2/0 (L R)  value= 2
                    3/0 (L C R)  value= 3
                    2/1 (L R S)  value= 4
                    3/1 (L C R S)  value= 5
                    2/2 (L R SL SR)  value= 6
                    3/2 (L C R SL SR)  value= 7  "
        ::= { iquav10CmdEntry 42461 }


    iquav10DolbyControlDolbyIntMetaCntrlLFEChannel OBJECT-TYPE
        SYNTAX            INTEGER { disable(0), enable(1)  }
        MAX-ACCESS        read-write
        STATUS            current
        DESCRIPTION
                "CMNT: - Dolby encoder internal metadata AC-3 low frequency effect channel
                 TYPE: - Checkbox
                 PAGE: - DolbyControl
                    LFE Channel  cmdID= 42467  "
        ::= { iquav10CmdEntry 42467 }


    iquav10DolbyControlDolbyIntMetaCntrlBitstreamMode OBJECT-TYPE
        SYNTAX            INTEGER {
                            valCompleteMain(0),
                            valMusicEffects(1),
                            valVisuallyImpaired(2),
                            valHearingImpaired(3),
                            valDialogue(4),
                            valCommentary(5),
                            valEmergency(6),
                            valVoiceOverKaraoke(7)
                            }
        MAX-ACCESS        read-write
        STATUS            current
        DESCRIPTION
                "CMNT: - Dolby encoder internal metadata AC-3 bitstream mode
                 TYPE: - RadiobuttonList
                 PAGE: - DolbyControl
                    Bitstream Mode  cmdID= 42460
                    Complete Main  value= 0
                    Music & Effects  value= 1
                    Visually Impaired  value= 2
                    Hearing Impaired  value= 3
                    Dialogue  value= 4
                    Commentary  value= 5
                    Emergency  value= 6
                    Voice Over/Karaoke  value= 7  "
        ::= { iquav10CmdEntry 42460 }


    iquav10DolbyControlDolbyIntMetaCntrlRFMode OBJECT-TYPE
        SYNTAX            INTEGER {
                            valNone(0),
                            valFilmStandard(1),
                            valFilmLight(2),
                            valMusicStandard(3),
                            valMusicLight(4),
                            valSpeech(5)
                            }
        MAX-ACCESS        read-write
        STATUS            current
        DESCRIPTION
                "CMNT: - Dolby encoder internal metadata AC-3 RF mode
                 TYPE: - RadiobuttonList
                 PAGE: - DolbyControl
                    RF Mode  cmdID= 42463
                    None  value= 0
                    Film Standard  value= 1
                    Film Light  value= 2
                    Music Standard  value= 3
                    Music Light  value= 4
                    Speech  value= 5  "
        ::= { iquav10CmdEntry 42463 }


    iquav10DolbyControlDolbyIntMetaCntrlLineMode OBJECT-TYPE
        SYNTAX            INTEGER {
                            valNone(0),
                            valFilmStandard(1),
                            valFilmLight(2),
                            valMusicStandard(3),
                            valMusicLight(4),
                            valSpeech(5)
                            }
        MAX-ACCESS        read-write
        STATUS            current
        DESCRIPTION
                "CMNT: - Dolby encoder internal metadata AC-3 line mode
                 TYPE: - RadiobuttonList
                 PAGE: - DolbyControl
                    Line Mode  cmdID= 42462
                    None  value= 0
                    Film Standard  value= 1
                    Film Light  value= 2
                    Music Standard  value= 3
                    Music Light  value= 4
                    Speech  value= 5  "
        ::= { iquav10CmdEntry 42462 }


    iquav10DolbyIntMetaCntrlAudioProductionInfoExists OBJECT-TYPE
        SYNTAX            INTEGER { disable(0), enable(1)  }
        MAX-ACCESS        read-write
        STATUS            current
        DESCRIPTION
                "CMNT: - Dolby encoder internal metadata AC-3 audio production information exists
                 TYPE: - Checkbox
                 PAGE: - Dolby Int Meta Cntrl
                    Exists  cmdID= 42469  "
        ::= { iquav10CmdEntry 42469 }


    iquav10DolbyIntMetaCntrlAudioProductionInfoMixLevel OBJECT-TYPE
        SYNTAX            INTEGER
        MAX-ACCESS        read-write
        STATUS            current
        DESCRIPTION
                "CMNT: - Dolby encoder internal metadata AC-3 audio production mix level
                 TYPE: - Number
                 PAGE: - Dolby Int Meta Cntrl
                    Mix Level  cmdID= 42470
                    min= 80  max= 111  step= 1  format= %0.0f dB SPL  div_scale= 1  preset= 105
                    Min = 80 dB SPL  Max = 111 dB SPL  Step = 1 dB SPL  Preset = 105 dB SPL  "
        ::= { iquav10CmdEntry 42470 }


    iquav10DolbyIntMetaCntrlAudioProductionInfoRoomType OBJECT-TYPE
        SYNTAX            INTEGER {
                            valNotindicated(0),
                            valLarge(1),
                            valSmall(2)
                            }
        MAX-ACCESS        read-write
        STATUS            current
        DESCRIPTION
                "CMNT: - Dolby encoder internal metadata AC-3 audio production room type
                 TYPE: - RadiobuttonList
                 PAGE: - Dolby Int Meta Cntrl
                    Room Type  cmdID= 42471
                    Not indicated  value= 0
                    Large  value= 1
                    Small  value= 2  "
        ::= { iquav10CmdEntry 42471 }


    iquav10DolbyControlDolbyIntMetaCntrlCentreMixLevel OBJECT-TYPE
        SYNTAX            INTEGER {
                            valn30dB(0),
                            valn45dB(1),
                            valn60dB(2)
                            }
        MAX-ACCESS        read-write
        STATUS            current
        DESCRIPTION
                "CMNT: - Dolby encoder internal metadata AC-3 centre mix level
                 TYPE: - RadiobuttonList
                 PAGE: - DolbyControl
                    Centre Mix Level  cmdID= 42464
                    -3.0dB  value= 0
                    -4.5dB  value= 1
                    -6.0dB  value= 2  "
        ::= { iquav10CmdEntry 42464 }


    iquav10DolbyControlDolbyIntMetaCntrlSurroundMixLevel OBJECT-TYPE
        SYNTAX            INTEGER {
                            valn30dB(0),
                            valn60dB(1),
                            valOff(2)
                            }
        MAX-ACCESS        read-write
        STATUS            current
        DESCRIPTION
                "CMNT: - Dolby encoder internal metadata AC-3 surround mix level
                 TYPE: - RadiobuttonList
                 PAGE: - DolbyControl
                    Surround Mix Level  cmdID= 42465
                    -3.0dB  value= 0
                    -6.0dB  value= 1
                    Off  value= 2  "
        ::= { iquav10CmdEntry 42465 }


    iquav10DolbyControlDolbyIntMetaCntrlSurroundMode OBJECT-TYPE
        SYNTAX            INTEGER {
                            valNotindicated(0),
                            valOff(1),
                            valOn(2)
                            }
        MAX-ACCESS        read-write
        STATUS            current
        DESCRIPTION
                "CMNT: - Dolby encoder internal metadata AC-3 surround mode
                 TYPE: - RadiobuttonList
                 PAGE: - DolbyControl
                    Surround Mode  cmdID= 42466
                    Not indicated  value= 0
                    Off  value= 1
                    On  value= 2  "
        ::= { iquav10CmdEntry 42466 }


    iquav10DolbyControlDolbyIntMetaCntrlCopyright OBJECT-TYPE
        SYNTAX            INTEGER { disable(0), enable(1)  }
        MAX-ACCESS        read-write
        STATUS            current
        DESCRIPTION
                "CMNT: - Dolby encoder internal metadata AC-3 copyright
                 TYPE: - Checkbox
                 PAGE: - DolbyControl
                    Copyright  cmdID= 42384  "
        ::= { iquav10CmdEntry 42384 }


    iquav10DolbyIntMetaCntrlExtendedBSI1Exists OBJECT-TYPE
        SYNTAX            INTEGER { disable(0), enable(1)  }
        MAX-ACCESS        read-write
        STATUS            current
        DESCRIPTION
                "CMNT: - Dolby encoder internal metadata AC-3 BSI 1 exists
                 TYPE: - Checkbox
                 PAGE: - Dolby Int Meta Cntrl
                    Exists  cmdID= 42472  "
        ::= { iquav10CmdEntry 42472 }


    iquav10DolbyIntMetaCntrlExtendedBSI1StereoDownmixMode OBJECT-TYPE
        SYNTAX            INTEGER {
                            valNotindicated(0),
                            valLtRtPreferred(1),
                            valLoRoPreferred(2)
                            }
        MAX-ACCESS        read-write
        STATUS            current
        DESCRIPTION
                "CMNT: - Dolby encoder internal metadata AC-3 BSI 1 preferred stereo downmix mode
                 TYPE: - RadiobuttonList
                 PAGE: - Dolby Int Meta Cntrl
                    Stereo Downmix Mode  cmdID= 42473
                    Not indicated  value= 0
                    LtRt Preferred  value= 1
                    LoRo Preferred  value= 2  "
        ::= { iquav10CmdEntry 42473 }


    iquav10DolbyIntMetaCntrlExtendedBSI1LtRtCentreMixLevel OBJECT-TYPE
        SYNTAX            INTEGER {
                            valp30dB(0),
                            valp15dB(1),
                            valp00dB(2),
                            valn15dB(3),
                            valn30dB(4),
                            valn45dB(5),
                            valn60dB(6),
                            valOff(7)
                            }
        MAX-ACCESS        read-write
        STATUS            current
        DESCRIPTION
                "CMNT: - Dolby encoder internal metadata AC-3 BSI 1 LtRt centre mix level
                 TYPE: - RadiobuttonList
                 PAGE: - Dolby Int Meta Cntrl
                    Lt/Rt Centre Mix Level  cmdID= 42474
                    +3.0dB  value= 0
                    +1.5dB  value= 1
                    +0.0dB  value= 2
                    -1.5dB  value= 3
                    -3.0dB  value= 4
                    -4.5dB  value= 5
                    -6.0dB  value= 6
                    Off  value= 7  "
        ::= { iquav10CmdEntry 42474 }


    iquav10DolbyIntMetaCntrlExtendedBSI1LtRtSurrMixLevel OBJECT-TYPE
        SYNTAX            INTEGER {
                            valn15dB(3),
                            valn30dB(4),
                            valn45dB(5),
                            valn60dB(6),
                            valOff(7)
                            }
        MAX-ACCESS        read-write
        STATUS            current
        DESCRIPTION
                "CMNT: - Dolby encoder internal metadata AC-3 BSI 1 LtRt surround mix level
                 TYPE: - RadiobuttonList
                 PAGE: - Dolby Int Meta Cntrl
                    Lt/Rt Surr Mix Level  cmdID= 42475
                    -1.5dB  value= 3
                    -3.0dB  value= 4
                    -4.5dB  value= 5
                    -6.0dB  value= 6
                    Off  value= 7  "
        ::= { iquav10CmdEntry 42475 }


    iquav10DolbyIntMetaCntrlExtendedBSI1LoRoCentreMixLevel OBJECT-TYPE
        SYNTAX            INTEGER {
                            valp30dB(0),
                            valp15dB(1),
                            valp00dB(2),
                            valn15dB(3),
                            valn30dB(4),
                            valn45dB(5),
                            valn60dB(6),
                            valOff(7)
                            }
        MAX-ACCESS        read-write
        STATUS            current
        DESCRIPTION
                "CMNT: - Dolby encoder internal metadata AC-3 BSI 1 LoRo centre mix level
                 TYPE: - RadiobuttonList
                 PAGE: - Dolby Int Meta Cntrl
                    Lo/Ro Centre Mix Level  cmdID= 42476
                    +3.0dB  value= 0
                    +1.5dB  value= 1
                    +0.0dB  value= 2
                    -1.5dB  value= 3
                    -3.0dB  value= 4
                    -4.5dB  value= 5
                    -6.0dB  value= 6
                    Off  value= 7  "
        ::= { iquav10CmdEntry 42476 }


    iquav10DolbyIntMetaCntrlExtendedBSI1LoRoSurrMixLevel OBJECT-TYPE
        SYNTAX            INTEGER {
                            valn15dB(3),
                            valn30dB(4),
                            valn45dB(5),
                            valn60dB(6),
                            valOff(7)
                            }
        MAX-ACCESS        read-write
        STATUS            current
        DESCRIPTION
                "CMNT: - Dolby encoder internal metadata AC-3 BSI 1 LoRo surround mix level
                 TYPE: - RadiobuttonList
                 PAGE: - Dolby Int Meta Cntrl
                    Lo/Ro Surr Mix Level  cmdID= 42477
                    -1.5dB  value= 3
                    -3.0dB  value= 4
                    -4.5dB  value= 5
                    -6.0dB  value= 6
                    Off  value= 7  "
        ::= { iquav10CmdEntry 42477 }


    iquav10DolbyIntMetaCntrlExtendedBSI2Exists OBJECT-TYPE
        SYNTAX            INTEGER { disable(0), enable(1)  }
        MAX-ACCESS        read-write
        STATUS            current
        DESCRIPTION
                "CMNT: - Dolby encoder internal metadata AC-3 BSI 2 exists
                 TYPE: - Checkbox
                 PAGE: - Dolby Int Meta Cntrl
                    Exists  cmdID= 42478  "
        ::= { iquav10CmdEntry 42478 }


    iquav10DolbyIntMetaCntrlExtendedBSI2SurroundEXMode OBJECT-TYPE
        SYNTAX            INTEGER {
                            valNotindicated(0),
                            valOff(1),
                            valOn(2)
                            }
        MAX-ACCESS        read-write
        STATUS            current
        DESCRIPTION
                "CMNT: - Dolby encoder internal metadata AC-3 BSI 2 surround EX mode
                 TYPE: - RadiobuttonList
                 PAGE: - Dolby Int Meta Cntrl
                    Surround EX Mode  cmdID= 42479
                    Not indicated  value= 0
                    Off  value= 1
                    On  value= 2  "
        ::= { iquav10CmdEntry 42479 }


    iquav10DolbyIntMetaCntrlExtendedBSI2LowpassFilter OBJECT-TYPE
        SYNTAX            INTEGER { disable(0), enable(1)  }
        MAX-ACCESS        read-write
        STATUS            current
        DESCRIPTION
                "CMNT: - Dolby encoder internal metadata AC-3 BSI 2 lowpass filter
                 TYPE: - Checkbox
                 PAGE: - Dolby Int Meta Cntrl
                    Lowpass Filter  cmdID= 42480  "
        ::= { iquav10CmdEntry 42480 }


    iquav10DolbyIntMetaCntrlExtendedBSI2LFEFIlter OBJECT-TYPE
        SYNTAX            INTEGER { disable(0), enable(1)  }
        MAX-ACCESS        read-write
        STATUS            current
        DESCRIPTION
                "CMNT: - Dolby encoder internal metadata AC-3 BSI 2 LFE filter
                 TYPE: - Checkbox
                 PAGE: - Dolby Int Meta Cntrl
                    LFE FIlter  cmdID= 42481  "
        ::= { iquav10CmdEntry 42481 }


    iquav10DolbyIntMetaCntrlExtendedBSI2SurrPhaseShiftFltr OBJECT-TYPE
        SYNTAX            INTEGER { disable(0), enable(1)  }
        MAX-ACCESS        read-write
        STATUS            current
        DESCRIPTION
                "CMNT: - Dolby encoder internal metadata AC-3 BSI 2 surround 90deg phase shift filter
                 TYPE: - Checkbox
                 PAGE: - Dolby Int Meta Cntrl
                    Surr Phase Shift Fltr  cmdID= 42482  "
        ::= { iquav10CmdEntry 42482 }


    iquav10DolbyIntMetaCntrlExtendedBSI2Surr3dBAttenuator OBJECT-TYPE
        SYNTAX            INTEGER { disable(0), enable(1)  }
        MAX-ACCESS        read-write
        STATUS            current
        DESCRIPTION
                "CMNT: - Dolby encoder internal metadata AC-3 BSI 2 3dB surround channel attenuator
                 TYPE: - Checkbox
                 PAGE: - Dolby Int Meta Cntrl
                    Surr 3dB Attenuator  cmdID= 42483  "
        ::= { iquav10CmdEntry 42483 }


    iquav10DolbyControlDolbyIntMetaCntrlProgramDescriptionL OBJECT-TYPE
        SYNTAX            RollCallString
        MAX-ACCESS        read-write
        STATUS            current
        DESCRIPTION
                "CMNT: - Dolby encoder internal metadata text description (LH part)
                 TYPE: - Editstring
                 PAGE: - DolbyControl
                    Program Description L  cmdID= 42510
                    preset= Prog"
        ::= { iquav10CmdEntry 42510 }


    iquav10DolbyControlDolbyIntMetaCntrlProgramDescriptionR OBJECT-TYPE
        SYNTAX            RollCallString
        MAX-ACCESS        read-write
        STATUS            current
        DESCRIPTION
                "CMNT: - Dolby encoder internal metadata text description (RH part)
                 TYPE: - Editstring
                 PAGE: - DolbyControl
                    Program Description R  cmdID= 42511
                    preset= Prog"
        ::= { iquav10CmdEntry 42511 }


    iquav10DolbyControlDolbyIntMetaCntrlIntMetaSaveset OBJECT-TYPE
        SYNTAX            INTEGER
        MAX-ACCESS        read-write
        STATUS            current
        DESCRIPTION
                "CMNT: - Used to save 8 internal metadata programs through RollCall
                 TYPE: - Number
                 PAGE: - DolbyControl
                    Int Meta Saveset  cmdID= 42590
                    min= 0  max= 8  step= 1  format= %0.0f  div_scale= 1  preset= 0
                    Min = 0  Max = 8  Step = 1  Preset = 0  "
        ::= { iquav10CmdEntry 42590 }


    iquav10DolbyControlDolbyDEncoderCntrlInternalMode OBJECT-TYPE
        SYNTAX            INTEGER {
                            valFilmSurround(0),
                            valFilmStereo(1),
                            valMusicSurround(2),
                            valMusicStereo(3),
                            valManual(4)
                            }
        MAX-ACCESS        read-write
        STATUS            current
        DESCRIPTION
                "CMNT: - Dolby Digital encoder internal metadata mode
                 TYPE: - RadiobuttonList
                 PAGE: - DolbyControl
                    Internal Mode  cmdID= 42485
                    Film Surround  value= 0
                    Film Stereo  value= 1
                    Music Surround  value= 2
                    Music Stereo  value= 3
                    Manual  value= 4  "
        ::= { iquav10CmdEntry 42485 }


    iquav10DolbyControlDolbyDEncoderCntrlBitstreamFormat OBJECT-TYPE
        SYNTAX            INTEGER {
                            val32bit(0),
                            val16bitChl1(1),
                            val16bitChl2(2)
                            }
        MAX-ACCESS        read-write
        STATUS            current
        DESCRIPTION
                "CMNT: - Dolby D encoder bit depth
                 TYPE: - RadiobuttonList
                 PAGE: - DolbyControl
                    Bitstream Format  cmdID= 42454
                    32 bit  value= 0
                    16 bit Chl1  value= 1
                    16 bit Chl2  value= 2  "
        ::= { iquav10CmdEntry 42454 }


    iquav10DolbyControlDolbyDEncoderCntrlMetadataSource OBJECT-TYPE
        SYNTAX            INTEGER {
                            valProgram1(0),
                            valProgram2(1),
                            valProgram3(2),
                            valProgram4(3),
                            valProgram5(4),
                            valProgram6(5),
                            valProgram7(6),
                            valProgram8(7),
                            valInternal(8)
                            }
        MAX-ACCESS        read-write
        STATUS            current
        DESCRIPTION
                "CMNT: - Dolby D encoder metadata sample rate converter
                 TYPE: - RadiobuttonList
                 PAGE: - DolbyControl
                    Metadata Source  cmdID= 42498
                    Program 1  value= 0
                    Program 2  value= 1
                    Program 3  value= 2
                    Program 4  value= 3
                    Program 5  value= 4
                    Program 6  value= 5
                    Program 7  value= 6
                    Program 8  value= 7
                    Internal  value= 8  "
        ::= { iquav10CmdEntry 42498 }


    iquav10DolbyControlDolbyDEncoderCntrlIntMetaDataRate OBJECT-TYPE
        SYNTAX            INTEGER {
                            valAuto384(0),
                            valAuto448(1),
                            val56kbps(2),
                            val64kbps(3),
                            val80kbps(4),
                            val96kbps(5),
                            val112kbps(6),
                            val128kbps(7),
                            val160kbps(8),
                            val192kbps(9),
                            val224kbps(10),
                            val256kbps(11),
                            val320kbps(12),
                            val384kbps(13),
                            val448kbps(14),
                            val512kbps(15),
                            val576kbps(16),
                            val640kbps(17)
                            }
        MAX-ACCESS        read-write
        STATUS            current
        DESCRIPTION
                "CMNT: - Dolby D encoder internal metadata rate
                 TYPE: - RadiobuttonList
                 PAGE: - DolbyControl
                    Int Meta Data Rate  cmdID= 42499
                    Auto 384  value= 0
                    Auto 448  value= 1
                    56 kbps  value= 2
                    64 kbps  value= 3
                    80 kbps  value= 4
                    96 kbps  value= 5
                    112 kbps  value= 6
                    128 kbps  value= 7
                    160 kbps  value= 8
                    192 kbps  value= 9
                    224 kbps  value= 10
                    256 kbps  value= 11
                    320 kbps  value= 12
                    384 kbps  value= 13
                    448 kbps  value= 14
                    512 kbps  value= 15
                    576 kbps  value= 16
                    640 kbps  value= 17  "
        ::= { iquav10CmdEntry 42499 }


    iquav10DolbyControlDolbyDEncoderCntrlExtMetaDataRate OBJECT-TYPE
        SYNTAX            INTEGER {
                            valAuto384(0),
                            valAuto448(1),
                            val56kbps(2),
                            val64kbps(3),
                            val80kbps(4),
                            val96kbps(5),
                            val112kbps(6),
                            val128kbps(7),
                            val160kbps(8),
                            val192kbps(9),
                            val224kbps(10),
                            val256kbps(11),
                            val320kbps(12),
                            val384kbps(13),
                            val448kbps(14),
                            val512kbps(15),
                            val576kbps(16),
                            val640kbps(17)
                            }
        MAX-ACCESS        read-write
        STATUS            current
        DESCRIPTION
                "CMNT: - Dolby D encoder external metadata rate
                 TYPE: - RadiobuttonList
                 PAGE: - DolbyControl
                    Ext Meta Data Rate  cmdID= 42500
                    Auto 384  value= 0
                    Auto 448  value= 1
                    56 kbps  value= 2
                    64 kbps  value= 3
                    80 kbps  value= 4
                    96 kbps  value= 5
                    112 kbps  value= 6
                    128 kbps  value= 7
                    160 kbps  value= 8
                    192 kbps  value= 9
                    224 kbps  value= 10
                    256 kbps  value= 11
                    320 kbps  value= 12
                    384 kbps  value= 13
                    448 kbps  value= 14
                    512 kbps  value= 15
                    576 kbps  value= 16
                    640 kbps  value= 17  "
        ::= { iquav10CmdEntry 42500 }


    iquav10DolbyControlDolbyDEncoderCntrlStreamNumber OBJECT-TYPE
        SYNTAX            INTEGER {
                            valStream0(0),
                            valStream1(1),
                            valStream2(2),
                            valStream3(3),
                            valStream4(4),
                            valStream5(5),
                            valStream6(6)
                            }
        MAX-ACCESS        read-write
        STATUS            current
        DESCRIPTION
                "CMNT: - Dolby D encoder stream number
                 TYPE: - RadiobuttonList
                 PAGE: - DolbyControl
                    Stream Number  cmdID= 42357
                    Stream 0  value= 0
                    Stream 1  value= 1
                    Stream 2  value= 2
                    Stream 3  value= 3
                    Stream 4  value= 4
                    Stream 5  value= 5
                    Stream 6  value= 6  "
        ::= { iquav10CmdEntry 42357 }


    iquav10DolbyControlDolbyMetaProgSelMetaProgramSelect OBJECT-TYPE
        SYNTAX            INTEGER {
                            valProgram1(0),
                            valProgram2(1),
                            valProgram3(2),
                            valProgram4(3),
                            valProgram5(4),
                            valProgram6(5),
                            valProgram7(6),
                            valProgram8(7)
                            }
        MAX-ACCESS        read-write
        STATUS            current
        DESCRIPTION
                "CMNT: - Dolby metadata program select
                 TYPE: - RadiobuttonList
                 PAGE: - DolbyControl
                    Meta Program Select  cmdID= 42413
                    Program 1  value= 0
                    Program 2  value= 1
                    Program 3  value= 2
                    Program 4  value= 3
                    Program 5  value= 4
                    Program 6  value= 5
                    Program 7  value= 6
                    Program 8  value= 7  "
        ::= { iquav10CmdEntry 42413 }


    iquav10DolbyStatusDolbyCommonStatusVideoSync OBJECT-TYPE
        SYNTAX            RollCallString
        MAX-ACCESS        read-only
        STATUS            current
        DESCRIPTION
                "CMNT: - Dolby video sync status
                 TYPE: - Display
                 PAGE: - DolbyStatus
                    Video Sync  cmdID= 42381  "
        ::= { iquav10CmdEntry 42381 }


    iquav10DolbyStatusDolbyCommonStatusFrameRate OBJECT-TYPE
        SYNTAX            RollCallString
        MAX-ACCESS        read-only
        STATUS            current
        DESCRIPTION
                "CMNT: - Dolby video frame rate
                 TYPE: - Display
                 PAGE: - DolbyStatus
                    Frame Rate  cmdID= 42412  "
        ::= { iquav10CmdEntry 42412 }


    iquav10DolbyStatusDolbyCommonStatusProgramConfig OBJECT-TYPE
        SYNTAX            RollCallString
        MAX-ACCESS        read-only
        STATUS            current
        DESCRIPTION
                "CMNT: - Dolby external metadata program configuration
                 TYPE: - Display
                 PAGE: - DolbyStatus
                    Program Config  cmdID= 42439  "
        ::= { iquav10CmdEntry 42439 }


    iquav10DolbyStatusDolbyCommonStatusFWVersion OBJECT-TYPE
        SYNTAX            RollCallString
        MAX-ACCESS        read-only
        STATUS            current
        DESCRIPTION
                "CMNT: - Dolby firmware version
                 TYPE: - Display
                 PAGE: - DolbyStatus
                    F/W Version  cmdID= 42493  "
        ::= { iquav10CmdEntry 42493 }


    iquav10DolbyStatusDolbyCommonStatusDeviceName OBJECT-TYPE
        SYNTAX            RollCallString
        MAX-ACCESS        read-only
        STATUS            current
        DESCRIPTION
                "CMNT: - Dolby device name
                 TYPE: - Display
                 PAGE: - DolbyStatus
                    Device Name  cmdID= 42495  "
        ::= { iquav10CmdEntry 42495 }


    iquav10DolbyCommonStatusChannelAssignmentDolbyA1 OBJECT-TYPE
        SYNTAX            RollCallString
        MAX-ACCESS        read-only
        STATUS            current
        DESCRIPTION
                "CMNT: - Dolby encoder A1 input channel assignment
                 TYPE: - Display
                 PAGE: - Dolby Common Status
                    Dolby A1  cmdID= 42548  "
        ::= { iquav10CmdEntry 42548 }


    iquav10DolbyCommonStatusChannelAssignmentDolbyA2 OBJECT-TYPE
        SYNTAX            RollCallString
        MAX-ACCESS        read-only
        STATUS            current
        DESCRIPTION
                "CMNT: - Dolby encoder A2 input channel assignment
                 TYPE: - Display
                 PAGE: - Dolby Common Status
                    Dolby A2  cmdID= 42549  "
        ::= { iquav10CmdEntry 42549 }


    iquav10DolbyCommonStatusChannelAssignmentDolbyB3 OBJECT-TYPE
        SYNTAX            RollCallString
        MAX-ACCESS        read-only
        STATUS            current
        DESCRIPTION
                "CMNT: - Dolby encoder B3 input channel assignment
                 TYPE: - Display
                 PAGE: - Dolby Common Status
                    Dolby B3  cmdID= 42550  "
        ::= { iquav10CmdEntry 42550 }


    iquav10DolbyCommonStatusChannelAssignmentDolbyB4 OBJECT-TYPE
        SYNTAX            RollCallString
        MAX-ACCESS        read-only
        STATUS            current
        DESCRIPTION
                "CMNT: - Dolby encoder B4 input channel assignment
                 TYPE: - Display
                 PAGE: - Dolby Common Status
                    Dolby B4  cmdID= 42551  "
        ::= { iquav10CmdEntry 42551 }


    iquav10DolbyCommonStatusChannelAssignmentDolbyC5 OBJECT-TYPE
        SYNTAX            RollCallString
        MAX-ACCESS        read-only
        STATUS            current
        DESCRIPTION
                "CMNT: - Dolby encoder C5 input channel assignment
                 TYPE: - Display
                 PAGE: - Dolby Common Status
                    Dolby C5  cmdID= 42552  "
        ::= { iquav10CmdEntry 42552 }


    iquav10DolbyCommonStatusChannelAssignmentDolbyC6 OBJECT-TYPE
        SYNTAX            RollCallString
        MAX-ACCESS        read-only
        STATUS            current
        DESCRIPTION
                "CMNT: - Dolby encoder C6 input channel assignment
                 TYPE: - Display
                 PAGE: - Dolby Common Status
                    Dolby C6  cmdID= 42553  "
        ::= { iquav10CmdEntry 42553 }


    iquav10DolbyCommonStatusChannelAssignmentDolbyD7 OBJECT-TYPE
        SYNTAX            RollCallString
        MAX-ACCESS        read-only
        STATUS            current
        DESCRIPTION
                "CMNT: - Dolby encoder D7 input channel assignment
                 TYPE: - Display
                 PAGE: - Dolby Common Status
                    Dolby D7  cmdID= 42554  "
        ::= { iquav10CmdEntry 42554 }


    iquav10DolbyCommonStatusChannelAssignmentDolbyD8 OBJECT-TYPE
        SYNTAX            RollCallString
        MAX-ACCESS        read-only
        STATUS            current
        DESCRIPTION
                "CMNT: - Dolby encoder D8 input channel assignment
                 TYPE: - Display
                 PAGE: - Dolby Common Status
                    Dolby D8  cmdID= 42555  "
        ::= { iquav10CmdEntry 42555 }


    iquav10DolbyCommonStatusChnlPairAssignmentDolby12 OBJECT-TYPE
        SYNTAX            RollCallString
        MAX-ACCESS        read-only
        STATUS            current
        DESCRIPTION
                "CMNT: - Dolby encoder A1/A2 output channel assignment
                 TYPE: - Display
                 PAGE: - Dolby Common Status
                    Dolby 1/2  cmdID= 42544  "
        ::= { iquav10CmdEntry 42544 }


    iquav10DolbyCommonStatusChnlPairAssignmentDolby34 OBJECT-TYPE
        SYNTAX            RollCallString
        MAX-ACCESS        read-only
        STATUS            current
        DESCRIPTION
                "CMNT: - Dolby encoder B3/B4 output channel assignment
                 TYPE: - Display
                 PAGE: - Dolby Common Status
                    Dolby 3/4  cmdID= 42545  "
        ::= { iquav10CmdEntry 42545 }


    iquav10DolbyCommonStatusChnlPairAssignmentDolby56 OBJECT-TYPE
        SYNTAX            RollCallString
        MAX-ACCESS        read-only
        STATUS            current
        DESCRIPTION
                "CMNT: - Dolby encoder C5/C6 output channel assignment
                 TYPE: - Display
                 PAGE: - Dolby Common Status
                    Dolby 5/6  cmdID= 42546  "
        ::= { iquav10CmdEntry 42546 }


    iquav10DolbyCommonStatusChnlPairAssignmentDolby78 OBJECT-TYPE
        SYNTAX            RollCallString
        MAX-ACCESS        read-only
        STATUS            current
        DESCRIPTION
                "CMNT: - Dolby encoder D7/D8 output channel assignment
                 TYPE: - Display
                 PAGE: - Dolby Common Status
                    Dolby 7/8  cmdID= 42547  "
        ::= { iquav10CmdEntry 42547 }


    iquav10DolbyStatusDolbyExtProgStatusP1Status OBJECT-TYPE
        SYNTAX            RollCallString
        MAX-ACCESS        read-only
        STATUS            current
        DESCRIPTION
                "CMNT: - Dolby external metadata program 1 status
                 TYPE: - Display
                 PAGE: - DolbyStatus
                    P1 Status  cmdID= 42441  "
        ::= { iquav10CmdEntry 42441 }


    iquav10DolbyStatusDolbyExtProgStatusP2Status OBJECT-TYPE
        SYNTAX            RollCallString
        MAX-ACCESS        read-only
        STATUS            current
        DESCRIPTION
                "CMNT: - Dolby external metadata program 2 status
                 TYPE: - Display
                 PAGE: - DolbyStatus
                    P2 Status  cmdID= 42442  "
        ::= { iquav10CmdEntry 42442 }


    iquav10DolbyStatusDolbyExtProgStatusP3Status OBJECT-TYPE
        SYNTAX            RollCallString
        MAX-ACCESS        read-only
        STATUS            current
        DESCRIPTION
                "CMNT: - Dolby external metadata program 3 status
                 TYPE: - Display
                 PAGE: - DolbyStatus
                    P3 Status  cmdID= 42443  "
        ::= { iquav10CmdEntry 42443 }


    iquav10DolbyStatusDolbyExtProgStatusP4Status OBJECT-TYPE
        SYNTAX            RollCallString
        MAX-ACCESS        read-only
        STATUS            current
        DESCRIPTION
                "CMNT: - Dolby external metadata program 4 status
                 TYPE: - Display
                 PAGE: - DolbyStatus
                    P4 Status  cmdID= 42444  "
        ::= { iquav10CmdEntry 42444 }


    iquav10DolbyStatusDolbyExtProgStatusP5Status OBJECT-TYPE
        SYNTAX            RollCallString
        MAX-ACCESS        read-only
        STATUS            current
        DESCRIPTION
                "CMNT: - Dolby external metadata program 5 status
                 TYPE: - Display
                 PAGE: - DolbyStatus
                    P5 Status  cmdID= 42445  "
        ::= { iquav10CmdEntry 42445 }


    iquav10DolbyStatusDolbyExtProgStatusP6Status OBJECT-TYPE
        SYNTAX            RollCallString
        MAX-ACCESS        read-only
        STATUS            current
        DESCRIPTION
                "CMNT: - Dolby external metadata program 6 status
                 TYPE: - Display
                 PAGE: - DolbyStatus
                    P6 Status  cmdID= 42446  "
        ::= { iquav10CmdEntry 42446 }


    iquav10DolbyStatusDolbyExtProgStatusP7Status OBJECT-TYPE
        SYNTAX            RollCallString
        MAX-ACCESS        read-only
        STATUS            current
        DESCRIPTION
                "CMNT: - Dolby external metadata program 7 status
                 TYPE: - Display
                 PAGE: - DolbyStatus
                    P7 Status  cmdID= 42447  "
        ::= { iquav10CmdEntry 42447 }


    iquav10DolbyStatusDolbyExtProgStatusP8Status OBJECT-TYPE
        SYNTAX            RollCallString
        MAX-ACCESS        read-only
        STATUS            current
        DESCRIPTION
                "CMNT: - Dolby external metadata program 8 status
                 TYPE: - Display
                 PAGE: - DolbyStatus
                    P8 Status  cmdID= 42448  "
        ::= { iquav10CmdEntry 42448 }


    iquav10DolbyStatusDolbyMetadataStatusProgramDescriptionL OBJECT-TYPE
        SYNTAX            RollCallString
        MAX-ACCESS        read-only
        STATUS            current
        DESCRIPTION
                "CMNT: - Dolby metadata AC-3 status text description (LH part)
                 TYPE: - Display
                 PAGE: - DolbyStatus
                    Program Description L  cmdID= 42508  "
        ::= { iquav10CmdEntry 42508 }


    iquav10DolbyStatusDolbyMetadataStatusProgramDescriptionR OBJECT-TYPE
        SYNTAX            RollCallString
        MAX-ACCESS        read-only
        STATUS            current
        DESCRIPTION
                "CMNT: - Dolby metadata AC-3 status text description (RH part)
                 TYPE: - Display
                 PAGE: - DolbyStatus
                    Program Description R  cmdID= 42509  "
        ::= { iquav10CmdEntry 42509 }


    iquav10DolbyStatusDolbyMetadataStatusDialogueNorm OBJECT-TYPE
        SYNTAX            RollCallString
        MAX-ACCESS        read-only
        STATUS            current
        DESCRIPTION
                "CMNT: - Dolby metadata AC-3 status dialogue normalisation
                 TYPE: - Display
                 PAGE: - DolbyStatus
                    Dialogue Norm  cmdID= 42422  "
        ::= { iquav10CmdEntry 42422 }


    iquav10DolbyStatusDolbyMetadataStatusChannelMode OBJECT-TYPE
        SYNTAX            RollCallString
        MAX-ACCESS        read-only
        STATUS            current
        DESCRIPTION
                "CMNT: - Dolby metadata AC-3 status channel (coding) mode
                 TYPE: - Display
                 PAGE: - DolbyStatus
                    Channel Mode  cmdID= 42415  "
        ::= { iquav10CmdEntry 42415 }


    iquav10DolbyStatusDolbyMetadataStatusLFE OBJECT-TYPE
        SYNTAX            RollCallString
        MAX-ACCESS        read-only
        STATUS            current
        DESCRIPTION
                "CMNT: - Dolby metadata AC-3 status low frequency effects channel
                 TYPE: - Display
                 PAGE: - DolbyStatus
                    LFE  cmdID= 42421  "
        ::= { iquav10CmdEntry 42421 }


    iquav10DolbyStatusDolbyMetadataStatusBitstreamMode OBJECT-TYPE
        SYNTAX            RollCallString
        MAX-ACCESS        read-only
        STATUS            current
        DESCRIPTION
                "CMNT: - Dolby metadata AC-3 status bitstream mode
                 TYPE: - Display
                 PAGE: - DolbyStatus
                    Bitstream Mode  cmdID= 42414  "
        ::= { iquav10CmdEntry 42414 }


    iquav10DolbyStatusDolbyMetadataStatusRFMode OBJECT-TYPE
        SYNTAX            RollCallString
        MAX-ACCESS        read-only
        STATUS            current
        DESCRIPTION
                "CMNT: - Dolby metadata AC-3 status RF mode
                 TYPE: - Display
                 PAGE: - DolbyStatus
                    RF Mode  cmdID= 42417  "
        ::= { iquav10CmdEntry 42417 }


    iquav10DolbyStatusDolbyMetadataStatusLineMode OBJECT-TYPE
        SYNTAX            RollCallString
        MAX-ACCESS        read-only
        STATUS            current
        DESCRIPTION
                "CMNT: - Dolby metadata AC-3 status line mode
                 TYPE: - Display
                 PAGE: - DolbyStatus
                    Line Mode  cmdID= 42416  "
        ::= { iquav10CmdEntry 42416 }


    iquav10DolbyStatusDolbyMetadataStatusCentreMixLevel OBJECT-TYPE
        SYNTAX            RollCallString
        MAX-ACCESS        read-only
        STATUS            current
        DESCRIPTION
                "CMNT: - Dolby metadata AC-3 status centre mix level
                 TYPE: - Display
                 PAGE: - DolbyStatus
                    Centre Mix Level  cmdID= 42418  "
        ::= { iquav10CmdEntry 42418 }


    iquav10DolbyStatusDolbyMetadataStatusSurroundMixLevel OBJECT-TYPE
        SYNTAX            RollCallString
        MAX-ACCESS        read-only
        STATUS            current
        DESCRIPTION
                "CMNT: - Dolby metadata AC-3 status surround mix level
                 TYPE: - Display
                 PAGE: - DolbyStatus
                    Surround Mix Level  cmdID= 42419  "
        ::= { iquav10CmdEntry 42419 }


    iquav10DolbyStatusDolbyMetadataStatusSurroundMode OBJECT-TYPE
        SYNTAX            RollCallString
        MAX-ACCESS        read-only
        STATUS            current
        DESCRIPTION
                "CMNT: - Dolby metadata AC-3 status surround mode
                 TYPE: - Display
                 PAGE: - DolbyStatus
                    Surround Mode  cmdID= 42420  "
        ::= { iquav10CmdEntry 42420 }


    iquav10DolbyStatusDolbyMetadataStatusCopyright OBJECT-TYPE
        SYNTAX            RollCallString
        MAX-ACCESS        read-only
        STATUS            current
        DESCRIPTION
                "CMNT: - Dolby metadata AC-3 status copyright
                 TYPE: - Display
                 PAGE: - DolbyStatus
                    Copyright  cmdID= 42438  "
        ::= { iquav10CmdEntry 42438 }


    iquav10DolbyMetadataStatusAudioProductionInfoAudioProdInfoExists OBJECT-TYPE
        SYNTAX            RollCallString
        MAX-ACCESS        read-only
        STATUS            current
        DESCRIPTION
                "CMNT: - Dolby metadata AC-3 status audio production information exists
                 TYPE: - Display
                 PAGE: - Dolby Metadata Status
                    Audio Prod Info Exists  cmdID= 42423  "
        ::= { iquav10CmdEntry 42423 }


    iquav10DolbyMetadataStatusAudioProductionInfoMixLevel OBJECT-TYPE
        SYNTAX            RollCallString
        MAX-ACCESS        read-only
        STATUS            current
        DESCRIPTION
                "CMNT: - Dolby metadata AC-3 status audio production mix level
                 TYPE: - Display
                 PAGE: - Dolby Metadata Status
                    Mix Level  cmdID= 42424  "
        ::= { iquav10CmdEntry 42424 }


    iquav10DolbyMetadataStatusAudioProductionInfoRoomType OBJECT-TYPE
        SYNTAX            RollCallString
        MAX-ACCESS        read-only
        STATUS            current
        DESCRIPTION
                "CMNT: - Dolby metadata AC-3 status audio production room type
                 TYPE: - Display
                 PAGE: - Dolby Metadata Status
                    Room Type  cmdID= 42425  "
        ::= { iquav10CmdEntry 42425 }


    iquav10DolbyStatusDolbyMetadataStatusExtendedBSI1Exists OBJECT-TYPE
        SYNTAX            RollCallString
        MAX-ACCESS        read-only
        STATUS            current
        DESCRIPTION
                "CMNT: - Dolby metadata AC-3 status BSI 1 exists
                 TYPE: - Display
                 PAGE: - DolbyStatus
                    Extended BSI1 Exists  cmdID= 42426  "
        ::= { iquav10CmdEntry 42426 }


    iquav10DolbyMetadataStatusExtendedBSI1StereoDownmixMode OBJECT-TYPE
        SYNTAX            RollCallString
        MAX-ACCESS        read-only
        STATUS            current
        DESCRIPTION
                "CMNT: - Dolby metadata AC-3 status BSI 1 preferred stereo downmix mode
                 TYPE: - Display
                 PAGE: - Dolby Metadata Status
                    Stereo Downmix Mode  cmdID= 42427  "
        ::= { iquav10CmdEntry 42427 }


    iquav10DolbyMetadataStatusExtendedBSI1LtRtCentreMixLevel OBJECT-TYPE
        SYNTAX            RollCallString
        MAX-ACCESS        read-only
        STATUS            current
        DESCRIPTION
                "CMNT: - Dolby metadata AC-3 status BSI 1 LtRt center mix level
                 TYPE: - Display
                 PAGE: - Dolby Metadata Status
                    Lt/Rt Centre Mix Level  cmdID= 42428  "
        ::= { iquav10CmdEntry 42428 }


    iquav10DolbyMetadataStatusExtendedBSI1LtRtSurrMixLevel OBJECT-TYPE
        SYNTAX            RollCallString
        MAX-ACCESS        read-only
        STATUS            current
        DESCRIPTION
                "CMNT: - Dolby metadata AC-3 status BSI 1 LtRt surround mix level
                 TYPE: - Display
                 PAGE: - Dolby Metadata Status
                    Lt/Rt Surr Mix Level  cmdID= 42429  "
        ::= { iquav10CmdEntry 42429 }


    iquav10DolbyMetadataStatusExtendedBSI1LoRoCentreMixLevel OBJECT-TYPE
        SYNTAX            RollCallString
        MAX-ACCESS        read-only
        STATUS            current
        DESCRIPTION
                "CMNT: - Dolby metadata AC-3 status BSI 1 LoRo center mix level
                 TYPE: - Display
                 PAGE: - Dolby Metadata Status
                    Lo/Ro Centre Mix Level  cmdID= 42430  "
        ::= { iquav10CmdEntry 42430 }


    iquav10DolbyMetadataStatusExtendedBSI1LoRoSurrMixLevel OBJECT-TYPE
        SYNTAX            RollCallString
        MAX-ACCESS        read-only
        STATUS            current
        DESCRIPTION
                "CMNT: - Dolby metadata AC-3 status BSI 1 LoRo surround mix level
                 TYPE: - Display
                 PAGE: - Dolby Metadata Status
                    Lo/Ro Surr Mix Level  cmdID= 42431  "
        ::= { iquav10CmdEntry 42431 }


    iquav10DolbyStatusDolbyMetadataStatusExtendedBSI2Exists OBJECT-TYPE
        SYNTAX            RollCallString
        MAX-ACCESS        read-only
        STATUS            current
        DESCRIPTION
                "CMNT: - Dolby metadata AC-3 status BSI 2 exists
                 TYPE: - Display
                 PAGE: - DolbyStatus
                    Extended BSI2 Exists  cmdID= 42432  "
        ::= { iquav10CmdEntry 42432 }


    iquav10DolbyMetadataStatusExtendedBSI2SurroundEXMode OBJECT-TYPE
        SYNTAX            RollCallString
        MAX-ACCESS        read-only
        STATUS            current
        DESCRIPTION
                "CMNT: - Dolby metadata AC-3 status BSI 2 surround EX mode
                 TYPE: - Display
                 PAGE: - Dolby Metadata Status
                    Surround EX Mode  cmdID= 42433  "
        ::= { iquav10CmdEntry 42433 }


    iquav10DolbyMetadataStatusExtendedBSI2LowpassFilter OBJECT-TYPE
        SYNTAX            RollCallString
        MAX-ACCESS        read-only
        STATUS            current
        DESCRIPTION
                "CMNT: - Dolby metadata AC-3 status BSI 2 lowpass filter
                 TYPE: - Display
                 PAGE: - Dolby Metadata Status
                    Lowpass Filter  cmdID= 42434  "
        ::= { iquav10CmdEntry 42434 }


    iquav10DolbyMetadataStatusExtendedBSI2LFEFilter OBJECT-TYPE
        SYNTAX            RollCallString
        MAX-ACCESS        read-only
        STATUS            current
        DESCRIPTION
                "CMNT: - Dolby metadata AC-3 status BSI 2 LFE filter
                 TYPE: - Display
                 PAGE: - Dolby Metadata Status
                    LFE Filter  cmdID= 42435  "
        ::= { iquav10CmdEntry 42435 }


    iquav10DolbyMetadataStatusExtendedBSI2SurrPhaseShiftFltr OBJECT-TYPE
        SYNTAX            RollCallString
        MAX-ACCESS        read-only
        STATUS            current
        DESCRIPTION
                "CMNT: - Dolby metadata AC-3 status BSI 2 surround 90deg phase shift filter
                 TYPE: - Display
                 PAGE: - Dolby Metadata Status
                    Surr Phase Shift Fltr  cmdID= 42436  "
        ::= { iquav10CmdEntry 42436 }


    iquav10DolbyMetadataStatusExtendedBSI2Surr3dBAtten OBJECT-TYPE
        SYNTAX            RollCallString
        MAX-ACCESS        read-only
        STATUS            current
        DESCRIPTION
                "CMNT: - Dolby metadata AC-3 status BSI 2 3dB surround channel attenuator
                 TYPE: - Display
                 PAGE: - Dolby Metadata Status
                    Surr 3dB Atten  cmdID= 42437  "
        ::= { iquav10CmdEntry 42437 }


    iquav10DolbyStatusDolbyEncoderStatusStatus OBJECT-TYPE
        SYNTAX            RollCallString
        MAX-ACCESS        read-only
        STATUS            current
        DESCRIPTION
                "CMNT: - Dolby encoder status
                 TYPE: - Display
                 PAGE: - DolbyStatus
                    Status  cmdID= 42491  "
        ::= { iquav10CmdEntry 42491 }


    iquav10DolbyStatusDolbyEncoderStatusBitstreamStatus OBJECT-TYPE
        SYNTAX            RollCallString
        MAX-ACCESS        read-only
        STATUS            current
        DESCRIPTION
                "CMNT: - Dolby encoder external metadata bitstream status
                 TYPE: - Display
                 PAGE: - DolbyStatus
                    Bitstream Status  cmdID= 42496  "
        ::= { iquav10CmdEntry 42496 }


    iquav10DolbyStatusDolbyEncoderStatusReversionStatus OBJECT-TYPE
        SYNTAX            RollCallString
        MAX-ACCESS        read-only
        STATUS            current
        DESCRIPTION
                "CMNT: - Dolby encoder external metadata reversion status
                 TYPE: - Display
                 PAGE: - DolbyStatus
                    Reversion Status  cmdID= 42497  "
        ::= { iquav10CmdEntry 42497 }


    iquav10DolbyStatusDolbyEncoderStatusHWVersion OBJECT-TYPE
        SYNTAX            RollCallString
        MAX-ACCESS        read-only
        STATUS            current
        DESCRIPTION
                "CMNT: - Dolby encoder hardware version
                 TYPE: - Display
                 PAGE: - DolbyStatus
                    H/W Version  cmdID= 42494  "
        ::= { iquav10CmdEntry 42494 }


    iquav10DolbyStatusDolbyEncoderStatusOPProgramConfig OBJECT-TYPE
        SYNTAX            RollCallString
        MAX-ACCESS        read-only
        STATUS            current
        DESCRIPTION
                "CMNT: - Dolby encoder output program configuration
                 TYPE: - Display
                 PAGE: - DolbyStatus
                    O/P Program Config  cmdID= 42392  "
        ::= { iquav10CmdEntry 42392 }


    iquav10RollCallMemoriesMemoriesABCRecallMemory OBJECT-TYPE
        SYNTAX            INTEGER {
                            valNoneSelected(0),
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - RollCall/Memories
                    Recall Memory  cmdID= 37100
                    None Selected  value= 0
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iquav10CmdEntry 37100 }


    iquav10RollCallMemoriesMemoriesABCSelMemory OBJECT-TYPE
        SYNTAX            INTEGER {
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - RollCall/Memories
                    Sel Memory  cmdID= 37101
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iquav10CmdEntry 37101 }


    iquav10RollCallMemoriesMemoriesABCSaveMemory OBJECT-TYPE
        SYNTAX            INTEGER { noAction(0),valSaveMemory(1) }
        MAX-ACCESS        read-write
        STATUS            current
        DESCRIPTION
                "CMNT: - 
                 TYPE: - Button
                 PAGE: - RollCall/Memories
                    Save Memory  cmdID= 37102
                    value= 1  "
        ::= { iquav10CmdEntry 37102 }


    iquav10RollCallMemoriesMemoriesABCClearMemory OBJECT-TYPE
        SYNTAX            INTEGER { noAction(0),valClearMemory(1) }
        MAX-ACCESS        read-write
        STATUS            current
        DESCRIPTION
                "CMNT: - Delete User Memory
                 TYPE: - Button
                 PAGE: - RollCall/Memories
                    Clear Memory  cmdID= 37105
                    value= 1  "
        ::= { iquav10CmdEntry 37105 }


    iquav10MemoriesABCMemoryNameChangeName OBJECT-TYPE
        SYNTAX            RollCallString
        MAX-ACCESS        read-write
        STATUS            current
        DESCRIPTION
                "CMNT: - 
                 TYPE: - Editstring
                 PAGE: - MemoriesABC
                    Change Name  cmdID= 37103
                    preset= Display Memory"
        ::= { iquav10CmdEntry 37103 }


    iquav10MemoriesABCMemoryNameLastUserMemory OBJECT-TYPE
        SYNTAX            RollCallString
        MAX-ACCESS        read-only
        STATUS            current
        DESCRIPTION
                "CMNT: - 
                 TYPE: - Display
                 PAGE: - MemoriesABC
                    Last User Memory  cmdID= 37104  "
        ::= { iquav10CmdEntry 37104 }


    iquav10RollCallMemoriesMemoriesABCMemoryName1 OBJECT-TYPE
        SYNTAX            RollCallString
        MAX-ACCESS        read-only
        STATUS            current
        DESCRIPTION
                "CMNT: - 
                 TYPE: - Display
                 PAGE: - RollCall/Memories
                    Memory Name1  cmdID= 37106  "
        ::= { iquav10CmdEntry 37106 }


    iquav10RollCallMemoriesMemoriesABCMemoryName2 OBJECT-TYPE
        SYNTAX            RollCallString
        MAX-ACCESS        read-only
        STATUS            current
        DESCRIPTION
                "CMNT: - 
                 TYPE: - Display
                 PAGE: - RollCall/Memories
                    Memory Name2  cmdID= 37107  "
        ::= { iquav10CmdEntry 37107 }


    iquav10RollCallMemoriesMemoriesABCMemoryName3 OBJECT-TYPE
        SYNTAX            RollCallString
        MAX-ACCESS        read-only
        STATUS            current
        DESCRIPTION
                "CMNT: - 
                 TYPE: - Display
                 PAGE: - RollCall/Memories
                    Memory Name3  cmdID= 37108  "
        ::= { iquav10CmdEntry 37108 }


    iquav10RollCallMemoriesMemoriesABCMemoryName4 OBJECT-TYPE
        SYNTAX            RollCallString
        MAX-ACCESS        read-only
        STATUS            current
        DESCRIPTION
                "CMNT: - 
                 TYPE: - Display
                 PAGE: - RollCall/Memories
                    Memory Name4  cmdID= 37109  "
        ::= { iquav10CmdEntry 37109 }


    iquav10RollCallMemoriesMemoriesABCMemoryName5 OBJECT-TYPE
        SYNTAX            RollCallString
        MAX-ACCESS        read-only
        STATUS            current
        DESCRIPTION
                "CMNT: - 
                 TYPE: - Display
                 PAGE: - RollCall/Memories
                    Memory Name5  cmdID= 37110  "
        ::= { iquav10CmdEntry 37110 }


    iquav10RollCallMemoriesMemoriesABCMemoryName6 OBJECT-TYPE
        SYNTAX            RollCallString
        MAX-ACCESS        read-only
        STATUS            current
        DESCRIPTION
                "CMNT: - 
                 TYPE: - Display
                 PAGE: - RollCall/Memories
                    Memory Name6  cmdID= 37111  "
        ::= { iquav10CmdEntry 37111 }


    iquav10RollCallMemoriesMemoriesABCMemoryName7 OBJECT-TYPE
        SYNTAX            RollCallString
        MAX-ACCESS        read-only
        STATUS            current
        DESCRIPTION
                "CMNT: - 
                 TYPE: - Display
                 PAGE: - RollCall/Memories
                    Memory Name7  cmdID= 37112  "
        ::= { iquav10CmdEntry 37112 }


    iquav10RollCallMemoriesMemoriesABCMemoryName8 OBJECT-TYPE
        SYNTAX            RollCallString
        MAX-ACCESS        read-only
        STATUS            current
        DESCRIPTION
                "CMNT: - 
                 TYPE: - Display
                 PAGE: - RollCall/Memories
                    Memory Name8  cmdID= 37113  "
        ::= { iquav10CmdEntry 37113 }


    iquav10RollCallMemoriesMemoriesABCMemoryName9 OBJECT-TYPE
        SYNTAX            RollCallString
        MAX-ACCESS        read-only
        STATUS            current
        DESCRIPTION
                "CMNT: - 
                 TYPE: - Display
                 PAGE: - RollCall/Memories
                    Memory Name9  cmdID= 37114  "
        ::= { iquav10CmdEntry 37114 }


    iquav10RollCallMemoriesMemoriesABCMemoryName10 OBJECT-TYPE
        SYNTAX            RollCallString
        MAX-ACCESS        read-only
        STATUS            current
        DESCRIPTION
                "CMNT: - 
                 TYPE: - Display
                 PAGE: - RollCall/Memories
                    Memory Name10  cmdID= 37115  "
        ::= { iquav10CmdEntry 37115 }


    iquav10RollCallMemoriesMemoriesABCMemoryName11 OBJECT-TYPE
        SYNTAX            RollCallString
        MAX-ACCESS        read-only
        STATUS            current
        DESCRIPTION
                "CMNT: - 
                 TYPE: - Display
                 PAGE: - RollCall/Memories
                    Memory Name11  cmdID= 37116  "
        ::= { iquav10CmdEntry 37116 }


    iquav10RollCallMemoriesMemoriesABCMemoryName12 OBJECT-TYPE
        SYNTAX            RollCallString
        MAX-ACCESS        read-only
        STATUS            current
        DESCRIPTION
                "CMNT: - 
                 TYPE: - Display
                 PAGE: - RollCall/Memories
                    Memory Name12  cmdID= 37117  "
        ::= { iquav10CmdEntry 37117 }


    iquav10RollCallMemoriesMemoriesABCMemoryName13 OBJECT-TYPE
        SYNTAX            RollCallString
        MAX-ACCESS        read-only
        STATUS            current
        DESCRIPTION
                "CMNT: - 
                 TYPE: - Display
                 PAGE: - RollCall/Memories
                    Memory Name13  cmdID= 37118  "
        ::= { iquav10CmdEntry 37118 }


    iquav10RollCallMemoriesMemoriesABCMemoryName14 OBJECT-TYPE
        SYNTAX            RollCallString
        MAX-ACCESS        read-only
        STATUS            current
        DESCRIPTION
                "CMNT: - 
                 TYPE: - Display
                 PAGE: - RollCall/Memories
                    Memory Name14  cmdID= 37119  "
        ::= { iquav10CmdEntry 37119 }


    iquav10RollCallMemoriesMemoriesABCMemoryName15 OBJECT-TYPE
        SYNTAX            RollCallString
        MAX-ACCESS        read-only
        STATUS            current
        DESCRIPTION
                "CMNT: - 
                 TYPE: - Display
                 PAGE: - RollCall/Memories
                    Memory Name15  cmdID= 37120  "
        ::= { iquav10CmdEntry 37120 }


    iquav10RollCallMemoriesMemoriesABCMemoryName16 OBJECT-TYPE
        SYNTAX            RollCallString
        MAX-ACCESS        read-only
        STATUS            current
        DESCRIPTION
                "CMNT: - 
                 TYPE: - Display
                 PAGE: - RollCall/Memories
                    Memory Name16  cmdID= 37121  "
        ::= { iquav10CmdEntry 37121 }


    iquav10Logging1AESInputAudLoggingLogAESInput1state OBJECT-TYPE
        SYNTAX            INTEGER { disable(0), enable(1)  }
        MAX-ACCESS        read-write
        STATUS            current
        DESCRIPTION
                "CMNT: - Enable/Disable logging for AES Input 1 state
                 TYPE: - Checkbox
                 PAGE: - Logging1
                    Log AES Input1 state  cmdID= 42016  "
        ::= { iquav10CmdEntry 42016 }


    iquav10Logging1AESInputAudLoggingAESInput1state OBJECT-TYPE
        SYNTAX            RollCallString
        MAX-ACCESS        read-only
        STATUS            current
        DESCRIPTION
                "CMNT: - Logging state for AES Input 1 state
                 TYPE: - Display
                 PAGE: - Logging1
                    AES Input1 state=  cmdID= 42216  "
        ::= { iquav10CmdEntry 42216 }


    iquav10Logging1AESInputAudLoggingLogAESInput2state OBJECT-TYPE
        SYNTAX            INTEGER { disable(0), enable(1)  }
        MAX-ACCESS        read-write
        STATUS            current
        DESCRIPTION
                "CMNT: - Enable/Disable logging for AES Input 2 state
                 TYPE: - Checkbox
                 PAGE: - Logging1
                    Log AES Input2 state  cmdID= 42017  "
        ::= { iquav10CmdEntry 42017 }


    iquav10Logging1AESInputAudLoggingAESInput2state OBJECT-TYPE
        SYNTAX            RollCallString
        MAX-ACCESS        read-only
        STATUS            current
        DESCRIPTION
                "CMNT: - Logging state for AES Input 2 state
                 TYPE: - Display
                 PAGE: - Logging1
                    AES Input2 state=  cmdID= 42217  "
        ::= { iquav10CmdEntry 42217 }


    iquav10Logging1AESInputAudLoggingLogAESInput3state OBJECT-TYPE
        SYNTAX            INTEGER { disable(0), enable(1)  }
        MAX-ACCESS        read-write
        STATUS            current
        DESCRIPTION
                "CMNT: - Enable/Disable logging for AES Input 3 state
                 TYPE: - Checkbox
                 PAGE: - Logging1
                    Log AES Input3 state  cmdID= 42018  "
        ::= { iquav10CmdEntry 42018 }


    iquav10Logging1AESInputAudLoggingAESInput3state OBJECT-TYPE
        SYNTAX            RollCallString
        MAX-ACCESS        read-only
        STATUS            current
        DESCRIPTION
                "CMNT: - Logging state for AES Input 3 state
                 TYPE: - Display
                 PAGE: - Logging1
                    AES Input3 state=  cmdID= 42218  "
        ::= { iquav10CmdEntry 42218 }


    iquav10Logging1AESInputAudLoggingLogAESInput4state OBJECT-TYPE
        SYNTAX            INTEGER { disable(0), enable(1)  }
        MAX-ACCESS        read-write
        STATUS            current
        DESCRIPTION
                "CMNT: - Enable/Disable logging for AES Input 4 state
                 TYPE: - Checkbox
                 PAGE: - Logging1
                    Log AES Input4 state  cmdID= 42019  "
        ::= { iquav10CmdEntry 42019 }


    iquav10Logging1AESInputAudLoggingAESInput4state OBJECT-TYPE
        SYNTAX            RollCallString
        MAX-ACCESS        read-only
        STATUS            current
        DESCRIPTION
                "CMNT: - Logging state for AES Input 4 state
                 TYPE: - Display
                 PAGE: - Logging1
                    AES Input4 state=  cmdID= 42219  "
        ::= { iquav10CmdEntry 42219 }


    iquav10Logging1AESInputAudLoggingLogAESInput5state OBJECT-TYPE
        SYNTAX            INTEGER { disable(0), enable(1)  }
        MAX-ACCESS        read-write
        STATUS            current
        DESCRIPTION
                "CMNT: - Enable/Disable logging for AES Input 5 state
                 TYPE: - Checkbox
                 PAGE: - Logging1
                    Log AES Input5 state  cmdID= 42020  "
        ::= { iquav10CmdEntry 42020 }


    iquav10Logging1AESInputAudLoggingAESInput5state OBJECT-TYPE
        SYNTAX            RollCallString
        MAX-ACCESS        read-only
        STATUS            current
        DESCRIPTION
                "CMNT: - Logging state for AES Input 5 state
                 TYPE: - Display
                 PAGE: - Logging1
                    AES Input5 state=  cmdID= 42220  "
        ::= { iquav10CmdEntry 42220 }


    iquav10Logging1AESInputAudLoggingLogAESInput6state OBJECT-TYPE
        SYNTAX            INTEGER { disable(0), enable(1)  }
        MAX-ACCESS        read-write
        STATUS            current
        DESCRIPTION
                "CMNT: - Enable/Disable logging for AES Input 6 state
                 TYPE: - Checkbox
                 PAGE: - Logging1
                    Log AES Input6 state  cmdID= 42021  "
        ::= { iquav10CmdEntry 42021 }


    iquav10Logging1AESInputAudLoggingAESInput6state OBJECT-TYPE
        SYNTAX            RollCallString
        MAX-ACCESS        read-only
        STATUS            current
        DESCRIPTION
                "CMNT: - Logging state for AES Input 6 state
                 TYPE: - Display
                 PAGE: - Logging1
                    AES Input6 state=  cmdID= 42221  "
        ::= { iquav10CmdEntry 42221 }


    iquav10Logging1AESInputAudLoggingLogAESInput7state OBJECT-TYPE
        SYNTAX            INTEGER { disable(0), enable(1)  }
        MAX-ACCESS        read-write
        STATUS            current
        DESCRIPTION
                "CMNT: - Enable/Disable logging for AES Input 7 state
                 TYPE: - Checkbox
                 PAGE: - Logging1
                    Log AES Input7 state  cmdID= 42022  "
        ::= { iquav10CmdEntry 42022 }


    iquav10Logging1AESInputAudLoggingAESInput7state OBJECT-TYPE
        SYNTAX            RollCallString
        MAX-ACCESS        read-only
        STATUS            current
        DESCRIPTION
                "CMNT: - Logging state for AES Input 7 state
                 TYPE: - Display
                 PAGE: - Logging1
                    AES Input7 state=  cmdID= 42222  "
        ::= { iquav10CmdEntry 42222 }


    iquav10Logging1AESInputAudLoggingLogAESInput8state OBJECT-TYPE
        SYNTAX            INTEGER { disable(0), enable(1)  }
        MAX-ACCESS        read-write
        STATUS            current
        DESCRIPTION
                "CMNT: - Enable/Disable logging for AES Input 8 state
                 TYPE: - Checkbox
                 PAGE: - Logging1
                    Log AES Input8 state  cmdID= 42023  "
        ::= { iquav10CmdEntry 42023 }


    iquav10Logging1AESInputAudLoggingAESInput8state OBJECT-TYPE
        SYNTAX            RollCallString
        MAX-ACCESS        read-only
        STATUS            current
        DESCRIPTION
                "CMNT: - Logging state for AES Input 8 state
                 TYPE: - Display
                 PAGE: - Logging1
                    AES Input8 state=  cmdID= 42223  "
        ::= { iquav10CmdEntry 42223 }


    iquav10Logging1OutEmbAudLoggingLogOutEmb11state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.11 state  cmdID= 42024  "
        ::= { iquav10CmdEntry 42024 }


    iquav10Logging1OutEmbAudLoggingOutEmb11state OBJECT-TYPE
        SYNTAX            RollCallString
        MAX-ACCESS        read-only
        STATUS            current
        DESCRIPTION
                "CMNT: - Logging state for Inp 1, Emb Pair 1 state
                 TYPE: - Display
                 PAGE: - Logging1
                    Out Emb.11 state=  cmdID= 42224  "
        ::= { iquav10CmdEntry 42224 }


    iquav10Logging1OutEmbAudLoggingLogOutEmb12state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.12 state  cmdID= 42025  "
        ::= { iquav10CmdEntry 42025 }


    iquav10Logging1OutEmbAudLoggingOutEmb12state OBJECT-TYPE
        SYNTAX            RollCallString
        MAX-ACCESS        read-only
        STATUS            current
        DESCRIPTION
                "CMNT: - Logging state for Inp 1, Emb Pair 1 state
                 TYPE: - Display
                 PAGE: - Logging1
                    Out Emb.12 state=  cmdID= 42225  "
        ::= { iquav10CmdEntry 42225 }


    iquav10Logging1OutEmbAudLoggingLogOutEmb21state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.21 state  cmdID= 42026  "
        ::= { iquav10CmdEntry 42026 }


    iquav10Logging1OutEmbAudLoggingOutEmb21state OBJECT-TYPE
        SYNTAX            RollCallString
        MAX-ACCESS        read-only
        STATUS            current
        DESCRIPTION
                "CMNT: - Logging state for Inp 1, Emb Pair 1 state
                 TYPE: - Display
                 PAGE: - Logging1
                    Out Emb.21 state=  cmdID= 42226  "
        ::= { iquav10CmdEntry 42226 }


    iquav10Logging1OutEmbAudLoggingLogOutEmb22state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.22 state  cmdID= 42027  "
        ::= { iquav10CmdEntry 42027 }


    iquav10Logging1OutEmbAudLoggingOutEmb22state OBJECT-TYPE
        SYNTAX            RollCallString
        MAX-ACCESS        read-only
        STATUS            current
        DESCRIPTION
                "CMNT: - Logging state for Inp 1, Emb Pair 1 state
                 TYPE: - Display
                 PAGE: - Logging1
                    Out Emb.22 state=  cmdID= 42227  "
        ::= { iquav10CmdEntry 42227 }


    iquav10Logging1OutEmbAudLoggingLogOutEmb31state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.31 state  cmdID= 42028  "
        ::= { iquav10CmdEntry 42028 }


    iquav10Logging1OutEmbAudLoggingOutEmb31state OBJECT-TYPE
        SYNTAX            RollCallString
        MAX-ACCESS        read-only
        STATUS            current
        DESCRIPTION
                "CMNT: - Logging state for Inp 1, Emb Pair 1 state
                 TYPE: - Display
                 PAGE: - Logging1
                    Out Emb.31 state=  cmdID= 42228  "
        ::= { iquav10CmdEntry 42228 }


    iquav10Logging1OutEmbAudLoggingLogOutEmb32state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.32 state  cmdID= 42029  "
        ::= { iquav10CmdEntry 42029 }


    iquav10Logging1OutEmbAudLoggingOutEmb32state OBJECT-TYPE
        SYNTAX            RollCallString
        MAX-ACCESS        read-only
        STATUS            current
        DESCRIPTION
                "CMNT: - Logging state for Inp 1, Emb Pair 1 state
                 TYPE: - Display
                 PAGE: - Logging1
                    Out Emb.32 state=  cmdID= 42229  "
        ::= { iquav10CmdEntry 42229 }


    iquav10Logging1OutEmbAudLoggingLogOutEmb41state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.41 state  cmdID= 42030  "
        ::= { iquav10CmdEntry 42030 }


    iquav10Logging1OutEmbAudLoggingOutEmb41state OBJECT-TYPE
        SYNTAX            RollCallString
        MAX-ACCESS        read-only
        STATUS            current
        DESCRIPTION
                "CMNT: - Logging state for Inp 1, Emb Pair 1 state
                 TYPE: - Display
                 PAGE: - Logging1
                    Out Emb.41 state=  cmdID= 42230  "
        ::= { iquav10CmdEntry 42230 }


    iquav10Logging1OutEmbAudLoggingLogOutEmb42state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.42 state  cmdID= 42031  "
        ::= { iquav10CmdEntry 42031 }


    iquav10Logging1OutEmbAudLoggingOutEmb42state OBJECT-TYPE
        SYNTAX            RollCallString
        MAX-ACCESS        read-only
        STATUS            current
        DESCRIPTION
                "CMNT: - Logging state for Inp 1, Emb Pair 1 state
                 TYPE: - Display
                 PAGE: - Logging1
                    Out Emb.42 state=  cmdID= 42231  "
        ::= { iquav10CmdEntry 42231 }


    iquav10Logging1OutEmbAudLoggingLogOutEmb51state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.51 state  cmdID= 42032  "
        ::= { iquav10CmdEntry 42032 }


    iquav10Logging1OutEmbAudLoggingOutEmb51state OBJECT-TYPE
        SYNTAX            RollCallString
        MAX-ACCESS        read-only
        STATUS            current
        DESCRIPTION
                "CMNT: - Logging state for Inp 1, Emb Pair 1 state
                 TYPE: - Display
                 PAGE: - Logging1
                    Out Emb.51 state=  cmdID= 42232  "
        ::= { iquav10CmdEntry 42232 }


    iquav10Logging1OutEmbAudLoggingLogOutEmb52state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.52 state  cmdID= 42033  "
        ::= { iquav10CmdEntry 42033 }


    iquav10Logging1OutEmbAudLoggingOutEmb52state OBJECT-TYPE
        SYNTAX            RollCallString
        MAX-ACCESS        read-only
        STATUS            current
        DESCRIPTION
                "CMNT: - Logging state for Inp 1, Emb Pair 1 state
                 TYPE: - Display
                 PAGE: - Logging1
                    Out Emb.52 state=  cmdID= 42233  "
        ::= { iquav10CmdEntry 42233 }


    iquav10Logging1OutEmbAudLoggingLogOutEmb61state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.61 state  cmdID= 42034  "
        ::= { iquav10CmdEntry 42034 }


    iquav10Logging1OutEmbAudLoggingOutEmb61state OBJECT-TYPE
        SYNTAX            RollCallString
        MAX-ACCESS        read-only
        STATUS            current
        DESCRIPTION
                "CMNT: - Logging state for Inp 1, Emb Pair 1 state
                 TYPE: - Display
                 PAGE: - Logging1
                    Out Emb.61 state=  cmdID= 42234  "
        ::= { iquav10CmdEntry 42234 }


    iquav10Logging1OutEmbAudLoggingLogOutEmb62state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.62 state  cmdID= 42035  "
        ::= { iquav10CmdEntry 42035 }


    iquav10Logging1OutEmbAudLoggingOutEmb62state OBJECT-TYPE
        SYNTAX            RollCallString
        MAX-ACCESS        read-only
        STATUS            current
        DESCRIPTION
                "CMNT: - Logging state for Inp 1, Emb Pair 1 state
                 TYPE: - Display
                 PAGE: - Logging1
                    Out Emb.62 state=  cmdID= 42235  "
        ::= { iquav10CmdEntry 42235 }


    iquav10Logging1OutEmbAudLoggingLogOutEmb71state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.71 state  cmdID= 42036  "
        ::= { iquav10CmdEntry 42036 }


    iquav10Logging1OutEmbAudLoggingOutEmb71state OBJECT-TYPE
        SYNTAX            RollCallString
        MAX-ACCESS        read-only
        STATUS            current
        DESCRIPTION
                "CMNT: - Logging state for Inp 1, Emb Pair 1 state
                 TYPE: - Display
                 PAGE: - Logging1
                    Out Emb.71 state=  cmdID= 42236  "
        ::= { iquav10CmdEntry 42236 }


    iquav10Logging1OutEmbAudLoggingLogOutEmb72state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.72 state  cmdID= 42037  "
        ::= { iquav10CmdEntry 42037 }


    iquav10Logging1OutEmbAudLoggingOutEmb72state OBJECT-TYPE
        SYNTAX            RollCallString
        MAX-ACCESS        read-only
        STATUS            current
        DESCRIPTION
                "CMNT: - Logging state for Inp 1, Emb Pair 1 state
                 TYPE: - Display
                 PAGE: - Logging1
                    Out Emb.72 state=  cmdID= 42237  "
        ::= { iquav10CmdEntry 42237 }


    iquav10Logging1OutEmbAudLoggingLogOutEmb81state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.81 state  cmdID= 42038  "
        ::= { iquav10CmdEntry 42038 }


    iquav10Logging1OutEmbAudLoggingOutEmb81state OBJECT-TYPE
        SYNTAX            RollCallString
        MAX-ACCESS        read-only
        STATUS            current
        DESCRIPTION
                "CMNT: - Logging state for Inp 1, Emb Pair 1 state
                 TYPE: - Display
                 PAGE: - Logging1
                    Out Emb.81 state=  cmdID= 42238  "
        ::= { iquav10CmdEntry 42238 }


    iquav10Logging1OutEmbAudLoggingLogOutEmb82state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.82 state  cmdID= 42039  "
        ::= { iquav10CmdEntry 42039 }


    iquav10Logging1OutEmbAudLoggingOutEmb82state OBJECT-TYPE
        SYNTAX            RollCallString
        MAX-ACCESS        read-only
        STATUS            current
        DESCRIPTION
                "CMNT: - Logging state for Inp 1, Emb Pair 1 state
                 TYPE: - Display
                 PAGE: - Logging1
                    Out Emb.82 state=  cmdID= 42239  "
        ::= { iquav10CmdEntry 42239 }


    iquav10Logging1AESOutputAudLoggingLogAESOutput11state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output11 state  cmdID= 42040  "
        ::= { iquav10CmdEntry 42040 }


    iquav10Logging1AESOutputAudLoggingAESOutput11state OBJECT-TYPE
        SYNTAX            RollCallString
        MAX-ACCESS        read-only
        STATUS            current
        DESCRIPTION
                "CMNT: - Logging state for Inp 1, Emb Pair 1 state
                 TYPE: - Display
                 PAGE: - Logging1
                    AES Output11 state=  cmdID= 42240  "
        ::= { iquav10CmdEntry 42240 }


    iquav10Logging1AESOutputAudLoggingLogAESOutput12state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output12 state  cmdID= 42041  "
        ::= { iquav10CmdEntry 42041 }


    iquav10Logging1AESOutputAudLoggingAESOutput12state OBJECT-TYPE
        SYNTAX            RollCallString
        MAX-ACCESS        read-only
        STATUS            current
        DESCRIPTION
                "CMNT: - Logging state for Inp 1, Emb Pair 1 state
                 TYPE: - Display
                 PAGE: - Logging1
                    AES Output12 state=  cmdID= 42241  "
        ::= { iquav10CmdEntry 42241 }


    iquav10Logging1AESOutputAudLoggingLogAESOutput21state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output21 state  cmdID= 42042  "
        ::= { iquav10CmdEntry 42042 }


    iquav10Logging1AESOutputAudLoggingAESOutput21state OBJECT-TYPE
        SYNTAX            RollCallString
        MAX-ACCESS        read-only
        STATUS            current
        DESCRIPTION
                "CMNT: - Logging state for Inp 1, Emb Pair 1 state
                 TYPE: - Display
                 PAGE: - Logging1
                    AES Output21 state=  cmdID= 42242  "
        ::= { iquav10CmdEntry 42242 }


    iquav10Logging1AESOutputAudLoggingLogAESOutput22state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output22 state  cmdID= 42043  "
        ::= { iquav10CmdEntry 42043 }


    iquav10Logging1AESOutputAudLoggingAESOutput22state OBJECT-TYPE
        SYNTAX            RollCallString
        MAX-ACCESS        read-only
        STATUS            current
        DESCRIPTION
                "CMNT: - Logging state for Inp 1, Emb Pair 1 state
                 TYPE: - Display
                 PAGE: - Logging1
                    AES Output22 state=  cmdID= 42243  "
        ::= { iquav10CmdEntry 42243 }


    iquav10Logging1AESOutputAudLoggingLogAESOutput31state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output31 state  cmdID= 42044  "
        ::= { iquav10CmdEntry 42044 }


    iquav10Logging1AESOutputAudLoggingAESOutput31state OBJECT-TYPE
        SYNTAX            RollCallString
        MAX-ACCESS        read-only
        STATUS            current
        DESCRIPTION
                "CMNT: - Logging state for Inp 1, Emb Pair 1 state
                 TYPE: - Display
                 PAGE: - Logging1
                    AES Output31 state=  cmdID= 42244  "
        ::= { iquav10CmdEntry 42244 }


    iquav10Logging1AESOutputAudLoggingLogAESOutput32state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output32 state  cmdID= 42045  "
        ::= { iquav10CmdEntry 42045 }


    iquav10Logging1AESOutputAudLoggingAESOutput32state OBJECT-TYPE
        SYNTAX            RollCallString
        MAX-ACCESS        read-only
        STATUS            current
        DESCRIPTION
                "CMNT: - Logging state for Inp 1, Emb Pair 1 state
                 TYPE: - Display
                 PAGE: - Logging1
                    AES Output32 state=  cmdID= 42245  "
        ::= { iquav10CmdEntry 42245 }


    iquav10Logging1AESOutputAudLoggingLogAESOutput41state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output41 state  cmdID= 42046  "
        ::= { iquav10CmdEntry 42046 }


    iquav10Logging1AESOutputAudLoggingAESOutput41state OBJECT-TYPE
        SYNTAX            RollCallString
        MAX-ACCESS        read-only
        STATUS            current
        DESCRIPTION
                "CMNT: - Logging state for Inp 1, Emb Pair 1 state
                 TYPE: - Display
                 PAGE: - Logging1
                    AES Output41 state=  cmdID= 42246  "
        ::= { iquav10CmdEntry 42246 }


    iquav10Logging1AESOutputAudLoggingLogAESOutput42state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output42 state  cmdID= 42047  "
        ::= { iquav10CmdEntry 42047 }


    iquav10Logging1AESOutputAudLoggingAESOutput42state OBJECT-TYPE
        SYNTAX            RollCallString
        MAX-ACCESS        read-only
        STATUS            current
        DESCRIPTION
                "CMNT: - Logging state for Inp 1, Emb Pair 1 state
                 TYPE: - Display
                 PAGE: - Logging1
                    AES Output42 state=  cmdID= 42247  "
        ::= { iquav10CmdEntry 42247 }


    iquav10Logging1AESOutputAudLoggingLogAESOutput51state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output51 state  cmdID= 42048  "
        ::= { iquav10CmdEntry 42048 }


    iquav10Logging1AESOutputAudLoggingAESOutput51state OBJECT-TYPE
        SYNTAX            RollCallString
        MAX-ACCESS        read-only
        STATUS            current
        DESCRIPTION
                "CMNT: - Logging state for Inp 1, Emb Pair 1 state
                 TYPE: - Display
                 PAGE: - Logging1
                    AES Output51 state=  cmdID= 42248  "
        ::= { iquav10CmdEntry 42248 }


    iquav10Logging1AESOutputAudLoggingLogAESOutput52state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output52 state  cmdID= 42049  "
        ::= { iquav10CmdEntry 42049 }


    iquav10Logging1AESOutputAudLoggingAESOutput52state OBJECT-TYPE
        SYNTAX            RollCallString
        MAX-ACCESS        read-only
        STATUS            current
        DESCRIPTION
                "CMNT: - Logging state for Inp 1, Emb Pair 1 state
                 TYPE: - Display
                 PAGE: - Logging1
                    AES Output52 state=  cmdID= 42249  "
        ::= { iquav10CmdEntry 42249 }


    iquav10Logging1AESOutputAudLoggingLogAESOutput61state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output61 state  cmdID= 42050  "
        ::= { iquav10CmdEntry 42050 }


    iquav10Logging1AESOutputAudLoggingAESOutput61state OBJECT-TYPE
        SYNTAX            RollCallString
        MAX-ACCESS        read-only
        STATUS            current
        DESCRIPTION
                "CMNT: - Logging state for Inp 1, Emb Pair 1 state
                 TYPE: - Display
                 PAGE: - Logging1
                    AES Output61 state=  cmdID= 42250  "
        ::= { iquav10CmdEntry 42250 }


    iquav10Logging1AESOutputAudLoggingLogAESOutput62state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output62 state  cmdID= 42051  "
        ::= { iquav10CmdEntry 42051 }


    iquav10Logging1AESOutputAudLoggingAESOutput62state OBJECT-TYPE
        SYNTAX            RollCallString
        MAX-ACCESS        read-only
        STATUS            current
        DESCRIPTION
                "CMNT: - Logging state for Inp 1, Emb Pair 1 state
                 TYPE: - Display
                 PAGE: - Logging1
                    AES Output62 state=  cmdID= 42251  "
        ::= { iquav10CmdEntry 42251 }


    iquav10Logging1AESOutputAudLoggingLogAESOutput71state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output71 state  cmdID= 42052  "
        ::= { iquav10CmdEntry 42052 }


    iquav10Logging1AESOutputAudLoggingAESOutput71state OBJECT-TYPE
        SYNTAX            RollCallString
        MAX-ACCESS        read-only
        STATUS            current
        DESCRIPTION
                "CMNT: - Logging state for Inp 1, Emb Pair 1 state
                 TYPE: - Display
                 PAGE: - Logging1
                    AES Output71 state=  cmdID= 42252  "
        ::= { iquav10CmdEntry 42252 }


    iquav10Logging1AESOutputAudLoggingLogAESOutput72state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output72 state  cmdID= 42053  "
        ::= { iquav10CmdEntry 42053 }


    iquav10Logging1AESOutputAudLoggingAESOutput72state OBJECT-TYPE
        SYNTAX            RollCallString
        MAX-ACCESS        read-only
        STATUS            current
        DESCRIPTION
                "CMNT: - Logging state for Inp 1, Emb Pair 1 state
                 TYPE: - Display
                 PAGE: - Logging1
                    AES Output72 state=  cmdID= 42253  "
        ::= { iquav10CmdEntry 42253 }


    iquav10Logging1AESOutputAudLoggingLogAESOutput81state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output81 state  cmdID= 42054  "
        ::= { iquav10CmdEntry 42054 }


    iquav10Logging1AESOutputAudLoggingAESOutput81state OBJECT-TYPE
        SYNTAX            RollCallString
        MAX-ACCESS        read-only
        STATUS            current
        DESCRIPTION
                "CMNT: - Logging state for Inp 1, Emb Pair 1 state
                 TYPE: - Display
                 PAGE: - Logging1
                    AES Output81 state=  cmdID= 42254  "
        ::= { iquav10CmdEntry 42254 }


    iquav10Logging1AESOutputAudLoggingLogAESOutput82state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log AES Output82 state  cmdID= 42055  "
        ::= { iquav10CmdEntry 42055 }


    iquav10Logging1AESOutputAudLoggingAESOutput82state OBJECT-TYPE
        SYNTAX            RollCallString
        MAX-ACCESS        read-only
        STATUS            current
        DESCRIPTION
                "CMNT: - Logging state for Inp 1, Emb Pair 1 state
                 TYPE: - Display
                 PAGE: - Logging1
                    AES Output82 state=  cmdID= 42255  "
        ::= { iquav10CmdEntry 42255 }


    iquav10Logging1AnlgOutAudLoggingLogAnlgOut11state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Anlg Out11 state  cmdID= 42056  "
        ::= { iquav10CmdEntry 42056 }


    iquav10Logging1AnlgOutAudLoggingAnlgOutput11state OBJECT-TYPE
        SYNTAX            RollCallString
        MAX-ACCESS        read-only
        STATUS            current
        DESCRIPTION
                "CMNT: - Logging state for Inp 1, Emb Pair 1 state
                 TYPE: - Display
                 PAGE: - Logging1
                    Anlg Output11 state=  cmdID= 42256  "
        ::= { iquav10CmdEntry 42256 }


    iquav10Logging1AnlgOutAudLoggingLogAnlgOut12state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Anlg Out12 state  cmdID= 42057  "
        ::= { iquav10CmdEntry 42057 }


    iquav10Logging1AnlgOutAudLoggingAnlgOutput12state OBJECT-TYPE
        SYNTAX            RollCallString
        MAX-ACCESS        read-only
        STATUS            current
        DESCRIPTION
                "CMNT: - Logging state for Inp 1, Emb Pair 1 state
                 TYPE: - Display
                 PAGE: - Logging1
                    Anlg Output12 state=  cmdID= 42257  "
        ::= { iquav10CmdEntry 42257 }


    iquav10Logging1AnlgOutAudLoggingLogAnlgOut21state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Anlg Out21 state  cmdID= 42058  "
        ::= { iquav10CmdEntry 42058 }


    iquav10Logging1AnlgOutAudLoggingAnlgOutput21state OBJECT-TYPE
        SYNTAX            RollCallString
        MAX-ACCESS        read-only
        STATUS            current
        DESCRIPTION
                "CMNT: - Logging state for Inp 1, Emb Pair 1 state
                 TYPE: - Display
                 PAGE: - Logging1
                    Anlg Output21 state=  cmdID= 42258  "
        ::= { iquav10CmdEntry 42258 }


    iquav10Logging1AnlgOutAudLoggingLogAnlgOut22state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Anlg Out22 state  cmdID= 42059  "
        ::= { iquav10CmdEntry 42059 }


    iquav10Logging1AnlgOutAudLoggingAnlgOutput22state OBJECT-TYPE
        SYNTAX            RollCallString
        MAX-ACCESS        read-only
        STATUS            current
        DESCRIPTION
                "CMNT: - Logging state for Inp 1, Emb Pair 1 state
                 TYPE: - Display
                 PAGE: - Logging1
                    Anlg Output22 state=  cmdID= 42259  "
        ::= { iquav10CmdEntry 42259 }


    iquav10Logging1DolbyDecoderLoggingLogBitstreamFormat OBJECT-TYPE
        SYNTAX            INTEGER { disable(0), enable(1)  }
        MAX-ACCESS        read-write
        STATUS            current
        DESCRIPTION
                "CMNT: - Enable/Disable logging for Dolby Decoder bitstream format
                 TYPE: - Checkbox
                 PAGE: - Logging1
                    Log Bitstream Format  cmdID= 42100  "
        ::= { iquav10CmdEntry 42100 }


    iquav10Logging1DolbyDecoderLoggingBitstreamFormat OBJECT-TYPE
        SYNTAX            RollCallString
        MAX-ACCESS        read-only
        STATUS            current
        DESCRIPTION
                "CMNT: - Logging state for Dolby Decoder bitstream format
                 TYPE: - Display
                 PAGE: - Logging1
                    Bitstream Format=  cmdID= 42300  "
        ::= { iquav10CmdEntry 42300 }


    iquav10Logging1DolbyDecoderLoggingLogBitstreamStatus OBJECT-TYPE
        SYNTAX            INTEGER { disable(0), enable(1)  }
        MAX-ACCESS        read-write
        STATUS            current
        DESCRIPTION
                "CMNT: - Enable/Disable logging for Dolby Decoder bitstream status
                 TYPE: - Checkbox
                 PAGE: - Logging1
                    Log Bitstream Status  cmdID= 42101  "
        ::= { iquav10CmdEntry 42101 }


    iquav10Logging1DolbyDecoderLoggingBitstreamStatus OBJECT-TYPE
        SYNTAX            RollCallString
        MAX-ACCESS        read-only
        STATUS            current
        DESCRIPTION
                "CMNT: - Logging state for Dolby Decoder bitstream status
                 TYPE: - Display
                 PAGE: - Logging1
                    Bitstream Status=  cmdID= 42301  "
        ::= { iquav10CmdEntry 42301 }


    iquav10Logging1DolbyDecoderLoggingLogDCRCErrors OBJECT-TYPE
        SYNTAX            INTEGER { disable(0), enable(1)  }
        MAX-ACCESS        read-write
        STATUS            current
        DESCRIPTION
                "CMNT: - Enable/Disable logging for Dolby DecoderD CRC error count
                 TYPE: - Checkbox
                 PAGE: - Logging1
                    Log D CRC Errors  cmdID= 42102  "
        ::= { iquav10CmdEntry 42102 }


    iquav10Logging1DolbyDecoderLoggingDCRCErrorCount OBJECT-TYPE
        SYNTAX            RollCallString
        MAX-ACCESS        read-only
        STATUS            current
        DESCRIPTION
                "CMNT: - Logging state for Dolby Decoder D CRC error count
                 TYPE: - Display
                 PAGE: - Logging1
                    D CRC Error Count=  cmdID= 42302  "
        ::= { iquav10CmdEntry 42302 }


    iquav10Logging1DolbyDecoderLoggingLogECRCErrors OBJECT-TYPE
        SYNTAX            INTEGER { disable(0), enable(1)  }
        MAX-ACCESS        read-write
        STATUS            current
        DESCRIPTION
                "CMNT: - Enable/Disable logging for Dolby Decoder E CRC error count
                 TYPE: - Checkbox
                 PAGE: - Logging1
                    Log E CRC Errors  cmdID= 42103  "
        ::= { iquav10CmdEntry 42103 }


    iquav10Logging1DolbyDecoderLoggingECRCErrorCount OBJECT-TYPE
        SYNTAX            RollCallString
        MAX-ACCESS        read-only
        STATUS            current
        DESCRIPTION
                "CMNT: - Logging state for Dolby Decoder E CRC error count
                 TYPE: - Display
                 PAGE: - Logging1
                    E CRC Error Count=  cmdID= 42303  "
        ::= { iquav10CmdEntry 42303 }


    iquav10Logging1DolbyEncoderLoggingLogEncoderStatus OBJECT-TYPE
        SYNTAX            INTEGER { disable(0), enable(1)  }
        MAX-ACCESS        read-write
        STATUS            current
        DESCRIPTION
                "CMNT: - Enable/Disable logging for Dolby Encoder status
                 TYPE: - Checkbox
                 PAGE: - Logging1
                    Log Encoder Status  cmdID= 42112  "
        ::= { iquav10CmdEntry 42112 }


    iquav10Logging1DolbyEncoderLoggingEncoderStatus OBJECT-TYPE
        SYNTAX            RollCallString
        MAX-ACCESS        read-only
        STATUS            current
        DESCRIPTION
                "CMNT: - Logging state for Dolby Encoder status
                 TYPE: - Display
                 PAGE: - Logging1
                    Encoder Status=  cmdID= 42312  "
        ::= { iquav10CmdEntry 42312 }


    iquav10Logging1DolbyEncoderLoggingLogBitstreamStatus OBJECT-TYPE
        SYNTAX            INTEGER { disable(0), enable(1)  }
        MAX-ACCESS        read-write
        STATUS            current
        DESCRIPTION
                "CMNT: - Enable/Disable logging for Dolby Encoder bitstream status
                 TYPE: - Checkbox
                 PAGE: - Logging1
                    Log Bitstream Status  cmdID= 42113  "
        ::= { iquav10CmdEntry 42113 }


    iquav10Logging1DolbyEncoderLoggingBitstreamStatus OBJECT-TYPE
        SYNTAX            RollCallString
        MAX-ACCESS        read-only
        STATUS            current
        DESCRIPTION
                "CMNT: - Logging state for Dolby Encoder bitstream status
                 TYPE: - Display
                 PAGE: - Logging1
                    Bitstream Status=  cmdID= 42313  "
        ::= { iquav10CmdEntry 42313 }


    iquav10Logging1DolbyEncoderLoggingLogReversionStatus OBJECT-TYPE
        SYNTAX            INTEGER { disable(0), enable(1)  }
        MAX-ACCESS        read-write
        STATUS            current
        DESCRIPTION
                "CMNT: - Enable/Disable logging for Dolby Encoder reversion status
                 TYPE: - Checkbox
                 PAGE: - Logging1
                    Log Reversion Status  cmdID= 42114  "
        ::= { iquav10CmdEntry 42114 }


    iquav10Logging1DolbyEncoderLoggingReversionStatus OBJECT-TYPE
        SYNTAX            RollCallString
        MAX-ACCESS        read-only
        STATUS            current
        DESCRIPTION
                "CMNT: - Logging state for Dolby Encoder reversion status
                 TYPE: - Display
                 PAGE: - Logging1
                    Reversion Status=  cmdID= 42314  "
        ::= { iquav10CmdEntry 42314 }


    iquav10Logging1DolbyLoggingLogVideoSync OBJECT-TYPE
        SYNTAX            INTEGER { disable(0), enable(1)  }
        MAX-ACCESS        read-write
        STATUS            current
        DESCRIPTION
                "CMNT: - Enable/Disable logging for Dolby video sync
                 TYPE: - Checkbox
                 PAGE: - Logging1
                    Log Video Sync  cmdID= 42104  "
        ::= { iquav10CmdEntry 42104 }


    iquav10Logging1DolbyLoggingVideoSync OBJECT-TYPE
        SYNTAX            RollCallString
        MAX-ACCESS        read-only
        STATUS            current
        DESCRIPTION
                "CMNT: - Logging state for Dolby video sync
                 TYPE: - Display
                 PAGE: - Logging1
                    Video Sync=  cmdID= 42304  "
        ::= { iquav10CmdEntry 42304 }


    iquav10Logging1DolbyLoggingLogFrameRate OBJECT-TYPE
        SYNTAX            INTEGER { disable(0), enable(1)  }
        MAX-ACCESS        read-write
        STATUS            current
        DESCRIPTION
                "CMNT: - Enable/Disable logging for Dolby frame rate
                 TYPE: - Checkbox
                 PAGE: - Logging1
                    Log Frame Rate  cmdID= 42105  "
        ::= { iquav10CmdEntry 42105 }


    iquav10Logging1DolbyLoggingFrameRate OBJECT-TYPE
        SYNTAX            RollCallString
        MAX-ACCESS        read-only
        STATUS            current
        DESCRIPTION
                "CMNT: - Logging state for Dolby frame rate
                 TYPE: - Display
                 PAGE: - Logging1
                    Frame Rate=  cmdID= 42305  "
        ::= { iquav10CmdEntry 42305 }


    iquav10Logging1DolbyLoggingLogProgramConfig OBJECT-TYPE
        SYNTAX            INTEGER { disable(0), enable(1)  }
        MAX-ACCESS        read-write
        STATUS            current
        DESCRIPTION
                "CMNT: - Enable/Disable logging for Dolby program config
                 TYPE: - Checkbox
                 PAGE: - Logging1
                    Log Program Config  cmdID= 42106  "
        ::= { iquav10CmdEntry 42106 }


    iquav10Logging1DolbyLoggingProgramConfig OBJECT-TYPE
        SYNTAX            RollCallString
        MAX-ACCESS        read-only
        STATUS            current
        DESCRIPTION
                "CMNT: - Logging state for Dolby program config
                 TYPE: - Display
                 PAGE: - Logging1
                    Program Config=  cmdID= 42306  "
        ::= { iquav10CmdEntry 42306 }


    iquav10Logging1DolbyMetadataLoggingLogSelectedProgram OBJECT-TYPE
        SYNTAX            INTEGER { disable(0), enable(1)  }
        MAX-ACCESS        read-write
        STATUS            current
        DESCRIPTION
                "CMNT: - Enable/Disable logging for Dolby selected program
                 TYPE: - Checkbox
                 PAGE: - Logging1
                    Log Selected Program  cmdID= 42107  "
        ::= { iquav10CmdEntry 42107 }


    iquav10Logging1DolbyMetadataLoggingSelectedProgram OBJECT-TYPE
        SYNTAX            RollCallString
        MAX-ACCESS        read-only
        STATUS            current
        DESCRIPTION
                "CMNT: - Logging state for Dolby selected program
                 TYPE: - Display
                 PAGE: - Logging1
                    Selected Program=  cmdID= 42307  "
        ::= { iquav10CmdEntry 42307 }


    iquav10Logging1DolbyMetadataLoggingLogProgramDescriptor OBJECT-TYPE
        SYNTAX            INTEGER { disable(0), enable(1)  }
        MAX-ACCESS        read-write
        STATUS            current
        DESCRIPTION
                "CMNT: - Enable/Disable logging for Dolby program descriptor
                 TYPE: - Checkbox
                 PAGE: - Logging1
                    Log Program Descriptor  cmdID= 42108  "
        ::= { iquav10CmdEntry 42108 }


    iquav10Logging1DolbyMetadataLoggingProgramDescriptor OBJECT-TYPE
        SYNTAX            RollCallString
        MAX-ACCESS        read-only
        STATUS            current
        DESCRIPTION
                "CMNT: - Logging state for Dolby program descriptor
                 TYPE: - Display
                 PAGE: - Logging1
                    Program Descriptor=  cmdID= 42308  "
        ::= { iquav10CmdEntry 42308 }


    iquav10Logging1DolbyMetadataLoggingProgramDescPt2 OBJECT-TYPE
        SYNTAX            RollCallString
        MAX-ACCESS        read-only
        STATUS            current
        DESCRIPTION
                "CMNT: - Used for displaying 2nd half of program descriptor on logging page
                 TYPE: - Display
                 PAGE: - Logging1
                    Program Desc Pt2  cmdID= 42400  "
        ::= { iquav10CmdEntry 42400 }


    iquav10Logging1DolbyMetadataLoggingLogChannelMode OBJECT-TYPE
        SYNTAX            INTEGER { disable(0), enable(1)  }
        MAX-ACCESS        read-write
        STATUS            current
        DESCRIPTION
                "CMNT: - Enable/Disable logging for Dolby channel mode
                 TYPE: - Checkbox
                 PAGE: - Logging1
                    Log Channel Mode  cmdID= 42109  "
        ::= { iquav10CmdEntry 42109 }


    iquav10Logging1DolbyMetadataLoggingChannelMode OBJECT-TYPE
        SYNTAX            RollCallString
        MAX-ACCESS        read-only
        STATUS            current
        DESCRIPTION
                "CMNT: - Logging state for Dolby channel mode
                 TYPE: - Display
                 PAGE: - Logging1
                    Channel Mode=  cmdID= 42309  "
        ::= { iquav10CmdEntry 42309 }


    iquav10Logging1DolbyMetadataLoggingLogLFEChannel OBJECT-TYPE
        SYNTAX            INTEGER { disable(0), enable(1)  }
        MAX-ACCESS        read-write
        STATUS            current
        DESCRIPTION
                "CMNT: - Enable/Disable logging for Dolby lfe channel
                 TYPE: - Checkbox
                 PAGE: - Logging1
                    Log LFE Channel  cmdID= 42110  "
        ::= { iquav10CmdEntry 42110 }


    iquav10Logging1DolbyMetadataLoggingLFEChannel OBJECT-TYPE
        SYNTAX            RollCallString
        MAX-ACCESS        read-only
        STATUS            current
        DESCRIPTION
                "CMNT: - Logging state for Dolby lfe channel
                 TYPE: - Display
                 PAGE: - Logging1
                    LFE Channel=  cmdID= 42310  "
        ::= { iquav10CmdEntry 42310 }


    iquav10Logging1DolbyMetadataLoggingLogDialogueNorm OBJECT-TYPE
        SYNTAX            INTEGER { disable(0), enable(1)  }
        MAX-ACCESS        read-write
        STATUS            current
        DESCRIPTION
                "CMNT: - Enable/Disable logging for Dolby dialogue norm
                 TYPE: - Checkbox
                 PAGE: - Logging1
                    Log Dialogue Norm  cmdID= 42111  "
        ::= { iquav10CmdEntry 42111 }


    iquav10Logging1DolbyMetadataLoggingDialogueNorm OBJECT-TYPE
        SYNTAX            RollCallString
        MAX-ACCESS        read-only
        STATUS            current
        DESCRIPTION
                "CMNT: - Logging state for Dolby dialogue norm
                 TYPE: - Display
                 PAGE: - Logging1
                    Dialogue Norm=  cmdID= 42311  "
        ::= { iquav10CmdEntry 42311 }


    iquav10Logging1AncillaryDataLoggingLogVIInp1 OBJECT-TYPE
        SYNTAX            INTEGER { disable(0), enable(1)  }
        MAX-ACCESS        read-write
        STATUS            current
        DESCRIPTION
                "CMNT: - Enable/Disable logging for ancillary data VI status
                 TYPE: - Checkbox
                 PAGE: - Logging1
                    Log VI Inp1  cmdID= 42120  "
        ::= { iquav10CmdEntry 42120 }


    iquav10Logging1AncillaryDataLoggingVIInp1 OBJECT-TYPE
        SYNTAX            RollCallString
        MAX-ACCESS        read-only
        STATUS            current
        DESCRIPTION
                "CMNT: - Logging state for VI ancillary data on input
                 TYPE: - Display
                 PAGE: - Logging1
                    VI Inp1=  cmdID= 42320  "
        ::= { iquav10CmdEntry 42320 }


    iquav10Logging1AncillaryDataLoggingLogWSSInp1 OBJECT-TYPE
        SYNTAX            INTEGER { disable(0), enable(1)  }
        MAX-ACCESS        read-write
        STATUS            current
        DESCRIPTION
                "CMNT: - Enable/Disable logging for ancillary data WSS status
                 TYPE: - Checkbox
                 PAGE: - Logging1
                    Log WSS Inp1  cmdID= 42121  "
        ::= { iquav10CmdEntry 42121 }


    iquav10Logging1AncillaryDataLoggingWSSInp1 OBJECT-TYPE
        SYNTAX            RollCallString
        MAX-ACCESS        read-only
        STATUS            current
        DESCRIPTION
                "CMNT: - Logging state for WSS ancillary data on input
                 TYPE: - Display
                 PAGE: - Logging1
                    WSS Inp1=  cmdID= 42321  "
        ::= { iquav10CmdEntry 42321 }


    iquav10Logging1AncillaryDataLoggingLogVITCInp1 OBJECT-TYPE
        SYNTAX            INTEGER { disable(0), enable(1)  }
        MAX-ACCESS        read-write
        STATUS            current
        DESCRIPTION
                "CMNT: - Enable/Disable logging for ancillary data VITC status
                 TYPE: - Checkbox
                 PAGE: - Logging1
                    Log VITC Inp1  cmdID= 42122  "
        ::= { iquav10CmdEntry 42122 }


    iquav10Logging1AncillaryDataLoggingVITCInp1 OBJECT-TYPE
        SYNTAX            RollCallString
        MAX-ACCESS        read-only
        STATUS            current
        DESCRIPTION
                "CMNT: - Logging state for VITC ancillary data on input
                 TYPE: - Display
                 PAGE: - Logging1
                    VITC Inp1=  cmdID= 42322  "
        ::= { iquav10CmdEntry 42322 }


    iquav10Logging1AncillaryDataLoggingLogWSTInp1 OBJECT-TYPE
        SYNTAX            INTEGER { disable(0), enable(1)  }
        MAX-ACCESS        read-write
        STATUS            current
        DESCRIPTION
                "CMNT: - Enable/Disable logging for ancillary data WST status
                 TYPE: - Checkbox
                 PAGE: - Logging1
                    Log WST Inp1  cmdID= 42123  "
        ::= { iquav10CmdEntry 42123 }


    iquav10Logging1AncillaryDataLoggingWSTInp1 OBJECT-TYPE
        SYNTAX            RollCallString
        MAX-ACCESS        read-only
        STATUS            current
        DESCRIPTION
                "CMNT: - Logging state for WST ancillary data on input
                 TYPE: - Display
                 PAGE: - Logging1
                    WST Inp1=  cmdID= 42323  "
        ::= { iquav10CmdEntry 42323 }


    iquav10Logging1AncillaryDataLoggingLogCC608Inp1 OBJECT-TYPE
        SYNTAX            INTEGER { disable(0), enable(1)  }
        MAX-ACCESS        read-write
        STATUS            current
        DESCRIPTION
                "CMNT: - Enable/Disable logging for ancillary data CC608 status
                 TYPE: - Checkbox
                 PAGE: - Logging1
                    Log CC608 Inp1  cmdID= 42124  "
        ::= { iquav10CmdEntry 42124 }


    iquav10Logging1AncillaryDataLoggingCC608Inp1 OBJECT-TYPE
        SYNTAX            RollCallString
        MAX-ACCESS        read-only
        STATUS            current
        DESCRIPTION
                "CMNT: - Logging state for CC608 ancillary data on input
                 TYPE: - Display
                 PAGE: - Logging1
                    CC608 Inp1=  cmdID= 42324  "
        ::= { iquav10CmdEntry 42324 }


    iquav10Logging1AncillaryDataLoggingLog2016Inp1 OBJECT-TYPE
        SYNTAX            INTEGER { disable(0), enable(1)  }
        MAX-ACCESS        read-write
        STATUS            current
        DESCRIPTION
                "CMNT: - Enable/Disable logging for ancillary data SMPTE2016 status
                 TYPE: - Checkbox
                 PAGE: - Logging1
                    Log 2016 Inp1  cmdID= 42125  "
        ::= { iquav10CmdEntry 42125 }


    iquav10Logging1AncillaryDataLogging2016Inp1 OBJECT-TYPE
        SYNTAX            RollCallString
        MAX-ACCESS        read-only
        STATUS            current
        DESCRIPTION
                "CMNT: - Logging state for SMPTE2016 ancillary data on input
                 TYPE: - Display
                 PAGE: - Logging1
                    2016 Inp1=  cmdID= 42325  "
        ::= { iquav10CmdEntry 42325 }


    iquav10Logging1AncillaryDataLoggingLogATCInp1 OBJECT-TYPE
        SYNTAX            INTEGER { disable(0), enable(1)  }
        MAX-ACCESS        read-write
        STATUS            current
        DESCRIPTION
                "CMNT: - Enable/Disable logging for ancillary data ATC status
                 TYPE: - Checkbox
                 PAGE: - Logging1
                    Log ATC Inp1  cmdID= 42126  "
        ::= { iquav10CmdEntry 42126 }


    iquav10Logging1AncillaryDataLoggingATCInp1 OBJECT-TYPE
        SYNTAX            RollCallString
        MAX-ACCESS        read-only
        STATUS            current
        DESCRIPTION
                "CMNT: - Logging state for ATC/VITC ancillary data on input
                 TYPE: - Display
                 PAGE: - Logging1
                    ATC Inp1=  cmdID= 42326  "
        ::= { iquav10CmdEntry 42326 }


    iquav10Logging1AncillaryDataLoggingLogCC708Inp1 OBJECT-TYPE
        SYNTAX            INTEGER { disable(0), enable(1)  }
        MAX-ACCESS        read-write
        STATUS            current
        DESCRIPTION
                "CMNT: - Enable/Disable logging for ancillary data CC708 status
                 TYPE: - Checkbox
                 PAGE: - Logging1
                    Log CC708 Inp1  cmdID= 42127  "
        ::= { iquav10CmdEntry 42127 }


    iquav10Logging1AncillaryDataLoggingCC708Inp1 OBJECT-TYPE
        SYNTAX            RollCallString
        MAX-ACCESS        read-only
        STATUS            current
        DESCRIPTION
                "CMNT: - Logging state for CC708/OP47 ancillary data on input
                 TYPE: - Display
                 PAGE: - Logging1
                    CC708 Inp1=  cmdID= 42327  "
        ::= { iquav10CmdEntry 42327 }


    iquav10Logging1AncillaryDataLoggingLogARInp1 OBJECT-TYPE
        SYNTAX            INTEGER { disable(0), enable(1)  }
        MAX-ACCESS        read-write
        STATUS            current
        DESCRIPTION
                "CMNT: - Enable/Disable logging for ancillary data I/P aspect ratio
                 TYPE: - Checkbox
                 PAGE: - Logging1
                    Log AR Inp1  cmdID= 42176  "
        ::= { iquav10CmdEntry 42176 }


    iquav10Logging1AncillaryDataLoggingARInp1 OBJECT-TYPE
        SYNTAX            RollCallString
        MAX-ACCESS        read-only
        STATUS            current
        DESCRIPTION
                "CMNT: - Logging state for aspect ratio on input
                 TYPE: - Display
                 PAGE: - Logging1
                    AR Inp1  cmdID= 42376  "
        ::= { iquav10CmdEntry 42376 }


    iquav10Logging1AncillaryDataLoggingLogAFDInp1 OBJECT-TYPE
        SYNTAX            INTEGER { disable(0), enable(1)  }
        MAX-ACCESS        read-write
        STATUS            current
        DESCRIPTION
                "CMNT: - Enable/Disable logging for ancillary data I/P AFD
                 TYPE: - Checkbox
                 PAGE: - Logging1
                    Log AFD Inp1  cmdID= 42177  "
        ::= { iquav10CmdEntry 42177 }


    iquav10Logging1AncillaryDataLoggingAFDInp1 OBJECT-TYPE
        SYNTAX            RollCallString
        MAX-ACCESS        read-only
        STATUS            current
        DESCRIPTION
                "CMNT: - Logging state for AFD on input
                 TYPE: - Display
                 PAGE: - Logging1
                    AFD Inp1=  cmdID= 42377  "
        ::= { iquav10CmdEntry 42377 }


    iquav10Logging1AncillaryDataLoggingLogVIInp2 OBJECT-TYPE
        SYNTAX            INTEGER { disable(0), enable(1)  }
        MAX-ACCESS        read-write
        STATUS            current
        DESCRIPTION
                "CMNT: - Enable/Disable logging for ancillary data VI status
                 TYPE: - Checkbox
                 PAGE: - Logging1
                    Log VI Inp2  cmdID= 42180  "
        ::= { iquav10CmdEntry 42180 }


    iquav10Logging1AncillaryDataLoggingVIInp2 OBJECT-TYPE
        SYNTAX            RollCallString
        MAX-ACCESS        read-only
        STATUS            current
        DESCRIPTION
                "CMNT: - Logging state for VI ancillary data on input
                 TYPE: - Display
                 PAGE: - Logging1
                    VI Inp2=  cmdID= 42290  "
        ::= { iquav10CmdEntry 42290 }


    iquav10Logging1AncillaryDataLoggingLogWSSInp2 OBJECT-TYPE
        SYNTAX            INTEGER { disable(0), enable(1)  }
        MAX-ACCESS        read-write
        STATUS            current
        DESCRIPTION
                "CMNT: - Enable/Disable logging for ancillary data WSS status
                 TYPE: - Checkbox
                 PAGE: - Logging1
                    Log WSS Inp2  cmdID= 42181  "
        ::= { iquav10CmdEntry 42181 }


    iquav10Logging1AncillaryDataLoggingWSSInp2 OBJECT-TYPE
        SYNTAX            RollCallString
        MAX-ACCESS        read-only
        STATUS            current
        DESCRIPTION
                "CMNT: - Logging state for WSS ancillary data on input
                 TYPE: - Display
                 PAGE: - Logging1
                    WSS Inp2=  cmdID= 42291  "
        ::= { iquav10CmdEntry 42291 }


    iquav10Logging1AncillaryDataLoggingLogVITCInp2 OBJECT-TYPE
        SYNTAX            INTEGER { disable(0), enable(1)  }
        MAX-ACCESS        read-write
        STATUS            current
        DESCRIPTION
                "CMNT: - Enable/Disable logging for ancillary data VITC status
                 TYPE: - Checkbox
                 PAGE: - Logging1
                    Log VITC Inp2  cmdID= 42182  "
        ::= { iquav10CmdEntry 42182 }


    iquav10Logging1AncillaryDataLoggingVITCInp2 OBJECT-TYPE
        SYNTAX            RollCallString
        MAX-ACCESS        read-only
        STATUS            current
        DESCRIPTION
                "CMNT: - Logging state for VITC ancillary data on input
                 TYPE: - Display
                 PAGE: - Logging1
                    VITC Inp2=  cmdID= 42292  "
        ::= { iquav10CmdEntry 42292 }


    iquav10Logging1AncillaryDataLoggingLogWSTInp2 OBJECT-TYPE
        SYNTAX            INTEGER { disable(0), enable(1)  }
        MAX-ACCESS        read-write
        STATUS            current
        DESCRIPTION
                "CMNT: - Enable/Disable logging for ancillary data WST status
                 TYPE: - Checkbox
                 PAGE: - Logging1
                    Log WST Inp2  cmdID= 42183  "
        ::= { iquav10CmdEntry 42183 }


    iquav10Logging1AncillaryDataLoggingWSTInp2 OBJECT-TYPE
        SYNTAX            RollCallString
        MAX-ACCESS        read-only
        STATUS            current
        DESCRIPTION
                "CMNT: - Logging state for WST ancillary data on input
                 TYPE: - Display
                 PAGE: - Logging1
                    WST Inp2=  cmdID= 42293  "
        ::= { iquav10CmdEntry 42293 }


    iquav10Logging1AncillaryDataLoggingLogCC608Inp2 OBJECT-TYPE
        SYNTAX            INTEGER { disable(0), enable(1)  }
        MAX-ACCESS        read-write
        STATUS            current
        DESCRIPTION
                "CMNT: - Enable/Disable logging for ancillary data CC608 status
                 TYPE: - Checkbox
                 PAGE: - Logging1
                    Log CC608 Inp2  cmdID= 42184  "
        ::= { iquav10CmdEntry 42184 }


    iquav10Logging1AncillaryDataLoggingCC608Inp2 OBJECT-TYPE
        SYNTAX            RollCallString
        MAX-ACCESS        read-only
        STATUS            current
        DESCRIPTION
                "CMNT: - Logging state for CC608 ancillary data on input
                 TYPE: - Display
                 PAGE: - Logging1
                    CC608 Inp2=  cmdID= 42294  "
        ::= { iquav10CmdEntry 42294 }


    iquav10Logging1AncillaryDataLoggingLog2016Inp2 OBJECT-TYPE
        SYNTAX            INTEGER { disable(0), enable(1)  }
        MAX-ACCESS        read-write
        STATUS            current
        DESCRIPTION
                "CMNT: - Enable/Disable logging for ancillary data SMPTE2016 status
                 TYPE: - Checkbox
                 PAGE: - Logging1
                    Log 2016 Inp2  cmdID= 42185  "
        ::= { iquav10CmdEntry 42185 }


    iquav10Logging1AncillaryDataLogging2016Inp2 OBJECT-TYPE
        SYNTAX            RollCallString
        MAX-ACCESS        read-only
        STATUS            current
        DESCRIPTION
                "CMNT: - Logging state for SMPTE2016 ancillary data on input
                 TYPE: - Display
                 PAGE: - Logging1
                    2016 Inp2=  cmdID= 42295  "
        ::= { iquav10CmdEntry 42295 }


    iquav10Logging1AncillaryDataLoggingLogATCInp2 OBJECT-TYPE
        SYNTAX            INTEGER { disable(0), enable(1)  }
        MAX-ACCESS        read-write
        STATUS            current
        DESCRIPTION
                "CMNT: - Enable/Disable logging for ancillary data ATC status
                 TYPE: - Checkbox
                 PAGE: - Logging1
                    Log ATC Inp2  cmdID= 42186  "
        ::= { iquav10CmdEntry 42186 }


    iquav10Logging1AncillaryDataLoggingATCInp2 OBJECT-TYPE
        SYNTAX            RollCallString
        MAX-ACCESS        read-only
        STATUS            current
        DESCRIPTION
                "CMNT: - Logging state for ATC/VITC ancillary data on input
                 TYPE: - Display
                 PAGE: - Logging1
                    ATC Inp2=  cmdID= 42296  "
        ::= { iquav10CmdEntry 42296 }


    iquav10Logging1AncillaryDataLoggingLogCC708Inp2 OBJECT-TYPE
        SYNTAX            INTEGER { disable(0), enable(1)  }
        MAX-ACCESS        read-write
        STATUS            current
        DESCRIPTION
                "CMNT: - Enable/Disable logging for ancillary data CC708 status
                 TYPE: - Checkbox
                 PAGE: - Logging1
                    Log CC708 Inp2  cmdID= 42187  "
        ::= { iquav10CmdEntry 42187 }


    iquav10Logging1AncillaryDataLoggingCC708Inp2 OBJECT-TYPE
        SYNTAX            RollCallString
        MAX-ACCESS        read-only
        STATUS            current
        DESCRIPTION
                "CMNT: - Logging state for CC708/OP47 ancillary data on input
                 TYPE: - Display
                 PAGE: - Logging1
                    CC708 Inp2=  cmdID= 42297  "
        ::= { iquav10CmdEntry 42297 }


    iquav10Logging1AncillaryDataLoggingLogARInp2 OBJECT-TYPE
        SYNTAX            INTEGER { disable(0), enable(1)  }
        MAX-ACCESS        read-write
        STATUS            current
        DESCRIPTION
                "CMNT: - Enable/Disable logging for ancillary data I/P aspect ratio
                 TYPE: - Checkbox
                 PAGE: - Logging1
                    Log AR Inp2  cmdID= 42188  "
        ::= { iquav10CmdEntry 42188 }


    iquav10Logging1AncillaryDataLoggingARInp2 OBJECT-TYPE
        SYNTAX            RollCallString
        MAX-ACCESS        read-only
        STATUS            current
        DESCRIPTION
                "CMNT: - Logging state for aspect ratio on input
                 TYPE: - Display
                 PAGE: - Logging1
                    AR Inp2  cmdID= 42298  "
        ::= { iquav10CmdEntry 42298 }


    iquav10Logging1AncillaryDataLoggingLogAFDInp2 OBJECT-TYPE
        SYNTAX            INTEGER { disable(0), enable(1)  }
        MAX-ACCESS        read-write
        STATUS            current
        DESCRIPTION
                "CMNT: - Enable/Disable logging for ancillary data I/P AFD
                 TYPE: - Checkbox
                 PAGE: - Logging1
                    Log AFD Inp2  cmdID= 42199  "
        ::= { iquav10CmdEntry 42199 }


    iquav10Logging1AncillaryDataLoggingAFDInp2 OBJECT-TYPE
        SYNTAX            RollCallString
        MAX-ACCESS        read-only
        STATUS            current
        DESCRIPTION
                "CMNT: - Logging state for AFD on input
                 TYPE: - Display
                 PAGE: - Logging1
                    AFD Inp2=  cmdID= 42299  "
        ::= { iquav10CmdEntry 42299 }


    iquav10Logging1AncillaryDataLoggingLogOutput OBJECT-TYPE
        SYNTAX            INTEGER { disable(0), enable(1)  }
        MAX-ACCESS        read-write
        STATUS            current
        DESCRIPTION
                "CMNT: - Enable/Disable logging for ancillary data WST status
                 TYPE: - Checkbox
                 PAGE: - Logging1
                    Log Output  cmdID= 42128  "
        ::= { iquav10CmdEntry 42128 }


    iquav10Logging1AncillaryDataLoggingOutput OBJECT-TYPE
        SYNTAX            RollCallString
        MAX-ACCESS        read-only
        STATUS            current
        DESCRIPTION
                "CMNT: - Logging state for ancillary data on output
                 TYPE: - Display
                 PAGE: - Logging1
                    Output=  cmdID= 42328  "
        ::= { iquav10CmdEntry 42328 }


    iquav10Logging1AncillaryDataLoggingLogOPAR OBJECT-TYPE
        SYNTAX            INTEGER { disable(0), enable(1)  }
        MAX-ACCESS        read-write
        STATUS            current
        DESCRIPTION
                "CMNT: - Enable/Disable logging for ancillary data O/P aspect ratio
                 TYPE: - Checkbox
                 PAGE: - Logging1
                    Log O/P AR  cmdID= 42178  "
        ::= { iquav10CmdEntry 42178 }


    iquav10Logging1AncillaryDataLoggingOPAR OBJECT-TYPE
        SYNTAX            RollCallString
        MAX-ACCESS        read-only
        STATUS            current
        DESCRIPTION
                "CMNT: - Logging state for aspect ratio on output
                 TYPE: - Display
                 PAGE: - Logging1
                    O/P AR  cmdID= 42378  "
        ::= { iquav10CmdEntry 42378 }


    iquav10Logging1AncillaryDataLoggingLogOPAFD OBJECT-TYPE
        SYNTAX            INTEGER { disable(0), enable(1)  }
        MAX-ACCESS        read-write
        STATUS            current
        DESCRIPTION
                "CMNT: - Enable/Disable logging for ancillary dataO/P AFD
                 TYPE: - Checkbox
                 PAGE: - Logging1
                    Log O/P AFD  cmdID= 42179  "
        ::= { iquav10CmdEntry 42179 }


    iquav10Logging1AncillaryDataLoggingOPAFD OBJECT-TYPE
        SYNTAX            RollCallString
        MAX-ACCESS        read-only
        STATUS            current
        DESCRIPTION
                "CMNT: - Logging state for AFD on output
                 TYPE: - Display
                 PAGE: - Logging1
                    O/P AFD=  cmdID= 42379  "
        ::= { iquav10CmdEntry 42379 }


    iquav10Logging2VideoRefLogInp1Type OBJECT-TYPE
        SYNTAX            INTEGER { disable(0), enable(1)  }
        MAX-ACCESS        read-write
        STATUS            current
        DESCRIPTION
                "CMNT: - Enable/Disable logging for Inp 1, Type
                 TYPE: - Checkbox
                 PAGE: - Logging2
                    Log Inp1 Type  cmdID= 42060  "
        ::= { iquav10CmdEntry 42060 }


    iquav10Logging2VideoRefInp1Type OBJECT-TYPE
        SYNTAX            RollCallString
        MAX-ACCESS        read-only
        STATUS            current
        DESCRIPTION
                "CMNT: - Logging state for Inp 1 Type
                 TYPE: - Display
                 PAGE: - Logging2
                    Inp1 Type=  cmdID= 42260  "
        ::= { iquav10CmdEntry 42260 }


    iquav10Logging2VideoRefLogInp1State OBJECT-TYPE
        SYNTAX            INTEGER { disable(0), enable(1)  }
        MAX-ACCESS        read-write
        STATUS            current
        DESCRIPTION
                "CMNT: - Enable/Disable logging for Inp 1, State
                 TYPE: - Checkbox
                 PAGE: - Logging2
                    Log Inp1 State  cmdID= 42063  "
        ::= { iquav10CmdEntry 42063 }


    iquav10Logging2VideoRefInp1State OBJECT-TYPE
        SYNTAX            RollCallString
        MAX-ACCESS        read-only
        STATUS            current
        DESCRIPTION
                "CMNT: - Logging state for Inp 1 State
                 TYPE: - Display
                 PAGE: - Logging2
                    Inp1 State=  cmdID= 42263  "
        ::= { iquav10CmdEntry 42263 }


    iquav10Logging2VideoRefLogInp1Std OBJECT-TYPE
        SYNTAX            INTEGER { disable(0), enable(1)  }
        MAX-ACCESS        read-write
        STATUS            current
        DESCRIPTION
                "CMNT: - Enable/Disable logging for Inp 1, Standard
                 TYPE: - Checkbox
                 PAGE: - Logging2
                    Log Inp1 Std  cmdID= 42066  "
        ::= { iquav10CmdEntry 42066 }


    iquav10Logging2VideoRefInp1Std OBJECT-TYPE
        SYNTAX            RollCallString
        MAX-ACCESS        read-only
        STATUS            current
        DESCRIPTION
                "CMNT: - Logging state for Inp 1 Standard
                 TYPE: - Display
                 PAGE: - Logging2
                    Inp1 Std=  cmdID= 42266  "
        ::= { iquav10CmdEntry 42266 }


    iquav10Logging2VideoRefLogInp1SDIErrs OBJECT-TYPE
        SYNTAX            INTEGER { disable(0), enable(1)  }
        MAX-ACCESS        read-write
        STATUS            current
        DESCRIPTION
                "CMNT: - Enable/Disable logging for Inp 1, Sdi Errs
                 TYPE: - Checkbox
                 PAGE: - Logging2
                    Log Inp1 SDIErrs  cmdID= 42069  "
        ::= { iquav10CmdEntry 42069 }


    iquav10Logging2VideoRefInp1SDIErrs OBJECT-TYPE
        SYNTAX            RollCallString
        MAX-ACCESS        read-only
        STATUS            current
        DESCRIPTION
                "CMNT: - Logging state for Inp 1 Sdi Errs
                 TYPE: - Display
                 PAGE: - Logging2
                    Inp1 SDIErrs=  cmdID= 42269  "
        ::= { iquav10CmdEntry 42269 }


    iquav10Logging2VideoRefLogInp1SDIErrSec OBJECT-TYPE
        SYNTAX            INTEGER { disable(0), enable(1)  }
        MAX-ACCESS        read-write
        STATUS            current
        DESCRIPTION
                "CMNT: - Enable/Disable logging for Inp 1, Sdi Errs
                 TYPE: - Checkbox
                 PAGE: - Logging2
                    Log Inp1 SDIErrSec  cmdID= 42071  "
        ::= { iquav10CmdEntry 42071 }


    iquav10Logging2VideoRefInp1SDIErrSec OBJECT-TYPE
        SYNTAX            RollCallString
        MAX-ACCESS        read-only
        STATUS            current
        DESCRIPTION
                "CMNT: - Logging state for Inp 1 Sdi Errs
                 TYPE: - Display
                 PAGE: - Logging2
                    Inp1 SDIErrSec=  cmdID= 42271  "
        ::= { iquav10CmdEntry 42271 }


    iquav10Logging2VideoRefLogInp1ANCerrs OBJECT-TYPE
        SYNTAX            INTEGER { disable(0), enable(1)  }
        MAX-ACCESS        read-write
        STATUS            current
        DESCRIPTION
                "CMNT: - Enable/Disable logging for Inp 1, Sdi Anc Errs
                 TYPE: - Checkbox
                 PAGE: - Logging2
                    Log Inp1 ANCerrs  cmdID= 42073  "
        ::= { iquav10CmdEntry 42073 }


    iquav10Logging2VideoRefInp1ANCerrs OBJECT-TYPE
        SYNTAX            RollCallString
        MAX-ACCESS        read-only
        STATUS            current
        DESCRIPTION
                "CMNT: - Logging state for Inp 1 Sdi Anc Errs
                 TYPE: - Display
                 PAGE: - Logging2
                    Inp1 ANCerrs=  cmdID= 42273  "
        ::= { iquav10CmdEntry 42273 }


    iquav10Logging2VideoRefLogInp1ANCerrSec OBJECT-TYPE
        SYNTAX            INTEGER { disable(0), enable(1)  }
        MAX-ACCESS        read-write
        STATUS            current
        DESCRIPTION
                "CMNT: - Enable/Disable logging for Inp 1, Sdi Anc Errs
                 TYPE: - Checkbox
                 PAGE: - Logging2
                    Log Inp1 ANCerrSec  cmdID= 42075  "
        ::= { iquav10CmdEntry 42075 }


    iquav10Logging2VideoRefInp1ANCerrSec OBJECT-TYPE
        SYNTAX            RollCallString
        MAX-ACCESS        read-only
        STATUS            current
        DESCRIPTION
                "CMNT: - Logging state for Inp 1 Sdi Anc Errs
                 TYPE: - Display
                 PAGE: - Logging2
                    Inp1 ANCerrSec=  cmdID= 42275  "
        ::= { iquav10CmdEntry 42275 }


    iquav10Logging2VideoRefLogInp2Type OBJECT-TYPE
        SYNTAX            INTEGER { disable(0), enable(1)  }
        MAX-ACCESS        read-write
        STATUS            current
        DESCRIPTION
                "CMNT: - Enable/Disable logging for Inp 2, Type
                 TYPE: - Checkbox
                 PAGE: - Logging2
                    Log Inp2 Type  cmdID= 42061  "
        ::= { iquav10CmdEntry 42061 }


    iquav10Logging2VideoRefInp2Type OBJECT-TYPE
        SYNTAX            RollCallString
        MAX-ACCESS        read-only
        STATUS            current
        DESCRIPTION
                "CMNT: - Logging state for Inp 2 Type
                 TYPE: - Display
                 PAGE: - Logging2
                    Inp2 Type=  cmdID= 42261  "
        ::= { iquav10CmdEntry 42261 }


    iquav10Logging2VideoRefLogInp2State OBJECT-TYPE
        SYNTAX            INTEGER { disable(0), enable(1)  }
        MAX-ACCESS        read-write
        STATUS            current
        DESCRIPTION
                "CMNT: - Enable/Disable logging for Inp 2, State
                 TYPE: - Checkbox
                 PAGE: - Logging2
                    Log Inp2 State  cmdID= 42064  "
        ::= { iquav10CmdEntry 42064 }


    iquav10Logging2VideoRefInp2State OBJECT-TYPE
        SYNTAX            RollCallString
        MAX-ACCESS        read-only
        STATUS            current
        DESCRIPTION
                "CMNT: - Logging state for Inp 2 State
                 TYPE: - Display
                 PAGE: - Logging2
                    Inp2 State=  cmdID= 42264  "
        ::= { iquav10CmdEntry 42264 }


    iquav10Logging2VideoRefLogInp2Std OBJECT-TYPE
        SYNTAX            INTEGER { disable(0), enable(1)  }
        MAX-ACCESS        read-write
        STATUS            current
        DESCRIPTION
                "CMNT: - Enable/Disable logging for Inp 2, Standard
                 TYPE: - Checkbox
                 PAGE: - Logging2
                    Log Inp2 Std  cmdID= 42067  "
        ::= { iquav10CmdEntry 42067 }


    iquav10Logging2VideoRefInp2Std OBJECT-TYPE
        SYNTAX            RollCallString
        MAX-ACCESS        read-only
        STATUS            current
        DESCRIPTION
                "CMNT: - Logging state for Inp 2 Standard
                 TYPE: - Display
                 PAGE: - Logging2
                    Inp2 Std=  cmdID= 42267  "
        ::= { iquav10CmdEntry 42267 }


    iquav10Logging2VideoRefLogInp2SDIErrs OBJECT-TYPE
        SYNTAX            INTEGER { disable(0), enable(1)  }
        MAX-ACCESS        read-write
        STATUS            current
        DESCRIPTION
                "CMNT: - Enable/Disable logging for Inp 2, Sdi Errs
                 TYPE: - Checkbox
                 PAGE: - Logging2
                    Log Inp2 SDIErrs  cmdID= 42070  "
        ::= { iquav10CmdEntry 42070 }


    iquav10Logging2VideoRefInp2SDIErrs OBJECT-TYPE
        SYNTAX            RollCallString
        MAX-ACCESS        read-only
        STATUS            current
        DESCRIPTION
                "CMNT: - Logging state for Inp 2 Sdi Errs
                 TYPE: - Display
                 PAGE: - Logging2
                    Inp2 SDIErrs=  cmdID= 42270  "
        ::= { iquav10CmdEntry 42270 }


    iquav10Logging2VideoRefLogInp2SDIErrSec OBJECT-TYPE
        SYNTAX            INTEGER { disable(0), enable(1)  }
        MAX-ACCESS        read-write
        STATUS            current
        DESCRIPTION
                "CMNT: - Enable/Disable logging for Inp 2, Sdi Errs
                 TYPE: - Checkbox
                 PAGE: - Logging2
                    Log Inp2 SDIErrSec  cmdID= 42072  "
        ::= { iquav10CmdEntry 42072 }


    iquav10Logging2VideoRefInp2SDIErrSec OBJECT-TYPE
        SYNTAX            RollCallString
        MAX-ACCESS        read-only
        STATUS            current
        DESCRIPTION
                "CMNT: - Logging state for Inp 2 Sdi Errs
                 TYPE: - Display
                 PAGE: - Logging2
                    Inp2 SDIErrSec=  cmdID= 42272  "
        ::= { iquav10CmdEntry 42272 }


    iquav10Logging2VideoRefLogInp2ANCerrs OBJECT-TYPE
        SYNTAX            INTEGER { disable(0), enable(1)  }
        MAX-ACCESS        read-write
        STATUS            current
        DESCRIPTION
                "CMNT: - Enable/Disable logging for Inp 2, Sdi Anc Errs
                 TYPE: - Checkbox
                 PAGE: - Logging2
                    Log Inp2 ANCerrs  cmdID= 42074  "
        ::= { iquav10CmdEntry 42074 }


    iquav10Logging2VideoRefInp2ANCerrs OBJECT-TYPE
        SYNTAX            RollCallString
        MAX-ACCESS        read-only
        STATUS            current
        DESCRIPTION
                "CMNT: - Logging state for Inp 2 Sdi Anc Errs
                 TYPE: - Display
                 PAGE: - Logging2
                    Inp2 ANCerrs=  cmdID= 42274  "
        ::= { iquav10CmdEntry 42274 }


    iquav10Logging2VideoRefLogInp2ANCerrSec OBJECT-TYPE
        SYNTAX            INTEGER { disable(0), enable(1)  }
        MAX-ACCESS        read-write
        STATUS            current
        DESCRIPTION
                "CMNT: - Enable/Disable logging for Inp 2, Sdi Anc Errs
                 TYPE: - Checkbox
                 PAGE: - Logging2
                    Log Inp2 ANCerrSec  cmdID= 42076  "
        ::= { iquav10CmdEntry 42076 }


    iquav10Logging2VideoRefInp2ANCerrSec OBJECT-TYPE
        SYNTAX            RollCallString
        MAX-ACCESS        read-only
        STATUS            current
        DESCRIPTION
                "CMNT: - Logging state for Inp 2 Sdi Anc Errs
                 TYPE: - Display
                 PAGE: - Logging2
                    Inp2 ANCerrSec=  cmdID= 42276  "
        ::= { iquav10CmdEntry 42276 }


    iquav10Logging2VideoRefLogInp3Type OBJECT-TYPE
        SYNTAX            INTEGER { disable(0), enable(1)  }
        MAX-ACCESS        read-write
        STATUS            current
        DESCRIPTION
                "CMNT: - Enable/Disable logging for Inp 3, Type
                 TYPE: - Checkbox
                 PAGE: - Logging2
                    Log Inp3 Type  cmdID= 42062  "
        ::= { iquav10CmdEntry 42062 }


    iquav10Logging2VideoRefInp3Type OBJECT-TYPE
        SYNTAX            RollCallString
        MAX-ACCESS        read-only
        STATUS            current
        DESCRIPTION
                "CMNT: - Logging state for Inp 3 Type
                 TYPE: - Display
                 PAGE: - Logging2
                    Inp3 Type=  cmdID= 42262  "
        ::= { iquav10CmdEntry 42262 }


    iquav10Logging2VideoRefLogInp3State OBJECT-TYPE
        SYNTAX            INTEGER { disable(0), enable(1)  }
        MAX-ACCESS        read-write
        STATUS            current
        DESCRIPTION
                "CMNT: - Enable/Disable logging for Inp 3, State
                 TYPE: - Checkbox
                 PAGE: - Logging2
                    Log Inp3 State  cmdID= 42065  "
        ::= { iquav10CmdEntry 42065 }


    iquav10Logging2VideoRefInp3State OBJECT-TYPE
        SYNTAX            RollCallString
        MAX-ACCESS        read-only
        STATUS            current
        DESCRIPTION
                "CMNT: - Logging state for Inp 3 State
                 TYPE: - Display
                 PAGE: - Logging2
                    Inp3 State=  cmdID= 42265  "
        ::= { iquav10CmdEntry 42265 }


    iquav10Logging2VideoRefLogInp3Std OBJECT-TYPE
        SYNTAX            INTEGER { disable(0), enable(1)  }
        MAX-ACCESS        read-write
        STATUS            current
        DESCRIPTION
                "CMNT: - Enable/Disable logging for Inp 3, Standard
                 TYPE: - Checkbox
                 PAGE: - Logging2
                    Log Inp3 Std  cmdID= 42068  "
        ::= { iquav10CmdEntry 42068 }


    iquav10Logging2VideoRefInp3Std OBJECT-TYPE
        SYNTAX            RollCallString
        MAX-ACCESS        read-only
        STATUS            current
        DESCRIPTION
                "CMNT: - Logging state for Inp 3 State
                 TYPE: - Display
                 PAGE: - Logging2
                    Inp3 Std=  cmdID= 42268  "
        ::= { iquav10CmdEntry 42268 }


    iquav10Logging2VideoRefLogOutp1Type OBJECT-TYPE
        SYNTAX            INTEGER { disable(0), enable(1)  }
        MAX-ACCESS        read-write
        STATUS            current
        DESCRIPTION
                "CMNT: - Enable/Disable logging for Out 1, Type
                 TYPE: - Checkbox
                 PAGE: - Logging2
                    Log Outp1 Type  cmdID= 42077  "
        ::= { iquav10CmdEntry 42077 }


    iquav10Logging2VideoRefOutp1Type OBJECT-TYPE
        SYNTAX            RollCallString
        MAX-ACCESS        read-only
        STATUS            current
        DESCRIPTION
                "CMNT: - Logging state for Out 1 Type
                 TYPE: - Display
                 PAGE: - Logging2
                    Outp1 Type=  cmdID= 42277  "
        ::= { iquav10CmdEntry 42277 }


    iquav10Logging2VideoRefLogOutp1State OBJECT-TYPE
        SYNTAX            INTEGER { disable(0), enable(1)  }
        MAX-ACCESS        read-write
        STATUS            current
        DESCRIPTION
                "CMNT: - Enable/Disable logging for Out 1, State
                 TYPE: - Checkbox
                 PAGE: - Logging2
                    Log Outp1 State  cmdID= 42078  "
        ::= { iquav10CmdEntry 42078 }


    iquav10Logging2VideoRefOutp1State OBJECT-TYPE
        SYNTAX            RollCallString
        MAX-ACCESS        read-only
        STATUS            current
        DESCRIPTION
                "CMNT: - Logging state for Out 1 State
                 TYPE: - Display
                 PAGE: - Logging2
                    Outp1 State=  cmdID= 42278  "
        ::= { iquav10CmdEntry 42278 }


    iquav10Logging2VideoRefLogOutp1Std OBJECT-TYPE
        SYNTAX            INTEGER { disable(0), enable(1)  }
        MAX-ACCESS        read-write
        STATUS            current
        DESCRIPTION
                "CMNT: - Enable/Disable logging for Out 1, Standard
                 TYPE: - Checkbox
                 PAGE: - Logging2
                    Log Outp1 Std  cmdID= 42079  "
        ::= { iquav10CmdEntry 42079 }


    iquav10Logging2VideoRefOutp1Std OBJECT-TYPE
        SYNTAX            RollCallString
        MAX-ACCESS        read-only
        STATUS            current
        DESCRIPTION
                "CMNT: - Logging state for Out 1 Standard
                 TYPE: - Display
                 PAGE: - Logging2
                    Outp1 Std=  cmdID= 42279  "
        ::= { iquav10CmdEntry 42279 }


    iquav10Logging2VideoRefLogOutp2State OBJECT-TYPE
        SYNTAX            INTEGER { disable(0), enable(1)  }
        MAX-ACCESS        read-write
        STATUS            current
        DESCRIPTION
                "CMNT: - Enable/Disable logging for Out 1, State
                 TYPE: - Checkbox
                 PAGE: - Logging2
                    Log Outp2 State  cmdID= 42086  "
        ::= { iquav10CmdEntry 42086 }


    iquav10Logging2VideoRefOutp2State OBJECT-TYPE
        SYNTAX            RollCallString
        MAX-ACCESS        read-only
        STATUS            current
        DESCRIPTION
                "CMNT: - Logging state for Out 1 State
                 TYPE: - Display
                 PAGE: - Logging2
                    Outp2 State=  cmdID= 42286  "
        ::= { iquav10CmdEntry 42286 }


    iquav10Logging2VideoRefLogOutp2Std OBJECT-TYPE
        SYNTAX            INTEGER { disable(0), enable(1)  }
        MAX-ACCESS        read-write
        STATUS            current
        DESCRIPTION
                "CMNT: - Enable/Disable logging for Out 1, Standard
                 TYPE: - Checkbox
                 PAGE: - Logging2
                    Log Outp2 Std  cmdID= 42087  "
        ::= { iquav10CmdEntry 42087 }


    iquav10Logging2VideoRefOutp2Std OBJECT-TYPE
        SYNTAX            RollCallString
        MAX-ACCESS        read-only
        STATUS            current
        DESCRIPTION
                "CMNT: - Logging state for Out 1 Standard
                 TYPE: - Display
                 PAGE: - Logging2
                    Outp2 Std=  cmdID= 42287  "
        ::= { iquav10CmdEntry 42287 }


    iquav10Logging2VideoRefLogOutp1 OBJECT-TYPE
        SYNTAX            INTEGER { disable(0), enable(1)  }
        MAX-ACCESS        read-write
        STATUS            current
        DESCRIPTION
                "CMNT: - Enable/Disable logging for Out 1, 
                 TYPE: - Checkbox
                 PAGE: - Logging2
                    Log Outp1  cmdID= 42080  "
        ::= { iquav10CmdEntry 42080 }


    iquav10Logging2VideoRefOutp1 OBJECT-TYPE
        SYNTAX            RollCallString
        MAX-ACCESS        read-only
        STATUS            current
        DESCRIPTION
                "CMNT: - Logging state for Out 1 
                 TYPE: - Display
                 PAGE: - Logging2
                    Outp1=  cmdID= 42280  "
        ::= { iquav10CmdEntry 42280 }


    iquav10Logging2VideoRefLogOutp1Capt OBJECT-TYPE
        SYNTAX            INTEGER { disable(0), enable(1)  }
        MAX-ACCESS        read-write
        STATUS            current
        DESCRIPTION
                "CMNT: - Enable/Disable logging for Out 1 CAPTION 
                 TYPE: - Checkbox
                 PAGE: - Logging2
                    Log Outp1 Capt  cmdID= 42081  "
        ::= { iquav10CmdEntry 42081 }


    iquav10Logging2VideoRefOutp1Capt OBJECT-TYPE
        SYNTAX            RollCallString
        MAX-ACCESS        read-only
        STATUS            current
        DESCRIPTION
                "CMNT: - Logging state for Out 1 CAPTION
                 TYPE: - Display
                 PAGE: - Logging2
                    Outp1 Capt=  cmdID= 42281  "
        ::= { iquav10CmdEntry 42281 }


    iquav10Logging2VideoRefLogRefType OBJECT-TYPE
        SYNTAX            INTEGER { disable(0), enable(1)  }
        MAX-ACCESS        read-write
        STATUS            current
        DESCRIPTION
                "CMNT: - Enable/Disable logging for REFERENCE 1, Type
                 TYPE: - Checkbox
                 PAGE: - Logging2
                    Log Ref Type  cmdID= 42083  "
        ::= { iquav10CmdEntry 42083 }


    iquav10Logging2VideoRefRefType OBJECT-TYPE
        SYNTAX            RollCallString
        MAX-ACCESS        read-only
        STATUS            current
        DESCRIPTION
                "CMNT: - Logging state for REFERENCE 1 Type
                 TYPE: - Display
                 PAGE: - Logging2
                    Ref Type=  cmdID= 42283  "
        ::= { iquav10CmdEntry 42283 }


    iquav10Logging2VideoRefLogRefState OBJECT-TYPE
        SYNTAX            INTEGER { disable(0), enable(1)  }
        MAX-ACCESS        read-write
        STATUS            current
        DESCRIPTION
                "CMNT: - Enable/Disable logging for REFERENCE 1 STATE
                 TYPE: - Checkbox
                 PAGE: - Logging2
                    Log Ref State  cmdID= 42084  "
        ::= { iquav10CmdEntry 42084 }


    iquav10Logging2VideoRefRefState OBJECT-TYPE
        SYNTAX            RollCallString
        MAX-ACCESS        read-only
        STATUS            current
        DESCRIPTION
                "CMNT: - Logging state for REFERENCE 1 STATE
                 TYPE: - Display
                 PAGE: - Logging2
                    Ref State=  cmdID= 42284  "
        ::= { iquav10CmdEntry 42284 }


    iquav10Logging2VideoRefLogRefStd OBJECT-TYPE
        SYNTAX            INTEGER { disable(0), enable(1)  }
        MAX-ACCESS        read-write
        STATUS            current
        DESCRIPTION
                "CMNT: - Enable/Disable logging for REFERENCE 1 STANDARD
                 TYPE: - Checkbox
                 PAGE: - Logging2
                    Log Ref Std  cmdID= 42085  "
        ::= { iquav10CmdEntry 42085 }


    iquav10Logging2VideoRefRefStd OBJECT-TYPE
        SYNTAX            RollCallString
        MAX-ACCESS        read-only
        STATUS            current
        DESCRIPTION
                "CMNT: - Logging state for REFERENCE 1 STANDARD
                 TYPE: - Display
                 PAGE: - Logging2
                    Ref Std=  cmdID= 42285  "
        ::= { iquav10CmdEntry 42285 }


    iquav10Logging2VideoRefLogGenlockState OBJECT-TYPE
        SYNTAX            INTEGER { disable(0), enable(1)  }
        MAX-ACCESS        read-write
        STATUS            current
        DESCRIPTION
                "CMNT: - Enable/Disable logging for GENLOCK 1, State
                 TYPE: - Checkbox
                 PAGE: - Logging2
                    Log Genlock State  cmdID= 42082  "
        ::= { iquav10CmdEntry 42082 }


    iquav10Logging2VideoRefGenlocState OBJECT-TYPE
        SYNTAX            RollCallString
        MAX-ACCESS        read-only
        STATUS            current
        DESCRIPTION
                "CMNT: - Logging state for GENLOCK 1 State
                 TYPE: - Display
                 PAGE: - Logging2
                    Genloc State=  cmdID= 42282  "
        ::= { iquav10CmdEntry 42282 }


    iquav10Logging2VideoRefLogInp1Ident OBJECT-TYPE
        SYNTAX            INTEGER { disable(0), enable(1)  }
        MAX-ACCESS        read-write
        STATUS            current
        DESCRIPTION
                "CMNT: - Enable/Disable logging for Inp 1, Ident
                 TYPE: - Checkbox
                 PAGE: - Logging2
                    Log Inp1 Ident  cmdID= 42130  "
        ::= { iquav10CmdEntry 42130 }


    iquav10Logging2VideoRefInp1Ident OBJECT-TYPE
        SYNTAX            RollCallString
        MAX-ACCESS        read-only
        STATUS            current
        DESCRIPTION
                "CMNT: - Logging state for Inp 1 Ident
                 TYPE: - Display
                 PAGE: - Logging2
                    Inp1 Ident=  cmdID= 42330  "
        ::= { iquav10CmdEntry 42330 }


    iquav10Logging2VideoRefLogInp1Name OBJECT-TYPE
        SYNTAX            INTEGER { disable(0), enable(1)  }
        MAX-ACCESS        read-write
        STATUS            current
        DESCRIPTION
                "CMNT: - Enable/Disable logging for Inp 1, Name
                 TYPE: - Checkbox
                 PAGE: - Logging2
                    Log Inp1 Name  cmdID= 42133  "
        ::= { iquav10CmdEntry 42133 }


    iquav10Logging2VideoRefInp1Name OBJECT-TYPE
        SYNTAX            RollCallString
        MAX-ACCESS        read-only
        STATUS            current
        DESCRIPTION
                "CMNT: - Logging state for Inp 1 Name
                 TYPE: - Display
                 PAGE: - Logging2
                    Inp1 Name=  cmdID= 42333  "
        ::= { iquav10CmdEntry 42333 }


    iquav10Logging2VideoRefLogInp2Ident OBJECT-TYPE
        SYNTAX            INTEGER { disable(0), enable(1)  }
        MAX-ACCESS        read-write
        STATUS            current
        DESCRIPTION
                "CMNT: - Enable/Disable logging for Inp 2, Ident
                 TYPE: - Checkbox
                 PAGE: - Logging2
                    Log Inp2 Ident  cmdID= 42131  "
        ::= { iquav10CmdEntry 42131 }


    iquav10Logging2VideoRefInp2Ident OBJECT-TYPE
        SYNTAX            RollCallString
        MAX-ACCESS        read-only
        STATUS            current
        DESCRIPTION
                "CMNT: - Logging state for Inp 2 Ident
                 TYPE: - Display
                 PAGE: - Logging2
                    Inp2 Ident=  cmdID= 42331  "
        ::= { iquav10CmdEntry 42331 }


    iquav10Logging2VideoRefLogInp2Name OBJECT-TYPE
        SYNTAX            INTEGER { disable(0), enable(1)  }
        MAX-ACCESS        read-write
        STATUS            current
        DESCRIPTION
                "CMNT: - Enable/Disable logging for Inp 2, Name
                 TYPE: - Checkbox
                 PAGE: - Logging2
                    Log Inp2 Name  cmdID= 42134  "
        ::= { iquav10CmdEntry 42134 }


    iquav10Logging2VideoRefInp2Name OBJECT-TYPE
        SYNTAX            RollCallString
        MAX-ACCESS        read-only
        STATUS            current
        DESCRIPTION
                "CMNT: - Logging state for Inp 2 Name
                 TYPE: - Display
                 PAGE: - Logging2
                    Inp2 Name=  cmdID= 42334  "
        ::= { iquav10CmdEntry 42334 }


    iquav10Logging2VideoRefLogInp3Ident OBJECT-TYPE
        SYNTAX            INTEGER { disable(0), enable(1)  }
        MAX-ACCESS        read-write
        STATUS            current
        DESCRIPTION
                "CMNT: - Enable/Disable logging for Inp 3, Ident
                 TYPE: - Checkbox
                 PAGE: - Logging2
                    Log Inp3 Ident  cmdID= 42132  "
        ::= { iquav10CmdEntry 42132 }


    iquav10Logging2VideoRefInp3Ident OBJECT-TYPE
        SYNTAX            RollCallString
        MAX-ACCESS        read-only
        STATUS            current
        DESCRIPTION
                "CMNT: - Logging state for Inp 3 Ident
                 TYPE: - Display
                 PAGE: - Logging2
                    Inp3 Ident=  cmdID= 42332  "
        ::= { iquav10CmdEntry 42332 }


    iquav10Logging2VideoRefLogInp3Name OBJECT-TYPE
        SYNTAX            INTEGER { disable(0), enable(1)  }
        MAX-ACCESS        read-write
        STATUS            current
        DESCRIPTION
                "CMNT: - Enable/Disable logging for Inp 3, Name
                 TYPE: - Checkbox
                 PAGE: - Logging2
                    Log Inp3 Name  cmdID= 42135  "
        ::= { iquav10CmdEntry 42135 }


    iquav10Logging2VideoRefInp3Name OBJECT-TYPE
        SYNTAX            RollCallString
        MAX-ACCESS        read-only
        STATUS            current
        DESCRIPTION
                "CMNT: - Logging state for Inp 3 Name
                 TYPE: - Display
                 PAGE: - Logging2
                    Inp3 Name=  cmdID= 42335  "
        ::= { iquav10CmdEntry 42335 }


    iquav10Logging2VideoRefLogOutp2Type OBJECT-TYPE
        SYNTAX            INTEGER { disable(0), enable(1)  }
        MAX-ACCESS        read-write
        STATUS            current
        DESCRIPTION
                "CMNT: - Enable/Disable logging for Out 2, Type
                 TYPE: - Checkbox
                 PAGE: - Logging2
                    Log Outp2 Type  cmdID= 42620  "
        ::= { iquav10CmdEntry 42620 }


    iquav10Logging2VideoRefOutp2Type OBJECT-TYPE
        SYNTAX            RollCallString
        MAX-ACCESS        read-only
        STATUS            current
        DESCRIPTION
                "CMNT: - Logging state for Out 2 Type
                 TYPE: - Display
                 PAGE: - Logging2
                    Outp2 Type=  cmdID= 42820  "
        ::= { iquav10CmdEntry 42820 }


    iquav10Logging2VideoRefLogOutp2 OBJECT-TYPE
        SYNTAX            INTEGER { disable(0), enable(1)  }
        MAX-ACCESS        read-write
        STATUS            current
        DESCRIPTION
                "CMNT: - Enable/Disable logging for Out 2
                 TYPE: - Checkbox
                 PAGE: - Logging2
                    Log Outp2  cmdID= 42622  "
        ::= { iquav10CmdEntry 42622 }


    iquav10Logging2VideoRefOutp2 OBJECT-TYPE
        SYNTAX            RollCallString
        MAX-ACCESS        read-only
        STATUS            current
        DESCRIPTION
                "CMNT: - Logging state for Out 2
                 TYPE: - Display
                 PAGE: - Logging2
                    Outp2=  cmdID= 42822  "
        ::= { iquav10CmdEntry 42822 }


    iquav10Logging2VideoRefLogOutp2Capt OBJECT-TYPE
        SYNTAX            INTEGER { disable(0), enable(1)  }
        MAX-ACCESS        read-write
        STATUS            current
        DESCRIPTION
                "CMNT: - Enable/Disable logging for Out 2, Type
                 TYPE: - Checkbox
                 PAGE: - Logging2
                    Log Outp2 Capt  cmdID= 42624  "
        ::= { iquav10CmdEntry 42624 }


    iquav10Logging2VideoRefOutp2Capt OBJECT-TYPE
        SYNTAX            RollCallString
        MAX-ACCESS        read-only
        STATUS            current
        DESCRIPTION
                "CMNT: - Logging state for Out 2 Type
                 TYPE: - Display
                 PAGE: - Logging2
                    Outp2 Capt=  cmdID= 42824  "
        ::= { iquav10CmdEntry 42824 }


    iquav10Logging2InEmbAudLoggingInpEmb1state OBJECT-TYPE
        SYNTAX            RollCallString
        MAX-ACCESS        read-only
        STATUS            current
        DESCRIPTION
                "CMNT: - Logging state for Inp 1, Emb Pair 1 state
                 TYPE: - Display
                 PAGE: - Logging2
                    Inp Emb.1 state=  cmdID= 42200  "
        ::= { iquav10CmdEntry 42200 }


    iquav10Logging2InEmbAudLoggingInpEmb2state OBJECT-TYPE
        SYNTAX            RollCallString
        MAX-ACCESS        read-only
        STATUS            current
        DESCRIPTION
                "CMNT: - Logging state for Inp 1, Emb Pair 2 state
                 TYPE: - Display
                 PAGE: - Logging2
                    Inp Emb.2 state=  cmdID= 42201  "
        ::= { iquav10CmdEntry 42201 }


    iquav10Logging2InEmbAudLoggingInpEmb3state OBJECT-TYPE
        SYNTAX            RollCallString
        MAX-ACCESS        read-only
        STATUS            current
        DESCRIPTION
                "CMNT: - Logging state for Inp 1, Emb Pair 3 state
                 TYPE: - Display
                 PAGE: - Logging2
                    Inp Emb.3 state=  cmdID= 42202  "
        ::= { iquav10CmdEntry 42202 }


    iquav10Logging2InEmbAudLoggingInpEmb4state OBJECT-TYPE
        SYNTAX            RollCallString
        MAX-ACCESS        read-only
        STATUS            current
        DESCRIPTION
                "CMNT: - Logging state for Inp 1, Emb Pair 4 state
                 TYPE: - Display
                 PAGE: - Logging2
                    Inp Emb.4 state=  cmdID= 42203  "
        ::= { iquav10CmdEntry 42203 }


    iquav10Logging2InEmbAudLoggingInpEmb5state OBJECT-TYPE
        SYNTAX            RollCallString
        MAX-ACCESS        read-only
        STATUS            current
        DESCRIPTION
                "CMNT: - Logging state for Inp 1, Emb Pair 5 state
                 TYPE: - Display
                 PAGE: - Logging2
                    Inp Emb.5 state=  cmdID= 42204  "
        ::= { iquav10CmdEntry 42204 }


    iquav10Logging2InEmbAudLoggingInpEmb6state OBJECT-TYPE
        SYNTAX            RollCallString
        MAX-ACCESS        read-only
        STATUS            current
        DESCRIPTION
                "CMNT: - Logging state for Inp 1, Emb Pair 6 state
                 TYPE: - Display
                 PAGE: - Logging2
                    Inp Emb.6 state=  cmdID= 42205  "
        ::= { iquav10CmdEntry 42205 }


    iquav10Logging2InEmbAudLoggingInpEmb7state OBJECT-TYPE
        SYNTAX            RollCallString
        MAX-ACCESS        read-only
        STATUS            current
        DESCRIPTION
                "CMNT: - Logging state for Inp 1, Emb Pair 7 state
                 TYPE: - Display
                 PAGE: - Logging2
                    Inp Emb.7 state=  cmdID= 42206  "
        ::= { iquav10CmdEntry 42206 }


    iquav10Logging2InEmbAudLoggingInpEmb8state OBJECT-TYPE
        SYNTAX            RollCallString
        MAX-ACCESS        read-only
        STATUS            current
        DESCRIPTION
                "CMNT: - Logging state for Inp 1, Emb Pair 8 state
                 TYPE: - Display
                 PAGE: - Logging2
                    Inp Emb.8 state=  cmdID= 42207  "
        ::= { iquav10CmdEntry 42207 }


    iquav10Logging2In1EmbAudLoggingLogInp1Emb1state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging2
                    Log Inp1 Emb.1 state  cmdID= 42139  "
        ::= { iquav10CmdEntry 42139 }


    iquav10Logging2In1EmbAudLoggingInp1Emb1state OBJECT-TYPE
        SYNTAX            RollCallString
        MAX-ACCESS        read-only
        STATUS            current
        DESCRIPTION
                "CMNT: - Logging state for Inp 1, Emb Pair 1 state
                 TYPE: - Display
                 PAGE: - Logging2
                    Inp1 Emb.1 state=  cmdID= 42339  "
        ::= { iquav10CmdEntry 42339 }


    iquav10Logging2In1EmbAudLoggingLogInp1Emb2state OBJECT-TYPE
        SYNTAX            INTEGER { disable(0), enable(1)  }
        MAX-ACCESS        read-write
        STATUS            current
        DESCRIPTION
                "CMNT: - Enable/Disable logging for Inp 1, Emb Pair 2 state
                 TYPE: - Checkbox
                 PAGE: - Logging2
                    Log Inp1 Emb.2 state  cmdID= 42140  "
        ::= { iquav10CmdEntry 42140 }


    iquav10Logging2In1EmbAudLoggingInp1Emb2state OBJECT-TYPE
        SYNTAX            RollCallString
        MAX-ACCESS        read-only
        STATUS            current
        DESCRIPTION
                "CMNT: - Logging state for Inp 1, Emb Pair 2 state
                 TYPE: - Display
                 PAGE: - Logging2
                    Inp1 Emb.2 state=  cmdID= 42340  "
        ::= { iquav10CmdEntry 42340 }


    iquav10Logging2In1EmbAudLoggingLogInp1Emb3state OBJECT-TYPE
        SYNTAX            INTEGER { disable(0), enable(1)  }
        MAX-ACCESS        read-write
        STATUS            current
        DESCRIPTION
                "CMNT: - Enable/Disable logging for Inp 1, Emb Pair 3 state
                 TYPE: - Checkbox
                 PAGE: - Logging2
                    Log Inp1 Emb.3 state  cmdID= 42141  "
        ::= { iquav10CmdEntry 42141 }


    iquav10Logging2In1EmbAudLoggingInp1Emb3state OBJECT-TYPE
        SYNTAX            RollCallString
        MAX-ACCESS        read-only
        STATUS            current
        DESCRIPTION
                "CMNT: - Logging state for Inp 1, Emb Pair 3 state
                 TYPE: - Display
                 PAGE: - Logging2
                    Inp1 Emb.3 state=  cmdID= 42341  "
        ::= { iquav10CmdEntry 42341 }


    iquav10Logging2In1EmbAudLoggingLogInp1Emb4state OBJECT-TYPE
        SYNTAX            INTEGER { disable(0), enable(1)  }
        MAX-ACCESS        read-write
        STATUS            current
        DESCRIPTION
                "CMNT: - Enable/Disable logging for Inp 1, Emb Pair 4 state
                 TYPE: - Checkbox
                 PAGE: - Logging2
                    Log Inp1 Emb.4 state  cmdID= 42142  "
        ::= { iquav10CmdEntry 42142 }


    iquav10Logging2In1EmbAudLoggingInp1Emb4state OBJECT-TYPE
        SYNTAX            RollCallString
        MAX-ACCESS        read-only
        STATUS            current
        DESCRIPTION
                "CMNT: - Logging state for Inp 1, Emb Pair 4 state
                 TYPE: - Display
                 PAGE: - Logging2
                    Inp1 Emb.4 state=  cmdID= 42342  "
        ::= { iquav10CmdEntry 42342 }


    iquav10Logging2In1EmbAudLoggingLogInp1Emb5state OBJECT-TYPE
        SYNTAX            INTEGER { disable(0), enable(1)  }
        MAX-ACCESS        read-write
        STATUS            current
        DESCRIPTION
                "CMNT: - Enable/Disable logging for Inp 1, Emb Pair 5 state
                 TYPE: - Checkbox
                 PAGE: - Logging2
                    Log Inp1 Emb.5 state  cmdID= 42143  "
        ::= { iquav10CmdEntry 42143 }


    iquav10Logging2In1EmbAudLoggingInp1Emb5state OBJECT-TYPE
        SYNTAX            RollCallString
        MAX-ACCESS        read-only
        STATUS            current
        DESCRIPTION
                "CMNT: - Logging state for Inp 1, Emb Pair 5 state
                 TYPE: - Display
                 PAGE: - Logging2
                    Inp1 Emb.5 state=  cmdID= 42343  "
        ::= { iquav10CmdEntry 42343 }


    iquav10Logging2In1EmbAudLoggingLogInp1Emb6state OBJECT-TYPE
        SYNTAX            INTEGER { disable(0), enable(1)  }
        MAX-ACCESS        read-write
        STATUS            current
        DESCRIPTION
                "CMNT: - Enable/Disable logging for Inp 1, Emb Pair 6 state
                 TYPE: - Checkbox
                 PAGE: - Logging2
                    Log Inp1 Emb.6 state  cmdID= 42144  "
        ::= { iquav10CmdEntry 42144 }


    iquav10Logging2In1EmbAudLoggingInp1Emb6state OBJECT-TYPE
        SYNTAX            RollCallString
        MAX-ACCESS        read-only
        STATUS            current
        DESCRIPTION
                "CMNT: - Logging state for Inp 1, Emb Pair 6 state
                 TYPE: - Display
                 PAGE: - Logging2
                    Inp1 Emb.6 state=  cmdID= 42344  "
        ::= { iquav10CmdEntry 42344 }


    iquav10Logging2In1EmbAudLoggingLogInp1Emb7state OBJECT-TYPE
        SYNTAX            INTEGER { disable(0), enable(1)  }
        MAX-ACCESS        read-write
        STATUS            current
        DESCRIPTION
                "CMNT: - Enable/Disable logging for Inp 1, Emb Pair 7 state
                 TYPE: - Checkbox
                 PAGE: - Logging2
                    Log Inp1 Emb.7 state  cmdID= 42145  "
        ::= { iquav10CmdEntry 42145 }


    iquav10Logging2In1EmbAudLoggingInp1Emb7state OBJECT-TYPE
        SYNTAX            RollCallString
        MAX-ACCESS        read-only
        STATUS            current
        DESCRIPTION
                "CMNT: - Logging state for Inp 1, Emb Pair 7 state
                 TYPE: - Display
                 PAGE: - Logging2
                    Inp1 Emb.7 state=  cmdID= 42345  "
        ::= { iquav10CmdEntry 42345 }


    iquav10Logging2In1EmbAudLoggingLogInp1Emb8state OBJECT-TYPE
        SYNTAX            INTEGER { disable(0), enable(1)  }
        MAX-ACCESS        read-write
        STATUS            current
        DESCRIPTION
                "CMNT: - Enable/Disable logging for Inp 1, Emb Pair 8 state
                 TYPE: - Checkbox
                 PAGE: - Logging2
                    Log Inp1 Emb.8 state  cmdID= 42146  "
        ::= { iquav10CmdEntry 42146 }


    iquav10Logging2In1EmbAudLoggingInp1Emb8state OBJECT-TYPE
        SYNTAX            RollCallString
        MAX-ACCESS        read-only
        STATUS            current
        DESCRIPTION
                "CMNT: - Logging state for Inp 1, Emb Pair 8 state
                 TYPE: - Display
                 PAGE: - Logging2
                    Inp1 Emb.8 state=  cmdID= 42346  "
        ::= { iquav10CmdEntry 42346 }


    iquav10Logging2In2EmbAudLoggingLogInp2Emb1state OBJECT-TYPE
        SYNTAX            INTEGER { disable(0), enable(1)  }
        MAX-ACCESS        read-write
        STATUS            current
        DESCRIPTION
                "CMNT: - Enable/Disable logging for Inp 2, Emb Pair 1 state
                 TYPE: - Checkbox
                 PAGE: - Logging2
                    Log Inp2 Emb.1 state  cmdID= 42147  "
        ::= { iquav10CmdEntry 42147 }


    iquav10Logging2In2EmbAudLoggingInp2Emb1state OBJECT-TYPE
        SYNTAX            RollCallString
        MAX-ACCESS        read-only
        STATUS            current
        DESCRIPTION
                "CMNT: - Logging state for Inp 2, Emb Pair 1 state
                 TYPE: - Display
                 PAGE: - Logging2
                    Inp2 Emb.1 state=  cmdID= 42347  "
        ::= { iquav10CmdEntry 42347 }


    iquav10Logging2In2EmbAudLoggingLogInp2Emb2state OBJECT-TYPE
        SYNTAX            INTEGER { disable(0), enable(1)  }
        MAX-ACCESS        read-write
        STATUS            current
        DESCRIPTION
                "CMNT: - Enable/Disable logging for Inp 2, Emb Pair 2 state
                 TYPE: - Checkbox
                 PAGE: - Logging2
                    Log Inp2 Emb.2 state  cmdID= 42148  "
        ::= { iquav10CmdEntry 42148 }


    iquav10Logging2In2EmbAudLoggingInp2Emb2state OBJECT-TYPE
        SYNTAX            RollCallString
        MAX-ACCESS        read-only
        STATUS            current
        DESCRIPTION
                "CMNT: - Logging state for Inp 2, Emb Pair 2 state
                 TYPE: - Display
                 PAGE: - Logging2
                    Inp2 Emb.2 state=  cmdID= 42348  "
        ::= { iquav10CmdEntry 42348 }


    iquav10Logging2In2EmbAudLoggingLogInp2Emb3state OBJECT-TYPE
        SYNTAX            INTEGER { disable(0), enable(1)  }
        MAX-ACCESS        read-write
        STATUS            current
        DESCRIPTION
                "CMNT: - Enable/Disable logging for Inp 2, Emb Pair 3 state
                 TYPE: - Checkbox
                 PAGE: - Logging2
                    Log Inp2 Emb.3 state  cmdID= 42149  "
        ::= { iquav10CmdEntry 42149 }


    iquav10Logging2In2EmbAudLoggingInp2Emb3state OBJECT-TYPE
        SYNTAX            RollCallString
        MAX-ACCESS        read-only
        STATUS            current
        DESCRIPTION
                "CMNT: - Logging state for Inp 2, Emb Pair 3 state
                 TYPE: - Display
                 PAGE: - Logging2
                    Inp2 Emb.3 state=  cmdID= 42349  "
        ::= { iquav10CmdEntry 42349 }


    iquav10Logging2In2EmbAudLoggingLogInp2Emb4state OBJECT-TYPE
        SYNTAX            INTEGER { disable(0), enable(1)  }
        MAX-ACCESS        read-write
        STATUS            current
        DESCRIPTION
                "CMNT: - Enable/Disable logging for Inp 2, Emb Pair 4 state
                 TYPE: - Checkbox
                 PAGE: - Logging2
                    Log Inp2 Emb.4 state  cmdID= 42150  "
        ::= { iquav10CmdEntry 42150 }


    iquav10Logging2In2EmbAudLoggingInp2Emb4state OBJECT-TYPE
        SYNTAX            RollCallString
        MAX-ACCESS        read-only
        STATUS            current
        DESCRIPTION
                "CMNT: - Logging state for Inp 2, Emb Pair 4 state
                 TYPE: - Display
                 PAGE: - Logging2
                    Inp2 Emb.4 state=  cmdID= 42350  "
        ::= { iquav10CmdEntry 42350 }


    iquav10Logging2In2EmbAudLoggingLogInp2Emb5state OBJECT-TYPE
        SYNTAX            INTEGER { disable(0), enable(1)  }
        MAX-ACCESS        read-write
        STATUS            current
        DESCRIPTION
                "CMNT: - Enable/Disable logging for Inp 2, Emb Pair 5 state
                 TYPE: - Checkbox
                 PAGE: - Logging2
                    Log Inp2 Emb.5 state  cmdID= 42151  "
        ::= { iquav10CmdEntry 42151 }


    iquav10Logging2In2EmbAudLoggingInp2Emb5state OBJECT-TYPE
        SYNTAX            RollCallString
        MAX-ACCESS        read-only
        STATUS            current
        DESCRIPTION
                "CMNT: - Logging state for Inp 2, Emb Pair 5 state
                 TYPE: - Display
                 PAGE: - Logging2
                    Inp2 Emb.5 state=  cmdID= 42351  "
        ::= { iquav10CmdEntry 42351 }


    iquav10Logging2In2EmbAudLoggingLogInp2Emb6state OBJECT-TYPE
        SYNTAX            INTEGER { disable(0), enable(1)  }
        MAX-ACCESS        read-write
        STATUS            current
        DESCRIPTION
                "CMNT: - Enable/Disable logging for Inp 2, Emb Pair 6 state
                 TYPE: - Checkbox
                 PAGE: - Logging2
                    Log Inp2 Emb.6 state  cmdID= 42152  "
        ::= { iquav10CmdEntry 42152 }


    iquav10Logging2In2EmbAudLoggingInp2Emb6state OBJECT-TYPE
        SYNTAX            RollCallString
        MAX-ACCESS        read-only
        STATUS            current
        DESCRIPTION
                "CMNT: - Logging state for Inp 2, Emb Pair 6 state
                 TYPE: - Display
                 PAGE: - Logging2
                    Inp2 Emb.6 state=  cmdID= 42352  "
        ::= { iquav10CmdEntry 42352 }


    iquav10Logging2In2EmbAudLoggingLogInp2Emb7state OBJECT-TYPE
        SYNTAX            INTEGER { disable(0), enable(1)  }
        MAX-ACCESS        read-write
        STATUS            current
        DESCRIPTION
                "CMNT: - Enable/Disable logging for Inp 2, Emb Pair 7 state
                 TYPE: - Checkbox
                 PAGE: - Logging2
                    Log Inp2 Emb.7 state  cmdID= 42153  "
        ::= { iquav10CmdEntry 42153 }


    iquav10Logging2In2EmbAudLoggingInp2Emb7state OBJECT-TYPE
        SYNTAX            RollCallString
        MAX-ACCESS        read-only
        STATUS            current
        DESCRIPTION
                "CMNT: - Logging state for Inp 2, Emb Pair 7 state
                 TYPE: - Display
                 PAGE: - Logging2
                    Inp2 Emb.7 state=  cmdID= 42353  "
        ::= { iquav10CmdEntry 42353 }


    iquav10Logging2In2EmbAudLoggingLogInp2Emb8state OBJECT-TYPE
        SYNTAX            INTEGER { disable(0), enable(1)  }
        MAX-ACCESS        read-write
        STATUS            current
        DESCRIPTION
                "CMNT: - Enable/Disable logging for Inp 2, Emb Pair 8 state
                 TYPE: - Checkbox
                 PAGE: - Logging2
                    Log Inp2 Emb.8 state  cmdID= 42154  "
        ::= { iquav10CmdEntry 42154 }


    iquav10Logging2In2EmbAudLoggingInp2Emb8state OBJECT-TYPE
        SYNTAX            RollCallString
        MAX-ACCESS        read-only
        STATUS            current
        DESCRIPTION
                "CMNT: - Logging state for Inp 2, Emb Pair 8 state
                 TYPE: - Display
                 PAGE: - Logging2
                    Inp2 Emb.8 state=  cmdID= 42354  "
        ::= { iquav10CmdEntry 42354 }


    iquav10Logging2DolbyEAlignLogOutEmb1dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.1 dolby  cmdID= 42160  "
        ::= { iquav10CmdEntry 42160 }


    iquav10Logging2DolbyEAlignOutEmb1Dolby OBJECT-TYPE
        SYNTAX            RollCallString
        MAX-ACCESS        read-only
        STATUS            current
        DESCRIPTION
                "CMNT: - Logging state for Outp 1, Emb Dolby
                 TYPE: - Display
                 PAGE: - Logging2
                    Out Emb.1 Dolby=  cmdID= 42360  "
        ::= { iquav10CmdEntry 42360 }


    iquav10Logging2DolbyEAlignLogOutEmb2dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.2 dolby  cmdID= 42161  "
        ::= { iquav10CmdEntry 42161 }


    iquav10Logging2DolbyEAlignOutEmb2Dolby OBJECT-TYPE
        SYNTAX            RollCallString
        MAX-ACCESS        read-only
        STATUS            current
        DESCRIPTION
                "CMNT: - Logging state for Outp 1, Emb Dolby
                 TYPE: - Display
                 PAGE: - Logging2
                    Out Emb.2 Dolby=  cmdID= 42361  "
        ::= { iquav10CmdEntry 42361 }


    iquav10Logging2DolbyEAlignLogOutEmb3dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.3 dolby  cmdID= 42162  "
        ::= { iquav10CmdEntry 42162 }


    iquav10Logging2DolbyEAlignOutEmb3Dolby OBJECT-TYPE
        SYNTAX            RollCallString
        MAX-ACCESS        read-only
        STATUS            current
        DESCRIPTION
                "CMNT: - Logging state for Outp 1, Emb Dolby
                 TYPE: - Display
                 PAGE: - Logging2
                    Out Emb.3 Dolby=  cmdID= 42362  "
        ::= { iquav10CmdEntry 42362 }


    iquav10Logging2DolbyEAlignLogOutEmb4dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.4 dolby  cmdID= 42163  "
        ::= { iquav10CmdEntry 42163 }


    iquav10Logging2DolbyEAlignOutEmb4Dolby OBJECT-TYPE
        SYNTAX            RollCallString
        MAX-ACCESS        read-only
        STATUS            current
        DESCRIPTION
                "CMNT: - Logging state for Outp 1, Emb Dolby
                 TYPE: - Display
                 PAGE: - Logging2
                    Out Emb.4 Dolby=  cmdID= 42363  "
        ::= { iquav10CmdEntry 42363 }


    iquav10Logging2DolbyEAlignLogOutEmb5dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.5 dolby  cmdID= 42164  "
        ::= { iquav10CmdEntry 42164 }


    iquav10Logging2DolbyEAlignOutEmb5Dolby OBJECT-TYPE
        SYNTAX            RollCallString
        MAX-ACCESS        read-only
        STATUS            current
        DESCRIPTION
                "CMNT: - Logging state for Outp 1, Emb Dolby
                 TYPE: - Display
                 PAGE: - Logging2
                    Out Emb.5 Dolby=  cmdID= 42364  "
        ::= { iquav10CmdEntry 42364 }


    iquav10Logging2DolbyEAlignLogOutEmb6dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.6 dolby  cmdID= 42165  "
        ::= { iquav10CmdEntry 42165 }


    iquav10Logging2DolbyEAlignOutEmb6Dolby OBJECT-TYPE
        SYNTAX            RollCallString
        MAX-ACCESS        read-only
        STATUS            current
        DESCRIPTION
                "CMNT: - Logging state for Outp 1, Emb Dolby
                 TYPE: - Display
                 PAGE: - Logging2
                    Out Emb.6 Dolby=  cmdID= 42365  "
        ::= { iquav10CmdEntry 42365 }


    iquav10Logging2DolbyEAlignLogOutEmb7dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.7 dolby  cmdID= 42166  "
        ::= { iquav10CmdEntry 42166 }


    iquav10Logging2DolbyEAlignOutEmb7Dolby OBJECT-TYPE
        SYNTAX            RollCallString
        MAX-ACCESS        read-only
        STATUS            current
        DESCRIPTION
                "CMNT: - Logging state for Outp 1, Emb Dolby
                 TYPE: - Display
                 PAGE: - Logging2
                    Out Emb.7 Dolby=  cmdID= 42366  "
        ::= { iquav10CmdEntry 42366 }


    iquav10Logging2DolbyEAlignLogOutEmb8dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.8 dolby  cmdID= 42167  "
        ::= { iquav10CmdEntry 42167 }


    iquav10Logging2DolbyEAlignOutEmb8Dolby OBJECT-TYPE
        SYNTAX            RollCallString
        MAX-ACCESS        read-only
        STATUS            current
        DESCRIPTION
                "CMNT: - Logging state for Outp 1, Emb Dolby
                 TYPE: - Display
                 PAGE: - Logging2
                    Out Emb.8 Dolby=  cmdID= 42367  "
        ::= { iquav10CmdEntry 42367 }


    iquav10Logging2MiscLoggingLogSerialNo OBJECT-TYPE
        SYNTAX            INTEGER { disable(0), enable(1)  }
        MAX-ACCESS        read-write
        STATUS            current
        DESCRIPTION
                "CMNT: - Enable/Disable logging for Serial No.
                 TYPE: - Checkbox
                 PAGE: - Logging2
                    Log Serial No.  cmdID= 35015  "
        ::= { iquav10CmdEntry 35015 }


    iquav10Logging2MiscLoggingSerialNo OBJECT-TYPE
        SYNTAX            RollCallString
        MAX-ACCESS        read-only
        STATUS            current
        DESCRIPTION
                "CMNT: - Logging state for Serial No.
                 TYPE: - Display
                 PAGE: - Logging2
                    Serial No.=  cmdID= 36015  "
        ::= { iquav10CmdEntry 36015 }


    iquav10Logging2MiscLoggingLogOSVersion OBJECT-TYPE
        SYNTAX            INTEGER { disable(0), enable(1)  }
        MAX-ACCESS        read-write
        STATUS            current
        DESCRIPTION
                "CMNT: - Enable/Disable logging for OS Version
                 TYPE: - Checkbox
                 PAGE: - Logging2
                    Log OS Version  cmdID= 35993  "
        ::= { iquav10CmdEntry 35993 }


    iquav10Logging2MiscLoggingOSVersion OBJECT-TYPE
        SYNTAX            RollCallString
        MAX-ACCESS        read-only
        STATUS            current
        DESCRIPTION
                "CMNT: - Logging state for OS Version
                 TYPE: - Display
                 PAGE: - Logging2
                    OS Version=  cmdID= 36993  "
        ::= { iquav10CmdEntry 36993 }


    iquav10Logging2MiscLoggingLogBuildNo OBJECT-TYPE
        SYNTAX            INTEGER { disable(0), enable(1)  }
        MAX-ACCESS        read-write
        STATUS            current
        DESCRIPTION
                "CMNT: - Enable/Disable logging for Build No.
                 TYPE: - Checkbox
                 PAGE: - Logging2
                    Log Build No.  cmdID= 35990  "
        ::= { iquav10CmdEntry 35990 }


    iquav10Logging2MiscLoggingBuildNo OBJECT-TYPE
        SYNTAX            RollCallString
        MAX-ACCESS        read-only
        STATUS            current
        DESCRIPTION
                "CMNT: - Logging state for Build No.
                 TYPE: - Display
                 PAGE: - Logging2
                    Build No.=  cmdID= 36990  "
        ::= { iquav10CmdEntry 36990 }


    iquav10Logging2MiscLoggingLogHardwareVer OBJECT-TYPE
        SYNTAX            INTEGER { disable(0), enable(1)  }
        MAX-ACCESS        read-write
        STATUS            current
        DESCRIPTION
                "CMNT: - Enable/Disable logging for Hardware Ver.
                 TYPE: - Checkbox
                 PAGE: - Logging2
                    Log Hardware Ver.  cmdID= 35992  "
        ::= { iquav10CmdEntry 35992 }


    iquav10Logging2MiscLoggingHardwareVer OBJECT-TYPE
        SYNTAX            RollCallString
        MAX-ACCESS        read-only
        STATUS            current
        DESCRIPTION
                "CMNT: - Logging state for Hardware Ver.
                 TYPE: - Display
                 PAGE: - Logging2
                    Hardware Ver.=  cmdID= 36992  "
        ::= { iquav10CmdEntry 36992 }


    iquav10Logging2MiscLoggingLogFirmwareVer OBJECT-TYPE
        SYNTAX            INTEGER { disable(0), enable(1)  }
        MAX-ACCESS        read-write
        STATUS            current
        DESCRIPTION
                "CMNT: - Enable/Disable logging for Firmware Ver.
                 TYPE: - Checkbox
                 PAGE: - Logging2
                    Log Firmware Ver.  cmdID= 35991  "
        ::= { iquav10CmdEntry 35991 }


    iquav10Logging2MiscLoggingFirmwareVer OBJECT-TYPE
        SYNTAX            RollCallString
        MAX-ACCESS        read-only
        STATUS            current
        DESCRIPTION
                "CMNT: - Logging state for Firmware Ver.
                 TYPE: - Display
                 PAGE: - Logging2
                    Firmware Ver.=  cmdID= 36991  "
        ::= { iquav10CmdEntry 36991 }


    iquav10Logging2MiscLoggingLogUpTime OBJECT-TYPE
        SYNTAX            INTEGER { disable(0), enable(1)  }
        MAX-ACCESS        read-write
        STATUS            current
        DESCRIPTION
                "CMNT: - Enable/Disable logging for Up Time
                 TYPE: - Checkbox
                 PAGE: - Logging2
                    Log Up Time  cmdID= 35994  "
        ::= { iquav10CmdEntry 35994 }


    iquav10Logging2MiscLoggingUpTime OBJECT-TYPE
        SYNTAX            RollCallString
        MAX-ACCESS        read-only
        STATUS            current
        DESCRIPTION
                "CMNT: - Logging state for Up Time
                 TYPE: - Display
                 PAGE: - Logging2
                    Up Time=  cmdID= 36994  "
        ::= { iquav10CmdEntry 36994 }


    iquav10Logging2MiscLoggingLogLicensedOpt OBJECT-TYPE
        SYNTAX            INTEGER { disable(0), enable(1)  }
        MAX-ACCESS        read-write
        STATUS            current
        DESCRIPTION
                "CMNT: - Enable/Disable logging for Display Licensed Options
                 TYPE: - Checkbox
                 PAGE: - Logging2
                    Log Licensed Opt.  cmdID= 35995  "
        ::= { iquav10CmdEntry 35995 }


    iquav10Logging2MiscLoggingLicensedOptions OBJECT-TYPE
        SYNTAX            RollCallString
        MAX-ACCESS        read-only
        STATUS            current
        DESCRIPTION
                "CMNT: - Logging Licened Options
                 TYPE: - Display
                 PAGE: - Logging2
                    Licensed Options   cmdID= 36995  "
        ::= { iquav10CmdEntry 36995 }


    iquav10Logging2MiscLoggingLogLicensedOpt2 OBJECT-TYPE
        SYNTAX            INTEGER { disable(0), enable(1)  }
        MAX-ACCESS        read-write
        STATUS            current
        DESCRIPTION
                "CMNT: - Enable/Disable logging for Display Licensed Options
                 TYPE: - Checkbox
                 PAGE: - Logging2
                    Log Licensed Opt2.  cmdID= 35996  "
        ::= { iquav10CmdEntry 35996 }


    iquav10Logging2MiscLoggingLicensedOptions2 OBJECT-TYPE
        SYNTAX            RollCallString
        MAX-ACCESS        read-only
        STATUS            current
        DESCRIPTION
                "CMNT: - Logging Licened Options
                 TYPE: - Display
                 PAGE: - Logging2
                    Licensed Options 2  cmdID= 36996  "
        ::= { iquav10CmdEntry 36996 }


    iquav10Logging2MiscLoggingLogTemp1State OBJECT-TYPE
        SYNTAX            INTEGER { disable(0), enable(1)  }
        MAX-ACCESS        read-write
        STATUS            current
        DESCRIPTION
                "CMNT: - Enable/Disable logging for TEMP 1 STATE
                 TYPE: - Checkbox
                 PAGE: - Logging2
                    Log Temp1State  cmdID= 42137  "
        ::= { iquav10CmdEntry 42137 }


    iquav10Logging2MiscLoggingTemp1State OBJECT-TYPE
        SYNTAX            RollCallString
        MAX-ACCESS        read-only
        STATUS            current
        DESCRIPTION
                "CMNT: - Logging state for TEMP_1_STATE
                 TYPE: - Display
                 PAGE: - Logging2
                    Temp1State=  cmdID= 42337  "
        ::= { iquav10CmdEntry 42337 }


    iquav10Logging2MiscLoggingLogTemp1Name OBJECT-TYPE
        SYNTAX            INTEGER { disable(0), enable(1)  }
        MAX-ACCESS        read-write
        STATUS            current
        DESCRIPTION
                "CMNT: - Enable/Disable logging for TEMP 1 NAME
                 TYPE: - Checkbox
                 PAGE: - Logging2
                    Log Temp1Name  cmdID= 42138  "
        ::= { iquav10CmdEntry 42138 }


    iquav10Logging2MiscLoggingTemp1Name OBJECT-TYPE
        SYNTAX            RollCallString
        MAX-ACCESS        read-only
        STATUS            current
        DESCRIPTION
                "CMNT: - Logging state for TEMP_1_NAME
                 TYPE: - Display
                 PAGE: - Logging2
                    Temp1Name=  cmdID= 42338  "
        ::= { iquav10CmdEntry 42338 }


    iquav10Logging2MiscLoggingLogRearId OBJECT-TYPE
        SYNTAX            INTEGER { disable(0), enable(1)  }
        MAX-ACCESS        read-write
        STATUS            current
        DESCRIPTION
                "CMNT: - Enable/Disable logging for Display Rear Id
                 TYPE: - Checkbox
                 PAGE: - Logging2
                    Log RearId  cmdID= 35997  "
        ::= { iquav10CmdEntry 35997 }


    iquav10Logging2MiscLoggingRearID OBJECT-TYPE
        SYNTAX            RollCallString
        MAX-ACCESS        read-only
        STATUS            current
        DESCRIPTION
                "CMNT: - Logging Rear ID
                 TYPE: - Display
                 PAGE: - Logging2
                    RearID=  cmdID= 36997  "
        ::= { iquav10CmdEntry 36997 }


    iquav10Logging2MiscLoggingLogSlotWidth OBJECT-TYPE
        SYNTAX            INTEGER { disable(0), enable(1)  }
        MAX-ACCESS        read-write
        STATUS            current
        DESCRIPTION
                "CMNT: - Enable/Disable logging for Display Slot Width
                 TYPE: - Checkbox
                 PAGE: - Logging2
                    Log Slot Width  cmdID= 35998  "
        ::= { iquav10CmdEntry 35998 }


    iquav10Logging2MiscLoggingSlotWidth OBJECT-TYPE
        SYNTAX            RollCallString
        MAX-ACCESS        read-only
        STATUS            current
        DESCRIPTION
                "CMNT: - Logging Slot width
                 TYPE: - Display
                 PAGE: - Logging2
                    SlotWidth=  cmdID= 36998  "
        ::= { iquav10CmdEntry 36998 }


    iquav10Logging2MiscLoggingLogSlotStart OBJECT-TYPE
        SYNTAX            INTEGER { disable(0), enable(1)  }
        MAX-ACCESS        read-write
        STATUS            current
        DESCRIPTION
                "CMNT: - Enable/Disable logging for Display Slot Start
                 TYPE: - Checkbox
                 PAGE: - Logging2
                    Log Slot Start  cmdID= 35999  "
        ::= { iquav10CmdEntry 35999 }


    iquav10Logging2MiscLoggingSlotStart OBJECT-TYPE
        SYNTAX            RollCallString
        MAX-ACCESS        read-only
        STATUS            current
        DESCRIPTION
                "CMNT: - Logging Slot start
                 TYPE: - Display
                 PAGE: - Logging2
                    SlotStart=  cmdID= 36999  "
        ::= { iquav10CmdEntry 36999 }


    iquav10Logging2MiscLoggingLogRearStatus OBJECT-TYPE
        SYNTAX            INTEGER { disable(0), enable(1)  }
        MAX-ACCESS        read-write
        STATUS            current
        DESCRIPTION
                "CMNT: - Enable/Disable logging for Display Rear Status
                 TYPE: - Checkbox
                 PAGE: - Logging2
                    Log RearStatus  cmdID= 36000  "
        ::= { iquav10CmdEntry 36000 }


    iquav10Logging2MiscLoggingRearSTATUS OBJECT-TYPE
        SYNTAX            RollCallString
        MAX-ACCESS        read-only
        STATUS            current
        DESCRIPTION
                "CMNT: - Logging Rear Status
                 TYPE: - Display
                 PAGE: - Logging2
                    RearSTATUS=  cmdID= 37000  "
        ::= { iquav10CmdEntry 37000 }


    iquav10RollCallMemoriesRollTrackDisableAll OBJECT-TYPE
        SYNTAX            INTEGER { disable(0), enable(1)  }
        MAX-ACCESS        read-write
        STATUS            current
        DESCRIPTION
                "CMNT: - Disable all rolltrack outputs
                 TYPE: - Checkbox
                 PAGE: - RollCall/Memories
                    Disable All  cmdID= 36104  "
        ::= { iquav10CmdEntry 36104 }


    iquav10RollCallMemoriesRollTrackIndex OBJECT-TYPE
        SYNTAX            INTEGER
        MAX-ACCESS        read-write
        STATUS            current
        DESCRIPTION
                "CMNT: - Select rolltrack to edit
                 TYPE: - BarGraph
                 PAGE: - RollCall/Memories
                    Index  cmdID= 36100
                    min= 1  max= 32  step= 1  format= %0.0f  div_scale= 1  preset= 1
                    Min = 1  Max = 32  Step = 1  Preset = 1  "
        ::= { iquav10CmdEntry 36100 }


    iquav10RollCallMemoriesRollTrackSource OBJECT-TYPE
        SYNTAX            INTEGER {
                            valUnused(-1),
                            valVideoDelay(0),
                            valInputPresent(2),
                            valInput1Present(3),
                            valInput2Present(4),
                            valAnalogPresent(5),
                            valInputLoss(6),
                            valInput1Loss(7),
                            valInput2Loss(8),
                            valAnalogLoss(9),
                            valInput1Select(10),
                            valInput2Select(11),
                            valAnalogSelect(12),
                            valInput108059p(13),
                            valInput108050p(14),
                            valInput108029i(15),
                            valInput108025i(16),
                            valInput72059p(17),
                            valInput72050p(18),
                            valInput52529i(19),
                            valInput62525i(20),
                            valOutputBlackOn(21),
                            valOutputBlackOff(22),
                            valOutputFreeze(23),
                            valOutputUnFreeze(24),
                            valOutputPatternOn(25),
                            valOutputPatternOff(26),
                            valOutputCaptionOn(27),
                            valOutputCaptionOff(28),
                            valReferenceOK(29),
                            valReferenceLoss(30),
                            valAES1PCM(31),
                            valAES1Data(32),
                            valAES1DolbyE(33),
                            valAES1Loss(34),
                            valAES2PCM(35),
                            valAES2Data(36),
                            valAES2DolbyE(37),
                            valAES2Loss(38),
                            valAES3PCM(39),
                            valAES3Data(40),
                            valAES3DolbyE(41),
                            valAES3Loss(42),
                            valAES4PCM(43),
                            valAES4Data(44),
                            valAES4DolbyE(45),
                            valAES4Loss(46),
                            valAES5PCM(47),
                            valAES5Data(48),
                            valAES5DolbyE(49),
                            valAES5Loss(50),
                            valAES6PCM(51),
                            valAES6Data(52),
                            valAES6DolbyE(53),
                            valAES6Loss(54),
                            valAES7PCM(55),
                            valAES7Data(56),
                            valAES7DolbyE(57),
                            valAES7Loss(58),
                            valAES8PCM(59),
                            valAES8Data(60),
                            valAES8DolbyE(61),
                            valAES8Loss(62),
                            valDisemb1PCM(63),
                            valDisemb1Data(64),
                            valDisemb1DolbyE(65),
                            valDisemb1Loss(66),
                            valDisemb2PCM(67),
                            valDisemb2Data(68),
                            valDisemb2DolbyE(69),
                            valDisemb2Loss(70),
                            valDisemb3PCM(71),
                            valDisemb3Data(72),
                            valDisemb3DolbyE(73),
                            valDisemb3Loss(74),
                            valDisemb4PCM(75),
                            valDisemb4Data(76),
                            valDisemb4DolbyE(77),
                            valDisemb4Loss(78),
                            valDisemb5PCM(79),
                            valDisemb5Data(80),
                            valDisemb5DolbyE(81),
                            valDisemb5Loss(82),
                            valDisemb6PCM(83),
                            valDisemb6Data(84),
                            valDisemb6DolbyE(85),
                            valDisemb6Loss(86),
                            valDisemb7PCM(87),
                            valDisemb7Data(88),
                            valDisemb7DolbyE(89),
                            valDisemb7Loss(90),
                            valDisemb8PCM(91),
                            valDisemb8Data(92),
                            valDisemb8DolbyE(93),
                            valDisemb8Loss(94),
                            valDecoderIPDolbyD(95),
                            valDecoderIPDolbyE(96),
                            valDecoderIPPCM(97),
                            valDecoderIPNoErr(98),
                            valDecoderIPError(99),
                            valExtMetaAbsent(100),
                            valExtMetaInvalid(101),
                            valExtMetaNoAC3(102),
                            valExtMetaNoBSI(103),
                            valExtMetaValid(104),
                            valVideoSyncOK(105),
                            valVideoSyncLoss(106),
                            valEncoderActive(107),
                            valEncoderStopped(108),
                            valEncoderPassthru(109)
                            }
        MAX-ACCESS        read-write
        STATUS            current
        DESCRIPTION
                "CMNT: - Source for Rolltrack
                 TYPE: - RadiobuttonList
                 PAGE: - RollCall/Memories
                    Source  cmdID= 36101
                    Unused  value= -1
                    Video Delay  value= 0
                    Input Present  value= 2
                    Input 1 Present  value= 3
                    Input 2 Present  value= 4
                    Analog Present  value= 5
                    Input Loss  value= 6
                    Input 1 Loss  value= 7
                    Input 2 Loss  value= 8
                    Analog Loss  value= 9
                    Input 1 Select  value= 10
                    Input 2 Select  value= 11
                    Analog Select  value= 12
                    Input 1080/59p  value= 13
                    Input 1080/50p  value= 14
                    Input 1080/29i  value= 15
                    Input 1080/25i  value= 16
                    Input 720/59p  value= 17
                    Input 720/50p  value= 18
                    Input 525/29i  value= 19
                    Input 625/25i  value= 20
                    Output Black On  value= 21
                    Output Black Off  value= 22
                    Output Freeze  value= 23
                    Output UnFreeze  value= 24
                    Output Pattern On  value= 25
                    Output Pattern Off  value= 26
                    Output Caption On  value= 27
                    Output Caption Off  value= 28
                    Reference OK  value= 29
                    Reference Loss  value= 30
                    AES 1 PCM  value= 31
                    AES 1 Data  value= 32
                    AES 1 DolbyE  value= 33
                    AES 1 Loss  value= 34
                    AES 2 PCM  value= 35
                    AES 2 Data  value= 36
                    AES 2 DolbyE  value= 37
                    AES 2 Loss  value= 38
                    AES 3 PCM  value= 39
                    AES 3 Data  value= 40
                    AES 3 DolbyE  value= 41
                    AES 3 Loss  value= 42
                    AES 4 PCM  value= 43
                    AES 4 Data  value= 44
                    AES 4 DolbyE  value= 45
                    AES 4 Loss  value= 46
                    AES 5 PCM  value= 47
                    AES 5 Data  value= 48
                    AES 5 DolbyE  value= 49
                    AES 5 Loss  value= 50
                    AES 6 PCM  value= 51
                    AES 6 Data  value= 52
                    AES 6 DolbyE  value= 53
                    AES 6 Loss  value= 54
                    AES 7 PCM  value= 55
                    AES 7 Data  value= 56
                    AES 7 DolbyE  value= 57
                    AES 7 Loss  value= 58
                    AES 8 PCM  value= 59
                    AES 8 Data  value= 60
                    AES 8 DolbyE  value= 61
                    AES 8 Loss  value= 62
                    Disemb 1 PCM  value= 63
                    Disemb 1 Data  value= 64
                    Disemb 1 DolbyE  value= 65
                    Disemb 1 Loss  value= 66
                    Disemb 2 PCM  value= 67
                    Disemb 2 Data  value= 68
                    Disemb 2 DolbyE  value= 69
                    Disemb 2 Loss  value= 70
                    Disemb 3 PCM  value= 71
                    Disemb 3 Data  value= 72
                    Disemb 3 DolbyE  value= 73
                    Disemb 3 Loss  value= 74
                    Disemb 4 PCM  value= 75
                    Disemb 4 Data  value= 76
                    Disemb 4 DolbyE  value= 77
                    Disemb 4 Loss  value= 78
                    Disemb 5 PCM  value= 79
                    Disemb 5 Data  value= 80
                    Disemb 5 DolbyE  value= 81
                    Disemb 5 Loss  value= 82
                    Disemb 6 PCM  value= 83
                    Disemb 6 Data  value= 84
                    Disemb 6 DolbyE  value= 85
                    Disemb 6 Loss  value= 86
                    Disemb 7 PCM  value= 87
                    Disemb 7 Data  value= 88
                    Disemb 7 DolbyE  value= 89
                    Disemb 7 Loss  value= 90
                    Disemb 8 PCM  value= 91
                    Disemb 8 Data  value= 92
                    Disemb 8 DolbyE  value= 93
                    Disemb 8 Loss  value= 94
                    Decoder I/P Dolby D  value= 95
                    Decoder I/P Dolby E  value= 96
                    Decoder I/P PCM  value= 97
                    Decoder I/P No Err  value= 98
                    Decoder I/P Error  value= 99
                    Ext Meta Absent  value= 100
                    Ext Meta Invalid  value= 101
                    Ext Meta No AC3  value= 102
                    Ext Meta No BSI  value= 103
                    Ext Meta Valid  value= 104
                    Video Sync OK  value= 105
                    Video Sync Loss  value= 106
                    Encoder Active  value= 107
                    Encoder Stopped  value= 108
                    Encoder Passthru  value= 109  "
        ::= { iquav10CmdEntry 36101 }


    iquav10RollCallMemoriesRollTrackAddress OBJECT-TYPE
        SYNTAX            RollCallString
        MAX-ACCESS        read-write
        STATUS            current
        DESCRIPTION
                "CMNT: - Unit address for Rolltrack message
                 TYPE: - Editstring
                 PAGE: - RollCall/Memories
                    Address  cmdID= 36102
                    preset= 0000:00:00*0"
        ::= { iquav10CmdEntry 36102 }


    iquav10RollCallMemoriesRollTrackCommand OBJECT-TYPE
        SYNTAX            RollCallString
        MAX-ACCESS        read-write
        STATUS            current
        DESCRIPTION
                "CMNT: - Command to send for Rolltrack message
                 TYPE: - Editstring
                 PAGE: - RollCall/Memories
                    Command  cmdID= 36103
                    preset= 000:000\0"
        ::= { iquav10CmdEntry 36103 }


    iquav10RollCallMemoriesRollTrackStatus OBJECT-TYPE
        SYNTAX            RollCallString
        MAX-ACCESS        read-only
        STATUS            current
        DESCRIPTION
                "CMNT: - Rolltrack status
                 TYPE: - Display
                 PAGE: - RollCall/Memories
                    Status  cmdID= 36105  "
        ::= { iquav10CmdEntry 36105 }


    iquav10RollCallMemoriesRollTrackSending OBJECT-TYPE
        SYNTAX            RollCallString
        MAX-ACCESS        read-only
        STATUS            current
        DESCRIPTION
                "CMNT: - Rolltrack sending status: true/false
                 TYPE: - Display
                 PAGE: - RollCall/Memories
                    Sending  cmdID= 36106  "
        ::= { iquav10CmdEntry 36106 }


    iquav10RollCallMemoriesHideGpio OBJECT-TYPE
        SYNTAX            INTEGER
        MAX-ACCESS        read-write
        STATUS            current
        DESCRIPTION
                "CMNT: - 
                 TYPE: - Number
                 PAGE: - RollCall/Memories
                    HideGpio  cmdID= 54
                    min= 0  max= 1  step= 1  format= %d  div_scale= 1  preset= 0
                    Min = 0  Max = 0  Step = 0  Preset = 0  "
        ::= { iquav10CmdEntry 54 }


    iquav10RollCallMemoriesHideInpAES14 OBJECT-TYPE
        SYNTAX            INTEGER
        MAX-ACCESS        read-write
        STATUS            current
        DESCRIPTION
                "CMNT: - 
                 TYPE: - Number
                 PAGE: - RollCall/Memories
                    HideInpAES1_4  cmdID= 56
                    min= 0  max= 1  step= 1  format= %d  div_scale= 1  preset= 0
                    Min = 0  Max = 0  Step = 0  Preset = 0  "
        ::= { iquav10CmdEntry 56 }


    iquav10RollCallMemoriesHideInpAES18 OBJECT-TYPE
        SYNTAX            INTEGER
        MAX-ACCESS        read-write
        STATUS            current
        DESCRIPTION
                "CMNT: - 
                 TYPE: - Number
                 PAGE: - RollCall/Memories
                    HideInpAES1_8  cmdID= 57
                    min= 0  max= 1  step= 1  format= %d  div_scale= 1  preset= 0
                    Min = 0  Max = 0  Step = 0  Preset = 0  "
        ::= { iquav10CmdEntry 57 }


    iquav10RollCallMemoriesHideInpLogAES14 OBJECT-TYPE
        SYNTAX            INTEGER
        MAX-ACCESS        read-write
        STATUS            current
        DESCRIPTION
                "CMNT: - 
                 TYPE: - Number
                 PAGE: - RollCall/Memories
                    HideInpLogAES1_4  cmdID= 55
                    min= 0  max= 1  step= 1  format= %d  div_scale= 1  preset= 0
                    Min = 0  Max = 0  Step = 0  Preset = 0  "
        ::= { iquav10CmdEntry 55 }


    iquav10RollCallMemoriesHideInpLogAES18 OBJECT-TYPE
        SYNTAX            INTEGER
        MAX-ACCESS        read-write
        STATUS            current
        DESCRIPTION
                "CMNT: - 
                 TYPE: - Number
                 PAGE: - RollCall/Memories
                    HideInpLogAES1_8  cmdID= 61
                    min= 0  max= 1  step= 1  format= %d  div_scale= 1  preset= 0
                    Min = 0  Max = 0  Step = 0  Preset = 0  "
        ::= { iquav10CmdEntry 61 }


    iquav10RollCallMemoriesHideOutAES14 OBJECT-TYPE
        SYNTAX            INTEGER
        MAX-ACCESS        read-write
        STATUS            current
        DESCRIPTION
                "CMNT: - 
                 TYPE: - Number
                 PAGE: - RollCall/Memories
                    HideOutAES1_4  cmdID= 58
                    min= 0  max= 1  step= 1  format= %d  div_scale= 1  preset= 0
                    Min = 0  Max = 0  Step = 0  Preset = 0  "
        ::= { iquav10CmdEntry 58 }


    iquav10RollCallMemoriesHideOutAES18 OBJECT-TYPE
        SYNTAX            INTEGER
        MAX-ACCESS        read-write
        STATUS            current
        DESCRIPTION
                "CMNT: - 
                 TYPE: - Number
                 PAGE: - RollCall/Memories
                    HideOutAES1_8  cmdID= 59
                    min= 0  max= 1  step= 1  format= %d  div_scale= 1  preset= 0
                    Min = 0  Max = 0  Step = 0  Preset = 0  "
        ::= { iquav10CmdEntry 59 }


    iquav10RollCallMemoriesHideOutLogAES14 OBJECT-TYPE
        SYNTAX            INTEGER
        MAX-ACCESS        read-write
        STATUS            current
        DESCRIPTION
                "CMNT: - 
                 TYPE: - Number
                 PAGE: - RollCall/Memories
                    HideOutLogAES1_4  cmdID= 60
                    min= 0  max= 1  step= 1  format= %d  div_scale= 1  preset= 0
                    Min = 0  Max = 0  Step = 0  Preset = 0  "
        ::= { iquav10CmdEntry 60 }


    iquav10RollCallMemoriesHideOutLogAES18 OBJECT-TYPE
        SYNTAX            INTEGER
        MAX-ACCESS        read-write
        STATUS            current
        DESCRIPTION
                "CMNT: - 
                 TYPE: - Number
                 PAGE: - RollCall/Memories
                    HideOutLogAES1_8  cmdID= 62
                    min= 0  max= 1  step= 1  format= %d  div_scale= 1  preset= 0
                    Min = 0  Max = 0  Step = 0  Preset = 0  "
        ::= { iquav10CmdEntry 62 }


    iquav10GPIOGPI1GPIO1Mode OBJECT-TYPE
        SYNTAX            INTEGER {
                            valUnused(0),
                            valInputGPI1(1),
                            valOutputGPO1(2)
                            }
        MAX-ACCESS        read-write
        STATUS            current
        DESCRIPTION
                "CMNT: - GPIO-1 Input/Output
                 TYPE: - RadiobuttonList
                 PAGE: - GPIO
                    GPI/O 1 Mode  cmdID= 36120
                    Unused  value= 0
                    Input (GPI1)  value= 1
                    Output (GPO1)  value= 2  "
        ::= { iquav10CmdEntry 36120 }


    iquav10GPIOGPI1GPI1IPHighSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Input High action
                 TYPE: - RadiobuttonList
                 PAGE: - GPIO
                    GPI 1 I/P High Select  cmdID= 36121
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iquav10CmdEntry 36121 }


    iquav10GPIOGPI1GPI1IPLowSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Input Low action
                 TYPE: - RadiobuttonList
                 PAGE: - GPIO
                    GPI 1 I/P Low Select  cmdID= 36125
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iquav10CmdEntry 36125 }


    iquav10GPIOGPI1GPO1OPSelect OBJECT-TYPE
        SYNTAX            INTEGER {
                            valUnused(-1),
                            valInputOK(0),
                            valInput1OK(50),
                            valInput2OK(51),
                            valAnalogInputOK(52),
                            valInput1Selected(53),
                            valInput2Selected(54),
                            valAnalogIPSelected(55),
                            valBlack(56),
                            valFreeze(57),
                            valPattern(58),
                            valNoUserMemSeld(99),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valNoDispMemSeld(60),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Output action
                 TYPE: - RadiobuttonList
                 PAGE: - GPIO
                    GPO 1 O/P Select  cmdID= 36122
                    Unused  value= -1
                    Input OK  value= 0
                    Input 1 OK  value= 50
                    Input 2 OK  value= 51
                    Analog Input OK  value= 52
                    Input 1 Selected  value= 53
                    Input 2 Selected  value= 54
                    Analog I/P Selected  value= 55
                    Black  value= 56
                    Freeze  value= 57
                    Pattern  value= 58
                    No User Mem Sel'd  value= 99
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    No Disp Mem Sel'd  value= 60
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iquav10CmdEntry 36122 }


    iquav10GPIOGPI1InvertGPIO1 OBJECT-TYPE
        SYNTAX            INTEGER { disable(0), enable(1)  }
        MAX-ACCESS        read-write
        STATUS            current
        DESCRIPTION
                "CMNT: - GPI-1 Port Invert
                 TYPE: - Checkbox
                 PAGE: - GPIO
                    Invert GPIO 1  cmdID= 36123  "
        ::= { iquav10CmdEntry 36123 }


    iquav10GPIOGPI1Status OBJECT-TYPE
        SYNTAX            RollCallString
        MAX-ACCESS        read-only
        STATUS            current
        DESCRIPTION
                "CMNT: - GPIO-1 Status
                 TYPE: - Display
                 PAGE: - GPIO
                    Status  cmdID= 36134  "
        ::= { iquav10CmdEntry 36134 }


    iquav10GPIOGPI2GPIO2Mode OBJECT-TYPE
        SYNTAX            INTEGER {
                            valUnused(0),
                            valInputGPI2(1),
                            valOutputGPO2(2)
                            }
        MAX-ACCESS        read-write
        STATUS            current
        DESCRIPTION
                "CMNT: - GPIO-2 Input/Output
                 TYPE: - RadiobuttonList
                 PAGE: - GPIO
                    GPI/O 2 Mode  cmdID= 36130
                    Unused  value= 0
                    Input (GPI2)  value= 1
                    Output (GPO2)  value= 2  "
        ::= { iquav10CmdEntry 36130 }


    iquav10GPIOGPI2GPI2IPHighSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Input High action
                 TYPE: - RadiobuttonList
                 PAGE: - GPIO
                    GPI 2 I/P High Select  cmdID= 36131
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iquav10CmdEntry 36131 }


    iquav10GPIOGPI2GPI2IPLowSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Input Low action
                 TYPE: - RadiobuttonList
                 PAGE: - GPIO
                    GPI 2 I/P Low Select  cmdID= 36137
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iquav10CmdEntry 36137 }


    iquav10GPIOGPI2GPO2OPSelect OBJECT-TYPE
        SYNTAX            INTEGER {
                            valUnused(-1),
                            valInputOK(0),
                            valInput1OK(50),
                            valInput2OK(51),
                            valAnalogInputOK(52),
                            valInput1Selected(53),
                            valInput2Selected(54),
                            valAnalogIPSelected(55),
                            valBlack(56),
                            valFreeze(57),
                            valPattern(58),
                            valNoUserMemSeld(99),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valNoDispMemSeld(60),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Output action
                 TYPE: - RadiobuttonList
                 PAGE: - GPIO
                    GPO 2 O/P Select  cmdID= 36132
                    Unused  value= -1
                    Input OK  value= 0
                    Input 1 OK  value= 50
                    Input 2 OK  value= 51
                    Analog Input OK  value= 52
                    Input 1 Selected  value= 53
                    Input 2 Selected  value= 54
                    Analog I/P Selected  value= 55
                    Black  value= 56
                    Freeze  value= 57
                    Pattern  value= 58
                    No User Mem Sel'd  value= 99
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    No Disp Mem Sel'd  value= 60
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iquav10CmdEntry 36132 }


    iquav10GPIOGPI2InvertGPIO2 OBJECT-TYPE
        SYNTAX            INTEGER { disable(0), enable(1)  }
        MAX-ACCESS        read-write
        STATUS            current
        DESCRIPTION
                "CMNT: - GPI-2 Port Invert
                 TYPE: - Checkbox
                 PAGE: - GPIO
                    Invert GPIO 2  cmdID= 36133  "
        ::= { iquav10CmdEntry 36133 }


    iquav10GPIOGPI2Status OBJECT-TYPE
        SYNTAX            RollCallString
        MAX-ACCESS        read-only
        STATUS            current
        DESCRIPTION
                "CMNT: - GPIO-2 Status
                 TYPE: - Display
                 PAGE: - GPIO
                    Status  cmdID= 36135  "
        ::= { iquav10CmdEntry 36135 }


    iquav10SetupDisplay OBJECT-TYPE
        SYNTAX            INTEGER {
                            valVideoStatus(0),
                            valAudioStatus(1),
                            valDolbyStatus(2),
                            valRefStatus(3),
                            valLedStatus(4),
                            valAncStatus(5),
                            valAfdStatus(6)
                            }
        MAX-ACCESS        read-write
        STATUS            current
        DESCRIPTION
                "CMNT: - Select Info display to show
                 TYPE: - RadiobuttonList
                 PAGE: - Setup
                    Display  cmdID= 32773
                    VideoStatus  value= 0
                    AudioStatus  value= 1
                    DolbyStatus  value= 2
                    RefStatus  value= 3
                    LedStatus  value= 4
                    AncStatus  value= 5
                    AfdStatus  value= 6  "
        ::= { iquav10CmdEntry 32773 }


    iquav10SetupProduct OBJECT-TYPE
        SYNTAX            RollCallString
        MAX-ACCESS        read-only
        STATUS            current
        DESCRIPTION
                "CMNT: - 
                 TYPE: - Display
                 PAGE: - Setup
                    Product  cmdID= 32771  "
        ::= { iquav10CmdEntry 32771 }


    iquav10SetupRelease OBJECT-TYPE
        SYNTAX            RollCallString
        MAX-ACCESS        read-only
        STATUS            current
        DESCRIPTION
                "CMNT: - Unit version number
                 TYPE: - Display
                 PAGE: - Setup
                    Release  cmdID= 2  "
        ::= { iquav10CmdEntry 2 }


    iquav10SetupBuild OBJECT-TYPE
        SYNTAX            RollCallString
        MAX-ACCESS        read-only
        STATUS            current
        DESCRIPTION
                "CMNT: - Unit build number
                 TYPE: - Display
                 PAGE: - Setup
                    Build  cmdID= 5  "
        ::= { iquav10CmdEntry 5 }


    iquav10SetupKOS OBJECT-TYPE
        SYNTAX            RollCallString
        MAX-ACCESS        read-only
        STATUS            current
        DESCRIPTION
                "CMNT: - 
                 TYPE: - Display
                 PAGE: - Setup
                    KOS  cmdID= 32772  "
        ::= { iquav10CmdEntry 32772 }


    iquav10SetupSerialNo OBJECT-TYPE
        SYNTAX            RollCallString
        MAX-ACCESS        read-only
        STATUS            current
        DESCRIPTION
                "CMNT: - Unit serial number
                 TYPE: - Display
                 PAGE: - Setup
                    Serial No.  cmdID= 1  "
        ::= { iquav10CmdEntry 1 }


    iquav10SetupFactoryDefault OBJECT-TYPE
        SYNTAX            INTEGER { noAction(0),valFactoryDefault(1) }
        MAX-ACCESS        read-write
        STATUS            current
        DESCRIPTION
                "CMNT: - Recall factory defaults
                 TYPE: - Button
                 PAGE: - Setup
                    Factory Default  cmdID= 37002
                    value= 1  "
        ::= { iquav10CmdEntry 37002 }


    iquav10SetupRestart OBJECT-TYPE
        SYNTAX            INTEGER { noAction(0),valRestart(1) }
        MAX-ACCESS        read-write
        STATUS            current
        DESCRIPTION
                "CMNT: - Restart unit
                 TYPE: - Button
                 PAGE: - Setup
                    Restart  cmdID= 4
                    value= 1  "
        ::= { iquav10CmdEntry 4 }


    iquav10SetupDefaultSettings OBJECT-TYPE
        SYNTAX            INTEGER { noAction(0),valDefaultSettings(1) }
        MAX-ACCESS        read-write
        STATUS            current
        DESCRIPTION
                "CMNT: - Recall factory defaults-KeepMemories
                 TYPE: - Button
                 PAGE: - Setup
                    Default Settings  cmdID= 37001
                    value= 1  "
        ::= { iquav10CmdEntry 37001 }


    iquav10SetupSerialNumber OBJECT-TYPE
        SYNTAX            RollCallString
        MAX-ACCESS        read-write
        STATUS            current
        DESCRIPTION
                "CMNT: - Edit serial number (On Factory Test Only)
                 TYPE: - Editstring
                 PAGE: - Setup
                    Serial Number  cmdID= 32774
                    preset= unknown"
        ::= { iquav10CmdEntry 32774 }


    iquav10SetupBoardID OBJECT-TYPE
        SYNTAX            INTEGER {
                            valIQUPC00(539),
                            valIQUPC01(540),
                            valIQDNC00(541),
                            valIQDNC01(549),
                            valIQDCC00(542),
                            valIQUDC10(543),
                            valIQUDC11(544),
                            valIQUCC00(548),
                            valIQUAV10(545),
                            valIQMUX33(546),
                            valIQDMX33(547),
                            valIQSYN33(551)
                            }
        MAX-ACCESS        read-write
        STATUS            current
        DESCRIPTION
                "CMNT: - Edit product type (On Factory Test Only)
                 TYPE: - RadiobuttonList
                 PAGE: - Setup
                    BoardID  cmdID= 32776
                    IQUPC00  value= 539
                    IQUPC01  value= 540
                    IQDNC00  value= 541
                    IQDNC01  value= 549
                    IQDCC00  value= 542
                    IQUDC10  value= 543
                    IQUDC11  value= 544
                    IQUCC00  value= 548
                    IQUAV10  value= 545
                    IQMUX33  value= 546
                    IQDMX33  value= 547
                    IQSYN33  value= 551  "
        ::= { iquav10CmdEntry 32776 }


    iquav10SetupSaveID OBJECT-TYPE
        SYNTAX            INTEGER { noAction(0),valSaveID(1) }
        MAX-ACCESS        read-write
        STATUS            current
        DESCRIPTION
                "CMNT: - Save serial number/board type (On Factory Test Only)
                 TYPE: - Button
                 PAGE: - Setup
                    Save ID  cmdID= 32775
                    value= 1  "
        ::= { iquav10CmdEntry 32775 }


    iquav10SetupFpgaBoardType OBJECT-TYPE
        SYNTAX            RollCallString
        MAX-ACCESS        read-only
        STATUS            current
        DESCRIPTION
                "CMNT: - FPGA board type
                 TYPE: - Display
                 PAGE: - Setup
                    Board Type  cmdID= 33152  "
        ::= { iquav10CmdEntry 33152 }


    iquav10SetupFpgaSerialNo OBJECT-TYPE
        SYNTAX            RollCallString
        MAX-ACCESS        read-only
        STATUS            current
        DESCRIPTION
                "CMNT: - FPGA serial number
                 TYPE: - Display
                 PAGE: - Setup
                    Fpga SerialNo  cmdID= 33156  "
        ::= { iquav10CmdEntry 33156 }


    iquav10SetupFpgaSoftVer OBJECT-TYPE
        SYNTAX            RollCallString
        MAX-ACCESS        read-only
        STATUS            current
        DESCRIPTION
                "CMNT: - FPGA version number
                 TYPE: - Display
                 PAGE: - Setup
                    Soft Ver  cmdID= 33150  "
        ::= { iquav10CmdEntry 33150 }


    iquav10SetupFpgaVer OBJECT-TYPE
        SYNTAX            RollCallString
        MAX-ACCESS        read-only
        STATUS            current
        DESCRIPTION
                "CMNT: - FPGA firmware version number
                 TYPE: - Display
                 PAGE: - Setup
                    Fpga Ver  cmdID= 33157  "
        ::= { iquav10CmdEntry 33157 }


    iquav10SetupFpgaTIVer OBJECT-TYPE
        SYNTAX            RollCallString
        MAX-ACCESS        read-only
        STATUS            current
        DESCRIPTION
                "CMNT: - FPGA TI version number
                 TYPE: - Display
                 PAGE: - Setup
                    TI Ver  cmdID= 33160  "
        ::= { iquav10CmdEntry 33160 }


    iquav10SetupFpgaDolbyModId OBJECT-TYPE
        SYNTAX            RollCallString
        MAX-ACCESS        read-only
        STATUS            current
        DESCRIPTION
                "CMNT: - FPGA Dolby Module Type
                 TYPE: - Display
                 PAGE: - Setup
                    Dolby Mod Id  cmdID= 33162  "
        ::= { iquav10CmdEntry 33162 }


    iquav10SetupFpgaProtVer OBJECT-TYPE
        SYNTAX            RollCallString
        MAX-ACCESS        read-only
        STATUS            current
        DESCRIPTION
                "CMNT: - FPGA protocol version
                 TYPE: - Display
                 PAGE: - Setup
                    Prot Ver  cmdID= 33151  "
        ::= { iquav10CmdEntry 33151 }


    iquav10SetupFpgaProgCRC OBJECT-TYPE
        SYNTAX            RollCallString
        MAX-ACCESS        read-only
        STATUS            current
        DESCRIPTION
                "CMNT: - FPGA code CRC
                 TYPE: - Display
                 PAGE: - Setup
                    Prog CRC  cmdID= 33155  "
        ::= { iquav10CmdEntry 33155 }


    iquav10SetupFpgaUptime OBJECT-TYPE
        SYNTAX            RollCallString
        MAX-ACCESS        read-only
        STATUS            current
        DESCRIPTION
                "CMNT: - FPGA Uptime
                 TYPE: - Display
                 PAGE: - Setup
                    Uptime  cmdID= 33163  "
        ::= { iquav10CmdEntry 33163 }


    iquav10SetupFpgaENGVXPVer OBJECT-TYPE
        SYNTAX            RollCallString
        MAX-ACCESS        read-only
        STATUS            current
        DESCRIPTION
                "CMNT: - FPGA VXP version number
                 TYPE: - Display
                 PAGE: - Setup
                    VXP Ver  cmdID= 33158  "
        ::= { iquav10CmdEntry 33158 }


    iquav10SetupFpgaENGSharcVer OBJECT-TYPE
        SYNTAX            RollCallString
        MAX-ACCESS        read-only
        STATUS            current
        DESCRIPTION
                "CMNT: - FPGA Sharc version number
                 TYPE: - Display
                 PAGE: - Setup
                    Sharc Ver  cmdID= 33159  "
        ::= { iquav10CmdEntry 33159 }


    iquav10SetupFpgaENGAlteraVer OBJECT-TYPE
        SYNTAX            RollCallString
        MAX-ACCESS        read-only
        STATUS            current
        DESCRIPTION
                "CMNT: - FPGA Altera version number
                 TYPE: - Display
                 PAGE: - Setup
                    Altera Ver  cmdID= 33161  "
        ::= { iquav10CmdEntry 33161 }


    iquav10SetupFpgaENGVCCint OBJECT-TYPE
        SYNTAX            RollCallString
        MAX-ACCESS        read-only
        STATUS            current
        DESCRIPTION
                "CMNT: - FPGA Internal Voltage
                 TYPE: - Display
                 PAGE: - Setup
                    VCCint  cmdID= 33164  "
        ::= { iquav10CmdEntry 33164 }


    iquav10SetupFpgaENGVCCaux OBJECT-TYPE
        SYNTAX            RollCallString
        MAX-ACCESS        read-only
        STATUS            current
        DESCRIPTION
                "CMNT: - FPGA Aux Voltage
                 TYPE: - Display
                 PAGE: - Setup
                    VCCaux  cmdID= 33165  "
        ::= { iquav10CmdEntry 33165 }


    iquav10SetupOptionsOption1 OBJECT-TYPE
        SYNTAX            RollCallString
        MAX-ACCESS        read-only
        STATUS            current
        DESCRIPTION
                "CMNT: - Upmix option
                 TYPE: - Display
                 PAGE: - Setup
                    Option1  cmdID= 33166  "
        ::= { iquav10CmdEntry 33166 }


    iquav10SetupOptionsOption2 OBJECT-TYPE
        SYNTAX            RollCallString
        MAX-ACCESS        read-only
        STATUS            current
        DESCRIPTION
                "CMNT: - Dolby Decode option
                 TYPE: - Display
                 PAGE: - Setup
                    Option2  cmdID= 33167  "
        ::= { iquav10CmdEntry 33167 }


    iquav10SetupOptionsOption3 OBJECT-TYPE
        SYNTAX            RollCallString
        MAX-ACCESS        read-only
        STATUS            current
        DESCRIPTION
                "CMNT: - Dolby Encode D option
                 TYPE: - Display
                 PAGE: - Setup
                    Option3  cmdID= 33168  "
        ::= { iquav10CmdEntry 33168 }


    iquav10SetupOptionsOption4 OBJECT-TYPE
        SYNTAX            RollCallString
        MAX-ACCESS        read-only
        STATUS            current
        DESCRIPTION
                "CMNT: - Dolby Encode E option
                 TYPE: - Display
                 PAGE: - Setup
                    Option4  cmdID= 33169  "
        ::= { iquav10CmdEntry 33169 }


    iquav10SetupOptionsOption5 OBJECT-TYPE
        SYNTAX            RollCallString
        MAX-ACCESS        read-only
        STATUS            current
        DESCRIPTION
                "CMNT: - Color corrector option
                 TYPE: - Display
                 PAGE: - Setup
                    Option5  cmdID= 33170  "
        ::= { iquav10CmdEntry 33170 }


    iquav10SetupOptionsOption6 OBJECT-TYPE
        SYNTAX            RollCallString
        MAX-ACCESS        read-only
        STATUS            current
        DESCRIPTION
                "CMNT: - Loudness 5.1 option
                 TYPE: - Display
                 PAGE: - Setup
                    Option6  cmdID= 33171  "
        ::= { iquav10CmdEntry 33171 }


    iquav10SetupOptionsOption7 OBJECT-TYPE
        SYNTAX            RollCallString
        MAX-ACCESS        read-only
        STATUS            current
        DESCRIPTION
                "CMNT: - Loudness 1x2.0 option
                 TYPE: - Display
                 PAGE: - Setup
                    Option7  cmdID= 33172  "
        ::= { iquav10CmdEntry 33172 }


    iquav10SetupOptionsOption8 OBJECT-TYPE
        SYNTAX            RollCallString
        MAX-ACCESS        read-only
        STATUS            current
        DESCRIPTION
                "CMNT: - Loudness 2x2.0 option
                 TYPE: - Display
                 PAGE: - Setup
                    Option8  cmdID= 33173  "
        ::= { iquav10CmdEntry 33173 }


    iquav10SetupOptionsOption9 OBJECT-TYPE
        SYNTAX            RollCallString
        MAX-ACCESS        read-only
        STATUS            current
        DESCRIPTION
                "CMNT: - 24 HOUR options
                 TYPE: - Display
                 PAGE: - Setup
                    Option9  cmdID= 33174  "
        ::= { iquav10CmdEntry 33174 }


    iquav10SetupOptionsMask OBJECT-TYPE
        SYNTAX            INTEGER
        MAX-ACCESS        read-write
        STATUS            current
        DESCRIPTION
                "CMNT: - Bit mask of current licence options
                 TYPE: - Number
                 PAGE: - Setup
                    OptionsMask  cmdID= 36147
                    min= 0  max= 65535  step= 1  format= %d  div_scale= 1  preset= 0
                    Min = 0  Max = 0  Step = 0  Preset = 0  "
        ::= { iquav10CmdEntry 36147 }


    iquav10SetupDemoNonDemoRestart OBJECT-TYPE
        SYNTAX            INTEGER { noAction(0),valNonDemoRestart(1) }
        MAX-ACCESS        read-write
        STATUS            current
        DESCRIPTION
                "CMNT: - hard restart, removes demo options
                 TYPE: - Button
                 PAGE: - Setup
                    NonDemoRestart  cmdID= 43092
                    value= 1  "
        ::= { iquav10CmdEntry 43092 }


    iquav10SetupDemoPeriod OBJECT-TYPE
        SYNTAX            INTEGER
        MAX-ACCESS        read-write
        STATUS            current
        DESCRIPTION
                "CMNT: - Factory configured total demo period,
                 TYPE: - Number
                 PAGE: - Setup
                    DemoPeriod  cmdID= 65
                    min= 0  max= 720  step= 1  format= %0.0f Hours  div_scale= 1  preset= 0
                    Min = 0 Hours  Max = 720 Hours  Step = 1 Hours  Preset = 0 Hours  "
        ::= { iquav10CmdEntry 65 }


    iquav10SetupDemoRestartMode OBJECT-TYPE
        SYNTAX            INTEGER { disable(0), enable(1)  }
        MAX-ACCESS        read-write
        STATUS            current
        DESCRIPTION
                "CMNT: - Restart mode demo/non-demo
                 TYPE: - Checkbox
                 PAGE: - Setup
                    RestartMode  cmdID= 43093  "
        ::= { iquav10CmdEntry 43093 }


    iquav10SetupDemoRemainingDemo OBJECT-TYPE
        SYNTAX            INTEGER
        MAX-ACCESS        read-write
        STATUS            current
        DESCRIPTION
                "CMNT: - demo remaining period,
                 TYPE: - Number
                 PAGE: - Setup
                    RemainingDemo  cmdID= 43091
                    min= 0  max= 50000  step= 1  format= %d  div_scale= 1  preset= 0
                    Min = 0  Max = 0  Step = 0  Preset = 0  "
        ::= { iquav10CmdEntry 43091 }


    iquav10SetupDemoRemaining24h OBJECT-TYPE
        SYNTAX            INTEGER
        MAX-ACCESS        read-write
        STATUS            current
        DESCRIPTION
                "CMNT: - demo remaining period before next restart
                 TYPE: - Number
                 PAGE: - Setup
                    Remaining24h  cmdID= 43094
                    min= 0  max= 1440  step= 1  format= %d  div_scale= 1  preset= 0
                    Min = 0  Max = 0  Step = 0  Preset = 0  "
        ::= { iquav10CmdEntry 43094 }


    iquav10SetupDemoStatus OBJECT-TYPE
        SYNTAX            INTEGER
        MAX-ACCESS        read-write
        STATUS            current
        DESCRIPTION
                "CMNT: - Factory configured total demo period Status
                 TYPE: - Number
                 PAGE: - Setup
                    DemoStatus  cmdID= 43101
                    min= 0  max= 1  step= 1  format= %0.0f  div_scale= 1  preset= 0
                    Min = 0  Max = 1  Step = 1  Preset = 0  "
        ::= { iquav10CmdEntry 43101 }


    iquav10SetupRestartHard OBJECT-TYPE
        SYNTAX            INTEGER { noAction(0),valRestartHard(1) }
        MAX-ACCESS        read-write
        STATUS            current
        DESCRIPTION
                "CMNT: - Restart unit
                 TYPE: - Button
                 PAGE: - Setup
                    Restart Hard  cmdID= 36138
                    value= 1  "
        ::= { iquav10CmdEntry 36138 }


    iquav10SetupInput1Name OBJECT-TYPE
        SYNTAX            RollCallString
        MAX-ACCESS        read-write
        STATUS            current
        DESCRIPTION
                "CMNT: - 
                 TYPE: - Editstring
                 PAGE: - Setup
                    Input 1 Name  cmdID= 9000
                    preset= INPUT 1 SERIAL IN"
        ::= { iquav10CmdEntry 9000 }


    iquav10SetupInput2Name OBJECT-TYPE
        SYNTAX            RollCallString
        MAX-ACCESS        read-write
        STATUS            current
        DESCRIPTION
                "CMNT: - 
                 TYPE: - Editstring
                 PAGE: - Setup
                    Input 2 Name  cmdID= 9001
                    preset= INPUT 2 SERIAL IN"
        ::= { iquav10CmdEntry 9001 }


    iquav10SetupInput3Name OBJECT-TYPE
        SYNTAX            RollCallString
        MAX-ACCESS        read-write
        STATUS            current
        DESCRIPTION
                "CMNT: - 
                 TYPE: - Editstring
                 PAGE: - Setup
                    Input 3 Name  cmdID= 9002
                    preset= INPUT 3 ANALOG IN"
        ::= { iquav10CmdEntry 9002 }


    iquav10SetupCalibrationVideoIn0 OBJECT-TYPE
        SYNTAX            INTEGER
        MAX-ACCESS        read-write
        STATUS            current
        DESCRIPTION
                "CMNT: - Analog cal video in 0
                 TYPE: - Number
                 PAGE: - Setup
                    VideoIn0  cmdID= 64
                    min= -128  max= 127  step= 1  format= %0.0f  div_scale= 1  preset= 0
                    Min = -128  Max = 127  Step = 1  Preset = 0  "
        ::= { iquav10CmdEntry 64 }


    iquav10SetupCalibrationVideoIn1 OBJECT-TYPE
        SYNTAX            INTEGER
        MAX-ACCESS        read-write
        STATUS            current
        DESCRIPTION
                "CMNT: - Analog cal video in 1
                 TYPE: - Number
                 PAGE: - Setup
                    VideoIn1  cmdID= 43051
                    min= -128  max= 127  step= 1  format= %0.0f  div_scale= 1  preset= 0
                    Min = -128  Max = 127  Step = 1  Preset = 0  "
        ::= { iquav10CmdEntry 43051 }


    iquav10SetupCalibrationVideoIn2 OBJECT-TYPE
        SYNTAX            INTEGER
        MAX-ACCESS        read-write
        STATUS            current
        DESCRIPTION
                "CMNT: - Analog cal video in 2
                 TYPE: - Number
                 PAGE: - Setup
                    VideoIn2  cmdID= 43052
                    min= -128  max= 127  step= 1  format= %0.0f  div_scale= 1  preset= 0
                    Min = -128  Max = 127  Step = 1  Preset = 0  "
        ::= { iquav10CmdEntry 43052 }


    iquav10SetupCalibrationVideoIn3 OBJECT-TYPE
        SYNTAX            INTEGER
        MAX-ACCESS        read-write
        STATUS            current
        DESCRIPTION
                "CMNT: - Analog cal video in 3
                 TYPE: - Number
                 PAGE: - Setup
                    VideoIn3  cmdID= 43053
                    min= -128  max= 127  step= 1  format= %0.0f  div_scale= 1  preset= 0
                    Min = -128  Max = 127  Step = 1  Preset = 0  "
        ::= { iquav10CmdEntry 43053 }


    iquav10SetupCalibrationVideoIn4 OBJECT-TYPE
        SYNTAX            INTEGER
        MAX-ACCESS        read-write
        STATUS            current
        DESCRIPTION
                "CMNT: - Analog cal video in 4
                 TYPE: - Number
                 PAGE: - Setup
                    VideoIn4  cmdID= 43054
                    min= -128  max= 127  step= 1  format= %0.0f  div_scale= 1  preset= 0
                    Min = -128  Max = 127  Step = 1  Preset = 0  "
        ::= { iquav10CmdEntry 43054 }


    iquav10SetupCalibrationVideoIn5 OBJECT-TYPE
        SYNTAX            INTEGER
        MAX-ACCESS        read-write
        STATUS            current
        DESCRIPTION
                "CMNT: - Analog cal video in 5
                 TYPE: - Number
                 PAGE: - Setup
                    VideoIn5  cmdID= 43055
                    min= -128  max= 127  step= 1  format= %0.0f  div_scale= 1  preset= 0
                    Min = -128  Max = 127  Step = 1  Preset = 0  "
        ::= { iquav10CmdEntry 43055 }


    iquav10SetupCalibrationVideoIn6 OBJECT-TYPE
        SYNTAX            INTEGER
        MAX-ACCESS        read-write
        STATUS            current
        DESCRIPTION
                "CMNT: - Analog cal video in 6
                 TYPE: - Number
                 PAGE: - Setup
                    VideoIn6  cmdID= 43056
                    min= -128  max= 127  step= 1  format= %0.0f  div_scale= 1  preset= 0
                    Min = -128  Max = 127  Step = 1  Preset = 0  "
        ::= { iquav10CmdEntry 43056 }


    iquav10SetupCalibrationVideoIn7 OBJECT-TYPE
        SYNTAX            INTEGER
        MAX-ACCESS        read-write
        STATUS            current
        DESCRIPTION
                "CMNT: - Analog cal video in 7
                 TYPE: - Number
                 PAGE: - Setup
                    VideoIn7  cmdID= 43057
                    min= -128  max= 127  step= 1  format= %0.0f  div_scale= 1  preset= 0
                    Min = -128  Max = 127  Step = 1  Preset = 0  "
        ::= { iquav10CmdEntry 43057 }


    iquav10SetupCalibrationVideoIn20 OBJECT-TYPE
        SYNTAX            INTEGER
        MAX-ACCESS        read-write
        STATUS            current
        DESCRIPTION
                "CMNT: - Analog cal video in 20
                 TYPE: - Number
                 PAGE: - Setup
                    VideoIn20  cmdID= 43070
                    min= -128  max= 127  step= 1  format= %0.0f  div_scale= 1  preset= 0
                    Min = -128  Max = 127  Step = 1  Preset = 0  "
        ::= { iquav10CmdEntry 43070 }


    iquav10SetupCalibrationVideoIn21 OBJECT-TYPE
        SYNTAX            INTEGER
        MAX-ACCESS        read-write
        STATUS            current
        DESCRIPTION
                "CMNT: - Analog cal video in 21
                 TYPE: - Number
                 PAGE: - Setup
                    VideoIn21  cmdID= 43071
                    min= -128  max= 127  step= 1  format= %0.0f  div_scale= 1  preset= 0
                    Min = -128  Max = 127  Step = 1  Preset = 0  "
        ::= { iquav10CmdEntry 43071 }


    iquav10SetupCalibrationVideoIn22 OBJECT-TYPE
        SYNTAX            INTEGER
        MAX-ACCESS        read-write
        STATUS            current
        DESCRIPTION
                "CMNT: - Analog cal video in 22
                 TYPE: - Number
                 PAGE: - Setup
                    VideoIn22  cmdID= 43072
                    min= -128  max= 127  step= 1  format= %0.0f  div_scale= 1  preset= 0
                    Min = -128  Max = 127  Step = 1  Preset = 0  "
        ::= { iquav10CmdEntry 43072 }


    iquav10SetupCalibrationVideoIn23 OBJECT-TYPE
        SYNTAX            INTEGER
        MAX-ACCESS        read-write
        STATUS            current
        DESCRIPTION
                "CMNT: - Analog cal video in 23
                 TYPE: - Number
                 PAGE: - Setup
                    VideoIn23  cmdID= 43073
                    min= -128  max= 127  step= 1  format= %0.0f  div_scale= 1  preset= 0
                    Min = -128  Max = 127  Step = 1  Preset = 0  "
        ::= { iquav10CmdEntry 43073 }


    iquav10SetupCalibrationVideoOut0 OBJECT-TYPE
        SYNTAX            INTEGER
        MAX-ACCESS        read-write
        STATUS            current
        DESCRIPTION
                "CMNT: - Analog cal video out 0
                 TYPE: - Number
                 PAGE: - Setup
                    VideoOut0  cmdID= 43074
                    min= -128  max= 127  step= 1  format= %0.0f  div_scale= 1  preset= 0
                    Min = -128  Max = 127  Step = 1  Preset = 0  "
        ::= { iquav10CmdEntry 43074 }


    iquav10SetupCalibrationVideoOut1 OBJECT-TYPE
        SYNTAX            INTEGER
        MAX-ACCESS        read-write
        STATUS            current
        DESCRIPTION
                "CMNT: - Analog cal video out 1
                 TYPE: - Number
                 PAGE: - Setup
                    VideoOut1  cmdID= 43075
                    min= -128  max= 127  step= 1  format= %0.0f  div_scale= 1  preset= 0
                    Min = -128  Max = 127  Step = 1  Preset = 0  "
        ::= { iquav10CmdEntry 43075 }


    iquav10SetupCalibrationVideoOut2 OBJECT-TYPE
        SYNTAX            INTEGER
        MAX-ACCESS        read-write
        STATUS            current
        DESCRIPTION
                "CMNT: - Analog cal video out 2
                 TYPE: - Number
                 PAGE: - Setup
                    VideoOut2  cmdID= 43076
                    min= -128  max= 127  step= 1  format= %0.0f  div_scale= 1  preset= 0
                    Min = -128  Max = 127  Step = 1  Preset = 0  "
        ::= { iquav10CmdEntry 43076 }


    iquav10SetupCalibrationVideoOut3 OBJECT-TYPE
        SYNTAX            INTEGER
        MAX-ACCESS        read-write
        STATUS            current
        DESCRIPTION
                "CMNT: - Analog cal video out 3
                 TYPE: - Number
                 PAGE: - Setup
                    VideoOut3  cmdID= 43077
                    min= -128  max= 127  step= 1  format= %0.0f  div_scale= 1  preset= 0
                    Min = -128  Max = 127  Step = 1  Preset = 0  "
        ::= { iquav10CmdEntry 43077 }


    iquav10SetupCalibrationVideoOut4 OBJECT-TYPE
        SYNTAX            INTEGER
        MAX-ACCESS        read-write
        STATUS            current
        DESCRIPTION
                "CMNT: - Analog cal video out 4
                 TYPE: - Number
                 PAGE: - Setup
                    VideoOut4  cmdID= 43078
                    min= -128  max= 127  step= 1  format= %0.0f  div_scale= 1  preset= 0
                    Min = -128  Max = 127  Step = 1  Preset = 0  "
        ::= { iquav10CmdEntry 43078 }


    iquav10SetupCalibrationVideoOut5 OBJECT-TYPE
        SYNTAX            INTEGER
        MAX-ACCESS        read-write
        STATUS            current
        DESCRIPTION
                "CMNT: - Analog cal video out 5
                 TYPE: - Number
                 PAGE: - Setup
                    VideoOut5  cmdID= 43079
                    min= -128  max= 127  step= 1  format= %0.0f  div_scale= 1  preset= 0
                    Min = -128  Max = 127  Step = 1  Preset = 0  "
        ::= { iquav10CmdEntry 43079 }


    iquav10SetupCalibrationVideoOut6 OBJECT-TYPE
        SYNTAX            INTEGER
        MAX-ACCESS        read-write
        STATUS            current
        DESCRIPTION
                "CMNT: - Analog cal video out 6
                 TYPE: - Number
                 PAGE: - Setup
                    VideoOut6  cmdID= 43095
                    min= -128  max= 127  step= 1  format= %0.0f  div_scale= 1  preset= 0
                    Min = -128  Max = 127  Step = 1  Preset = 0  "
        ::= { iquav10CmdEntry 43095 }


    iquav10SetupCalibrationVideoOut7 OBJECT-TYPE
        SYNTAX            INTEGER
        MAX-ACCESS        read-write
        STATUS            current
        DESCRIPTION
                "CMNT: - Analog cal video out 7
                 TYPE: - Number
                 PAGE: - Setup
                    VideoOut7  cmdID= 43096
                    min= -128  max= 127  step= 1  format= %0.0f  div_scale= 1  preset= 0
                    Min = -128  Max = 127  Step = 1  Preset = 0  "
        ::= { iquav10CmdEntry 43096 }


    iquav10SetupCalibrationVideoOut8 OBJECT-TYPE
        SYNTAX            INTEGER
        MAX-ACCESS        read-write
        STATUS            current
        DESCRIPTION
                "CMNT: - Analog cal video out 8
                 TYPE: - Number
                 PAGE: - Setup
                    VideoOut8  cmdID= 43097
                    min= -128  max= 127  step= 1  format= %0.0f  div_scale= 1  preset= 0
                    Min = -128  Max = 127  Step = 1  Preset = 0  "
        ::= { iquav10CmdEntry 43097 }


    iquav10SetupCalibrationVideoOut9 OBJECT-TYPE
        SYNTAX            INTEGER
        MAX-ACCESS        read-write
        STATUS            current
        DESCRIPTION
                "CMNT: - Analog cal video out 9
                 TYPE: - Number
                 PAGE: - Setup
                    VideoOut9  cmdID= 43098
                    min= -128  max= 127  step= 1  format= %0.0f  div_scale= 1  preset= 0
                    Min = -128  Max = 127  Step = 1  Preset = 0  "
        ::= { iquav10CmdEntry 43098 }


    iquav10SetupCalibrationVideoOut10 OBJECT-TYPE
        SYNTAX            INTEGER
        MAX-ACCESS        read-write
        STATUS            current
        DESCRIPTION
                "CMNT: - Analog cal video out 10
                 TYPE: - Number
                 PAGE: - Setup
                    VideoOut10  cmdID= 43099
                    min= -128  max= 127  step= 1  format= %0.0f  div_scale= 1  preset= 0
                    Min = -128  Max = 127  Step = 1  Preset = 0  "
        ::= { iquav10CmdEntry 43099 }


    iquav10SetupCalibrationVideoOut11 OBJECT-TYPE
        SYNTAX            INTEGER
        MAX-ACCESS        read-write
        STATUS            current
        DESCRIPTION
                "CMNT: - Analog cal video out 11
                 TYPE: - Number
                 PAGE: - Setup
                    VideoOut11  cmdID= 43100
                    min= -128  max= 127  step= 1  format= %0.0f  div_scale= 1  preset= 0
                    Min = -128  Max = 127  Step = 1  Preset = 0  "
        ::= { iquav10CmdEntry 43100 }


    iquav10SetupCalibrationAudio0 OBJECT-TYPE
        SYNTAX            INTEGER
        MAX-ACCESS        read-write
        STATUS            current
        DESCRIPTION
                "CMNT: - Analog cal audio 0
                 TYPE: - Number
                 PAGE: - Setup
                    Audio0  cmdID= 43080
                    min= -128  max= 127  step= 1  format= %0.2f  div_scale= 100  preset= 0
                    Min = -1.28  Max = 1.27  Step = 0.01  Preset = 0.00  "
        ::= { iquav10CmdEntry 43080 }


    iquav10SetupCalibrationAudio1 OBJECT-TYPE
        SYNTAX            INTEGER
        MAX-ACCESS        read-write
        STATUS            current
        DESCRIPTION
                "CMNT: - Analog cal audio 1
                 TYPE: - Number
                 PAGE: - Setup
                    Audio1  cmdID= 43081
                    min= -128  max= 127  step= 1  format= %0.2f  div_scale= 100  preset= 0
                    Min = -1.28  Max = 1.27  Step = 0.01  Preset = 0.00  "
        ::= { iquav10CmdEntry 43081 }


    iquav10SetupCalibrationAudio2 OBJECT-TYPE
        SYNTAX            INTEGER
        MAX-ACCESS        read-write
        STATUS            current
        DESCRIPTION
                "CMNT: - Analog cal audio 2
                 TYPE: - Number
                 PAGE: - Setup
                    Audio2  cmdID= 43082
                    min= -128  max= 127  step= 1  format= %0.2f  div_scale= 100  preset= 0
                    Min = -1.28  Max = 1.27  Step = 0.01  Preset = 0.00  "
        ::= { iquav10CmdEntry 43082 }


    iquav10SetupCalibrationAudio3 OBJECT-TYPE
        SYNTAX            INTEGER
        MAX-ACCESS        read-write
        STATUS            current
        DESCRIPTION
                "CMNT: - Analog cal audio 3
                 TYPE: - Number
                 PAGE: - Setup
                    Audio3  cmdID= 43083
                    min= -128  max= 127  step= 1  format= %0.2f  div_scale= 100  preset= 0
                    Min = -1.28  Max = 1.27  Step = 0.01  Preset = 0.00  "
        ::= { iquav10CmdEntry 43083 }


    iquav10SetupCalibrationAudio4 OBJECT-TYPE
        SYNTAX            INTEGER
        MAX-ACCESS        read-write
        STATUS            current
        DESCRIPTION
                "CMNT: - Analog cal audio 4
                 TYPE: - Number
                 PAGE: - Setup
                    Audio4  cmdID= 43084
                    min= -128  max= 127  step= 1  format= %0.2f  div_scale= 100  preset= 0
                    Min = -1.28  Max = 1.27  Step = 0.01  Preset = 0.00  "
        ::= { iquav10CmdEntry 43084 }


    iquav10SetupCalibrationAudio5 OBJECT-TYPE
        SYNTAX            INTEGER
        MAX-ACCESS        read-write
        STATUS            current
        DESCRIPTION
                "CMNT: - Analog cal audio 5
                 TYPE: - Number
                 PAGE: - Setup
                    Audio5  cmdID= 43085
                    min= -128  max= 127  step= 1  format= %0.2f  div_scale= 100  preset= 0
                    Min = -1.28  Max = 1.27  Step = 0.01  Preset = 0.00  "
        ::= { iquav10CmdEntry 43085 }


    iquav10SetupCalibrationAudio6 OBJECT-TYPE
        SYNTAX            INTEGER
        MAX-ACCESS        read-write
        STATUS            current
        DESCRIPTION
                "CMNT: - Analog cal audio 6
                 TYPE: - Number
                 PAGE: - Setup
                    Audio6  cmdID= 43086
                    min= -128  max= 127  step= 1  format= %0.2f  div_scale= 100  preset= 0
                    Min = -1.28  Max = 1.27  Step = 0.01  Preset = 0.00  "
        ::= { iquav10CmdEntry 43086 }


    iquav10SetupCalibrationAudio7 OBJECT-TYPE
        SYNTAX            INTEGER
        MAX-ACCESS        read-write
        STATUS            current
        DESCRIPTION
                "CMNT: - Analog cal audio 7
                 TYPE: - Number
                 PAGE: - Setup
                    Audio7  cmdID= 43087
                    min= -128  max= 127  step= 1  format= %0.2f  div_scale= 100  preset= 0
                    Min = -1.28  Max = 1.27  Step = 0.01  Preset = 0.00  "
        ::= { iquav10CmdEntry 43087 }


    iquav10SetupCalibrationCalibrateTake OBJECT-TYPE
        SYNTAX            INTEGER { noAction(0),valCalibrateTake(1) }
        MAX-ACCESS        read-write
        STATUS            current
        DESCRIPTION
                "CMNT: - Analog take
                 TYPE: - Button
                 PAGE: - Setup
                    CalibrateTake  cmdID= 43088
                    value= 1  "
        ::= { iquav10CmdEntry 43088 }


    iquav10SetupCalibrationCalibratePreset OBJECT-TYPE
        SYNTAX            INTEGER { noAction(0),valCalibratePreset(1) }
        MAX-ACCESS        read-write
        STATUS            current
        DESCRIPTION
                "CMNT: - Analog preset
                 TYPE: - Button
                 PAGE: - Setup
                    CalibratePreset  cmdID= 43089
                    value= 1  "
        ::= { iquav10CmdEntry 43089 }


    iquav10SetupCalibrationCalibrateDefault OBJECT-TYPE
        SYNTAX            INTEGER { noAction(0),valCalibrateDefault(1) }
        MAX-ACCESS        read-write
        STATUS            current
        DESCRIPTION
                "CMNT: - Analog SET defaults
                 TYPE: - Button
                 PAGE: - Setup
                    CalibrateDefault  cmdID= 43102
                    value= 1  "
        ::= { iquav10CmdEntry 43102 }


    iquav10SetupCalibrationCalibrateFactory OBJECT-TYPE
        SYNTAX            INTEGER { noAction(0),valCalibrateFactory(1) }
        MAX-ACCESS        read-write
        STATUS            current
        DESCRIPTION
                "CMNT: - Analog SET FACTORY
                 TYPE: - Button
                 PAGE: - Setup
                    CalibrateFactory  cmdID= 43103
                    value= 1  "
        ::= { iquav10CmdEntry 43103 }


    iquav10SetupCalibrationCalUnlock OBJECT-TYPE
        SYNTAX            RollCallString
        MAX-ACCESS        read-write
        STATUS            current
        DESCRIPTION
                "CMNT: - Analog SET Unlock
                 TYPE: - Editstring
                 PAGE: - Setup
                    CalUnlock  cmdID= 43104
                    preset= UnlockString"
        ::= { iquav10CmdEntry 43104 }


    iquav10LKFS1SourceLSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43200
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iquav10CmdEntry 43200 }


    iquav10LKFS1SourceRSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43201
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iquav10CmdEntry 43201 }


    iquav10LKFS1SourceLSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43202
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iquav10CmdEntry 43202 }


    iquav10LKFS1SourceRSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43203
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iquav10CmdEntry 43203 }


    iquav10LKFS1SourceCSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43204
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iquav10CmdEntry 43204 }


    iquav10LKFS1ResetSession OBJECT-TYPE
        SYNTAX            INTEGER { noAction(0),valResetSession(1) }
        MAX-ACCESS        read-write
        STATUS            current
        DESCRIPTION
                "CMNT: - lkfs Process 1 sess reset
                 TYPE: - Button
                 PAGE: - LKFS1
                    ResetSession  cmdID= 43211
                    value= 1  "
        ::= { iquav10CmdEntry 43211 }


    iquav10LKFS1SessLevel OBJECT-TYPE
        SYNTAX            RollCallString
        MAX-ACCESS        read-only
        STATUS            current
        DESCRIPTION
                "CMNT: - lkfs Process 1 Sess LEVEL
                 TYPE: - Display
                 PAGE: - LKFS1
                    SessLevel  cmdID= 43217  "
        ::= { iquav10CmdEntry 43217 }


    iquav10LKFS1SessTime OBJECT-TYPE
        SYNTAX            RollCallString
        MAX-ACCESS        read-only
        STATUS            current
        DESCRIPTION
                "CMNT: - lkfs Process 1 Session Period
                 TYPE: - Display
                 PAGE: - LKFS1
                    SessTime  cmdID= 43225  "
        ::= { iquav10CmdEntry 43225 }


    iquav10LKFS1currrate OBJECT-TYPE
        SYNTAX            INTEGER
        MAX-ACCESS        read-write
        STATUS            current
        DESCRIPTION
                "CMNT: - lkfs Process 1 update rate
                 TYPE: - Number
                 PAGE: - LKFS1
                    curr rate  cmdID= 43213
                    min= 1  max= 63  step= 1  format= %0.0f  div_scale= 1  preset= 2
                    Min = 1  Max = 63  Step = 1  Preset = 2  "
        ::= { iquav10CmdEntry 43213 }


    iquav10LKFS1CurrLevelTime OBJECT-TYPE
        SYNTAX            RollCallString
        MAX-ACCESS        read-only
        STATUS            current
        DESCRIPTION
                "CMNT: - lkfs Process 1 LEVEL Update Timeout
                 TYPE: - Display
                 PAGE: - LKFS1
                    CurrLevelTime  cmdID= 43221  "
        ::= { iquav10CmdEntry 43221 }


    iquav10LKFS1CurrLevel OBJECT-TYPE
        SYNTAX            RollCallString
        MAX-ACCESS        read-only
        STATUS            current
        DESCRIPTION
                "CMNT: - lkfs Process 1 CUR LEVEL
                 TYPE: - Display
                 PAGE: - LKFS1
                    CurrLevel  cmdID= 43215  "
        ::= { iquav10CmdEntry 43215 }


    iquav10LKFS1CurrLevel2 OBJECT-TYPE
        SYNTAX            RollCallString
        MAX-ACCESS        read-only
        STATUS            current
        DESCRIPTION
                "CMNT: - lkfs Process 1 CUR LEVEL
                 TYPE: - Display
                 PAGE: - LKFS1
                    CurrLevel2  cmdID= 43226  "
        ::= { iquav10CmdEntry 43226 }


    iquav10LKFS1RollMapUpd OBJECT-TYPE
        SYNTAX            RollCallString
        MAX-ACCESS        read-only
        STATUS            current
        DESCRIPTION
                "CMNT: - Audio Loudness updates to rollmap
                 TYPE: - Display
                 PAGE: - LKFS1
                    RollMapUpd  cmdID= 38277  "
        ::= { iquav10CmdEntry 38277 }


    iquav10LKFS1UpdateRate OBJECT-TYPE
        SYNTAX            INTEGER {
                            valOn(1),
                            valOff(0)
                            }
        MAX-ACCESS        read-write
        STATUS            current
        DESCRIPTION
                "CMNT: - lkfs Process 1 LEVEL Update
                 TYPE: - RadiobuttonList
                 PAGE: - LKFS1
                    Update Rate  cmdID= 43219
                    On  value= 1
                    Off  value= 0  "
        ::= { iquav10CmdEntry 43219 }


    iquav10LKFS2SourceLSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43206
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iquav10CmdEntry 43206 }


    iquav10LKFS2SourceRSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43207
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iquav10CmdEntry 43207 }


    iquav10LKFS2SourceLSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43208
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iquav10CmdEntry 43208 }


    iquav10LKFS2SourceRSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43209
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iquav10CmdEntry 43209 }


    iquav10LKFS2SourceCSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43210
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iquav10CmdEntry 43210 }


    iquav10LKFS2SessLevel OBJECT-TYPE
        SYNTAX            RollCallString
        MAX-ACCESS        read-only
        STATUS            current
        DESCRIPTION
                "CMNT: - lkfs Process 2 Sess LEVEL
                 TYPE: - Display
                 PAGE: - LKFS2
                    SessLevel  cmdID= 43218  "
        ::= { iquav10CmdEntry 43218 }


    iquav10LKFS2CurrLevel OBJECT-TYPE
        SYNTAX            RollCallString
        MAX-ACCESS        read-only
        STATUS            current
        DESCRIPTION
                "CMNT: - lkfs Process 2 CUR LEVEL
                 TYPE: - Display
                 PAGE: - LKFS2
                    CurrLevel  cmdID= 43216  "
        ::= { iquav10CmdEntry 43216 }


    iquav10LKFS2CurrLevel2 OBJECT-TYPE
        SYNTAX            RollCallString
        MAX-ACCESS        read-only
        STATUS            current
        DESCRIPTION
                "CMNT: - lkfs Process 2 CUR LEVEL
                 TYPE: - Display
                 PAGE: - LKFS2
                    CurrLevel2  cmdID= 43227  "
        ::= { iquav10CmdEntry 43227 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: S40512345
-- Comments		: Serial number of unit
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 100:10:35:00
-- Comments		: Uptime in days/hours/mins
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
--
-- Value(s)		: 103
-- Comments		: ID of rear interface
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
--
-- Value(s)		: INPUT 1
--				: INPUT 2
--				: INPUT 3
-- Comments		:
--
---------------------------------------------------------------------------------------------------
-- Header		: OUTPUT_2
--
-- MIB ref		: swCardEventLogSlotXX       .8.79.85.84.80.85.84.95.50
-- absolute OID	: 1.3.6.1.4.1.7995.2.6.1.1.XX.8.79.85.84.80.85.84.95.50
--
-- Value(s)		: INPUT 1
--				: INPUT 2
--				: INPUT 3
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: V115 Release
-- Comments		: Operating system version
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
--
-- Value(s)		: 7
-- Comments		: First Slot position of rear
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
--
-- Value(s)		: 2
--				: 3
-- Comments		: Number of slots rear uses
--
---------------------------------------------------------------------------------------------------
-- Header		: INPUT_1_AFD
--
-- MIB ref		: swCardEventLogSlotXX       .11.73.78.80.85.84.95.49.95.65.70.68
-- absolute OID	: 1.3.6.1.4.1.7995.2.6.1.1.XX.11.73.78.80.85.84.95.49.95.65.70.68
--
-- Value(s)		: Reserved(0)
--				: Reserved(1)
--				: Box 16:9 top
--				: Box 14:9 top
--				: Box>16:9 ctr
--				: Reserved(5)
--				: Reserved(6)
--				: Reserved(7)
--				: Coded Frame
--				: 4:3 center
--				: 16:9 center
--				: 14:9 center
--				: Reserved(12)
--				: 4:3 SP 14:9
--				: 16:9 SP 14:9
--				: 16:9 SP 4:3
-- Comments		:
--
---------------------------------------------------------------------------------------------------
-- Header		: INPUT_2_AFD
--
-- MIB ref		: swCardEventLogSlotXX       .11.73.78.80.85.84.95.50.95.65.70.68
-- absolute OID	: 1.3.6.1.4.1.7995.2.6.1.1.XX.11.73.78.80.85.84.95.50.95.65.70.68
--
-- Value(s)		: Reserved(0)
--				: Reserved(1)
--				: Box 16:9 top
--				: Box 14:9 top
--				: Box>16:9 ctr
--				: Reserved(5)
--				: Reserved(6)
--				: Reserved(7)
--				: Coded Frame
--				: 4:3 center
--				: 16:9 center
--				: 14:9 center
--				: Reserved(12)
--				: 4:3 SP 14:9
--				: 16:9 SP 14:9
--				: 16:9 SP 4:3
-- Comments		:
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
--
-- Value(s)		: OK
--				: WARN:Type Mismatch
-- Comments		: Status of rear
--
---------------------------------------------------------------------------------------------------
-- Header		: TEMP_1_NAME
--
-- MIB ref		: swCardEventLogSlotXX       .11.84.69.77.80.95.49.95.78.65.77.69
-- absolute OID	: 1.3.6.1.4.1.7995.2.6.1.1.XX.11.84.69.77.80.95.49.95.78.65.77.69
--
-- Value(s)		: Temperature FPGA
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 0004304563
-- Comments		: Software Build Number
--
---------------------------------------------------------------------------------------------------
-- Header		: INPUT_1_2016
--
-- MIB ref		: swCardEventLogSlotXX       .12.73.78.80.85.84.95.49.95.50.48.49.54
-- absolute OID	: 1.3.6.1.4.1.7995.2.6.1.1.XX.12.73.78.80.85.84.95.49.95.50.48.49.54
--
-- Value(s)		: WARN:None
--				: OK:Present
--				: Disabled:Present
--				: Disabled:None
--				: Unknown
-- Comments		:
--
---------------------------------------------------------------------------------------------------
-- Header		: INPUT_1_NAME
--
-- MIB ref		: swCardEventLogSlotXX       .12.73.78.80.85.84.95.49.95.78.65.77.69
-- absolute OID	: 1.3.6.1.4.1.7995.2.6.1.1.XX.12.73.78.80.85.84.95.49.95.78.65.77.69
--
-- Value(s)		: INPUT 1 SERIAL IN
-- Comments		:
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD/SD/3G SDI
--				: HD/SD SDI
-- Comments		:
--
---------------------------------------------------------------------------------------------------
-- Header		: INPUT_2_2016
--
-- MIB ref		: swCardEventLogSlotXX       .12.73.78.80.85.84.95.50.95.50.48.49.54
-- absolute OID	: 1.3.6.1.4.1.7995.2.6.1.1.XX.12.73.78.80.85.84.95.50.95.50.48.49.54
--
-- Value(s)		: WARN:None
--				: OK:Present
--				: Disabled:Present
--				: Disabled:None
--				: Unknown
-- Comments		:
--
---------------------------------------------------------------------------------------------------
-- Header		: INPUT_2_NAME
--
-- MIB ref		: swCardEventLogSlotXX       .12.73.78.80.85.84.95.50.95.78.65.77.69
-- absolute OID	: 1.3.6.1.4.1.7995.2.6.1.1.XX.12.73.78.80.85.84.95.50.95.78.65.77.69
--
-- Value(s)		: INPUT 2 SERIAL IN
-- Comments		:
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
--
-- Value(s)		: HD/SD/3G SDI
--				: HD/SD SDI
-- Comments		:
--
---------------------------------------------------------------------------------------------------
-- Header		: INPUT_3_NAME
--
-- MIB ref		: swCardEventLogSlotXX       .12.73.78.80.85.84.95.51.95.78.65.77.69
-- absolute OID	: 1.3.6.1.4.1.7995.2.6.1.1.XX.12.73.78.80.85.84.95.51.95.78.65.77.69
--
-- Value(s)		: INPUT 3 ANALOG IN
-- Comments		:
--
---------------------------------------------------------------------------------------------------
-- Header		: INPUT_3_TYPE
--
-- MIB ref		: swCardEventLogSlotXX       .12.73.78.80.85.84.95.51.95.84.89.80.69
-- absolute OID	: 1.3.6.1.4.1.7995.2.6.1.1.XX.12.73.78.80.85.84.95.51.95.84.89.80.69
--
-- Value(s)		: HD / SD Analog
--				: SD Analog
-- Comments		:
--
---------------------------------------------------------------------------------------------------
-- Header		: OUTPUT_1_AFD
--
-- MIB ref		: swCardEventLogSlotXX       .12.79.85.84.80.85.84.95.49.95.65.70.68
-- absolute OID	: 1.3.6.1.4.1.7995.2.6.1.1.XX.12.79.85.84.80.85.84.95.49.95.65.70.68
--
-- Value(s)		: Reserved(0)
--				: Reserved(1)
--				: Box 16:9 top
--				: Box 14:9 top
--				: Box>16:9 ctr
--				: Reserved(5)
--				: Reserved(6)
--				: Reserved(7)
--				: Coded Frame
--				: 4:3 center
--				: 16:9 center
--				: 14:9 center
--				: Reserved(12)
--				: 4:3 SP 14:9
--				: 16:9 SP 14:9
--				: 16:9 SP 4:3
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: TEMP_1_STATE
--
-- MIB ref		: swCardEventLogSlotXX       .12.84.69.77.80.95.49.95.83.84.65.84.69
-- absolute OID	: 1.3.6.1.4.1.7995.2.6.1.1.XX.12.84.69.77.80.95.49.95.83.84.65.84.69
--
-- Value(s)		: OK
--				: Unknown
--				: WARN_High
--				: FAIL:Fan
-- Comments		:
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
--
-- Value(s)		: SER IN 1
-- Comments		: Text on Rear
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: OK
--				: WARN:Mismatch
--				: FAIL:Lost
-- Comments		:
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
--
-- Value(s)		: SER IN 2
-- Comments		:
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
--
-- Value(s)		: OK
--				: WARN:Mismatch
--				: FAIL:Lost
-- Comments		:
--
---------------------------------------------------------------------------------------------------
-- Header		: INPUT_3_IDENT
--
-- MIB ref		: swCardEventLogSlotXX       .13.73.78.80.85.84.95.51.95.73.68.69.78.84
-- absolute OID	: 1.3.6.1.4.1.7995.2.6.1.1.XX.13.73.78.80.85.84.95.51.95.73.68.69.78.84
--
-- Value(s)		: Y/C:YPbPr:COMP In
--				: COMP In
-- Comments		:
--
---------------------------------------------------------------------------------------------------
-- Header		: INPUT_3_STATE
--
-- MIB ref		: swCardEventLogSlotXX       .13.73.78.80.85.84.95.51.95.83.84.65.84.69
-- absolute OID	: 1.3.6.1.4.1.7995.2.6.1.1.XX.13.73.78.80.85.84.95.51.95.83.84.65.84.69
--
-- Value(s)		: OK
--				: WARN:Mismatch
--				: FAIL:Lost
-- Comments		:
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
--
-- Value(s)		: HD/SD SDI
--				: HD/SD/3G SDI
-- Comments		:
--
---------------------------------------------------------------------------------------------------
-- Header		: OUTPUT_2_TYPE
--
-- MIB ref		: swCardEventLogSlotXX       .13.79.85.84.80.85.84.95.50.95.84.89.80.69
-- absolute OID	: 1.3.6.1.4.1.7995.2.6.1.1.XX.13.79.85.84.80.85.84.95.50.95.84.89.80.69
--
-- Value(s)		: HD/SD SDI
--				: HD/SD/3G SDI
-- Comments		:
--
---------------------------------------------------------------------------------------------------
-- Header		: INPUT_1_ASPECT
--
-- MIB ref		: swCardEventLogSlotXX       .14.73.78.80.85.84.95.49.95.65.83.80.69.67.84
-- absolute OID	: 1.3.6.1.4.1.7995.2.6.1.1.XX.14.73.78.80.85.84.95.49.95.65.83.80.69.67.84
--
-- Value(s)		: Unknown
--				: 16:9
--				: 4/3
-- Comments		:
--
---------------------------------------------------------------------------------------------------
-- Header		: INPUT_2_ASPECT
--
-- MIB ref		: swCardEventLogSlotXX       .14.73.78.80.85.84.95.50.95.65.83.80.69.67.84
-- absolute OID	: 1.3.6.1.4.1.7995.2.6.1.1.XX.14.73.78.80.85.84.95.50.95.65.83.80.69.67.84
--
-- Value(s)		: Unknown
--				: 16:9
--				: 4/3
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
--
-- Value(s)		: OK
--				: WARN:Black
--				: WARN:Freeze
--				: WARN:Pattern
--				: WARN:Input
--				: WARN:Reclocked
--				: WARN:Disabled
-- Comments		:
--
---------------------------------------------------------------------------------------------------
-- Header		: OUTPUT_2_STATE
--
-- MIB ref		: swCardEventLogSlotXX       .14.79.85.84.80.85.84.95.50.95.83.84.65.84.69
-- absolute OID	: 1.3.6.1.4.1.7995.2.6.1.1.XX.14.79.85.84.80.85.84.95.50.95.83.84.65.84.69
--
-- Value(s)		: OK
--				: WARN:Black
--				: WARN:Freeze
--				: WARN:Pattern
--				: WARN:Input
--				: WARN:Reclocked
--				: WARN:Disabled
-- Comments		:
--
---------------------------------------------------------------------------------------------------
-- Header		: GENLOCK_1_STATE
--
-- MIB ref		: swCardEventLogSlotXX       .15.71.69.78.76.79.67.75.95.49.95.83.84.65.84.69
-- absolute OID	: 1.3.6.1.4.1.7995.2.6.1.1.XX.15.71.69.78.76.79.67.75.95.49.95.83.84.65.84.69
--
-- Value(s)		: WARN:Freerun
--				: OK:Reference
--				: OK:Input
-- Comments		: Internal genlock state
--
---------------------------------------------------------------------------------------------------
-- Header		: OUTPUT_1_ASPECT
--
-- MIB ref		: swCardEventLogSlotXX       .15.79.85.84.80.85.84.95.49.95.65.83.80.69.67.84
-- absolute OID	: 1.3.6.1.4.1.7995.2.6.1.1.XX.15.79.85.84.80.85.84.95.49.95.65.83.80.69.67.84
--
-- Value(s)		: Unknown
--				: 16:9
--				: 4/3
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: 520505115
-- Comments		: Fpga version number
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: RGMPP1C
-- Comments		:
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
--
-- Value(s)		: OK
--				: WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: LOST
--				: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
--
-- Value(s)		: OK
--				: WARN
-- Comments		:
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
--
-- Value(s)		: LOST
--				: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: INPUT_3_STANDARD
--
-- MIB ref		: swCardEventLogSlotXX       .16.73.78.80.85.84.95.51.95.83.84.65.78.68.65.82.68
-- absolute OID	: 1.3.6.1.4.1.7995.2.6.1.1.XX.16.73.78.80.85.84.95.51.95.83.84.65.78.68.65.82.68
--
-- Value(s)		: LOST
--				: 525/29i
--				: 625/25i
--				: 720/50p
--				: 720/59p
--				: 1080/25i
--				: 1080/29i
-- Comments		:
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
--
-- Value(s)		: FAIL:Bad File
--				: WARN:NONE
--				: FAIL:No File
--				: SDHD
--				: SDHD:3G
-- Comments		:
--
---------------------------------------------------------------------------------------------------
-- Header		: OUTPUT_1_CAPTION
--
-- MIB ref		: swCardEventLogSlotXX       .16.79.85.84.80.85.84.95.49.95.67.65.80.84.73.79.78
-- absolute OID	: 1.3.6.1.4.1.7995.2.6.1.1.XX.16.79.85.84.80.85.84.95.49.95.67.65.80.84.73.79.78
--
-- Value(s)		: OK:Off
--				: WARN:On[CaptionText]
-- Comments		:
--
---------------------------------------------------------------------------------------------------
-- Header		: OUTPUT_2_CAPTION
--
-- MIB ref		: swCardEventLogSlotXX       .16.79.85.84.80.85.84.95.50.95.67.65.80.84.73.79.78
-- absolute OID	: 1.3.6.1.4.1.7995.2.6.1.1.XX.16.79.85.84.80.85.84.95.50.95.67.65.80.84.73.79.78
--
-- Value(s)		: OK:Off
--				: WARN:On[CaptionText]
-- Comments		:
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
--
-- Value(s)		: OK:Tri-Level
--				: OK:Bi-Level
--				: WARN:Unknown
-- Comments		:
--
---------------------------------------------------------------------------------------------------
-- Header		: AES_INPUT_1_STATE
--
-- MIB ref		: swCardEventLogSlotXX       .17.65.69.83.95.73.78.80.85.84.95.49.95.83.84.65.84.69
-- absolute OID	: 1.3.6.1.4.1.7995.2.6.1.1.XX.17.65.69.83.95.73.78.80.85.84.95.49.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_2_STATE
--
-- MIB ref		: swCardEventLogSlotXX       .17.65.69.83.95.73.78.80.85.84.95.50.95.83.84.65.84.69
-- absolute OID	: 1.3.6.1.4.1.7995.2.6.1.1.XX.17.65.69.83.95.73.78.80.85.84.95.50.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_3_STATE
--
-- MIB ref		: swCardEventLogSlotXX       .17.65.69.83.95.73.78.80.85.84.95.51.95.83.84.65.84.69
-- absolute OID	: 1.3.6.1.4.1.7995.2.6.1.1.XX.17.65.69.83.95.73.78.80.85.84.95.51.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_4_STATE
--
-- MIB ref		: swCardEventLogSlotXX       .17.65.69.83.95.73.78.80.85.84.95.52.95.83.84.65.84.69
-- absolute OID	: 1.3.6.1.4.1.7995.2.6.1.1.XX.17.65.69.83.95.73.78.80.85.84.95.52.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_5_STATE
--
-- MIB ref		: swCardEventLogSlotXX       .17.65.69.83.95.73.78.80.85.84.95.53.95.83.84.65.84.69
-- absolute OID	: 1.3.6.1.4.1.7995.2.6.1.1.XX.17.65.69.83.95.73.78.80.85.84.95.53.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_6_STATE
--
-- MIB ref		: swCardEventLogSlotXX       .17.65.69.83.95.73.78.80.85.84.95.54.95.83.84.65.84.69
-- absolute OID	: 1.3.6.1.4.1.7995.2.6.1.1.XX.17.65.69.83.95.73.78.80.85.84.95.54.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_7_STATE
--
-- MIB ref		: swCardEventLogSlotXX       .17.65.69.83.95.73.78.80.85.84.95.55.95.83.84.65.84.69
-- absolute OID	: 1.3.6.1.4.1.7995.2.6.1.1.XX.17.65.69.83.95.73.78.80.85.84.95.55.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_8_STATE
--
-- MIB ref		: swCardEventLogSlotXX       .17.65.69.83.95.73.78.80.85.84.95.56.95.83.84.65.84.69
-- absolute OID	: 1.3.6.1.4.1.7995.2.6.1.1.XX.17.65.69.83.95.73.78.80.85.84.95.56.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
--
-- Value(s)		: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: OUTPUT_2_STANDARD
--
-- MIB ref		: swCardEventLogSlotXX       .17.79.85.84.80.85.84.95.50.95.83.84.65.78.68.65.82.68
-- absolute OID	: 1.3.6.1.4.1.7995.2.6.1.1.XX.17.79.85.84.80.85.84.95.50.95.83.84.65.78.68.65.82.68
--
-- Value(s)		: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
--
-- Value(s)		: OK
--				: WARN:Mismatch
--				: FAIL:Lost
-- Comments		: External ref state
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
--
-- Value(s)		: 0
--				: 1
--				: 2
-- Comments		: Number of error seconds
--
---------------------------------------------------------------------------------------------------
-- Header		: INPUT_2_SDI_ERRSEC
--
-- MIB ref		: swCardEventLogSlotXX       .18.73.78.80.85.84.95.50.95.83.68.73.95.69.82.82.83.69.67
-- absolute OID	: 1.3.6.1.4.1.7995.2.6.1.1.XX.18.73.78.80.85.84.95.50.95.83.68.73.95.69.82.82.83.69.67
--
-- Value(s)		: 0
--				: 1
--				: 2
-- Comments		: Number of error seconds
--
---------------------------------------------------------------------------------------------------
-- Header		: LICENSED_OPTIONS_2
--
-- MIB ref		: swCardEventLogSlotXX       .18.76.73.67.69.78.83.69.68.95.79.80.84.73.79.78.83.95.50
-- absolute OID	: 1.3.6.1.4.1.7995.2.6.1.1.XX.18.76.73.67.69.78.83.69.68.95.79.80.84.73.79.78.83.95.50
--
-- Value(s)		: FAIL:No File
--				: FAIL:Bad SerialNum
--				: WARN:Type??
--				: FAIL:Type Unknown
--				: WARN:Type Mismatch
--				: WARN:Bad File
--				: FAIL:Invalid
--				: OK:0 Options(s)
--				: OK:1 Options(s)
-- Comments		:
--
---------------------------------------------------------------------------------------------------
-- Header		: AES_OUTPUT_1_1_STATE
--
-- MIB ref		: swCardEventLogSlotXX       .20.65.69.83.95.79.85.84.80.85.84.95.49.95.49.95.83.84.65.84.69
-- absolute OID	: 1.3.6.1.4.1.7995.2.6.1.1.XX.20.65.69.83.95.79.85.84.80.85.84.95.49.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_1_2_STATE
--
-- MIB ref		: swCardEventLogSlotXX       .20.65.69.83.95.79.85.84.80.85.84.95.49.95.50.95.83.84.65.84.69
-- absolute OID	: 1.3.6.1.4.1.7995.2.6.1.1.XX.20.65.69.83.95.79.85.84.80.85.84.95.49.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_2_1_STATE
--
-- MIB ref		: swCardEventLogSlotXX       .20.65.69.83.95.79.85.84.80.85.84.95.50.95.49.95.83.84.65.84.69
-- absolute OID	: 1.3.6.1.4.1.7995.2.6.1.1.XX.20.65.69.83.95.79.85.84.80.85.84.95.50.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_2_2_STATE
--
-- MIB ref		: swCardEventLogSlotXX       .20.65.69.83.95.79.85.84.80.85.84.95.50.95.50.95.83.84.65.84.69
-- absolute OID	: 1.3.6.1.4.1.7995.2.6.1.1.XX.20.65.69.83.95.79.85.84.80.85.84.95.50.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_3_1_STATE
--
-- MIB ref		: swCardEventLogSlotXX       .20.65.69.83.95.79.85.84.80.85.84.95.51.95.49.95.83.84.65.84.69
-- absolute OID	: 1.3.6.1.4.1.7995.2.6.1.1.XX.20.65.69.83.95.79.85.84.80.85.84.95.51.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_3_2_STATE
--
-- MIB ref		: swCardEventLogSlotXX       .20.65.69.83.95.79.85.84.80.85.84.95.51.95.50.95.83.84.65.84.69
-- absolute OID	: 1.3.6.1.4.1.7995.2.6.1.1.XX.20.65.69.83.95.79.85.84.80.85.84.95.51.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_4_1_STATE
--
-- MIB ref		: swCardEventLogSlotXX       .20.65.69.83.95.79.85.84.80.85.84.95.52.95.49.95.83.84.65.84.69
-- absolute OID	: 1.3.6.1.4.1.7995.2.6.1.1.XX.20.65.69.83.95.79.85.84.80.85.84.95.52.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_4_2_STATE
--
-- MIB ref		: swCardEventLogSlotXX       .20.65.69.83.95.79.85.84.80.85.84.95.52.95.50.95.83.84.65.84.69
-- absolute OID	: 1.3.6.1.4.1.7995.2.6.1.1.XX.20.65.69.83.95.79.85.84.80.85.84.95.52.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_5_1_STATE
--
-- MIB ref		: swCardEventLogSlotXX       .20.65.69.83.95.79.85.84.80.85.84.95.53.95.49.95.83.84.65.84.69
-- absolute OID	: 1.3.6.1.4.1.7995.2.6.1.1.XX.20.65.69.83.95.79.85.84.80.85.84.95.53.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_5_2_STATE
--
-- MIB ref		: swCardEventLogSlotXX       .20.65.69.83.95.79.85.84.80.85.84.95.53.95.50.95.83.84.65.84.69
-- absolute OID	: 1.3.6.1.4.1.7995.2.6.1.1.XX.20.65.69.83.95.79.85.84.80.85.84.95.53.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_6_1_STATE
--
-- MIB ref		: swCardEventLogSlotXX       .20.65.69.83.95.79.85.84.80.85.84.95.54.95.49.95.83.84.65.84.69
-- absolute OID	: 1.3.6.1.4.1.7995.2.6.1.1.XX.20.65.69.83.95.79.85.84.80.85.84.95.54.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_6_2_STATE
--
-- MIB ref		: swCardEventLogSlotXX       .20.65.69.83.95.79.85.84.80.85.84.95.54.95.50.95.83.84.65.84.69
-- absolute OID	: 1.3.6.1.4.1.7995.2.6.1.1.XX.20.65.69.83.95.79.85.84.80.85.84.95.54.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_7_1_STATE
--
-- MIB ref		: swCardEventLogSlotXX       .20.65.69.83.95.79.85.84.80.85.84.95.55.95.49.95.83.84.65.84.69
-- absolute OID	: 1.3.6.1.4.1.7995.2.6.1.1.XX.20.65.69.83.95.79.85.84.80.85.84.95.55.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_7_2_STATE
--
-- MIB ref		: swCardEventLogSlotXX       .20.65.69.83.95.79.85.84.80.85.84.95.55.95.50.95.83.84.65.84.69
-- absolute OID	: 1.3.6.1.4.1.7995.2.6.1.1.XX.20.65.69.83.95.79.85.84.80.85.84.95.55.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_8_1_STATE
--
-- MIB ref		: swCardEventLogSlotXX       .20.65.69.83.95.79.85.84.80.85.84.95.56.95.49.95.83.84.65.84.69
-- absolute OID	: 1.3.6.1.4.1.7995.2.6.1.1.XX.20.65.69.83.95.79.85.84.80.85.84.95.56.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: AES_OUTPUT_8_2_STATE
--
-- MIB ref		: swCardEventLogSlotXX       .20.65.69.83.95.79.85.84.80.85.84.95.56.95.50.95.83.84.65.84.69
-- absolute OID	: 1.3.6.1.4.1.7995.2.6.1.1.XX.20.65.69.83.95.79.85.84.80.85.84.95.56.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
--				: WARN:Output
--				: WARN:Input
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
--
-- Value(s)		: OK
--				: WARN
-- Comments		:
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
--
-- Value(s)		: OK
--				: WARN
-- Comments		:
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
--
-- Value(s)		: LOST
--				: 525/29i
--				: 625/25i
--				: 720/50p
--				: 720/59p
--				: 1080/25i
--				: 1080/29i
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
--
-- Value(s)		: 0
--				: 1
--				: 2
-- Comments		: Number of error seconds
--
---------------------------------------------------------------------------------------------------
-- Header		: INPUT_2_SDI_ANC_ERRSECS
--
-- MIB ref		: swCardEventLogSlotXX       .23.73.78.80.85.84.95.50.95.83.68.73.95.65.78.67.95.69.82.82.83.69.67.83
-- absolute OID	: 1.3.6.1.4.1.7995.2.6.1.1.XX.23.73.78.80.85.84.95.50.95.83.68.73.95.65.78.67.95.69.82.82.83.69.67.83
--
-- Value(s)		: 0
--				: 1
--				: 2
-- Comments		: Number of error seconds
--
---------------------------------------------------------------------------------------------------
-- Header		: ANALOG_AUDIO_OUTPUT_1_1_STATE
--
-- MIB ref		: swCardEventLogSlotXX       .29.65.78.65.76.79.71.95.65.85.68.73.79.95.79.85.84.80.85.84.95.49.95.49.95.83.84.65.84.69
-- absolute OID	: 1.3.6.1.4.1.7995.2.6.1.1.XX.29.65.78.65.76.79.71.95.65.85.68.73.79.95.79.85.84.80.85.84.95.49.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: ANALOG_AUDIO_OUTPUT_1_2_STATE
--
-- MIB ref		: swCardEventLogSlotXX       .29.65.78.65.76.79.71.95.65.85.68.73.79.95.79.85.84.80.85.84.95.49.95.50.95.83.84.65.84.69
-- absolute OID	: 1.3.6.1.4.1.7995.2.6.1.1.XX.29.65.78.65.76.79.71.95.65.85.68.73.79.95.79.85.84.80.85.84.95.49.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: ANALOG_AUDIO_OUTPUT_2_1_STATE
--
-- MIB ref		: swCardEventLogSlotXX       .29.65.78.65.76.79.71.95.65.85.68.73.79.95.79.85.84.80.85.84.95.50.95.49.95.83.84.65.84.69
-- absolute OID	: 1.3.6.1.4.1.7995.2.6.1.1.XX.29.65.78.65.76.79.71.95.65.85.68.73.79.95.79.85.84.80.85.84.95.50.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: ANALOG_AUDIO_OUTPUT_2_2_STATE
--
-- MIB ref		: swCardEventLogSlotXX       .29.65.78.65.76.79.71.95.65.85.68.73.79.95.79.85.84.80.85.84.95.50.95.50.95.83.84.65.84.69
-- absolute OID	: 1.3.6.1.4.1.7995.2.6.1.1.XX.29.65.78.65.76.79.71.95.65.85.68.73.79.95.79.85.84.80.85.84.95.50.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
--
-- Value(s)		: OK:PCM
--				: OK:Data
--				: OK:DolbyE
--				: WARN:Unknown
--				: FAIL:Lost
--				: FAIL:Input Lost
-- Comments		:
--
---------------------------------------------------------------------------------------------------
-- Header		: OUTPUT_1_EMBED_AUDIO_1_1_STATE
--
-- MIB ref		: swCardEventLogSlotXX       .30.79.85.84.80.85.84.95.49.95.69.77.66.69.68.95.65.85.68.73.79.95.49.95.49.95.83.84.65.84.69
-- absolute OID	: 1.3.6.1.4.1.7995.2.6.1.1.XX.30.79.85.84.80.85.84.95.49.95.69.77.66.69.68.95.65.85.68.73.79.95.49.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_1_2_STATE
--
-- MIB ref		: swCardEventLogSlotXX       .30.79.85.84.80.85.84.95.49.95.69.77.66.69.68.95.65.85.68.73.79.95.49.95.50.95.83.84.65.84.69
-- absolute OID	: 1.3.6.1.4.1.7995.2.6.1.1.XX.30.79.85.84.80.85.84.95.49.95.69.77.66.69.68.95.65.85.68.73.79.95.49.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_2_1_STATE
--
-- MIB ref		: swCardEventLogSlotXX       .30.79.85.84.80.85.84.95.49.95.69.77.66.69.68.95.65.85.68.73.79.95.50.95.49.95.83.84.65.84.69
-- absolute OID	: 1.3.6.1.4.1.7995.2.6.1.1.XX.30.79.85.84.80.85.84.95.49.95.69.77.66.69.68.95.65.85.68.73.79.95.50.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_2_2_STATE
--
-- MIB ref		: swCardEventLogSlotXX       .30.79.85.84.80.85.84.95.49.95.69.77.66.69.68.95.65.85.68.73.79.95.50.95.50.95.83.84.65.84.69
-- absolute OID	: 1.3.6.1.4.1.7995.2.6.1.1.XX.30.79.85.84.80.85.84.95.49.95.69.77.66.69.68.95.65.85.68.73.79.95.50.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_3_1_STATE
--
-- MIB ref		: swCardEventLogSlotXX       .30.79.85.84.80.85.84.95.49.95.69.77.66.69.68.95.65.85.68.73.79.95.51.95.49.95.83.84.65.84.69
-- absolute OID	: 1.3.6.1.4.1.7995.2.6.1.1.XX.30.79.85.84.80.85.84.95.49.95.69.77.66.69.68.95.65.85.68.73.79.95.51.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_3_2_STATE
--
-- MIB ref		: swCardEventLogSlotXX       .30.79.85.84.80.85.84.95.49.95.69.77.66.69.68.95.65.85.68.73.79.95.51.95.50.95.83.84.65.84.69
-- absolute OID	: 1.3.6.1.4.1.7995.2.6.1.1.XX.30.79.85.84.80.85.84.95.49.95.69.77.66.69.68.95.65.85.68.73.79.95.51.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_4_1_STATE
--
-- MIB ref		: swCardEventLogSlotXX       .30.79.85.84.80.85.84.95.49.95.69.77.66.69.68.95.65.85.68.73.79.95.52.95.49.95.83.84.65.84.69
-- absolute OID	: 1.3.6.1.4.1.7995.2.6.1.1.XX.30.79.85.84.80.85.84.95.49.95.69.77.66.69.68.95.65.85.68.73.79.95.52.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_4_2_STATE
--
-- MIB ref		: swCardEventLogSlotXX       .30.79.85.84.80.85.84.95.49.95.69.77.66.69.68.95.65.85.68.73.79.95.52.95.50.95.83.84.65.84.69
-- absolute OID	: 1.3.6.1.4.1.7995.2.6.1.1.XX.30.79.85.84.80.85.84.95.49.95.69.77.66.69.68.95.65.85.68.73.79.95.52.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_5_1_STATE
--
-- MIB ref		: swCardEventLogSlotXX       .30.79.85.84.80.85.84.95.49.95.69.77.66.69.68.95.65.85.68.73.79.95.53.95.49.95.83.84.65.84.69
-- absolute OID	: 1.3.6.1.4.1.7995.2.6.1.1.XX.30.79.85.84.80.85.84.95.49.95.69.77.66.69.68.95.65.85.68.73.79.95.53.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_5_2_STATE
--
-- MIB ref		: swCardEventLogSlotXX       .30.79.85.84.80.85.84.95.49.95.69.77.66.69.68.95.65.85.68.73.79.95.53.95.50.95.83.84.65.84.69
-- absolute OID	: 1.3.6.1.4.1.7995.2.6.1.1.XX.30.79.85.84.80.85.84.95.49.95.69.77.66.69.68.95.65.85.68.73.79.95.53.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_6_1_STATE
--
-- MIB ref		: swCardEventLogSlotXX       .30.79.85.84.80.85.84.95.49.95.69.77.66.69.68.95.65.85.68.73.79.95.54.95.49.95.83.84.65.84.69
-- absolute OID	: 1.3.6.1.4.1.7995.2.6.1.1.XX.30.79.85.84.80.85.84.95.49.95.69.77.66.69.68.95.65.85.68.73.79.95.54.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_6_2_STATE
--
-- MIB ref		: swCardEventLogSlotXX       .30.79.85.84.80.85.84.95.49.95.69.77.66.69.68.95.65.85.68.73.79.95.54.95.50.95.83.84.65.84.69
-- absolute OID	: 1.3.6.1.4.1.7995.2.6.1.1.XX.30.79.85.84.80.85.84.95.49.95.69.77.66.69.68.95.65.85.68.73.79.95.54.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_7_1_STATE
--
-- MIB ref		: swCardEventLogSlotXX       .30.79.85.84.80.85.84.95.49.95.69.77.66.69.68.95.65.85.68.73.79.95.55.95.49.95.83.84.65.84.69
-- absolute OID	: 1.3.6.1.4.1.7995.2.6.1.1.XX.30.79.85.84.80.85.84.95.49.95.69.77.66.69.68.95.65.85.68.73.79.95.55.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_7_2_STATE
--
-- MIB ref		: swCardEventLogSlotXX       .30.79.85.84.80.85.84.95.49.95.69.77.66.69.68.95.65.85.68.73.79.95.55.95.50.95.83.84.65.84.69
-- absolute OID	: 1.3.6.1.4.1.7995.2.6.1.1.XX.30.79.85.84.80.85.84.95.49.95.69.77.66.69.68.95.65.85.68.73.79.95.55.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_8_1_STATE
--
-- MIB ref		: swCardEventLogSlotXX       .30.79.85.84.80.85.84.95.49.95.69.77.66.69.68.95.65.85.68.73.79.95.56.95.49.95.83.84.65.84.69
-- absolute OID	: 1.3.6.1.4.1.7995.2.6.1.1.XX.30.79.85.84.80.85.84.95.49.95.69.77.66.69.68.95.65.85.68.73.79.95.56.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_8_2_STATE
--
-- MIB ref		: swCardEventLogSlotXX       .30.79.85.84.80.85.84.95.49.95.69.77.66.69.68.95.65.85.68.73.79.95.56.95.50.95.83.84.65.84.69
-- absolute OID	: 1.3.6.1.4.1.7995.2.6.1.1.XX.30.79.85.84.80.85.84.95.49.95.69.77.66.69.68.95.65.85.68.73.79.95.56.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
--
-- Value(s)		: NONE
--				: OK
--				: WARN:Early
--				: WARN:Late
--				: FAIL:Early
--				: FAIL:Late
-- Comments		:
--
---------------------------------------------------------------------------------------------------
