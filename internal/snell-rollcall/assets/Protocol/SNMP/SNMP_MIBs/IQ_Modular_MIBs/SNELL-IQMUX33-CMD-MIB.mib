-- ************************************************************************************
--        Snell Card:IQMUX33
--        Module Id#:546
--       Command Set:12
--          Filename:SNELL-IQMUX33-CMD-MIB.mib
--       Source File:nemocombined.xml
--        Source Ver:5.7..12
--    Logging Source:nemologging.csv
--            Author:jonathanriches
--              Date:12/10/2011
--              Time:17:43
--
-- Copyright (c) 2010 Snell Ltd
-- All rights reserved.
--
-- ************************************************************************************

SNELL-IQMUX33-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQMUX33,
    moduleIQMUX33MIB
        FROM SNELL-WILCOX-PRODUCT-REG;

moduleIQMUX33CmdMi MODULE-IDENTITY
    LAST-UPDATED "1110121743Z"
    ORGANIZATION "Snell Ltd"
    CONTACT-INFO
        "Primary Author:jonathanriches

         postal:    Hartman House
                    Danehill
                    Lower Earley,
                    Reading, Berks
                    RG6 4PB
         phone:     +44 (0)118 9866123
         email:     support.uk@snellgroup.com"
    DESCRIPTION
        "This file defines the Snell card, command set translations."
    ::= { moduleIQMUX33MIB 1 }




--********************************************************************************
--*
--*  Snell Card:
--*  command set:
--*  list commands/menus:
--*
--******************************************************************************
    iqmux33CmdTable OBJECT-TYPE
        SYNTAX          SEQUENCE OF Iqmux33CmdEntry
        MAX-ACCESS      not-accessible
        STATUS          current
        DESCRIPTION
                "Note the instance of this table is relected in the command set Version"
        ::= { moduleIQMUX33 1 }

    iqmux33CmdEntry OBJECT-TYPE
        SYNTAX          Iqmux33CmdEntry
        MAX-ACCESS      not-accessible
        STATUS          current
        DESCRIPTION
                "Entry in command table."
        INDEX   { iqmux33SlotIndex }
        ::= { iqmux33CmdTable 1 }

    Iqmux33CmdEntry ::=
        SEQUENCE {
            iqmux33SlotIndex
                Unsigned32,
            iqmux33Video1VideoInputInput1Std
                RollCallString,
            iqmux33VideoInputValidStandards108050p
                INTEGER,
            iqmux33VideoInputValidStandards108059p
                INTEGER,
            iqmux33VideoInputValidStandards108025i
                INTEGER,
            iqmux33VideoInputValidStandards108029i
                INTEGER,
            iqmux33VideoInputValidStandards72050p
                INTEGER,
            iqmux33VideoInputValidStandards72059p
                INTEGER,
            iqmux33VideoInputValidStandards62525i
                INTEGER,
            iqmux33VideoInputValidStandards52529i
                INTEGER,
            iqmux33VideoInputValidStandards108023psf
                INTEGER,
            iqmux33VideoInputValidStandards108025psf
                INTEGER,
            iqmux33VideoInputValidStandards108025p
                INTEGER,
            iqmux33VideoInputValidStandards108029p
                INTEGER,
            iqmux33VideoInputErrorsErrorReset
                INTEGER,
            iqmux33VideoInputErrorsResetSec
                RollCallString,
            iqmux33VideoInputErrorsCRCErrs1
                RollCallString,
            iqmux33VideoInputErrorsANCErrs1
                RollCallString,
            iqmux33VideoInputErrorsCRCErrSec1
                RollCallString,
            iqmux33VideoInputErrorsANCErrSec1
                RollCallString,
            iqmux33Video1VideoInputYCDelay
                INTEGER,
            iqmux33Video1BackupQualifyInvStd
                INTEGER,
            iqmux33Video1BackupQualifyAudioFail
                INTEGER,
            iqmux33BackupInput1SelStatInp1OK
                RollCallString,
            iqmux33BackupInput1SelStatGPI1
                RollCallString,
            iqmux33BackupInput1SelStatGPI2
                RollCallString,
            iqmux33BackupInput1SelEnblInp1OK
                INTEGER,
            iqmux33BackupInput1SelEnblGPI1
                INTEGER,
            iqmux33BackupInput1SelEnblGPI2
                INTEGER,
            iqmux33BackupInput1SelDlyInp1OK
                INTEGER,
            iqmux33BackupInput1SelDlyGPI1
                INTEGER,
            iqmux33BackupInput1SelDlyGPI2
                INTEGER,
            iqmux33BackupInput1SelGPI1State
                INTEGER,
            iqmux33BackupInput1SelGPI2State
                INTEGER,
            iqmux33BackupInput2SelStatInp2OK
                RollCallString,
            iqmux33BackupInput2SelStatGPI1
                RollCallString,
            iqmux33BackupInput2SelStatGPI2
                RollCallString,
            iqmux33BackupInput2SelEnblInp2OK
                INTEGER,
            iqmux33BackupInput2SelEnblGPI1
                INTEGER,
            iqmux33BackupInput2SelEnblGPI2
                INTEGER,
            iqmux33BackupInput2SelDlyInp2OK
                INTEGER,
            iqmux33BackupInput2SelDlyGPI1
                INTEGER,
            iqmux33BackupInput2SelDlyGPI2
                INTEGER,
            iqmux33BackupInput2SelGPI1State
                INTEGER,
            iqmux33BackupInput2SelGPI2State
                INTEGER,
            iqmux33Video2VideoOutputOutputAType
                INTEGER,
            iqmux33Video2VideoOutputOutputBType
                INTEGER,
            iqmux33Video2VideoOutputOutput1Std
                RollCallString,
            iqmux33VideoOutputVideoProcMasterGain
                INTEGER,
            iqmux33VideoOutputVideoProcYGain
                INTEGER,
            iqmux33VideoOutputVideoProcCGain
                INTEGER,
            iqmux33VideoOutputVideoProcBlackLevel
                INTEGER,
            iqmux33VideoOutputVideoProcHueLevel
                INTEGER,
            iqmux33VideoOutputVideoProcActiveSig
                INTEGER,
            iqmux33Video2VideoOutputDefaultOutput
                INTEGER,
            iqmux33Video2VideoOutputOutputMode
                INTEGER,
            iqmux33Video2VideoOutputPatternType
                INTEGER,
            iqmux33VideoOutputUserCaptionsEnable
                INTEGER,
            iqmux33VideoOutputUserCaptionsEnableAlt
                INTEGER,
            iqmux33VideoOutputUserCaptionsText
                RollCallString,
            iqmux33VideoOutputUserCaptionsTextAlt
                RollCallString,
            iqmux33VideoOutputUserCaptionsXPos
                INTEGER,
            iqmux33VideoOutputUserCaptionsYPos
                INTEGER,
            iqmux33VideoOutputUserCaptionsXSize
                INTEGER,
            iqmux33VideoOutputUserCaptionsYSize
                INTEGER,
            iqmux33Video2VideoOutputOutStdnonConv
                INTEGER,
            iqmux33Video2VideoOutputFollowStdnonConv
                INTEGER,
            iqmux33Video2VideoOutputLastRefStd
                INTEGER,
            iqmux33Video2VideoOutputLastFrameRate
                INTEGER,
            iqmux33ARCCtrlSaveset
                INTEGER,
            iqmux33ARCCtrlDefaultALLMemory
                INTEGER,
            iqmux33GenlockBlankingGenlockStandard
                INTEGER,
            iqmux33GenlockBlankingGenlockDelayMode
                INTEGER,
            iqmux33GenlockSetDelayDelayFrames
                INTEGER,
            iqmux33GenlockSetDelayVerticalPhase
                INTEGER,
            iqmux33GenlockSetDelayHorizontalPhase
                INTEGER,
            iqmux33GenlockSetDelayVerticalDelay
                INTEGER,
            iqmux33GenlockSetDelayHorizontalDelay
                INTEGER,
            iqmux33GenlockBlankingGenlockRefLogHide
                RollCallString,
            iqmux33GenlockDolbyELineStandard
                INTEGER,
            iqmux33GenlockDolbyELineAutoLineNo
                INTEGER,
            iqmux33DolbyELineUserDolbyELinePair1
                INTEGER,
            iqmux33DolbyELineUserDolbyELinePair2
                INTEGER,
            iqmux33DolbyELineUserDolbyELinePair3
                INTEGER,
            iqmux33DolbyELineUserDolbyELinePair4
                INTEGER,
            iqmux33DolbyELineUserDolbyELinePair5
                INTEGER,
            iqmux33DolbyELineUserDolbyELinePair6
                INTEGER,
            iqmux33DolbyELineUserDolbyELinePair7
                INTEGER,
            iqmux33DolbyELineUserDolbyELinePair8
                INTEGER,
            iqmux33GenlockDolbyELineUserLine525i29
                INTEGER,
            iqmux33GenlockDolbyELineUserLine625i25
                INTEGER,
            iqmux33GenlockDolbyELineUserLine720p23
                INTEGER,
            iqmux33GenlockDolbyELineUserLine720p24
                INTEGER,
            iqmux33GenlockDolbyELineUserLine720p25
                INTEGER,
            iqmux33GenlockDolbyELineUserLine720p29
                INTEGER,
            iqmux33GenlockDolbyELineUserLine720p30
                INTEGER,
            iqmux33GenlockDolbyELineUserLine720p50
                INTEGER,
            iqmux33GenlockDolbyELineUserLine720p59
                INTEGER,
            iqmux33GenlockDolbyELineUserLine720p60
                INTEGER,
            iqmux33GenlockDolbyELineUserLine1080i25
                INTEGER,
            iqmux33GenlockDolbyELineUserLine1080i29
                INTEGER,
            iqmux33GenlockDolbyELineUserLine1080i30
                INTEGER,
            iqmux33GenlockDolbyELineUserLine1080p23sf
                INTEGER,
            iqmux33GenlockDolbyELineUserLine1080p24sf
                INTEGER,
            iqmux33GenlockDolbyELineUserLine1080p25sf
                INTEGER,
            iqmux33GenlockDolbyELineUserLine1080p23
                INTEGER,
            iqmux33GenlockDolbyELineUserLine1080p24
                INTEGER,
            iqmux33GenlockDolbyELineUserLine1080p25
                INTEGER,
            iqmux33GenlockDolbyELineUserLine1080p29
                INTEGER,
            iqmux33GenlockDolbyELineUserLine1080p30
                INTEGER,
            iqmux33GenlockDolbyELineUserLine1080p50
                INTEGER,
            iqmux33GenlockDolbyELineUserLine1080p59
                INTEGER,
            iqmux33GenlockDolbyELineUserLine1080p60
                INTEGER,
            iqmux33GenlockDolbyELineAutoAlign1
                INTEGER,
            iqmux33GenlockDolbyELineAutoAlign2
                INTEGER,
            iqmux33GenlockDolbyELineAutoAlign3
                INTEGER,
            iqmux33GenlockDolbyELineAutoAlign4
                INTEGER,
            iqmux33GenlockDolbyELineAutoAlign5
                INTEGER,
            iqmux33GenlockDolbyELineAutoAlign6
                INTEGER,
            iqmux33GenlockDolbyELineAutoAlign7
                INTEGER,
            iqmux33GenlockDolbyELineAutoAlign8
                INTEGER,
            iqmux33BlankingHANCVBIBlankingStandard
                INTEGER,
            iqmux33BlankingHANCVBIBlankingBlankAll
                INTEGER,
            iqmux33BlankingHANCVBIBlankingPassAll
                INTEGER,
            iqmux33BlankingHANCVBIBlankingBlank1
                INTEGER,
            iqmux33BlankingHANCVBIBlankingBlank2
                INTEGER,
            iqmux33BlankingHANCVBIBlankingBlank3
                INTEGER,
            iqmux33BlankingHANCVBIBlankingBlank4
                INTEGER,
            iqmux33BlankingHANCVBIBlankingBlank5
                INTEGER,
            iqmux33BlankingHANCVBIBlankingBlank6
                INTEGER,
            iqmux33BlankingHANCVBIBlankingBlank7
                INTEGER,
            iqmux33BlankingHANCVBIBlankingBlank8
                INTEGER,
            iqmux33BlankingHANCVBIBlankingBlank9
                INTEGER,
            iqmux33BlankingHANCVBIBlankingBlank10
                INTEGER,
            iqmux33BlankingHANCVBIBlankingBlank11
                INTEGER,
            iqmux33BlankingHANCVBIBlankingBlank12
                INTEGER,
            iqmux33BlankingHANCVBIBlankingBlank13
                INTEGER,
            iqmux33BlankingHANCVBIBlankingBlank14
                INTEGER,
            iqmux33BlankingHANCVBIBlankingBlank15
                INTEGER,
            iqmux33BlankingHANCVBIBlankingBlank16
                INTEGER,
            iqmux33BlankingHANCVBIBlankingBlank17
                INTEGER,
            iqmux33BlankingHANCVBIBlankingBlank18
                INTEGER,
            iqmux33BlankingHANCVBIBlankingBlank19
                INTEGER,
            iqmux33BlankingHANCVBIBlankingBlank20
                INTEGER,
            iqmux33BlankingHANCVBIBlankingBlank21
                INTEGER,
            iqmux33BlankingHANCVBIBlankingBlank22
                INTEGER,
            iqmux33BlankingHANCVBIBlankingBlank23
                INTEGER,
            iqmux33BlankingHANCVBIBlankingBlank24
                INTEGER,
            iqmux33BlankingHANCVBIBlankingBlank25
                INTEGER,
            iqmux33BlankingHANCVBIBlankingBlank26
                INTEGER,
            iqmux33BlankingHANCVBIBlankingBlank27
                INTEGER,
            iqmux33BlankingHANCVBIBlankingBlank28
                INTEGER,
            iqmux33BlankingHANCVBIBlankingBlank29
                INTEGER,
            iqmux33BlankingHANCVBIBlankingBlank30
                INTEGER,
            iqmux33BlankingHANCVBIBlankingBlank31
                INTEGER,
            iqmux33BlankingHANCVBIBlankingBlank32
                INTEGER,
            iqmux33BlankingHANCVBIBlankingBlank33
                INTEGER,
            iqmux33BlankingHANCVBIBlankingBlank34
                INTEGER,
            iqmux33BlankingHANCVBIBlankingBlank35
                INTEGER,
            iqmux33BlankingHANCVBIBlankingBlank36
                INTEGER,
            iqmux33BlankingHANCVBIBlankingBlankHANC
                INTEGER,
            iqmux33WSSCtrlNewNumber
                INTEGER,
            iqmux33WSSCtrlBlank62523
                INTEGER,
            iqmux33WSSCtrlBlank625336
                INTEGER,
            iqmux33WSSCtrlBlank52521
                INTEGER,
            iqmux33WSSCtrlBlank52522
                INTEGER,
            iqmux33WSSCtrlBlank525283
                INTEGER,
            iqmux33WSSCtrlBlank525284
                INTEGER,
            iqmux33AncillaryDataSDVBIVITCIPStatus
                INTEGER,
            iqmux33AncillaryDataSDVBIWSTIPStatus
                INTEGER,
            iqmux33AncillaryDataSDVBICC608IPStatus
                INTEGER,
            iqmux33AncillaryDataHDVANCATCEnable
                INTEGER,
            iqmux33AncillaryDataHDVANCATCIPF1Line
                RollCallString,
            iqmux33AncillaryDataHDVANCATCOPF1Line
                INTEGER,
            iqmux33AncillaryDataHDVANCATCOPF2Line
                INTEGER,
            iqmux33AncillaryDataHDVANCATCFollow
                INTEGER,
            iqmux33AncillaryDataHDVANCHDCaptionEnable
                INTEGER,
            iqmux33AncillaryDataHDVANCHDCaptionIPLine
                RollCallString,
            iqmux33AncillaryDataHDVANCHDCaptionOPLine
                INTEGER,
            iqmux33HDVANCHDCaptionHDFollowIPLine
                INTEGER,
            iqmux33AudioInputDisembed18Disembed11procamp
                INTEGER,
            iqmux33AudioInputDisembed18Disembed12procamp
                INTEGER,
            iqmux33Disembed18Disembed1Mute11
                INTEGER,
            iqmux33Disembed18Disembed1Mute12
                INTEGER,
            iqmux33Disembed18Disembed1Stereo1
                INTEGER,
            iqmux33AudioInputDisembed18Disembed11invert
                INTEGER,
            iqmux33AudioInputDisembed18Disembed12invert
                INTEGER,
            iqmux33Disembed18Disembed1dolbyLine
                RollCallString,
            iqmux33AudioInputDisembed18Disembed21procamp
                INTEGER,
            iqmux33AudioInputDisembed18Disembed22procamp
                INTEGER,
            iqmux33Disembed18Disembed2Mute21
                INTEGER,
            iqmux33Disembed18Disembed2Mute22
                INTEGER,
            iqmux33Disembed18Disembed2Stereo2
                INTEGER,
            iqmux33AudioInputDisembed18Disembed21invert
                INTEGER,
            iqmux33AudioInputDisembed18Disembed22invert
                INTEGER,
            iqmux33Disembed18Disembed2dolbyLine
                RollCallString,
            iqmux33AudioInputDisembed18Disembed31procamp
                INTEGER,
            iqmux33AudioInputDisembed18Disembed32procamp
                INTEGER,
            iqmux33Disembed18Disembed3Mute31
                INTEGER,
            iqmux33Disembed18Disembed3Mute32
                INTEGER,
            iqmux33Disembed18Disembed3Stereo3
                INTEGER,
            iqmux33AudioInputDisembed18Disembed31invert
                INTEGER,
            iqmux33AudioInputDisembed18Disembed32invert
                INTEGER,
            iqmux33Disembed18Disembed3dolbyLine
                RollCallString,
            iqmux33AudioInputDisembed18Disembed41procamp
                INTEGER,
            iqmux33AudioInputDisembed18Disembed42procamp
                INTEGER,
            iqmux33Disembed18Disembed4Mute41
                INTEGER,
            iqmux33Disembed18Disembed4Mute42
                INTEGER,
            iqmux33Disembed18Disembed4Stereo4
                INTEGER,
            iqmux33AudioInputDisembed18Disembed41invert
                INTEGER,
            iqmux33AudioInputDisembed18Disembed42invert
                INTEGER,
            iqmux33Disembed18Disembed4dolbyLine
                RollCallString,
            iqmux33AudioInputDisembed18Disembed51procamp
                INTEGER,
            iqmux33AudioInputDisembed18Disembed52procamp
                INTEGER,
            iqmux33Disembed18Disembed5Mute51
                INTEGER,
            iqmux33Disembed18Disembed5Mute52
                INTEGER,
            iqmux33Disembed18Disembed5Stereo5
                INTEGER,
            iqmux33AudioInputDisembed18Disembed51invert
                INTEGER,
            iqmux33AudioInputDisembed18Disembed52invert
                INTEGER,
            iqmux33Disembed18Disembed5dolbyLine
                RollCallString,
            iqmux33AudioInputDisembed18Disembed61procamp
                INTEGER,
            iqmux33AudioInputDisembed18Disembed62procamp
                INTEGER,
            iqmux33Disembed18Disembed6Mute61
                INTEGER,
            iqmux33Disembed18Disembed6Mute62
                INTEGER,
            iqmux33Disembed18Disembed6Stereo6
                INTEGER,
            iqmux33AudioInputDisembed18Disembed61invert
                INTEGER,
            iqmux33AudioInputDisembed18Disembed62invert
                INTEGER,
            iqmux33Disembed18Disembed6dolbyLine
                RollCallString,
            iqmux33AudioInputDisembed18Disembed71procamp
                INTEGER,
            iqmux33AudioInputDisembed18Disembed72procamp
                INTEGER,
            iqmux33Disembed18Disembed7Mute71
                INTEGER,
            iqmux33Disembed18Disembed7Mute72
                INTEGER,
            iqmux33Disembed18Disembed7Stereo7
                INTEGER,
            iqmux33AudioInputDisembed18Disembed71invert
                INTEGER,
            iqmux33AudioInputDisembed18Disembed72invert
                INTEGER,
            iqmux33Disembed18Disembed7dolbyLine
                RollCallString,
            iqmux33AudioInputDisembed18Disembed81procamp
                INTEGER,
            iqmux33AudioInputDisembed18Disembed82procamp
                INTEGER,
            iqmux33Disembed18Disembed8Mute81
                INTEGER,
            iqmux33Disembed18Disembed8Mute82
                INTEGER,
            iqmux33Disembed18Disembed8Stereo8
                INTEGER,
            iqmux33AudioInputDisembed18Disembed81invert
                INTEGER,
            iqmux33AudioInputDisembed18Disembed82invert
                INTEGER,
            iqmux33Disembed18Disembed8dolbyLine
                RollCallString,
            iqmux33AudioInputDisembed18ProcampSaveset
                INTEGER,
            iqmux33AudioInputAESInput18AESInput11procamp
                INTEGER,
            iqmux33AudioInputAESInput18AESInput12procamp
                INTEGER,
            iqmux33AESInput18AESInput1Mute11
                INTEGER,
            iqmux33AESInput18AESInput1Mute12
                INTEGER,
            iqmux33AESInput18AESInput1Stereo1
                INTEGER,
            iqmux33AudioInputAESInput18AESInput11invert
                INTEGER,
            iqmux33AudioInputAESInput18AESInput12invert
                INTEGER,
            iqmux33AudioInputAESInput18AESInput21procamp
                INTEGER,
            iqmux33AudioInputAESInput18AESInput22procamp
                INTEGER,
            iqmux33AESInput18AESInput2Mute21
                INTEGER,
            iqmux33AESInput18AESInput2Mute22
                INTEGER,
            iqmux33AESInput18AESInput2Stereo2
                INTEGER,
            iqmux33AudioInputAESInput18AESInput21invert
                INTEGER,
            iqmux33AudioInputAESInput18AESInput22invert
                INTEGER,
            iqmux33AudioInputAESInput18AESInput31procamp
                INTEGER,
            iqmux33AudioInputAESInput18AESInput32procamp
                INTEGER,
            iqmux33AESInput18AESInput3Mute31
                INTEGER,
            iqmux33AESInput18AESInput3Mute32
                INTEGER,
            iqmux33AESInput18AESInput3Stereo3
                INTEGER,
            iqmux33AudioInputAESInput18AESInput31invert
                INTEGER,
            iqmux33AudioInputAESInput18AESInput32invert
                INTEGER,
            iqmux33AudioInputAESInput18AESInput41procamp
                INTEGER,
            iqmux33AudioInputAESInput18AESInput42procamp
                INTEGER,
            iqmux33AESInput18AESInput4Mute41
                INTEGER,
            iqmux33AESInput18AESInput4Mute42
                INTEGER,
            iqmux33AESInput18AESInput4Stereo4
                INTEGER,
            iqmux33AudioInputAESInput18AESInput41invert
                INTEGER,
            iqmux33AudioInputAESInput18AESInput42invert
                INTEGER,
            iqmux33AudioInputAESInput18AESInput51procamp
                INTEGER,
            iqmux33AudioInputAESInput18AESInput52procamp
                INTEGER,
            iqmux33AESInput18AESInput5Mute51
                INTEGER,
            iqmux33AESInput18AESInput5Mute52
                INTEGER,
            iqmux33AESInput18AESInput5Stereo5
                INTEGER,
            iqmux33AudioInputAESInput18AESInput51invert
                INTEGER,
            iqmux33AudioInputAESInput18AESInput52invert
                INTEGER,
            iqmux33AudioInputAESInput18AESInput61procamp
                INTEGER,
            iqmux33AudioInputAESInput18AESInput62procamp
                INTEGER,
            iqmux33AESInput18AESInput6Mute61
                INTEGER,
            iqmux33AESInput18AESInput6Mute62
                INTEGER,
            iqmux33AESInput18AESInput6Stereo6
                INTEGER,
            iqmux33AudioInputAESInput18AESInput61invert
                INTEGER,
            iqmux33AudioInputAESInput18AESInput62invert
                INTEGER,
            iqmux33AudioInputAESInput18AESInput71procamp
                INTEGER,
            iqmux33AudioInputAESInput18AESInput72procamp
                INTEGER,
            iqmux33AESInput18AESInput7Mute71
                INTEGER,
            iqmux33AESInput18AESInput7Mute72
                INTEGER,
            iqmux33AESInput18AESInput7Stereo7
                INTEGER,
            iqmux33AudioInputAESInput18AESInput71invert
                INTEGER,
            iqmux33AudioInputAESInput18AESInput72invert
                INTEGER,
            iqmux33AudioInputAESInput18AESInput81procamp
                INTEGER,
            iqmux33AudioInputAESInput18AESInput82procamp
                INTEGER,
            iqmux33AESInput18AESInput8Mute81
                INTEGER,
            iqmux33AESInput18AESInput8Mute82
                INTEGER,
            iqmux33AESInput18AESInput8Stereo8
                INTEGER,
            iqmux33AudioInputAESInput18AESInput81invert
                INTEGER,
            iqmux33AudioInputAESInput18AESInput82invert
                INTEGER,
            iqmux33AudioInputAnalogInput12AnalogInput11procamp
                INTEGER,
            iqmux33AudioInputAnalogInput12AnalogInput12procamp
                INTEGER,
            iqmux33AnalogInput12AnalogInput1Mute11
                INTEGER,
            iqmux33AnalogInput12AnalogInput1Mute12
                INTEGER,
            iqmux33AnalogInput12AnalogInput1Stereo1
                INTEGER,
            iqmux33AudioInputAnalogInput12AnalogInput11invert
                INTEGER,
            iqmux33AudioInputAnalogInput12AnalogInput12invert
                INTEGER,
            iqmux33AudioInputAnalogInput12AnalogInput21procamp
                INTEGER,
            iqmux33AudioInputAnalogInput12AnalogInput22procamp
                INTEGER,
            iqmux33AnalogInput12AnalogInput2Mute21
                INTEGER,
            iqmux33AnalogInput12AnalogInput2Mute22
                INTEGER,
            iqmux33AnalogInput12AnalogInput2Stereo2
                INTEGER,
            iqmux33AudioInputAnalogInput12AnalogInput21invert
                INTEGER,
            iqmux33AudioInputAnalogInput12AnalogInput22invert
                INTEGER,
            iqmux33AudioOutputEmbed18Embed11procamp
                INTEGER,
            iqmux33AudioOutputEmbed18Embed12procamp
                INTEGER,
            iqmux33Embed18Embed1Mute11
                INTEGER,
            iqmux33Embed18Embed1Mute12
                INTEGER,
            iqmux33Embed18Embed1Stereo1
                INTEGER,
            iqmux33Embed18Embed1dolbyLine
                RollCallString,
            iqmux33AudioOutputEmbed18Embed21procamp
                INTEGER,
            iqmux33AudioOutputEmbed18Embed22procamp
                INTEGER,
            iqmux33Embed18Embed2Mute21
                INTEGER,
            iqmux33Embed18Embed2Mute22
                INTEGER,
            iqmux33Embed18Embed2Stereo2
                INTEGER,
            iqmux33Embed18Embed2dolbyLine
                RollCallString,
            iqmux33AudioOutputEmbed18Embed31procamp
                INTEGER,
            iqmux33AudioOutputEmbed18Embed32procamp
                INTEGER,
            iqmux33Embed18Embed3Mute31
                INTEGER,
            iqmux33Embed18Embed3Mute32
                INTEGER,
            iqmux33Embed18Embed3Stereo3
                INTEGER,
            iqmux33Embed18Embed3dolbyLine
                RollCallString,
            iqmux33AudioOutputEmbed18Embed41procamp
                INTEGER,
            iqmux33AudioOutputEmbed18Embed42procamp
                INTEGER,
            iqmux33Embed18Embed4Mute41
                INTEGER,
            iqmux33Embed18Embed4Mute42
                INTEGER,
            iqmux33Embed18Embed4Stereo4
                INTEGER,
            iqmux33Embed18Embed4dolbyLine
                RollCallString,
            iqmux33AudioOutputEmbed18Embed51procamp
                INTEGER,
            iqmux33AudioOutputEmbed18Embed52procamp
                INTEGER,
            iqmux33Embed18Embed5Mute51
                INTEGER,
            iqmux33Embed18Embed5Mute52
                INTEGER,
            iqmux33Embed18Embed5Stereo5
                INTEGER,
            iqmux33Embed18Embed5dolbyLine
                RollCallString,
            iqmux33AudioOutputEmbed18Embed61procamp
                INTEGER,
            iqmux33AudioOutputEmbed18Embed62procamp
                INTEGER,
            iqmux33Embed18Embed6Mute61
                INTEGER,
            iqmux33Embed18Embed6Mute62
                INTEGER,
            iqmux33Embed18Embed6Stereo6
                INTEGER,
            iqmux33Embed18Embed6dolbyLine
                RollCallString,
            iqmux33AudioOutputEmbed18Embed71procamp
                INTEGER,
            iqmux33AudioOutputEmbed18Embed72procamp
                INTEGER,
            iqmux33Embed18Embed7Mute71
                INTEGER,
            iqmux33Embed18Embed7Mute72
                INTEGER,
            iqmux33Embed18Embed7Stereo7
                INTEGER,
            iqmux33Embed18Embed7dolbyLine
                RollCallString,
            iqmux33AudioOutputEmbed18Embed81procamp
                INTEGER,
            iqmux33AudioOutputEmbed18Embed82procamp
                INTEGER,
            iqmux33Embed18Embed8Mute81
                INTEGER,
            iqmux33Embed18Embed8Mute82
                INTEGER,
            iqmux33Embed18Embed8Stereo8
                INTEGER,
            iqmux33Embed18Embed8dolbyLine
                RollCallString,
            iqmux33Embed18GroupEmbGroup1
                INTEGER,
            iqmux33Embed18GroupEmbGroup2
                INTEGER,
            iqmux33Embed18GroupEmbGroup3
                INTEGER,
            iqmux33Embed18GroupEmbGroup4
                INTEGER,
            iqmux33AudSetupDelaySelectTotalDelayBus1
                RollCallString,
            iqmux33AudSetupDelaySelectTotalDelayBus2
                RollCallString,
            iqmux33AudSetupDelaySelectTotalDelayBus3
                RollCallString,
            iqmux33AudSetupDelaySelectTotalDelayBus4
                RollCallString,
            iqmux33AudSetupDelaySelectTotalDelayBus5
                RollCallString,
            iqmux33AudSetupDelaySelectTotalDelayBus6
                RollCallString,
            iqmux33AudSetupDelaySelectTotalDelayBus7
                RollCallString,
            iqmux33AudSetupDelaySelectTotalDelayBus8
                RollCallString,
            iqmux33AudSetupDelaySelectBus1Delay
                INTEGER,
            iqmux33AudSetupDelaySelectBus2Delay
                INTEGER,
            iqmux33AudSetupDelaySelectBus3Delay
                INTEGER,
            iqmux33AudSetupDelaySelectBus4Delay
                INTEGER,
            iqmux33AudSetupDelaySelectBus5Delay
                INTEGER,
            iqmux33AudSetupDelaySelectBus6Delay
                INTEGER,
            iqmux33AudSetupDelaySelectBus7Delay
                INTEGER,
            iqmux33AudSetupDelaySelectBus8Delay
                INTEGER,
            iqmux33AudSetupDelaySelectBus1Fine
                INTEGER,
            iqmux33AudSetupDelaySelectBus2Fine
                INTEGER,
            iqmux33AudSetupDelaySelectBus3Fine
                INTEGER,
            iqmux33AudSetupDelaySelectBus4Fine
                INTEGER,
            iqmux33AudSetupDelaySelectBus5Fine
                INTEGER,
            iqmux33AudSetupDelaySelectBus6Fine
                INTEGER,
            iqmux33AudSetupDelaySelectBus7Fine
                INTEGER,
            iqmux33AudSetupDelaySelectBus8Fine
                INTEGER,
            iqmux33AudSetupDelaySelectBusBulkDelay
                INTEGER,
            iqmux33AudSetupDelaySelectThreshold
                INTEGER,
            iqmux33AudSetupDelaySelectRtrack14
                INTEGER,
            iqmux33AudSetupDelaySelectRtrack15
                INTEGER,
            iqmux33AudSetupDelaySelectRtrack16
                INTEGER,
            iqmux33AudSetupDelaySelectRtrack17
                INTEGER,
            iqmux33AudSetupDelaySelectEnableBulk
                INTEGER,
            iqmux33AudSetupDelaySelectEnableVideo
                INTEGER,
            iqmux33AudioAudSetupRollTrack14
                RollCallString,
            iqmux33AudioAudSetupRollTrack15
                RollCallString,
            iqmux33AudioAudSetupRollTrack16
                RollCallString,
            iqmux33AudioAudSetupRollTrack17
                RollCallString,
            iqmux33AudioAudSetupCurrentVidDelay
                RollCallString,
            iqmux33AudioAudSetupMinVidAudDelay
                RollCallString,
            iqmux33AudioAudSetupCurrRTrack14Delay
                RollCallString,
            iqmux33AudioAudSetupCurrRlTrack15Delay
                RollCallString,
            iqmux33AudioAudSetupCurrRTrack16Delay
                RollCallString,
            iqmux33AudioAudSetupCurrRTrack17Delay
                RollCallString,
            iqmux33AudSetupTonesFreq0
                INTEGER,
            iqmux33AudSetupTonesFreq1
                INTEGER,
            iqmux33AudSetupTonesFreq2
                INTEGER,
            iqmux33AudSetupTonesFreq3
                INTEGER,
            iqmux33AudSetupTonesFreq4
                INTEGER,
            iqmux33AudSetupTonesFreq5
                INTEGER,
            iqmux33AudSetupTonesFreq6
                INTEGER,
            iqmux33AudSetupTonesFreq7
                INTEGER,
            iqmux33AudSetupTonesIdent0
                INTEGER,
            iqmux33AudSetupTonesIdent1
                INTEGER,
            iqmux33AudSetupTonesIdent2
                INTEGER,
            iqmux33AudSetupTonesIdent3
                INTEGER,
            iqmux33AudSetupTonesIdent4
                INTEGER,
            iqmux33AudSetupTonesIdent5
                INTEGER,
            iqmux33AudSetupTonesIdent6
                INTEGER,
            iqmux33AudSetupTonesIdent7
                INTEGER,
            iqmux33AudioAudSetupNeg1Frame
                INTEGER,
            iqmux33AudioAudSetupNeg1ms
                INTEGER,
            iqmux33AudioAudSetupNeg4samp
                INTEGER,
            iqmux33AudioAudSetupPos4samp
                INTEGER,
            iqmux33AudioAudSetupPos1ms
                INTEGER,
            iqmux33AudioAudSetupPos1Frame
                INTEGER,
            iqmux33AudioAudSetupSilentLevel
                INTEGER,
            iqmux33AudioAudSetupOverloadLevel
                INTEGER,
            iqmux33AudioAudSetupLevelTimeout
                INTEGER,
            iqmux33AudioAudSetupLevelUpdateEnb
                INTEGER,
            iqmux33AudioAudSetupAudLevel
                RollCallString,
            iqmux33AudioAudSetupHeadroomIn
                INTEGER,
            iqmux33AudioAudSetupLineupIn
                INTEGER,
            iqmux33AudioRoutingInputRouteDest1
                INTEGER,
            iqmux33AudioRoutingInputRouteDest2
                INTEGER,
            iqmux33AudioRoutingInputRouteDest3
                INTEGER,
            iqmux33AudioRoutingInputRouteDest4
                INTEGER,
            iqmux33AudioRoutingInputRouteDest5
                INTEGER,
            iqmux33AudioRoutingInputRouteDest6
                INTEGER,
            iqmux33AudioRoutingInputRouteDest7
                INTEGER,
            iqmux33AudioRoutingInputRouteDest8
                INTEGER,
            iqmux33AudioRoutingInputNameAnalog
                RollCallString,
            iqmux33AudioRoutingInputNameDlby1
                RollCallString,
            iqmux33AudioRoutingInputNameDlby2
                RollCallString,
            iqmux33AudioRoutingInputNameDlby3
                RollCallString,
            iqmux33AudioRoutingInputNameDlby4
                RollCallString,
            iqmux33AudioRoutingInputNameDlby5
                RollCallString,
            iqmux33AudioRoutingInputHideAES1
                RollCallString,
            iqmux33AudioRoutingInputHideAES2
                RollCallString,
            iqmux33AudioRoutingInputHideAES3
                RollCallString,
            iqmux33AudioRoutingInputHideAES4
                RollCallString,
            iqmux33AudioRoutingInputHideAES5
                RollCallString,
            iqmux33AudioRoutingInputHideAES6
                RollCallString,
            iqmux33AudioRoutingInputHideAES7
                RollCallString,
            iqmux33AudioRoutingInputHideAES8
                RollCallString,
            iqmux33AudioRoutingOutputHideAES1
                RollCallString,
            iqmux33AudioRoutingOutputHideAES2
                RollCallString,
            iqmux33AudioRoutingOutputHideAES3
                RollCallString,
            iqmux33AudioRoutingOutputHideAES4
                RollCallString,
            iqmux33AudioRoutingOutputHideAES5
                RollCallString,
            iqmux33AudioRoutingOutputHideAES6
                RollCallString,
            iqmux33AudioRoutingOutputHideAES7
                RollCallString,
            iqmux33AudioRoutingOutputHideAES8
                RollCallString,
            iqmux33AudioRoutingDolbyDecodeSource
                INTEGER,
            iqmux33AudioRoutingDolbyDecodeNum
                INTEGER,
            iqmux33AudioOutputRoutingOutDest1
                INTEGER,
            iqmux33AudioOutputRoutingOutDest2
                INTEGER,
            iqmux33AudioOutputRoutingOutDest3
                INTEGER,
            iqmux33AudioOutputRoutingOutDest4
                INTEGER,
            iqmux33AudioOutputRoutingOutDest5
                INTEGER,
            iqmux33AudioOutputRoutingOutDest6
                INTEGER,
            iqmux33AudioOutputRoutingOutDest7
                INTEGER,
            iqmux33AudioOutputRoutingOutDest8
                INTEGER,
            iqmux33AudioOutputRoutingOutDest9
                INTEGER,
            iqmux33AudioOutputRoutingOutDest10
                INTEGER,
            iqmux33AudioOutputRoutingOutDest11
                INTEGER,
            iqmux33AudioOutputRoutingOutDest12
                INTEGER,
            iqmux33AudioOutputRoutingOutDest13
                INTEGER,
            iqmux33AudioOutputRoutingOutDest14
                INTEGER,
            iqmux33AudioOutputRoutingOutDest15
                INTEGER,
            iqmux33AudioOutputRoutingOutDest16
                INTEGER,
            iqmux33AudioOutputRoutingDolbyEncEnb
                RollCallString,
            iqmux33AudioOutputRoutingUpmixEnb
                RollCallString,
            iqmux33AudioProcDefaultEmbed
                INTEGER,
            iqmux33AudioRoutingMatrixBus1audsel
                INTEGER,
            iqmux33AudioRoutingMatrixBus2audsel
                INTEGER,
            iqmux33AudioRoutingMatrixBus3audsel
                INTEGER,
            iqmux33AudioRoutingMatrixBus4audsel
                INTEGER,
            iqmux33AudioRoutingMatrixBus5audsel
                INTEGER,
            iqmux33AudioRoutingMatrixBus6audsel
                INTEGER,
            iqmux33AudioRoutingMatrixBus7audsel
                INTEGER,
            iqmux33AudioRoutingMatrixBus8audsel
                INTEGER,
            iqmux33AudioOutRouteMatrixEmbed12MatrixEmbed11audsel
                INTEGER,
            iqmux33AudioOutRouteMatrixEmbed12MatrixEmbed12audsel
                INTEGER,
            iqmux33AudioOutRouteMatrixEmbed12MatrixEmbed21audsel
                INTEGER,
            iqmux33AudioOutRouteMatrixEmbed12MatrixEmbed22audsel
                INTEGER,
            iqmux33AudioOutRouteMatrixEmbed34MatrixEmbed31audsel
                INTEGER,
            iqmux33AudioOutRouteMatrixEmbed34MatrixEmbed32audsel
                INTEGER,
            iqmux33AudioOutRouteMatrixEmbed34MatrixEmbed41audsel
                INTEGER,
            iqmux33AudioOutRouteMatrixEmbed34MatrixEmbed42audsel
                INTEGER,
            iqmux33AudioOutRouteMatrixEmbed56MatrixEmbed51audsel
                INTEGER,
            iqmux33AudioOutRouteMatrixEmbed56MatrixEmbed52audsel
                INTEGER,
            iqmux33AudioOutRouteMatrixEmbed56MatrixEmbed61audsel
                INTEGER,
            iqmux33AudioOutRouteMatrixEmbed56MatrixEmbed62audsel
                INTEGER,
            iqmux33AudioOutRouteMatrixEmbed78MatrixEmbed71audsel
                INTEGER,
            iqmux33AudioOutRouteMatrixEmbed78MatrixEmbed72audsel
                INTEGER,
            iqmux33AudioOutRouteMatrixEmbed78MatrixEmbed81audsel
                INTEGER,
            iqmux33AudioOutRouteMatrixEmbed78MatrixEmbed82audsel
                INTEGER,
            iqmux33AudioOutRouteMatrixDefaultsEmbOut
                INTEGER,
            iqmux33UpMixerLoud14Source1ProcGain
                INTEGER,
            iqmux33UpMixerLoud14Source1Mute
                INTEGER,
            iqmux33UpMixerLoud14Source1Src
                INTEGER,
            iqmux33UpMixerLoud14Source2ProcGain
                INTEGER,
            iqmux33UpMixerLoud14Source2Mute
                INTEGER,
            iqmux33UpMixerLoud14Source2Src
                INTEGER,
            iqmux33UpMixerLoud14Source3ProcGain
                INTEGER,
            iqmux33UpMixerLoud14Source3Mute
                INTEGER,
            iqmux33UpMixerLoud14Source3Src
                INTEGER,
            iqmux33UpMixerLoud14Source4ProcGain
                INTEGER,
            iqmux33UpMixerLoud14Source4Mute
                INTEGER,
            iqmux33UpMixerLoud14Source4Src
                INTEGER,
            iqmux33UpMixerLoud14Mode
                INTEGER,
            iqmux33UpMixerLoud14Status
                RollCallString,
            iqmux33UpMixerLoud14XfadeBypass
                INTEGER,
            iqmux33UpMixerLoud14XfadeUpmix
                INTEGER,
            iqmux33UpMixerLoud14Detect
                INTEGER,
            iqmux33UpMixerLoud14CenterWidth
                INTEGER,
            iqmux33UpMixerLoud14Surround
                INTEGER,
            iqmux33UpMixerLoud14AlgorithmType
                INTEGER,
            iqmux33UpMixerLoud58LoudnessPreset1
                INTEGER,
            iqmux33UpMixerLoud58LoudnessMasterLevel1
                INTEGER,
            iqmux33UpMixerLoud58LoudnessName1
                RollCallString,
            iqmux33UpMixerLoud58LoudnessBypass1
                INTEGER,
            iqmux33UpMixerLoud58LoudnessPreset2
                INTEGER,
            iqmux33UpMixerLoud58LoudnessMasterLevel2
                INTEGER,
            iqmux33UpMixerLoud58LoudnessName2
                RollCallString,
            iqmux33UpMixerLoud58LoudnessBypass2
                INTEGER,
            iqmux33UpMixerLoud58Source5ProcGain
                INTEGER,
            iqmux33UpMixerLoud58Source5Mute
                INTEGER,
            iqmux33UpMixerLoud58Source5Src
                INTEGER,
            iqmux33UpMixerLoud58Source6ProcGain
                INTEGER,
            iqmux33UpMixerLoud58Source6Mute
                INTEGER,
            iqmux33UpMixerLoud58Source6Src
                INTEGER,
            iqmux33UpMixerLoud58Source7ProcGain
                INTEGER,
            iqmux33UpMixerLoud58Source7Mute
                INTEGER,
            iqmux33UpMixerLoud58Source7Src
                INTEGER,
            iqmux33UpMixerLoud58Source8ProcGain
                INTEGER,
            iqmux33UpMixerLoud58Source8Mute
                INTEGER,
            iqmux33UpMixerLoud58Source8Src
                INTEGER,
            iqmux33UpMixerLoud58UpmixHide
                RollCallString,
            iqmux33UpMixerLoud58Chan1Name
                RollCallString,
            iqmux33UpMixerLoud58Chan2Name
                RollCallString,
            iqmux33UpMixerLoud58Chan3Name
                RollCallString,
            iqmux33UpMixerLoud58Chan4Name
                RollCallString,
            iqmux33UpMixerLoud58Chan5Name
                RollCallString,
            iqmux33UpMixerLoud58Chan6Name
                RollCallString,
            iqmux33UpMixerLoud58Chan7Name
                RollCallString,
            iqmux33UpMixerLoud58Chan8Name
                RollCallString,
            iqmux33UpMixerLoud58Chan1NameIn
                RollCallString,
            iqmux33UpMixerLoud58Chan2NameIn
                RollCallString,
            iqmux33UpMixerLoud58Chan3NameIn
                RollCallString,
            iqmux33UpMixerLoud58Chan4NameIn
                RollCallString,
            iqmux33UpMixerLoud58Chan5NameIn
                RollCallString,
            iqmux33UpMixerLoud58Chan6NameIn
                RollCallString,
            iqmux33UpMixerLoud58Chan7NameIn
                RollCallString,
            iqmux33UpMixerLoud58Chan8NameIn
                RollCallString,
            iqmux33UpMixerLoud58DialogHide
                RollCallString,
            iqmux33LoudCustomBlock1Name
                RollCallString,
            iqmux33LoudCustomBlock1inagcfreeze
                INTEGER,
            iqmux33LoudCustomBlock1inagcgate
                INTEGER,
            iqmux33LoudCustomBlock1inagcratio
                INTEGER,
            iqmux33LoudCustomBlock1inagcrange
                INTEGER,
            iqmux33LoudCustomBlock1inagcthresh
                INTEGER,
            iqmux33LoudCustomBlock1inagcattack
                INTEGER,
            iqmux33LoudCustomBlock1inagcrelease
                INTEGER,
            iqmux33LoudCustomBlock1peqfreq1
                INTEGER,
            iqmux33LoudCustomBlock1peqq1
                INTEGER,
            iqmux33LoudCustomBlock1peqlevel1
                INTEGER,
            iqmux33LoudCustomBlock1peqfreq2
                INTEGER,
            iqmux33LoudCustomBlock1peqq2
                INTEGER,
            iqmux33LoudCustomBlock1peqlevel2
                INTEGER,
            iqmux33LoudCustomBlock1peqfreq3
                INTEGER,
            iqmux33LoudCustomBlock1peqq3
                INTEGER,
            iqmux33LoudCustomBlock1peqlevel3
                INTEGER,
            iqmux33LoudCustomBlock1mbagcatk1
                INTEGER,
            iqmux33LoudCustomBlock1mbagcrel1
                INTEGER,
            iqmux33LoudCustomBlock1mbagcthresh1
                INTEGER,
            iqmux33LoudCustomBlock1mbagcoutlev1
                INTEGER,
            iqmux33LoudCustomBlock1mbagclimthresh1
                INTEGER,
            iqmux33LoudCustomBlock1mbagcinfthr1
                INTEGER,
            iqmux33LoudCustomBlock1mbagcatk2
                INTEGER,
            iqmux33LoudCustomBlock1mbagcrel2
                INTEGER,
            iqmux33LoudCustomBlock1mbagcthresh2
                INTEGER,
            iqmux33LoudCustomBlock1mbagcoutlev2
                INTEGER,
            iqmux33LoudCustomBlock1mbagclimthresh2
                INTEGER,
            iqmux33LoudCustomBlock1mbagcinfthr2
                INTEGER,
            iqmux33LoudCustomBlock1mbagcatk3
                INTEGER,
            iqmux33LoudCustomBlock1mbagcrel3
                INTEGER,
            iqmux33LoudCustomBlock1mbagcthresh3
                INTEGER,
            iqmux33LoudCustomBlock1mbagcoutlev3
                INTEGER,
            iqmux33LoudCustomBlock1mbagclimthresh3
                INTEGER,
            iqmux33LoudCustomBlock1mbagcinfthr3
                INTEGER,
            iqmux33LoudCustomBlock1mbagcatk4
                INTEGER,
            iqmux33LoudCustomBlock1mbagcrel4
                INTEGER,
            iqmux33LoudCustomBlock1mbagcthresh4
                INTEGER,
            iqmux33LoudCustomBlock1mbagcoutlev4
                INTEGER,
            iqmux33LoudCustomBlock1mbagclimthresh4
                INTEGER,
            iqmux33LoudCustomBlock1mbagcinfthr4
                INTEGER,
            iqmux33LoudCustomBlock1mbagcatk5
                INTEGER,
            iqmux33LoudCustomBlock1mbagcrel5
                INTEGER,
            iqmux33LoudCustomBlock1mbagcthresh5
                INTEGER,
            iqmux33LoudCustomBlock1mbagcoutlev5
                INTEGER,
            iqmux33LoudCustomBlock1mbagclimthresh5
                INTEGER,
            iqmux33LoudCustomBlock1mbagcinfthr5
                INTEGER,
            iqmux33LoudCustomBlock1mbrange
                INTEGER,
            iqmux33LoudCustomBlock1mbprogrise
                INTEGER,
            iqmux33LoudCustomBlock1mbsoftclip1
                INTEGER,
            iqmux33LoudCustomBlock1mbsoftclip2
                INTEGER,
            iqmux33LoudCustomBlock1mbratio
                INTEGER,
            iqmux33LoudCustomBlock1mblimdrive
                INTEGER,
            iqmux33LoudCustomBlock1CustomPreset
                INTEGER,
            iqmux33LoudCustomBlock1Copyto2
                INTEGER,
            iqmux33LoudCustomBlock2Name
                RollCallString,
            iqmux33LoudCustomBlock2inagcfreeze
                INTEGER,
            iqmux33LoudCustomBlock2inagcgate
                INTEGER,
            iqmux33LoudCustomBlock2inagcratio
                INTEGER,
            iqmux33LoudCustomBlock2inagcrange
                INTEGER,
            iqmux33LoudCustomBlock2inagcthresh
                INTEGER,
            iqmux33LoudCustomBlock2inagcattack
                INTEGER,
            iqmux33LoudCustomBlock2inagcrelease
                INTEGER,
            iqmux33LoudCustomBlock2peqfreq1
                INTEGER,
            iqmux33LoudCustomBlock2peqq1
                INTEGER,
            iqmux33LoudCustomBlock2peqlevel1
                INTEGER,
            iqmux33LoudCustomBlock2peqfreq2
                INTEGER,
            iqmux33LoudCustomBlock2peqq2
                INTEGER,
            iqmux33LoudCustomBlock2peqlevel2
                INTEGER,
            iqmux33LoudCustomBlock2peqfreq3
                INTEGER,
            iqmux33LoudCustomBlock2peqq3
                INTEGER,
            iqmux33LoudCustomBlock2peqlevel3
                INTEGER,
            iqmux33LoudCustomBlock2mbagcatk1
                INTEGER,
            iqmux33LoudCustomBlock2mbagcrel1
                INTEGER,
            iqmux33LoudCustomBlock2mbagcthresh1
                INTEGER,
            iqmux33LoudCustomBlock2mbagcoutlev1
                INTEGER,
            iqmux33LoudCustomBlock2mbagclimthresh1
                INTEGER,
            iqmux33LoudCustomBlock2mbagcinfthr1
                INTEGER,
            iqmux33LoudCustomBlock2mbagcatk2
                INTEGER,
            iqmux33LoudCustomBlock2mbagcrel2
                INTEGER,
            iqmux33LoudCustomBlock2mbagcthresh2
                INTEGER,
            iqmux33LoudCustomBlock2mbagcoutlev2
                INTEGER,
            iqmux33LoudCustomBlock2mbagclimthresh2
                INTEGER,
            iqmux33LoudCustomBlock2mbagcinfthr2
                INTEGER,
            iqmux33LoudCustomBlock2mbagcatk3
                INTEGER,
            iqmux33LoudCustomBlock2mbagcrel3
                INTEGER,
            iqmux33LoudCustomBlock2mbagcthresh3
                INTEGER,
            iqmux33LoudCustomBlock2mbagcoutlev3
                INTEGER,
            iqmux33LoudCustomBlock2mbagclimthresh3
                INTEGER,
            iqmux33LoudCustomBlock2mbagcinfthr3
                INTEGER,
            iqmux33LoudCustomBlock2mbagcatk4
                INTEGER,
            iqmux33LoudCustomBlock2mbagcrel4
                INTEGER,
            iqmux33LoudCustomBlock2mbagcthresh4
                INTEGER,
            iqmux33LoudCustomBlock2mbagcoutlev4
                INTEGER,
            iqmux33LoudCustomBlock2mbagclimthresh4
                INTEGER,
            iqmux33LoudCustomBlock2mbagcinfthr4
                INTEGER,
            iqmux33LoudCustomBlock2mbagcatk5
                INTEGER,
            iqmux33LoudCustomBlock2mbagcrel5
                INTEGER,
            iqmux33LoudCustomBlock2mbagcthresh5
                INTEGER,
            iqmux33LoudCustomBlock2mbagcoutlev5
                INTEGER,
            iqmux33LoudCustomBlock2mbagclimthresh5
                INTEGER,
            iqmux33LoudCustomBlock2mbagcinfthr5
                INTEGER,
            iqmux33LoudCustomBlock2mbrange
                INTEGER,
            iqmux33LoudCustomBlock2mbprogrise
                INTEGER,
            iqmux33LoudCustomBlock2mbsoftclip1
                INTEGER,
            iqmux33LoudCustomBlock2mbsoftclip2
                INTEGER,
            iqmux33LoudCustomBlock2mbratio
                INTEGER,
            iqmux33LoudCustomBlock2mblimdrive
                INTEGER,
            iqmux33LoudCustomBlock2CustomPreset
                INTEGER,
            iqmux33LoudCustomBlock2Copyto1
                INTEGER,
            iqmux33LoudCustomMasterLevelCustom1
                INTEGER,
            iqmux33LoudCustomMasterLevelCustom2
                INTEGER,
            iqmux33LoudCustomMasterLevelGen51
                INTEGER,
            iqmux33LoudCustomMasterLevelLight51
                INTEGER,
            iqmux33LoudCustomMasterLevelHeavy51
                INTEGER,
            iqmux33LoudCustomMasterLevelLoud51
                INTEGER,
            iqmux33LoudCustomMasterLevelLoudLimit51
                INTEGER,
            iqmux33LoudCustomMasterLevelProtect51
                INTEGER,
            iqmux33LoudCustomMasterLevelGenSterA
                INTEGER,
            iqmux33LoudCustomMasterLevelLightSterA
                INTEGER,
            iqmux33LoudCustomMasterLevelHeavySterA
                INTEGER,
            iqmux33LoudCustomMasterLevelLoudSterA
                INTEGER,
            iqmux33LoudCustomMasterLevelLoudLimitSterA
                INTEGER,
            iqmux33LoudCustomMasterLevelProtectSterA
                INTEGER,
            iqmux33LoudCustomMasterLevelGenSterB
                INTEGER,
            iqmux33LoudCustomMasterLevelLightSterB
                INTEGER,
            iqmux33LoudCustomMasterLevelHeavySterB
                INTEGER,
            iqmux33LoudCustomMasterLevelLoudSterB
                INTEGER,
            iqmux33LoudCustomMasterLevelLoudLimitSterB
                INTEGER,
            iqmux33LoudCustomMasterLevelProtectSterB
                INTEGER,
            iqmux33Mixers13Select
                INTEGER,
            iqmux33Mixers13Source1ProcGain
                INTEGER,
            iqmux33Mixers13Source1Invert
                INTEGER,
            iqmux33Mixers13Source1Mute
                INTEGER,
            iqmux33Mixers13Source1Src
                INTEGER,
            iqmux33Mixers13Source1Name
                RollCallString,
            iqmux33Mixers13Source2ProcGain
                INTEGER,
            iqmux33Mixers13Source2Invert
                INTEGER,
            iqmux33Mixers13Source2Mute
                INTEGER,
            iqmux33Mixers13Source2Src
                INTEGER,
            iqmux33Mixers13Source2Name
                RollCallString,
            iqmux33Mixers13Source3ProcGain
                INTEGER,
            iqmux33Mixers13Source3Invert
                INTEGER,
            iqmux33Mixers13Source3Mute
                INTEGER,
            iqmux33Mixers13Source3Src
                INTEGER,
            iqmux33Mixers13Source3Name
                RollCallString,
            iqmux33Mixers13MixerLoRo
                INTEGER,
            iqmux33Mixers46Source4ProcGain
                INTEGER,
            iqmux33Mixers46Source4Invert
                INTEGER,
            iqmux33Mixers46Source4Mute
                INTEGER,
            iqmux33Mixers46Source4Src
                INTEGER,
            iqmux33Mixers46Source4Name
                RollCallString,
            iqmux33Mixers46Source5ProcGain
                INTEGER,
            iqmux33Mixers46Source5Invert
                INTEGER,
            iqmux33Mixers46Source5Mute
                INTEGER,
            iqmux33Mixers46Source5Src
                INTEGER,
            iqmux33Mixers46Source5Name
                RollCallString,
            iqmux33Mixers46Source6ProcGain
                INTEGER,
            iqmux33Mixers46Source6Invert
                INTEGER,
            iqmux33Mixers46Source6Mute
                INTEGER,
            iqmux33Mixers46Source6Src
                INTEGER,
            iqmux33Mixers46Source6Name
                RollCallString,
            iqmux33DolbyDecodeDolbyDecoderDetectMode
                INTEGER,
            iqmux33DolbyDecodeDolbyDecoderAESChannelSelect
                INTEGER,
            iqmux33DolbyDecodeDolbyDecoderPCMLatency
                INTEGER,
            iqmux33DolbyDecodeDolbyDecoderListeningModeDolbyD
                INTEGER,
            iqmux33DolbyDecodeDolbyDecoderDynamicRange
                INTEGER,
            iqmux33DolbyDecoderAuxChannelProgramSelect
                INTEGER,
            iqmux33DolbyDecoderAuxChannelDynamicRange
                INTEGER,
            iqmux33DolbyDecoderAuxChannelOutputMode
                INTEGER,
            iqmux33DolbyDecoderDecoderStatusBitstreamFormat
                RollCallString,
            iqmux33DolbyDecoderDecoderStatusBitstreamStatus
                RollCallString,
            iqmux33DolbyDecoderDecoderStatusDCRCErrorCount
                RollCallString,
            iqmux33DolbyDecoderDecoderStatusDCRCErrorTime
                RollCallString,
            iqmux33DolbyDecoderDecoderStatusECRCErrorCount
                RollCallString,
            iqmux33DolbyDecoderDecoderStatusECRCErrorTime
                RollCallString,
            iqmux33DolbyDecoderDecoderStatusResetErrors
                INTEGER,
            iqmux33DolbyDecoderDecoderStatusResetTime
                RollCallString,
            iqmux33DolbyDecoderOutputsA1A2A1Gain
                INTEGER,
            iqmux33DolbyDecoderOutputsA1A2A2Gain
                INTEGER,
            iqmux33DolbyDecoderOutputsA1A2MuteA1
                INTEGER,
            iqmux33DolbyDecoderOutputsA1A2MuteA2
                INTEGER,
            iqmux33DolbyDecoderOutputsA1A2StereoA
                INTEGER,
            iqmux33DolbyDecoderOutputsB3B4B3Gain
                INTEGER,
            iqmux33DolbyDecoderOutputsB3B4B4Gain
                INTEGER,
            iqmux33DolbyDecoderOutputsB3B4MuteB3
                INTEGER,
            iqmux33DolbyDecoderOutputsB3B4MuteB4
                INTEGER,
            iqmux33DolbyDecoderOutputsB3B4StereoB
                INTEGER,
            iqmux33DolbyDecoderOutputsC5C6C5Gain
                INTEGER,
            iqmux33DolbyDecoderOutputsC5C6C6Gain
                INTEGER,
            iqmux33DolbyDecoderOutputsC5C6MuteC5
                INTEGER,
            iqmux33DolbyDecoderOutputsC5C6MuteC6
                INTEGER,
            iqmux33DolbyDecoderOutputsC5C6StereoC
                INTEGER,
            iqmux33DolbyDecoderOutputsD7D8D7Gain
                INTEGER,
            iqmux33DolbyDecoderOutputsD7D8D8Gain
                INTEGER,
            iqmux33DolbyDecoderOutputsD7D8MuteD7
                INTEGER,
            iqmux33DolbyDecoderOutputsD7D8MuteD8
                INTEGER,
            iqmux33DolbyDecoderOutputsD7D8StereoD
                INTEGER,
            iqmux33DolbyDecoderOutputsMLMRMLGain
                INTEGER,
            iqmux33DolbyDecoderOutputsMLMRMRGain
                INTEGER,
            iqmux33DolbyDecoderOutputsMLMRMuteML
                INTEGER,
            iqmux33DolbyDecoderOutputsMLMRMuteMR
                INTEGER,
            iqmux33DolbyDecoderOutputsMLMRStereoM
                INTEGER,
            iqmux33DolbyDecodeDolbyDecoderOutputsMasterGain
                INTEGER,
            iqmux33DolbyDecodeDolbyDecoderOutputsMasterMute
                INTEGER,
            iqmux33DolbyEncInp14Source1ProcGain
                INTEGER,
            iqmux33DolbyEncInp14Source1Mute
                INTEGER,
            iqmux33DolbyEncInp14Source1Src
                INTEGER,
            iqmux33DolbyEncInp14Source2ProcGain
                INTEGER,
            iqmux33DolbyEncInp14Source2Mute
                INTEGER,
            iqmux33DolbyEncInp14Source2Src
                INTEGER,
            iqmux33DolbyEncInp14Source3ProcGain
                INTEGER,
            iqmux33DolbyEncInp14Source3Mute
                INTEGER,
            iqmux33DolbyEncInp14Source3Src
                INTEGER,
            iqmux33DolbyEncInp14Source4ProcGain
                INTEGER,
            iqmux33DolbyEncInp14Source4Mute
                INTEGER,
            iqmux33DolbyEncInp14Source4Src
                INTEGER,
            iqmux33DolbyEncInp58Source5ProcGain
                INTEGER,
            iqmux33DolbyEncInp58Source5Mute
                INTEGER,
            iqmux33DolbyEncInp58Source5Src
                INTEGER,
            iqmux33DolbyEncInp58Source6ProcGain
                INTEGER,
            iqmux33DolbyEncInp58Source6Mute
                INTEGER,
            iqmux33DolbyEncInp58Source6Src
                INTEGER,
            iqmux33DolbyEncInp58Source7ProcGain
                INTEGER,
            iqmux33DolbyEncInp58Source7Mute
                INTEGER,
            iqmux33DolbyEncInp58Source7Src
                INTEGER,
            iqmux33DolbyEncInp58Source8ProcGain
                INTEGER,
            iqmux33DolbyEncInp58Source8Mute
                INTEGER,
            iqmux33DolbyEncInp58Source8Src
                INTEGER,
            iqmux33DolbyControlDolbyEncoderControlSampleRateConversion
                INTEGER,
            iqmux33DolbyControlDolbyEncoderControlMetaRevertMode
                INTEGER,
            iqmux33DolbyControlDolbyEncoderControlEncodingMode
                INTEGER,
            iqmux33DolbyControlDolbyEEncoderCntrlBitDepth
                INTEGER,
            iqmux33DolbyControlDolbyEEncoderCntrlMetadataSource
                INTEGER,
            iqmux33DolbyControlDolbyEEncoderCntrlInternalConfig
                INTEGER,
            iqmux33DolbyControlDolbyEEncoderCntrlDefaultAllMeta
                INTEGER,
            iqmux33DolbyControlDolbyIntMetaCntrlCopyExtMetadata
                INTEGER,
            iqmux33DolbyControlDolbyIntMetaCntrlDefaultProgramMeta
                INTEGER,
            iqmux33DolbyControlDolbyIntMetaCntrlDialogueNorm
                INTEGER,
            iqmux33DolbyControlDolbyIntMetaCntrlChannelMode
                INTEGER,
            iqmux33DolbyControlDolbyIntMetaCntrlLFEChannel
                INTEGER,
            iqmux33DolbyControlDolbyIntMetaCntrlBitstreamMode
                INTEGER,
            iqmux33DolbyControlDolbyIntMetaCntrlRFMode
                INTEGER,
            iqmux33DolbyControlDolbyIntMetaCntrlLineMode
                INTEGER,
            iqmux33DolbyIntMetaCntrlAudioProductionInfoExists
                INTEGER,
            iqmux33DolbyIntMetaCntrlAudioProductionInfoMixLevel
                INTEGER,
            iqmux33DolbyIntMetaCntrlAudioProductionInfoRoomType
                INTEGER,
            iqmux33DolbyControlDolbyIntMetaCntrlCentreMixLevel
                INTEGER,
            iqmux33DolbyControlDolbyIntMetaCntrlSurroundMixLevel
                INTEGER,
            iqmux33DolbyControlDolbyIntMetaCntrlSurroundMode
                INTEGER,
            iqmux33DolbyControlDolbyIntMetaCntrlCopyright
                INTEGER,
            iqmux33DolbyIntMetaCntrlExtendedBSI1Exists
                INTEGER,
            iqmux33DolbyIntMetaCntrlExtendedBSI1StereoDownmixMode
                INTEGER,
            iqmux33DolbyIntMetaCntrlExtendedBSI1LtRtCentreMixLevel
                INTEGER,
            iqmux33DolbyIntMetaCntrlExtendedBSI1LtRtSurrMixLevel
                INTEGER,
            iqmux33DolbyIntMetaCntrlExtendedBSI1LoRoCentreMixLevel
                INTEGER,
            iqmux33DolbyIntMetaCntrlExtendedBSI1LoRoSurrMixLevel
                INTEGER,
            iqmux33DolbyIntMetaCntrlExtendedBSI2Exists
                INTEGER,
            iqmux33DolbyIntMetaCntrlExtendedBSI2SurroundEXMode
                INTEGER,
            iqmux33DolbyIntMetaCntrlExtendedBSI2LowpassFilter
                INTEGER,
            iqmux33DolbyIntMetaCntrlExtendedBSI2LFEFIlter
                INTEGER,
            iqmux33DolbyIntMetaCntrlExtendedBSI2SurrPhaseShiftFltr
                INTEGER,
            iqmux33DolbyIntMetaCntrlExtendedBSI2Surr3dBAttenuator
                INTEGER,
            iqmux33DolbyControlDolbyIntMetaCntrlProgramDescriptionL
                RollCallString,
            iqmux33DolbyControlDolbyIntMetaCntrlProgramDescriptionR
                RollCallString,
            iqmux33DolbyControlDolbyIntMetaCntrlIntMetaSaveset
                INTEGER,
            iqmux33DolbyControlDolbyDEncoderCntrlInternalMode
                INTEGER,
            iqmux33DolbyControlDolbyDEncoderCntrlBitstreamFormat
                INTEGER,
            iqmux33DolbyControlDolbyDEncoderCntrlMetadataSource
                INTEGER,
            iqmux33DolbyControlDolbyDEncoderCntrlIntMetaDataRate
                INTEGER,
            iqmux33DolbyControlDolbyDEncoderCntrlExtMetaDataRate
                INTEGER,
            iqmux33DolbyControlDolbyDEncoderCntrlStreamNumber
                INTEGER,
            iqmux33DolbyControlDolbyMetaProgSelMetaProgramSelect
                INTEGER,
            iqmux33DolbyStatusDolbyCommonStatusVideoSync
                RollCallString,
            iqmux33DolbyStatusDolbyCommonStatusFrameRate
                RollCallString,
            iqmux33DolbyStatusDolbyCommonStatusProgramConfig
                RollCallString,
            iqmux33DolbyStatusDolbyCommonStatusFWVersion
                RollCallString,
            iqmux33DolbyStatusDolbyCommonStatusDeviceName
                RollCallString,
            iqmux33DolbyCommonStatusChannelAssignmentDolbyA1
                RollCallString,
            iqmux33DolbyCommonStatusChannelAssignmentDolbyA2
                RollCallString,
            iqmux33DolbyCommonStatusChannelAssignmentDolbyB3
                RollCallString,
            iqmux33DolbyCommonStatusChannelAssignmentDolbyB4
                RollCallString,
            iqmux33DolbyCommonStatusChannelAssignmentDolbyC5
                RollCallString,
            iqmux33DolbyCommonStatusChannelAssignmentDolbyC6
                RollCallString,
            iqmux33DolbyCommonStatusChannelAssignmentDolbyD7
                RollCallString,
            iqmux33DolbyCommonStatusChannelAssignmentDolbyD8
                RollCallString,
            iqmux33DolbyCommonStatusChnlPairAssignmentDolby12
                RollCallString,
            iqmux33DolbyCommonStatusChnlPairAssignmentDolby34
                RollCallString,
            iqmux33DolbyCommonStatusChnlPairAssignmentDolby56
                RollCallString,
            iqmux33DolbyCommonStatusChnlPairAssignmentDolby78
                RollCallString,
            iqmux33DolbyStatusDolbyExtProgStatusP1Status
                RollCallString,
            iqmux33DolbyStatusDolbyExtProgStatusP2Status
                RollCallString,
            iqmux33DolbyStatusDolbyExtProgStatusP3Status
                RollCallString,
            iqmux33DolbyStatusDolbyExtProgStatusP4Status
                RollCallString,
            iqmux33DolbyStatusDolbyExtProgStatusP5Status
                RollCallString,
            iqmux33DolbyStatusDolbyExtProgStatusP6Status
                RollCallString,
            iqmux33DolbyStatusDolbyExtProgStatusP7Status
                RollCallString,
            iqmux33DolbyStatusDolbyExtProgStatusP8Status
                RollCallString,
            iqmux33DolbyStatusDolbyMetadataStatusProgramDescriptionL
                RollCallString,
            iqmux33DolbyStatusDolbyMetadataStatusProgramDescriptionR
                RollCallString,
            iqmux33DolbyStatusDolbyMetadataStatusDialogueNorm
                RollCallString,
            iqmux33DolbyStatusDolbyMetadataStatusChannelMode
                RollCallString,
            iqmux33DolbyStatusDolbyMetadataStatusLFE
                RollCallString,
            iqmux33DolbyStatusDolbyMetadataStatusBitstreamMode
                RollCallString,
            iqmux33DolbyStatusDolbyMetadataStatusRFMode
                RollCallString,
            iqmux33DolbyStatusDolbyMetadataStatusLineMode
                RollCallString,
            iqmux33DolbyStatusDolbyMetadataStatusCentreMixLevel
                RollCallString,
            iqmux33DolbyStatusDolbyMetadataStatusSurroundMixLevel
                RollCallString,
            iqmux33DolbyStatusDolbyMetadataStatusSurroundMode
                RollCallString,
            iqmux33DolbyStatusDolbyMetadataStatusCopyright
                RollCallString,
            iqmux33DolbyMetadataStatusAudioProductionInfoAudioProdInfoExists
                RollCallString,
            iqmux33DolbyMetadataStatusAudioProductionInfoMixLevel
                RollCallString,
            iqmux33DolbyMetadataStatusAudioProductionInfoRoomType
                RollCallString,
            iqmux33DolbyStatusDolbyMetadataStatusExtendedBSI1Exists
                RollCallString,
            iqmux33DolbyMetadataStatusExtendedBSI1StereoDownmixMode
                RollCallString,
            iqmux33DolbyMetadataStatusExtendedBSI1LtRtCentreMixLevel
                RollCallString,
            iqmux33DolbyMetadataStatusExtendedBSI1LtRtSurrMixLevel
                RollCallString,
            iqmux33DolbyMetadataStatusExtendedBSI1LoRoCentreMixLevel
                RollCallString,
            iqmux33DolbyMetadataStatusExtendedBSI1LoRoSurrMixLevel
                RollCallString,
            iqmux33DolbyStatusDolbyMetadataStatusExtendedBSI2Exists
                RollCallString,
            iqmux33DolbyMetadataStatusExtendedBSI2SurroundEXMode
                RollCallString,
            iqmux33DolbyMetadataStatusExtendedBSI2LowpassFilter
                RollCallString,
            iqmux33DolbyMetadataStatusExtendedBSI2LFEFilter
                RollCallString,
            iqmux33DolbyMetadataStatusExtendedBSI2SurrPhaseShiftFltr
                RollCallString,
            iqmux33DolbyMetadataStatusExtendedBSI2Surr3dBAtten
                RollCallString,
            iqmux33DolbyStatusDolbyEncoderStatusStatus
                RollCallString,
            iqmux33DolbyStatusDolbyEncoderStatusBitstreamStatus
                RollCallString,
            iqmux33DolbyStatusDolbyEncoderStatusReversionStatus
                RollCallString,
            iqmux33DolbyStatusDolbyEncoderStatusHWVersion
                RollCallString,
            iqmux33DolbyStatusDolbyEncoderStatusOPProgramConfig
                RollCallString,
            iqmux33RollCallMemoriesMemoriesABCRecallMemory
                INTEGER,
            iqmux33RollCallMemoriesMemoriesABCSelMemory
                INTEGER,
            iqmux33RollCallMemoriesMemoriesABCSaveMemory
                INTEGER,
            iqmux33RollCallMemoriesMemoriesABCClearMemory
                INTEGER,
            iqmux33MemoriesABCMemoryNameChangeName
                RollCallString,
            iqmux33MemoriesABCMemoryNameLastUserMemory
                RollCallString,
            iqmux33RollCallMemoriesMemoriesABCMemoryName1
                RollCallString,
            iqmux33RollCallMemoriesMemoriesABCMemoryName2
                RollCallString,
            iqmux33RollCallMemoriesMemoriesABCMemoryName3
                RollCallString,
            iqmux33RollCallMemoriesMemoriesABCMemoryName4
                RollCallString,
            iqmux33RollCallMemoriesMemoriesABCMemoryName5
                RollCallString,
            iqmux33RollCallMemoriesMemoriesABCMemoryName6
                RollCallString,
            iqmux33RollCallMemoriesMemoriesABCMemoryName7
                RollCallString,
            iqmux33RollCallMemoriesMemoriesABCMemoryName8
                RollCallString,
            iqmux33RollCallMemoriesMemoriesABCMemoryName9
                RollCallString,
            iqmux33RollCallMemoriesMemoriesABCMemoryName10
                RollCallString,
            iqmux33RollCallMemoriesMemoriesABCMemoryName11
                RollCallString,
            iqmux33RollCallMemoriesMemoriesABCMemoryName12
                RollCallString,
            iqmux33RollCallMemoriesMemoriesABCMemoryName13
                RollCallString,
            iqmux33RollCallMemoriesMemoriesABCMemoryName14
                RollCallString,
            iqmux33RollCallMemoriesMemoriesABCMemoryName15
                RollCallString,
            iqmux33RollCallMemoriesMemoriesABCMemoryName16
                RollCallString,
            iqmux33Logging1AESInputAudLoggingLogAESInput1state
                INTEGER,
            iqmux33Logging1AESInputAudLoggingAESInput1state
                RollCallString,
            iqmux33Logging1AESInputAudLoggingLogAESInput2state
                INTEGER,
            iqmux33Logging1AESInputAudLoggingAESInput2state
                RollCallString,
            iqmux33Logging1AESInputAudLoggingLogAESInput3state
                INTEGER,
            iqmux33Logging1AESInputAudLoggingAESInput3state
                RollCallString,
            iqmux33Logging1AESInputAudLoggingLogAESInput4state
                INTEGER,
            iqmux33Logging1AESInputAudLoggingAESInput4state
                RollCallString,
            iqmux33Logging1AESInputAudLoggingLogAESInput5state
                INTEGER,
            iqmux33Logging1AESInputAudLoggingAESInput5state
                RollCallString,
            iqmux33Logging1AESInputAudLoggingLogAESInput6state
                INTEGER,
            iqmux33Logging1AESInputAudLoggingAESInput6state
                RollCallString,
            iqmux33Logging1AESInputAudLoggingLogAESInput7state
                INTEGER,
            iqmux33Logging1AESInputAudLoggingAESInput7state
                RollCallString,
            iqmux33Logging1AESInputAudLoggingLogAESInput8state
                INTEGER,
            iqmux33Logging1AESInputAudLoggingAESInput8state
                RollCallString,
            iqmux33Logging1OutEmbAudLoggingLogOutEmb11state
                INTEGER,
            iqmux33Logging1OutEmbAudLoggingOutEmb11state
                RollCallString,
            iqmux33Logging1OutEmbAudLoggingLogOutEmb12state
                INTEGER,
            iqmux33Logging1OutEmbAudLoggingOutEmb12state
                RollCallString,
            iqmux33Logging1OutEmbAudLoggingLogOutEmb21state
                INTEGER,
            iqmux33Logging1OutEmbAudLoggingOutEmb21state
                RollCallString,
            iqmux33Logging1OutEmbAudLoggingLogOutEmb22state
                INTEGER,
            iqmux33Logging1OutEmbAudLoggingOutEmb22state
                RollCallString,
            iqmux33Logging1OutEmbAudLoggingLogOutEmb31state
                INTEGER,
            iqmux33Logging1OutEmbAudLoggingOutEmb31state
                RollCallString,
            iqmux33Logging1OutEmbAudLoggingLogOutEmb32state
                INTEGER,
            iqmux33Logging1OutEmbAudLoggingOutEmb32state
                RollCallString,
            iqmux33Logging1OutEmbAudLoggingLogOutEmb41state
                INTEGER,
            iqmux33Logging1OutEmbAudLoggingOutEmb41state
                RollCallString,
            iqmux33Logging1OutEmbAudLoggingLogOutEmb42state
                INTEGER,
            iqmux33Logging1OutEmbAudLoggingOutEmb42state
                RollCallString,
            iqmux33Logging1OutEmbAudLoggingLogOutEmb51state
                INTEGER,
            iqmux33Logging1OutEmbAudLoggingOutEmb51state
                RollCallString,
            iqmux33Logging1OutEmbAudLoggingLogOutEmb52state
                INTEGER,
            iqmux33Logging1OutEmbAudLoggingOutEmb52state
                RollCallString,
            iqmux33Logging1OutEmbAudLoggingLogOutEmb61state
                INTEGER,
            iqmux33Logging1OutEmbAudLoggingOutEmb61state
                RollCallString,
            iqmux33Logging1OutEmbAudLoggingLogOutEmb62state
                INTEGER,
            iqmux33Logging1OutEmbAudLoggingOutEmb62state
                RollCallString,
            iqmux33Logging1OutEmbAudLoggingLogOutEmb71state
                INTEGER,
            iqmux33Logging1OutEmbAudLoggingOutEmb71state
                RollCallString,
            iqmux33Logging1OutEmbAudLoggingLogOutEmb72state
                INTEGER,
            iqmux33Logging1OutEmbAudLoggingOutEmb72state
                RollCallString,
            iqmux33Logging1OutEmbAudLoggingLogOutEmb81state
                INTEGER,
            iqmux33Logging1OutEmbAudLoggingOutEmb81state
                RollCallString,
            iqmux33Logging1OutEmbAudLoggingLogOutEmb82state
                INTEGER,
            iqmux33Logging1OutEmbAudLoggingOutEmb82state
                RollCallString,
            iqmux33Logging1DolbyDecoderLoggingLogBitstreamFormat
                INTEGER,
            iqmux33Logging1DolbyDecoderLoggingBitstreamFormat
                RollCallString,
            iqmux33Logging1DolbyDecoderLoggingLogBitstreamStatus
                INTEGER,
            iqmux33Logging1DolbyDecoderLoggingBitstreamStatus
                RollCallString,
            iqmux33Logging1DolbyDecoderLoggingLogDCRCErrors
                INTEGER,
            iqmux33Logging1DolbyDecoderLoggingDCRCErrorCount
                RollCallString,
            iqmux33Logging1DolbyDecoderLoggingLogECRCErrors
                INTEGER,
            iqmux33Logging1DolbyDecoderLoggingECRCErrorCount
                RollCallString,
            iqmux33Logging1DolbyEncoderLoggingLogEncoderStatus
                INTEGER,
            iqmux33Logging1DolbyEncoderLoggingEncoderStatus
                RollCallString,
            iqmux33Logging1DolbyEncoderLoggingLogBitstreamStatus
                INTEGER,
            iqmux33Logging1DolbyEncoderLoggingBitstreamStatus
                RollCallString,
            iqmux33Logging1DolbyEncoderLoggingLogReversionStatus
                INTEGER,
            iqmux33Logging1DolbyEncoderLoggingReversionStatus
                RollCallString,
            iqmux33Logging1DolbyLoggingLogVideoSync
                INTEGER,
            iqmux33Logging1DolbyLoggingVideoSync
                RollCallString,
            iqmux33Logging1DolbyLoggingLogFrameRate
                INTEGER,
            iqmux33Logging1DolbyLoggingFrameRate
                RollCallString,
            iqmux33Logging1DolbyLoggingLogProgramConfig
                INTEGER,
            iqmux33Logging1DolbyLoggingProgramConfig
                RollCallString,
            iqmux33Logging1DolbyMetadataLoggingLogSelectedProgram
                INTEGER,
            iqmux33Logging1DolbyMetadataLoggingSelectedProgram
                RollCallString,
            iqmux33Logging1DolbyMetadataLoggingLogProgramDescriptor
                INTEGER,
            iqmux33Logging1DolbyMetadataLoggingProgramDescriptor
                RollCallString,
            iqmux33Logging1DolbyMetadataLoggingProgramDescPt2
                RollCallString,
            iqmux33Logging1DolbyMetadataLoggingLogChannelMode
                INTEGER,
            iqmux33Logging1DolbyMetadataLoggingChannelMode
                RollCallString,
            iqmux33Logging1DolbyMetadataLoggingLogLFEChannel
                INTEGER,
            iqmux33Logging1DolbyMetadataLoggingLFEChannel
                RollCallString,
            iqmux33Logging1DolbyMetadataLoggingLogDialogueNorm
                INTEGER,
            iqmux33Logging1DolbyMetadataLoggingDialogueNorm
                RollCallString,
            iqmux33Logging1AncillaryDataLoggingLogVIInp1
                INTEGER,
            iqmux33Logging1AncillaryDataLoggingVIInp1
                RollCallString,
            iqmux33Logging1AncillaryDataLoggingLogWSSInp1
                INTEGER,
            iqmux33Logging1AncillaryDataLoggingWSSInp1
                RollCallString,
            iqmux33Logging1AncillaryDataLoggingLogVITCInp1
                INTEGER,
            iqmux33Logging1AncillaryDataLoggingVITCInp1
                RollCallString,
            iqmux33Logging1AncillaryDataLoggingLogWSTInp1
                INTEGER,
            iqmux33Logging1AncillaryDataLoggingWSTInp1
                RollCallString,
            iqmux33Logging1AncillaryDataLoggingLogCC608Inp1
                INTEGER,
            iqmux33Logging1AncillaryDataLoggingCC608Inp1
                RollCallString,
            iqmux33Logging1AncillaryDataLoggingLogATCInp1
                INTEGER,
            iqmux33Logging1AncillaryDataLoggingATCInp1
                RollCallString,
            iqmux33Logging1AncillaryDataLoggingLogCC708Inp1
                INTEGER,
            iqmux33Logging1AncillaryDataLoggingCC708Inp1
                RollCallString,
            iqmux33Logging1AncillaryDataLoggingLogVIInp2
                INTEGER,
            iqmux33Logging1AncillaryDataLoggingVIInp2
                RollCallString,
            iqmux33Logging1AncillaryDataLoggingLogWSSInp2
                INTEGER,
            iqmux33Logging1AncillaryDataLoggingWSSInp2
                RollCallString,
            iqmux33Logging1AncillaryDataLoggingLogVITCInp2
                INTEGER,
            iqmux33Logging1AncillaryDataLoggingVITCInp2
                RollCallString,
            iqmux33Logging1AncillaryDataLoggingLogWSTInp2
                INTEGER,
            iqmux33Logging1AncillaryDataLoggingWSTInp2
                RollCallString,
            iqmux33Logging1AncillaryDataLoggingLogCC608Inp2
                INTEGER,
            iqmux33Logging1AncillaryDataLoggingCC608Inp2
                RollCallString,
            iqmux33Logging1AncillaryDataLoggingLogATCInp2
                INTEGER,
            iqmux33Logging1AncillaryDataLoggingATCInp2
                RollCallString,
            iqmux33Logging1AncillaryDataLoggingLogCC708Inp2
                INTEGER,
            iqmux33Logging1AncillaryDataLoggingCC708Inp2
                RollCallString,
            iqmux33Logging2VideoRefLogInp1Type
                INTEGER,
            iqmux33Logging2VideoRefInp1Type
                RollCallString,
            iqmux33Logging2VideoRefLogInp1State
                INTEGER,
            iqmux33Logging2VideoRefInp1State
                RollCallString,
            iqmux33Logging2VideoRefLogInp1Std
                INTEGER,
            iqmux33Logging2VideoRefInp1Std
                RollCallString,
            iqmux33Logging2VideoRefLogInp1SDIErrs
                INTEGER,
            iqmux33Logging2VideoRefInp1SDIErrs
                RollCallString,
            iqmux33Logging2VideoRefLogInp1SDIErrSec
                INTEGER,
            iqmux33Logging2VideoRefInp1SDIErrSec
                RollCallString,
            iqmux33Logging2VideoRefLogInp1ANCerrs
                INTEGER,
            iqmux33Logging2VideoRefInp1ANCerrs
                RollCallString,
            iqmux33Logging2VideoRefLogInp1ANCerrSec
                INTEGER,
            iqmux33Logging2VideoRefInp1ANCerrSec
                RollCallString,
            iqmux33Logging2VideoRefLogOutp1Type
                INTEGER,
            iqmux33Logging2VideoRefOutp1Type
                RollCallString,
            iqmux33Logging2VideoRefLogOutp1State
                INTEGER,
            iqmux33Logging2VideoRefOutp1State
                RollCallString,
            iqmux33Logging2VideoRefLogOutp1Std
                INTEGER,
            iqmux33Logging2VideoRefOutp1Std
                RollCallString,
            iqmux33Logging2VideoRefLogOutp1Capt
                INTEGER,
            iqmux33Logging2VideoRefOutp1Capt
                RollCallString,
            iqmux33Logging2VideoRefLogRefType
                INTEGER,
            iqmux33Logging2VideoRefRefType
                RollCallString,
            iqmux33Logging2VideoRefLogRefState
                INTEGER,
            iqmux33Logging2VideoRefRefState
                RollCallString,
            iqmux33Logging2VideoRefLogRefStd
                INTEGER,
            iqmux33Logging2VideoRefRefStd
                RollCallString,
            iqmux33Logging2VideoRefLogGenlockState
                INTEGER,
            iqmux33Logging2VideoRefGenlocState
                RollCallString,
            iqmux33Logging2VideoRefLogInp1Ident
                INTEGER,
            iqmux33Logging2VideoRefInp1Ident
                RollCallString,
            iqmux33Logging2VideoRefLogInp1Name
                INTEGER,
            iqmux33Logging2VideoRefInp1Name
                RollCallString,
            iqmux33Logging2InEmbAudLoggingInpEmb1state
                RollCallString,
            iqmux33Logging2InEmbAudLoggingInpEmb2state
                RollCallString,
            iqmux33Logging2InEmbAudLoggingInpEmb3state
                RollCallString,
            iqmux33Logging2InEmbAudLoggingInpEmb4state
                RollCallString,
            iqmux33Logging2InEmbAudLoggingInpEmb5state
                RollCallString,
            iqmux33Logging2InEmbAudLoggingInpEmb6state
                RollCallString,
            iqmux33Logging2InEmbAudLoggingInpEmb7state
                RollCallString,
            iqmux33Logging2InEmbAudLoggingInpEmb8state
                RollCallString,
            iqmux33Logging2In1EmbAudLoggingLogInp1Emb1state
                INTEGER,
            iqmux33Logging2In1EmbAudLoggingInp1Emb1state
                RollCallString,
            iqmux33Logging2In1EmbAudLoggingLogInp1Emb2state
                INTEGER,
            iqmux33Logging2In1EmbAudLoggingInp1Emb2state
                RollCallString,
            iqmux33Logging2In1EmbAudLoggingLogInp1Emb3state
                INTEGER,
            iqmux33Logging2In1EmbAudLoggingInp1Emb3state
                RollCallString,
            iqmux33Logging2In1EmbAudLoggingLogInp1Emb4state
                INTEGER,
            iqmux33Logging2In1EmbAudLoggingInp1Emb4state
                RollCallString,
            iqmux33Logging2In1EmbAudLoggingLogInp1Emb5state
                INTEGER,
            iqmux33Logging2In1EmbAudLoggingInp1Emb5state
                RollCallString,
            iqmux33Logging2In1EmbAudLoggingLogInp1Emb6state
                INTEGER,
            iqmux33Logging2In1EmbAudLoggingInp1Emb6state
                RollCallString,
            iqmux33Logging2In1EmbAudLoggingLogInp1Emb7state
                INTEGER,
            iqmux33Logging2In1EmbAudLoggingInp1Emb7state
                RollCallString,
            iqmux33Logging2In1EmbAudLoggingLogInp1Emb8state
                INTEGER,
            iqmux33Logging2In1EmbAudLoggingInp1Emb8state
                RollCallString,
            iqmux33Logging2DolbyEAlignLogOutEmb1dolby
                INTEGER,
            iqmux33Logging2DolbyEAlignOutEmb1Dolby
                RollCallString,
            iqmux33Logging2DolbyEAlignLogOutEmb2dolby
                INTEGER,
            iqmux33Logging2DolbyEAlignOutEmb2Dolby
                RollCallString,
            iqmux33Logging2DolbyEAlignLogOutEmb3dolby
                INTEGER,
            iqmux33Logging2DolbyEAlignOutEmb3Dolby
                RollCallString,
            iqmux33Logging2DolbyEAlignLogOutEmb4dolby
                INTEGER,
            iqmux33Logging2DolbyEAlignOutEmb4Dolby
                RollCallString,
            iqmux33Logging2DolbyEAlignLogOutEmb5dolby
                INTEGER,
            iqmux33Logging2DolbyEAlignOutEmb5Dolby
                RollCallString,
            iqmux33Logging2DolbyEAlignLogOutEmb6dolby
                INTEGER,
            iqmux33Logging2DolbyEAlignOutEmb6Dolby
                RollCallString,
            iqmux33Logging2DolbyEAlignLogOutEmb7dolby
                INTEGER,
            iqmux33Logging2DolbyEAlignOutEmb7Dolby
                RollCallString,
            iqmux33Logging2DolbyEAlignLogOutEmb8dolby
                INTEGER,
            iqmux33Logging2DolbyEAlignOutEmb8Dolby
                RollCallString,
            iqmux33Logging2MiscLoggingLogSerialNo
                INTEGER,
            iqmux33Logging2MiscLoggingSerialNo
                RollCallString,
            iqmux33Logging2MiscLoggingLogOSVersion
                INTEGER,
            iqmux33Logging2MiscLoggingOSVersion
                RollCallString,
            iqmux33Logging2MiscLoggingLogBuildNo
                INTEGER,
            iqmux33Logging2MiscLoggingBuildNo
                RollCallString,
            iqmux33Logging2MiscLoggingLogHardwareVer
                INTEGER,
            iqmux33Logging2MiscLoggingHardwareVer
                RollCallString,
            iqmux33Logging2MiscLoggingLogFirmwareVer
                INTEGER,
            iqmux33Logging2MiscLoggingFirmwareVer
                RollCallString,
            iqmux33Logging2MiscLoggingLogUpTime
                INTEGER,
            iqmux33Logging2MiscLoggingUpTime
                RollCallString,
            iqmux33Logging2MiscLoggingLogLicensedOpt
                INTEGER,
            iqmux33Logging2MiscLoggingLicensedOptions
                RollCallString,
            iqmux33Logging2MiscLoggingLogLicensedOpt2
                INTEGER,
            iqmux33Logging2MiscLoggingLicensedOptions2
                RollCallString,
            iqmux33Logging2MiscLoggingLogTemp1State
                INTEGER,
            iqmux33Logging2MiscLoggingTemp1State
                RollCallString,
            iqmux33Logging2MiscLoggingLogTemp1Name
                INTEGER,
            iqmux33Logging2MiscLoggingTemp1Name
                RollCallString,
            iqmux33Logging2MiscLoggingLogRearId
                INTEGER,
            iqmux33Logging2MiscLoggingRearID
                RollCallString,
            iqmux33Logging2MiscLoggingLogSlotWidth
                INTEGER,
            iqmux33Logging2MiscLoggingSlotWidth
                RollCallString,
            iqmux33Logging2MiscLoggingLogSlotStart
                INTEGER,
            iqmux33Logging2MiscLoggingSlotStart
                RollCallString,
            iqmux33Logging2MiscLoggingLogRearStatus
                INTEGER,
            iqmux33Logging2MiscLoggingRearSTATUS
                RollCallString,
            iqmux33RollCallMemoriesRollTrackDisableAll
                INTEGER,
            iqmux33RollCallMemoriesRollTrackIndex
                INTEGER,
            iqmux33RollCallMemoriesRollTrackSource
                INTEGER,
            iqmux33RollCallMemoriesRollTrackAddress
                RollCallString,
            iqmux33RollCallMemoriesRollTrackCommand
                RollCallString,
            iqmux33RollCallMemoriesRollTrackStatus
                RollCallString,
            iqmux33RollCallMemoriesRollTrackSending
                RollCallString,
            iqmux33RollCallMemoriesHideGpio
                INTEGER,
            iqmux33RollCallMemoriesHideInpAES14
                INTEGER,
            iqmux33RollCallMemoriesHideInpAES18
                INTEGER,
            iqmux33RollCallMemoriesHideInpLogAES14
                INTEGER,
            iqmux33RollCallMemoriesHideInpLogAES18
                INTEGER,
            iqmux33RollCallMemoriesHideOutAES14
                INTEGER,
            iqmux33RollCallMemoriesHideOutAES18
                INTEGER,
            iqmux33RollCallMemoriesHideOutLogAES14
                INTEGER,
            iqmux33RollCallMemoriesHideOutLogAES18
                INTEGER,
            iqmux33GPIOGPI1GPIO1Mode
                INTEGER,
            iqmux33GPIOGPI1GPI1IPHighSelect
                INTEGER,
            iqmux33GPIOGPI1GPI1IPLowSelect
                INTEGER,
            iqmux33GPIOGPI1GPO1OPSelect
                INTEGER,
            iqmux33GPIOGPI1InvertGPIO1
                INTEGER,
            iqmux33GPIOGPI1Status
                RollCallString,
            iqmux33GPIOGPI2GPIO2Mode
                INTEGER,
            iqmux33GPIOGPI2GPI2IPHighSelect
                INTEGER,
            iqmux33GPIOGPI2GPI2IPLowSelect
                INTEGER,
            iqmux33GPIOGPI2GPO2OPSelect
                INTEGER,
            iqmux33GPIOGPI2InvertGPIO2
                INTEGER,
            iqmux33GPIOGPI2Status
                RollCallString,
            iqmux33SetupDisplay
                INTEGER,
            iqmux33SetupProduct
                RollCallString,
            iqmux33SetupRelease
                RollCallString,
            iqmux33SetupBuild
                RollCallString,
            iqmux33SetupKOS
                RollCallString,
            iqmux33SetupSerialNo
                RollCallString,
            iqmux33SetupFactoryDefault
                INTEGER,
            iqmux33SetupRestart
                INTEGER,
            iqmux33SetupDefaultSettings
                INTEGER,
            iqmux33SetupSerialNumber
                RollCallString,
            iqmux33SetupBoardID
                INTEGER,
            iqmux33SetupSaveID
                INTEGER,
            iqmux33SetupFpgaBoardType
                RollCallString,
            iqmux33SetupFpgaSerialNo
                RollCallString,
            iqmux33SetupFpgaSoftVer
                RollCallString,
            iqmux33SetupFpgaVer
                RollCallString,
            iqmux33SetupFpgaTIVer
                RollCallString,
            iqmux33SetupFpgaDolbyModId
                RollCallString,
            iqmux33SetupFpgaProtVer
                RollCallString,
            iqmux33SetupFpgaProgCRC
                RollCallString,
            iqmux33SetupFpgaUptime
                RollCallString,
            iqmux33SetupFpgaENGVXPVer
                RollCallString,
            iqmux33SetupFpgaENGSharcVer
                RollCallString,
            iqmux33SetupFpgaENGAlteraVer
                RollCallString,
            iqmux33SetupFpgaENGVCCint
                RollCallString,
            iqmux33SetupFpgaENGVCCaux
                RollCallString,
            iqmux33SetupOptionsOption1
                RollCallString,
            iqmux33SetupOptionsOption2
                RollCallString,
            iqmux33SetupOptionsOption3
                RollCallString,
            iqmux33SetupOptionsOption4
                RollCallString,
            iqmux33SetupOptionsOption5
                RollCallString,
            iqmux33SetupOptionsOption6
                RollCallString,
            iqmux33SetupOptionsOption7
                RollCallString,
            iqmux33SetupOptionsOption8
                RollCallString,
            iqmux33SetupOptionsOption9
                RollCallString,
            iqmux33SetupOptionsMask
                INTEGER,
            iqmux33SetupDemoNonDemoRestart
                INTEGER,
            iqmux33SetupDemoPeriod
                INTEGER,
            iqmux33SetupDemoRestartMode
                INTEGER,
            iqmux33SetupDemoRemainingDemo
                INTEGER,
            iqmux33SetupDemoRemaining24h
                INTEGER,
            iqmux33SetupDemoStatus
                INTEGER,
            iqmux33SetupRestartHard
                INTEGER,
            iqmux33SetupInput1Name
                RollCallString,
            iqmux33SetupInput2Name
                RollCallString,
            iqmux33SetupInput3Name
                RollCallString,
            iqmux33SetupCalibrationVideoOut8
                INTEGER,
            iqmux33SetupCalibrationVideoOut10
                INTEGER,
            iqmux33SetupCalibrationVideoOut11
                INTEGER,
            iqmux33SetupCalibrationAudio0
                INTEGER,
            iqmux33SetupCalibrationAudio1
                INTEGER,
            iqmux33SetupCalibrationAudio2
                INTEGER,
            iqmux33SetupCalibrationAudio3
                INTEGER,
            iqmux33SetupCalibrationCalibrateTake
                INTEGER,
            iqmux33SetupCalibrationCalibratePreset
                INTEGER,
            iqmux33SetupCalibrationCalibrateDefault
                INTEGER,
            iqmux33SetupCalibrationCalibrateFactory
                INTEGER,
            iqmux33SetupCalibrationCalUnlock
                RollCallString,
            iqmux33LKFS1SourceLSrc
                INTEGER,
            iqmux33LKFS1SourceRSrc
                INTEGER,
            iqmux33LKFS1SourceLSSrc
                INTEGER,
            iqmux33LKFS1SourceRSSrc
                INTEGER,
            iqmux33LKFS1SourceCSrc
                INTEGER,
            iqmux33LKFS1ResetSession
                INTEGER,
            iqmux33LKFS1SessLevel
                RollCallString,
            iqmux33LKFS1SessTime
                RollCallString,
            iqmux33LKFS1currrate
                INTEGER,
            iqmux33LKFS1CurrLevelTime
                RollCallString,
            iqmux33LKFS1CurrLevel
                RollCallString,
            iqmux33LKFS1CurrLevel2
                RollCallString,
            iqmux33LKFS1RollMapUpd
                RollCallString,
            iqmux33LKFS1UpdateRate
                INTEGER,
            iqmux33LKFS2SourceLSrc
                INTEGER,
            iqmux33LKFS2SourceRSrc
                INTEGER,
            iqmux33LKFS2SourceLSSrc
                INTEGER,
            iqmux33LKFS2SourceRSSrc
                INTEGER,
            iqmux33LKFS2SourceCSrc
                INTEGER,
            iqmux33LKFS2SessLevel
                RollCallString,
            iqmux33LKFS2CurrLevel
                RollCallString,
            iqmux33LKFS2CurrLevel2
                RollCallString
        }

    iqmux33SlotIndex OBJECT-TYPE
        SYNTAX            Unsigned32
        MAX-ACCESS        not-accessible
        STATUS            current
        DESCRIPTION
                "The unique Index value for each slot.  Its value
                ranges between 1 and the value of slotNumber."
        ::= { iqmux33CmdEntry 99999 }


    iqmux33Video1VideoInputInput1Std OBJECT-TYPE
        SYNTAX            RollCallString
        MAX-ACCESS        read-only
        STATUS            current
        DESCRIPTION
                "CMNT: - Input 1 Standard
                 TYPE: - Display
                 PAGE: - Video1
                    Input 1 Std  cmdID= 40703  "
        ::= { iqmux33CmdEntry 40703 }


    iqmux33VideoInputValidStandards108050p OBJECT-TYPE
        SYNTAX            INTEGER { disable(0), enable(1)  }
        MAX-ACCESS        read-write
        STATUS            current
        DESCRIPTION
                "CMNT: - Select valid input standards
                 TYPE: - Checkbox
                 PAGE: - Video Input
                    1080/50p  cmdID= 33004  "
        ::= { iqmux33CmdEntry 33004 }


    iqmux33VideoInputValidStandards108059p OBJECT-TYPE
        SYNTAX            INTEGER { disable(0), enable(1)  }
        MAX-ACCESS        read-write
        STATUS            current
        DESCRIPTION
                "CMNT: - Select valid input standards
                 TYPE: - Checkbox
                 PAGE: - Video Input
                    1080/59p  cmdID= 33005  "
        ::= { iqmux33CmdEntry 33005 }


    iqmux33VideoInputValidStandards108025i OBJECT-TYPE
        SYNTAX            INTEGER { disable(0), enable(1)  }
        MAX-ACCESS        read-write
        STATUS            current
        DESCRIPTION
                "CMNT: - Select valid input standards
                 TYPE: - Checkbox
                 PAGE: - Video Input
                    1080/25i  cmdID= 33006  "
        ::= { iqmux33CmdEntry 33006 }


    iqmux33VideoInputValidStandards108029i OBJECT-TYPE
        SYNTAX            INTEGER { disable(0), enable(1)  }
        MAX-ACCESS        read-write
        STATUS            current
        DESCRIPTION
                "CMNT: - Select valid input standards
                 TYPE: - Checkbox
                 PAGE: - Video Input
                    1080/29i  cmdID= 33007  "
        ::= { iqmux33CmdEntry 33007 }


    iqmux33VideoInputValidStandards72050p OBJECT-TYPE
        SYNTAX            INTEGER { disable(0), enable(1)  }
        MAX-ACCESS        read-write
        STATUS            current
        DESCRIPTION
                "CMNT: - Select valid input standards
                 TYPE: - Checkbox
                 PAGE: - Video Input
                    720/50p  cmdID= 33010  "
        ::= { iqmux33CmdEntry 33010 }


    iqmux33VideoInputValidStandards72059p OBJECT-TYPE
        SYNTAX            INTEGER { disable(0), enable(1)  }
        MAX-ACCESS        read-write
        STATUS            current
        DESCRIPTION
                "CMNT: - Select valid input standards
                 TYPE: - Checkbox
                 PAGE: - Video Input
                    720/59p  cmdID= 33011  "
        ::= { iqmux33CmdEntry 33011 }


    iqmux33VideoInputValidStandards62525i OBJECT-TYPE
        SYNTAX            INTEGER { disable(0), enable(1)  }
        MAX-ACCESS        read-write
        STATUS            current
        DESCRIPTION
                "CMNT: - Select valid input standards
                 TYPE: - Checkbox
                 PAGE: - Video Input
                    625/25i  cmdID= 33009  "
        ::= { iqmux33CmdEntry 33009 }


    iqmux33VideoInputValidStandards52529i OBJECT-TYPE
        SYNTAX            INTEGER { disable(0), enable(1)  }
        MAX-ACCESS        read-write
        STATUS            current
        DESCRIPTION
                "CMNT: - Select valid input standards
                 TYPE: - Checkbox
                 PAGE: - Video Input
                    525/29i  cmdID= 33008  "
        ::= { iqmux33CmdEntry 33008 }


    iqmux33VideoInputValidStandards108023psf OBJECT-TYPE
        SYNTAX            INTEGER { disable(0), enable(1)  }
        MAX-ACCESS        read-write
        STATUS            current
        DESCRIPTION
                "CMNT: - Select valid input standards
                 TYPE: - Checkbox
                 PAGE: - Video Input
                    1080/23psf  cmdID= 33046  "
        ::= { iqmux33CmdEntry 33046 }


    iqmux33VideoInputValidStandards108025psf OBJECT-TYPE
        SYNTAX            INTEGER { disable(0), enable(1)  }
        MAX-ACCESS        read-write
        STATUS            current
        DESCRIPTION
                "CMNT: - Select valid input standards
                 TYPE: - Checkbox
                 PAGE: - Video Input
                    1080/25psf  cmdID= 33047  "
        ::= { iqmux33CmdEntry 33047 }


    iqmux33VideoInputValidStandards108025p OBJECT-TYPE
        SYNTAX            INTEGER { disable(0), enable(1)  }
        MAX-ACCESS        read-write
        STATUS            current
        DESCRIPTION
                "CMNT: - Select valid input standards
                 TYPE: - Checkbox
                 PAGE: - Video Input
                    1080/25p  cmdID= 33048  "
        ::= { iqmux33CmdEntry 33048 }


    iqmux33VideoInputValidStandards108029p OBJECT-TYPE
        SYNTAX            INTEGER { disable(0), enable(1)  }
        MAX-ACCESS        read-write
        STATUS            current
        DESCRIPTION
                "CMNT: - Select valid input standards
                 TYPE: - Checkbox
                 PAGE: - Video Input
                    1080/29p  cmdID= 33049  "
        ::= { iqmux33CmdEntry 33049 }


    iqmux33VideoInputErrorsErrorReset OBJECT-TYPE
        SYNTAX            INTEGER { noAction(0),valErrorReset(1) }
        MAX-ACCESS        read-write
        STATUS            current
        DESCRIPTION
                "CMNT: - 
                 TYPE: - Button
                 PAGE: - Video Input
                    Error Reset  cmdID= 33014
                    value= 1  "
        ::= { iqmux33CmdEntry 33014 }


    iqmux33VideoInputErrorsResetSec OBJECT-TYPE
        SYNTAX            RollCallString
        MAX-ACCESS        read-only
        STATUS            current
        DESCRIPTION
                "CMNT: - 
                 TYPE: - Display
                 PAGE: - Video Input
                    ResetSec  cmdID= 33015  "
        ::= { iqmux33CmdEntry 33015 }


    iqmux33VideoInputErrorsCRCErrs1 OBJECT-TYPE
        SYNTAX            RollCallString
        MAX-ACCESS        read-only
        STATUS            current
        DESCRIPTION
                "CMNT: - 
                 TYPE: - Display
                 PAGE: - Video Input
                    CRC Errs1  cmdID= 33016  "
        ::= { iqmux33CmdEntry 33016 }


    iqmux33VideoInputErrorsANCErrs1 OBJECT-TYPE
        SYNTAX            RollCallString
        MAX-ACCESS        read-only
        STATUS            current
        DESCRIPTION
                "CMNT: - 
                 TYPE: - Display
                 PAGE: - Video Input
                    ANC Errs1  cmdID= 33020  "
        ::= { iqmux33CmdEntry 33020 }


    iqmux33VideoInputErrorsCRCErrSec1 OBJECT-TYPE
        SYNTAX            RollCallString
        MAX-ACCESS        read-only
        STATUS            current
        DESCRIPTION
                "CMNT: - 
                 TYPE: - Display
                 PAGE: - Video Input
                    CRC ErrSec1  cmdID= 33017  "
        ::= { iqmux33CmdEntry 33017 }


    iqmux33VideoInputErrorsANCErrSec1 OBJECT-TYPE
        SYNTAX            RollCallString
        MAX-ACCESS        read-only
        STATUS            current
        DESCRIPTION
                "CMNT: - 
                 TYPE: - Display
                 PAGE: - Video Input
                    ANC ErrSec1  cmdID= 33021  "
        ::= { iqmux33CmdEntry 33021 }


    iqmux33Video1VideoInputYCDelay OBJECT-TYPE
        SYNTAX            INTEGER
        MAX-ACCESS        read-write
        STATUS            current
        DESCRIPTION
                "CMNT: - 
                 TYPE: - Number
                 PAGE: - Video1
                    YC Delay  cmdID= 32999
                    min= -8  max= 7  step= 1  format= %0.0f  div_scale= 1  preset= 0
                    Min = -8  Max = 7  Step = 1  Preset = 0  "
        ::= { iqmux33CmdEntry 32999 }


    iqmux33Video1BackupQualifyInvStd OBJECT-TYPE
        SYNTAX            INTEGER { disable(0), enable(1)  }
        MAX-ACCESS        read-write
        STATUS            current
        DESCRIPTION
                "CMNT: - Backup Invalid Standard
                 TYPE: - Checkbox
                 PAGE: - Video1
                    Qualify Inv Std  cmdID= 39104  "
        ::= { iqmux33CmdEntry 39104 }


    iqmux33Video1BackupQualifyAudioFail OBJECT-TYPE
        SYNTAX            INTEGER { disable(0), enable(1)  }
        MAX-ACCESS        read-write
        STATUS            current
        DESCRIPTION
                "CMNT: - Backup Qual Audio Lost
                 TYPE: - Checkbox
                 PAGE: - Video1
                    Qualify Audio Fail  cmdID= 39142  "
        ::= { iqmux33CmdEntry 39142 }


    iqmux33BackupInput1SelStatInp1OK OBJECT-TYPE
        SYNTAX            RollCallString
        MAX-ACCESS        read-only
        STATUS            current
        DESCRIPTION
                "CMNT: - Backup Sel 1 Inp 1 OK Status
                 TYPE: - Display
                 PAGE: - Backup
                    Stat Inp1 OK  cmdID= 39127  "
        ::= { iqmux33CmdEntry 39127 }


    iqmux33BackupInput1SelStatGPI1 OBJECT-TYPE
        SYNTAX            RollCallString
        MAX-ACCESS        read-only
        STATUS            current
        DESCRIPTION
                "CMNT: - Backup Sel 1 GPI 1 Status
                 TYPE: - Display
                 PAGE: - Backup
                    Stat GPI 1  cmdID= 39129  "
        ::= { iqmux33CmdEntry 39129 }


    iqmux33BackupInput1SelStatGPI2 OBJECT-TYPE
        SYNTAX            RollCallString
        MAX-ACCESS        read-only
        STATUS            current
        DESCRIPTION
                "CMNT: - Backup Sel 1 GPI 2 Status
                 TYPE: - Display
                 PAGE: - Backup
                    Stat GPI 2  cmdID= 39130  "
        ::= { iqmux33CmdEntry 39130 }


    iqmux33BackupInput1SelEnblInp1OK OBJECT-TYPE
        SYNTAX            INTEGER { disable(0), enable(1)  }
        MAX-ACCESS        read-write
        STATUS            current
        DESCRIPTION
                "CMNT: - Backup Sel 1 Inp 1 OK
                 TYPE: - Checkbox
                 PAGE: - Backup
                    Enbl Inp1 OK  cmdID= 39107  "
        ::= { iqmux33CmdEntry 39107 }


    iqmux33BackupInput1SelEnblGPI1 OBJECT-TYPE
        SYNTAX            INTEGER { disable(0), enable(1)  }
        MAX-ACCESS        read-write
        STATUS            current
        DESCRIPTION
                "CMNT: - Backup Sel 1 GPI 1
                 TYPE: - Checkbox
                 PAGE: - Backup
                    Enbl GPI 1  cmdID= 39109  "
        ::= { iqmux33CmdEntry 39109 }


    iqmux33BackupInput1SelEnblGPI2 OBJECT-TYPE
        SYNTAX            INTEGER { disable(0), enable(1)  }
        MAX-ACCESS        read-write
        STATUS            current
        DESCRIPTION
                "CMNT: - Backup Sel 1 GPI 2
                 TYPE: - Checkbox
                 PAGE: - Backup
                    Enbl GPI 2  cmdID= 39110  "
        ::= { iqmux33CmdEntry 39110 }


    iqmux33BackupInput1SelDlyInp1OK OBJECT-TYPE
        SYNTAX            INTEGER
        MAX-ACCESS        read-write
        STATUS            current
        DESCRIPTION
                "CMNT: - Backup Sel 1 Inp 1 OK Delay
                 TYPE: - Number
                 PAGE: - Backup
                    Dly Inp1 OK  cmdID= 39115
                    min= 10  max= 100  step= 1  format= %0.1f s  div_scale= 10  preset= 10
                    Min = 1.0 s  Max = 10.0 s  Step = 0.1 s  Preset = 1.0 s  "
        ::= { iqmux33CmdEntry 39115 }


    iqmux33BackupInput1SelDlyGPI1 OBJECT-TYPE
        SYNTAX            INTEGER
        MAX-ACCESS        read-write
        STATUS            current
        DESCRIPTION
                "CMNT: - Backup Sel 1 GPI 1 Delay
                 TYPE: - Number
                 PAGE: - Backup
                    Dly GPI 1  cmdID= 39117
                    min= 0  max= 100  step= 1  format= %0.1f s  div_scale= 10  preset= 0
                    Min = 0.0 s  Max = 10.0 s  Step = 0.1 s  Preset = 0.0 s  "
        ::= { iqmux33CmdEntry 39117 }


    iqmux33BackupInput1SelDlyGPI2 OBJECT-TYPE
        SYNTAX            INTEGER
        MAX-ACCESS        read-write
        STATUS            current
        DESCRIPTION
                "CMNT: - Backup Sel 1 GPI 2 Delay
                 TYPE: - Number
                 PAGE: - Backup
                    Dly GPI 2  cmdID= 39118
                    min= 0  max= 100  step= 1  format= %0.1f s  div_scale= 10  preset= 0
                    Min = 0.0 s  Max = 10.0 s  Step = 0.1 s  Preset = 0.0 s  "
        ::= { iqmux33CmdEntry 39118 }


    iqmux33BackupInput1SelGPI1State OBJECT-TYPE
        SYNTAX            INTEGER {
                            valHigh(1),
                            valLow(0)
                            }
        MAX-ACCESS        read-write
        STATUS            current
        DESCRIPTION
                "CMNT: - Backup Sel 1 GPI 1 val
                 TYPE: - RadiobuttonList
                 PAGE: - Backup
                    GPI 1 State  cmdID= 39123
                    High  value= 1
                    Low  value= 0  "
        ::= { iqmux33CmdEntry 39123 }


    iqmux33BackupInput1SelGPI2State OBJECT-TYPE
        SYNTAX            INTEGER {
                            valHigh(1),
                            valLow(0)
                            }
        MAX-ACCESS        read-write
        STATUS            current
        DESCRIPTION
                "CMNT: - Backup Sel 1 GPI 2 val
                 TYPE: - RadiobuttonList
                 PAGE: - Backup
                    GPI 2 State  cmdID= 39124
                    High  value= 1
                    Low  value= 0  "
        ::= { iqmux33CmdEntry 39124 }


    iqmux33BackupInput2SelStatInp2OK OBJECT-TYPE
        SYNTAX            RollCallString
        MAX-ACCESS        read-only
        STATUS            current
        DESCRIPTION
                "CMNT: - Backup Sel 2 Inp 2 OK Status
                 TYPE: - Display
                 PAGE: - Backup
                    Stat Inp2 OK  cmdID= 39131  "
        ::= { iqmux33CmdEntry 39131 }


    iqmux33BackupInput2SelStatGPI1 OBJECT-TYPE
        SYNTAX            RollCallString
        MAX-ACCESS        read-only
        STATUS            current
        DESCRIPTION
                "CMNT: - Backup Sel 2 GPI 1 Status
                 TYPE: - Display
                 PAGE: - Backup
                    Stat GPI 1  cmdID= 39133  "
        ::= { iqmux33CmdEntry 39133 }


    iqmux33BackupInput2SelStatGPI2 OBJECT-TYPE
        SYNTAX            RollCallString
        MAX-ACCESS        read-only
        STATUS            current
        DESCRIPTION
                "CMNT: - Backup Sel 2 GPI 2 Status
                 TYPE: - Display
                 PAGE: - Backup
                    Stat GPI 2  cmdID= 39134  "
        ::= { iqmux33CmdEntry 39134 }


    iqmux33BackupInput2SelEnblInp2OK OBJECT-TYPE
        SYNTAX            INTEGER { disable(0), enable(1)  }
        MAX-ACCESS        read-write
        STATUS            current
        DESCRIPTION
                "CMNT: - Backup Sel 2 Inp 2 OK
                 TYPE: - Checkbox
                 PAGE: - Backup
                    Enbl Inp2 OK  cmdID= 39111  "
        ::= { iqmux33CmdEntry 39111 }


    iqmux33BackupInput2SelEnblGPI1 OBJECT-TYPE
        SYNTAX            INTEGER { disable(0), enable(1)  }
        MAX-ACCESS        read-write
        STATUS            current
        DESCRIPTION
                "CMNT: - Backup Sel 2 GPI 1
                 TYPE: - Checkbox
                 PAGE: - Backup
                    Enbl GPI 1  cmdID= 39113  "
        ::= { iqmux33CmdEntry 39113 }


    iqmux33BackupInput2SelEnblGPI2 OBJECT-TYPE
        SYNTAX            INTEGER { disable(0), enable(1)  }
        MAX-ACCESS        read-write
        STATUS            current
        DESCRIPTION
                "CMNT: - Backup Sel 2 GPI 2
                 TYPE: - Checkbox
                 PAGE: - Backup
                    Enbl GPI 2  cmdID= 39114  "
        ::= { iqmux33CmdEntry 39114 }


    iqmux33BackupInput2SelDlyInp2OK OBJECT-TYPE
        SYNTAX            INTEGER
        MAX-ACCESS        read-write
        STATUS            current
        DESCRIPTION
                "CMNT: - Backup Sel 2 Inp 2 OK Delay
                 TYPE: - Number
                 PAGE: - Backup
                    Dly Inp2 OK  cmdID= 39119
                    min= 10  max= 100  step= 1  format= %0.1f s  div_scale= 10  preset= 10
                    Min = 1.0 s  Max = 10.0 s  Step = 0.1 s  Preset = 1.0 s  "
        ::= { iqmux33CmdEntry 39119 }


    iqmux33BackupInput2SelDlyGPI1 OBJECT-TYPE
        SYNTAX            INTEGER
        MAX-ACCESS        read-write
        STATUS            current
        DESCRIPTION
                "CMNT: - Backup Sel 2 GPI 1 Delay
                 TYPE: - Number
                 PAGE: - Backup
                    Dly GPI 1  cmdID= 39121
                    min= 0  max= 100  step= 1  format= %0.1f s  div_scale= 10  preset= 0
                    Min = 0.0 s  Max = 10.0 s  Step = 0.1 s  Preset = 0.0 s  "
        ::= { iqmux33CmdEntry 39121 }


    iqmux33BackupInput2SelDlyGPI2 OBJECT-TYPE
        SYNTAX            INTEGER
        MAX-ACCESS        read-write
        STATUS            current
        DESCRIPTION
                "CMNT: - Backup Sel 2 GPI 2 Delay
                 TYPE: - Number
                 PAGE: - Backup
                    Dly GPI 2  cmdID= 39122
                    min= 0  max= 100  step= 1  format= %0.1f s  div_scale= 10  preset= 0
                    Min = 0.0 s  Max = 10.0 s  Step = 0.1 s  Preset = 0.0 s  "
        ::= { iqmux33CmdEntry 39122 }


    iqmux33BackupInput2SelGPI1State OBJECT-TYPE
        SYNTAX            INTEGER {
                            valOn(0),
                            valOff(1)
                            }
        MAX-ACCESS        read-write
        STATUS            current
        DESCRIPTION
                "CMNT: - Backup Sel 2 GPI 1 val
                 TYPE: - RadiobuttonList
                 PAGE: - Backup
                    GPI 1 State  cmdID= 39125
                    On  value= 0
                    Off  value= 1  "
        ::= { iqmux33CmdEntry 39125 }


    iqmux33BackupInput2SelGPI2State OBJECT-TYPE
        SYNTAX            INTEGER {
                            valOn(0),
                            valOff(1)
                            }
        MAX-ACCESS        read-write
        STATUS            current
        DESCRIPTION
                "CMNT: - Backup Sel 2 GPI 2 val
                 TYPE: - RadiobuttonList
                 PAGE: - Backup
                    GPI 2 State  cmdID= 39126
                    On  value= 0
                    Off  value= 1  "
        ::= { iqmux33CmdEntry 39126 }


    iqmux33Video2VideoOutputOutputAType OBJECT-TYPE
        SYNTAX            INTEGER {
                            valProcessed(0),
                            valReclocked(1)
                            }
        MAX-ACCESS        read-write
        STATUS            current
        DESCRIPTION
                "CMNT: - Output A type
                 TYPE: - RadiobuttonList
                 PAGE: - Video2
                    Output A Type  cmdID= 40701
                    Processed  value= 0
                    Reclocked  value= 1  "
        ::= { iqmux33CmdEntry 40701 }


    iqmux33Video2VideoOutputOutputBType OBJECT-TYPE
        SYNTAX            INTEGER {
                            valProcessed(0),
                            valReclocked(1)
                            }
        MAX-ACCESS        read-write
        STATUS            current
        DESCRIPTION
                "CMNT: - Output B type
                 TYPE: - RadiobuttonList
                 PAGE: - Video2
                    Output B Type  cmdID= 40702
                    Processed  value= 0
                    Reclocked  value= 1  "
        ::= { iqmux33CmdEntry 40702 }


    iqmux33Video2VideoOutputOutput1Std OBJECT-TYPE
        SYNTAX            RollCallString
        MAX-ACCESS        read-only
        STATUS            current
        DESCRIPTION
                "CMNT: - Output 1 Standard
                 TYPE: - Display
                 PAGE: - Video2
                    Output 1 Std  cmdID= 40706  "
        ::= { iqmux33CmdEntry 40706 }


    iqmux33VideoOutputVideoProcMasterGain OBJECT-TYPE
        SYNTAX            INTEGER
        MAX-ACCESS        read-write
        STATUS            current
        DESCRIPTION
                "CMNT: - Video Master Gain
                 TYPE: - Number
                 PAGE: - Video Output
                    Master Gain  cmdID= 33000
                    min= 0  max= 2000  step= 1  format= %d  div_scale= 1  preset= 1000
                    Min = 0  Max = 0  Step = 0  Preset = 0  "
        ::= { iqmux33CmdEntry 33000 }


    iqmux33VideoOutputVideoProcYGain OBJECT-TYPE
        SYNTAX            INTEGER
        MAX-ACCESS        read-write
        STATUS            current
        DESCRIPTION
                "CMNT: - Video Luminance gain
                 TYPE: - Number
                 PAGE: - Video Output
                    Y Gain  cmdID= 33001
                    min= 0  max= 2000  step= 1  format= %d  div_scale= 1  preset= 1000
                    Min = 0  Max = 0  Step = 0  Preset = 0  "
        ::= { iqmux33CmdEntry 33001 }


    iqmux33VideoOutputVideoProcCGain OBJECT-TYPE
        SYNTAX            INTEGER
        MAX-ACCESS        read-write
        STATUS            current
        DESCRIPTION
                "CMNT: - Video CbCr Gain
                 TYPE: - Number
                 PAGE: - Video Output
                    C Gain  cmdID= 33003
                    min= 0  max= 2000  step= 1  format= %d  div_scale= 1  preset= 1000
                    Min = 0  Max = 0  Step = 0  Preset = 0  "
        ::= { iqmux33CmdEntry 33003 }


    iqmux33VideoOutputVideoProcBlackLevel OBJECT-TYPE
        SYNTAX            INTEGER
        MAX-ACCESS        read-write
        STATUS            current
        DESCRIPTION
                "CMNT: - Video Black Level
                 TYPE: - Number
                 PAGE: - Video Output
                    Black Level  cmdID= 33002
                    min= -200  max= 200  step= 1  format= %0.0f mV  div_scale= 1  preset= 0
                    Min = -200 mV  Max = 200 mV  Step = 1 mV  Preset = 0 mV  "
        ::= { iqmux33CmdEntry 33002 }


    iqmux33VideoOutputVideoProcHueLevel OBJECT-TYPE
        SYNTAX            INTEGER
        MAX-ACCESS        read-write
        STATUS            current
        DESCRIPTION
                "CMNT: - Video Hue
                 TYPE: - Number
                 PAGE: - Video Output
                    Hue Level  cmdID= 33025
                    min= -180  max= 180  step= 1  format= %0.0f degrees  div_scale= 1  preset= 0
                    Min = -180 degrees  Max = 180 degrees  Step = 1 degrees  Preset = 0 degrees  "
        ::= { iqmux33CmdEntry 33025 }


    iqmux33VideoOutputVideoProcActiveSig OBJECT-TYPE
        SYNTAX            INTEGER { disable(0), enable(1)  }
        MAX-ACCESS        read-write
        STATUS            current
        DESCRIPTION
                "CMNT: - Active signalling video passthrough
                 TYPE: - Checkbox
                 PAGE: - Video Output
                    ActiveSig  cmdID= 32998  "
        ::= { iqmux33CmdEntry 32998 }


    iqmux33Video2VideoOutputDefaultOutput OBJECT-TYPE
        SYNTAX            INTEGER {
                            valBlack(1),
                            valFreeze(2),
                            valOutPattern(3)
                            }
        MAX-ACCESS        read-write
        STATUS            current
        DESCRIPTION
                "CMNT: - What to do on input loss
                 TYPE: - RadiobuttonList
                 PAGE: - Video2
                    Default Output  cmdID= 33026
                    Black  value= 1
                    Freeze  value= 2
                    Out Pattern  value= 3  "
        ::= { iqmux33CmdEntry 33026 }


    iqmux33Video2VideoOutputOutputMode OBJECT-TYPE
        SYNTAX            INTEGER {
                            valDefaultVideo(0),
                            valBlack(1),
                            valFreeze(2),
                            valOutPattern(3)
                            }
        MAX-ACCESS        read-write
        STATUS            current
        DESCRIPTION
                "CMNT: - Video Output mode
                 TYPE: - RadiobuttonList
                 PAGE: - Video2
                    Output Mode  cmdID= 33027
                    Default Video  value= 0
                    Black  value= 1
                    Freeze  value= 2
                    Out Pattern  value= 3  "
        ::= { iqmux33CmdEntry 33027 }


    iqmux33Video2VideoOutputPatternType OBJECT-TYPE
        SYNTAX            INTEGER {
                            val75ColorBars(0),
                            val100ColorBars(1),
                            valSMPTEBars(2),
                            valTartanBars(9),
                            valBlack(8),
                            valPluge(3),
                            valRamp(4),
                            valSweep(5),
                            valPulseBar(6),
                            valBurst(7)
                            }
        MAX-ACCESS        read-write
        STATUS            current
        DESCRIPTION
                "CMNT: - TPG pattern type
                 TYPE: - RadiobuttonList
                 PAGE: - Video2
                    Pattern Type  cmdID= 33028
                    75% Color Bars  value= 0
                    100% Color Bars  value= 1
                    SMPTE Bars  value= 2
                    Tartan Bars  value= 9
                    Black  value= 8
                    Pluge  value= 3
                    Ramp  value= 4
                    Sweep  value= 5
                    Pulse & Bar  value= 6
                    Burst  value= 7  "
        ::= { iqmux33CmdEntry 33028 }


    iqmux33VideoOutputUserCaptionsEnable OBJECT-TYPE
        SYNTAX            INTEGER { disable(0), enable(1)  }
        MAX-ACCESS        read-write
        STATUS            current
        DESCRIPTION
                "CMNT: - 
                 TYPE: - Checkbox
                 PAGE: - Video Output
                    Enable  cmdID= 6080  "
        ::= { iqmux33CmdEntry 6080 }


    iqmux33VideoOutputUserCaptionsEnableAlt OBJECT-TYPE
        SYNTAX            INTEGER { disable(0), enable(1)  }
        MAX-ACCESS        read-write
        STATUS            current
        DESCRIPTION
                "CMNT: - 
                 TYPE: - Checkbox
                 PAGE: - Video Output
                    EnableAlt  cmdID= 6087  "
        ::= { iqmux33CmdEntry 6087 }


    iqmux33VideoOutputUserCaptionsText OBJECT-TYPE
        SYNTAX            RollCallString
        MAX-ACCESS        read-write
        STATUS            current
        DESCRIPTION
                "CMNT: - 
                 TYPE: - Editstring
                 PAGE: - Video Output
                    Text  cmdID= 6085
                    preset= IQUAV10"
        ::= { iqmux33CmdEntry 6085 }


    iqmux33VideoOutputUserCaptionsTextAlt OBJECT-TYPE
        SYNTAX            RollCallString
        MAX-ACCESS        read-write
        STATUS            current
        DESCRIPTION
                "CMNT: - 
                 TYPE: - Editstring
                 PAGE: - Video Output
                    TextAlt  cmdID= 6086
                    preset= IQUAV10*"
        ::= { iqmux33CmdEntry 6086 }


    iqmux33VideoOutputUserCaptionsXPos OBJECT-TYPE
        SYNTAX            INTEGER
        MAX-ACCESS        read-write
        STATUS            current
        DESCRIPTION
                "CMNT: - 
                 TYPE: - Number
                 PAGE: - Video Output
                    X Pos  cmdID= 6081
                    min= 0  max= 1000  step= 1  format= %0.1f  div_scale= 10  preset= 0
                    Min = 0.0  Max = 100.0  Step = 0.1  Preset = 0.0  "
        ::= { iqmux33CmdEntry 6081 }


    iqmux33VideoOutputUserCaptionsYPos OBJECT-TYPE
        SYNTAX            INTEGER
        MAX-ACCESS        read-write
        STATUS            current
        DESCRIPTION
                "CMNT: - 
                 TYPE: - Number
                 PAGE: - Video Output
                    Y Pos  cmdID= 6082
                    min= -1000  max= 0  step= 1  format= %0.1f  div_scale= 10  preset= 0
                    Min = -100.0  Max = 0.0  Step = 0.1  Preset = 0.0  "
        ::= { iqmux33CmdEntry 6082 }


    iqmux33VideoOutputUserCaptionsXSize OBJECT-TYPE
        SYNTAX            INTEGER
        MAX-ACCESS        read-write
        STATUS            current
        DESCRIPTION
                "CMNT: - 
                 TYPE: - Number
                 PAGE: - Video Output
                    X Size  cmdID= 6083
                    min= 1  max= 10  step= 1  format= %0.0f  div_scale= 1  preset= 1
                    Min = 1  Max = 10  Step = 1  Preset = 1  "
        ::= { iqmux33CmdEntry 6083 }


    iqmux33VideoOutputUserCaptionsYSize OBJECT-TYPE
        SYNTAX            INTEGER
        MAX-ACCESS        read-write
        STATUS            current
        DESCRIPTION
                "CMNT: - 
                 TYPE: - Number
                 PAGE: - Video Output
                    Y Size  cmdID= 6084
                    min= 1  max= 10  step= 1  format= %0.0f  div_scale= 1  preset= 1
                    Min = 1  Max = 10  Step = 1  Preset = 1  "
        ::= { iqmux33CmdEntry 6084 }


    iqmux33Video2VideoOutputOutStdnonConv OBJECT-TYPE
        SYNTAX            INTEGER {
                            val108059pnA(1),
                            val108029i(3),
                            val72059p(5),
                            val52529i(7),
                            val108050pnA(2),
                            val108025i(4),
                            val72050p(6),
                            val62525i(8),
                            val108023psf(9),
                            val108025psf(10),
                            val108025p(11),
                            val108029p(12)
                            }
        MAX-ACCESS        read-write
        STATUS            current
        DESCRIPTION
                "CMNT: - Select output standard
                 TYPE: - RadiobuttonList
                 PAGE: - Video2
                    OutStd-nonConv  cmdID= 36144
                    1080/59p-A  value= 1
                    1080/29i  value= 3
                    720/59p  value= 5
                    525/29i  value= 7
                    1080/50p-A  value= 2
                    1080/25i  value= 4
                    720/50p  value= 6
                    625/25i  value= 8
                    1080/23psf  value= 9
                    1080/25psf  value= 10
                    1080/25p  value= 11
                    1080/29p  value= 12  "
        ::= { iqmux33CmdEntry 36144 }


    iqmux33Video2VideoOutputFollowStdnonConv OBJECT-TYPE
        SYNTAX            INTEGER {
                            valManualSelection(0),
                            valFollowsInputStd(1),
                            valFollowsRefStd(2)
                            }
        MAX-ACCESS        read-write
        STATUS            current
        DESCRIPTION
                "CMNT: - Output follows std: Man/Input/Ext.Reference
                 TYPE: - RadiobuttonList
                 PAGE: - Video2
                    FollowStd-nonConv  cmdID= 36143
                    Manual Selection  value= 0
                    Follows Input Std.  value= 1
                    Follows Ref. Std.  value= 2  "
        ::= { iqmux33CmdEntry 36143 }


    iqmux33Video2VideoOutputLastRefStd OBJECT-TYPE
        SYNTAX            INTEGER
        MAX-ACCESS        read-write
        STATUS            current
        DESCRIPTION
                "CMNT: - Last Known ref std
                 TYPE: - Number
                 PAGE: - Video2
                    LastRefStd  cmdID= 36145
                    min= 0  max= 10  step= 1  format= %d  div_scale= 1  preset= 0
                    Min = 0  Max = 0  Step = 0  Preset = 0  "
        ::= { iqmux33CmdEntry 36145 }


    iqmux33Video2VideoOutputLastFrameRate OBJECT-TYPE
        SYNTAX            INTEGER
        MAX-ACCESS        read-write
        STATUS            current
        DESCRIPTION
                "CMNT: - Last Known Input rate
                 TYPE: - Number
                 PAGE: - Video2
                    LastFrameRate  cmdID= 36146
                    min= 0  max= 2  step= 1  format= %d  div_scale= 1  preset= 0
                    Min = 0  Max = 0  Step = 0  Preset = 0  "
        ::= { iqmux33CmdEntry 36146 }


    iqmux33ARCCtrlSaveset OBJECT-TYPE
        SYNTAX            INTEGER
        MAX-ACCESS        read-write
        STATUS            current
        DESCRIPTION
                "CMNT: - 
                 TYPE: - Number
                 PAGE: - ARC Ctrl
                    Saveset  cmdID= 6045
                    min= 0  max= 33  step= 1  format= %d  div_scale= 1  preset= 0
                    Min = 0  Max = 0  Step = 0  Preset = 0  "
        ::= { iqmux33CmdEntry 6045 }


    iqmux33ARCCtrlDefaultALLMemory OBJECT-TYPE
        SYNTAX            INTEGER { noAction(0),valDefaultALLMemory(1) }
        MAX-ACCESS        read-write
        STATUS            current
        DESCRIPTION
                "CMNT: - 
                 TYPE: - Button
                 PAGE: - ARC Ctrl
                    Default ALL Memory  cmdID= 38702
                    value= 1  "
        ::= { iqmux33CmdEntry 38702 }


    iqmux33GenlockBlankingGenlockStandard OBJECT-TYPE
        SYNTAX            INTEGER {
                            val52529i(1),
                            val62525i(2),
                            val72023p(3),
                            val72024p(4),
                            val72025p(5),
                            val72029p(6),
                            val72030p(7),
                            val72059p(8),
                            val72050p(9),
                            val72060p(10),
                            val108025i(11),
                            val108029i(12),
                            val108030i(13),
                            val108023sf(14),
                            val108024sf(15),
                            val108025sf(16),
                            val108023p(17),
                            val108024p(18),
                            val108025p(19),
                            val108029p(20),
                            val108030p(21),
                            val108050p(22),
                            val108059p(23),
                            val108060p(24)
                            }
        MAX-ACCESS        read-write
        STATUS            current
        DESCRIPTION
                "CMNT: - Select std for Ref display/set
                 TYPE: - RadiobuttonList
                 PAGE: - Genlock/Blanking
                    Standard  cmdID= 37203
                    525/29i  value= 1
                    625/25i  value= 2
                    720/23p  value= 3
                    720/24p  value= 4
                    720/25p  value= 5
                    720/29p  value= 6
                    720/30p  value= 7
                    720/59p  value= 8
                    720/50p  value= 9
                    720/60p  value= 10
                    1080/25i  value= 11
                    1080/29i  value= 12
                    1080/30i  value= 13
                    1080/23sf  value= 14
                    1080/24sf  value= 15
                    1080/25sf  value= 16
                    1080/23p  value= 17
                    1080/24p  value= 18
                    1080/25p  value= 19
                    1080/29p  value= 20
                    1080/30p  value= 21
                    1080/50p  value= 22
                    1080/59p  value= 23
                    1080/60p  value= 24  "
        ::= { iqmux33CmdEntry 37203 }


    iqmux33GenlockBlankingGenlockDelayMode OBJECT-TYPE
        SYNTAX            INTEGER {
                            valFreeRun(0),
                            valLocktoReference(1),
                            valManualHV(2)
                            }
        MAX-ACCESS        read-write
        STATUS            current
        DESCRIPTION
                "CMNT: - Video Reference Mode source: Free Run/LockRef/LockRef(Delay Mismatch)/Minimum/Frames/Manual/Manual ms
                 TYPE: - RadiobuttonList
                 PAGE: - Genlock/Blanking
                    Delay Mode  cmdID= 33029
                    Free Run  value= 0
                    Lock to Reference  value= 1
                    Manual H/V  value= 2  "
        ::= { iqmux33CmdEntry 33029 }


    iqmux33GenlockSetDelayDelayFrames OBJECT-TYPE
        SYNTAX            INTEGER
        MAX-ACCESS        read-write
        STATUS            current
        DESCRIPTION
                "CMNT: - Set video delay in frames
                 TYPE: - Number
                 PAGE: - Genlock
                    Delay Frames  cmdID= 33031
                    min= 0  max= 147  step= 1  format= %0.0f frames  div_scale= 1  preset= 1
                    Min = 0 frames  Max = 147 frames  Step = 1 frames  Preset = 1 frames  "
        ::= { iqmux33CmdEntry 33031 }


    iqmux33GenlockSetDelayVerticalPhase OBJECT-TYPE
        SYNTAX            INTEGER
        MAX-ACCESS        read-write
        STATUS            current
        DESCRIPTION
                "CMNT: - Reference vertical timing
                 TYPE: - Number
                 PAGE: - Genlock
                    Vertical Phase  cmdID= 33033
                    min= -1125  max= 1125  step= 1  format= %0.0f lines  div_scale= 1  preset= 0
                    Min = -1125 lines  Max = 1125 lines  Step = 1 lines  Preset = 0 lines  "
        ::= { iqmux33CmdEntry 33033 }


    iqmux33GenlockSetDelayHorizontalPhase OBJECT-TYPE
        SYNTAX            INTEGER
        MAX-ACCESS        read-write
        STATUS            current
        DESCRIPTION
                "CMNT: - Reference horizontal timing
                 TYPE: - Number
                 PAGE: - Genlock
                    Horizontal Phase  cmdID= 33032
                    min= -4125  max= 4125  step= 1  format= %0.0f pixels  div_scale= 1  preset= 0
                    Min = -4125 pixels  Max = 4125 pixels  Step = 1 pixels  Preset = 0 pixels  "
        ::= { iqmux33CmdEntry 33032 }


    iqmux33GenlockSetDelayVerticalDelay OBJECT-TYPE
        SYNTAX            INTEGER
        MAX-ACCESS        read-write
        STATUS            current
        DESCRIPTION
                "CMNT: - Reference vertical timing
                 TYPE: - Number
                 PAGE: - Genlock
                    Vertical Delay  cmdID= 33045
                    min= 0  max= 1125  step= 1  format= %0.0f lines  div_scale= 1  preset= 0
                    Min = 0 lines  Max = 1125 lines  Step = 1 lines  Preset = 0 lines  "
        ::= { iqmux33CmdEntry 33045 }


    iqmux33GenlockSetDelayHorizontalDelay OBJECT-TYPE
        SYNTAX            INTEGER
        MAX-ACCESS        read-write
        STATUS            current
        DESCRIPTION
                "CMNT: - Reference horizontal timing
                 TYPE: - Number
                 PAGE: - Genlock
                    Horizontal Delay  cmdID= 33044
                    min= 0  max= 4125  step= 1  format= %0.0f pixels  div_scale= 1  preset= 0
                    Min = 0 pixels  Max = 4125 pixels  Step = 1 pixels  Preset = 0 pixels  "
        ::= { iqmux33CmdEntry 33044 }


    iqmux33GenlockBlankingGenlockRefLogHide OBJECT-TYPE
        SYNTAX            RollCallString
        MAX-ACCESS        read-only
        STATUS            current
        DESCRIPTION
                "CMNT: - Hide logging for Reference
                 TYPE: - Display
                 PAGE: - Genlock/Blanking
                    RefLogHide  cmdID= 33175  "
        ::= { iqmux33CmdEntry 33175 }


    iqmux33GenlockDolbyELineStandard OBJECT-TYPE
        SYNTAX            INTEGER {
                            val52529i(1),
                            val62525i(2),
                            val72023p(3),
                            val72024p(4),
                            val72025p(5),
                            val72029p(6),
                            val72030p(7),
                            val72050p(8),
                            val72059p(9),
                            val72060p(10),
                            val108025i(11),
                            val108029i(12),
                            val108030i(13),
                            val108023psf(14),
                            val108024psf(15),
                            val108025psf(16),
                            val108023p(17),
                            val108024p(18),
                            val108025p(19),
                            val108029p(20),
                            val108030p(21),
                            val108050p(22),
                            val108059p(23),
                            val108060p(24)
                            }
        MAX-ACCESS        read-write
        STATUS            current
        DESCRIPTION
                "CMNT: - Select standard to display Dolby E Auto-Line for
                 TYPE: - RadiobuttonList
                 PAGE: - Genlock
                    Standard  cmdID= 38655
                    525/29i  value= 1
                    625/25i  value= 2
                    720/23p  value= 3
                    720/24p  value= 4
                    720/25p  value= 5
                    720/29p  value= 6
                    720/30p  value= 7
                    720/50p  value= 8
                    720/59p  value= 9
                    720/60p  value= 10
                    1080/25i  value= 11
                    1080/29i  value= 12
                    1080/30i  value= 13
                    1080/23psf  value= 14
                    1080/24psf  value= 15
                    1080/25psf  value= 16
                    1080/23p  value= 17
                    1080/24p  value= 18
                    1080/25p  value= 19
                    1080/29p  value= 20
                    1080/30p  value= 21
                    1080/50p  value= 22
                    1080/59p  value= 23
                    1080/60p  value= 24  "
        ::= { iqmux33CmdEntry 38655 }


    iqmux33GenlockDolbyELineAutoLineNo OBJECT-TYPE
        SYNTAX            INTEGER
        MAX-ACCESS        read-write
        STATUS            current
        DESCRIPTION
                "CMNT: - Select standard to display Dolby E Auto-Line for
                 TYPE: - Number
                 PAGE: - Genlock
                    Auto Line No.  cmdID= 38656
                    min= 0  max= 1125  step= 1  format= %0.0f  div_scale= 1  preset= 1
                    Min = 0  Max = 1125  Step = 1  Preset = 1  "
        ::= { iqmux33CmdEntry 38656 }


    iqmux33DolbyELineUserDolbyELinePair1 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair1  cmdID= 38670
                    Default  value= 0
                    User  value= 1  "
        ::= { iqmux33CmdEntry 38670 }


    iqmux33DolbyELineUserDolbyELinePair2 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair2  cmdID= 38671
                    Default  value= 0
                    User  value= 1  "
        ::= { iqmux33CmdEntry 38671 }


    iqmux33DolbyELineUserDolbyELinePair3 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair3  cmdID= 38672
                    Default  value= 0
                    User  value= 1  "
        ::= { iqmux33CmdEntry 38672 }


    iqmux33DolbyELineUserDolbyELinePair4 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair4  cmdID= 38673
                    Default  value= 0
                    User  value= 1  "
        ::= { iqmux33CmdEntry 38673 }


    iqmux33DolbyELineUserDolbyELinePair5 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair5  cmdID= 38674
                    Default  value= 0
                    User  value= 1  "
        ::= { iqmux33CmdEntry 38674 }


    iqmux33DolbyELineUserDolbyELinePair6 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair6  cmdID= 38675
                    Default  value= 0
                    User  value= 1  "
        ::= { iqmux33CmdEntry 38675 }


    iqmux33DolbyELineUserDolbyELinePair7 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair7  cmdID= 38676
                    Default  value= 0
                    User  value= 1  "
        ::= { iqmux33CmdEntry 38676 }


    iqmux33DolbyELineUserDolbyELinePair8 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair8  cmdID= 38677
                    Default  value= 0
                    User  value= 1  "
        ::= { iqmux33CmdEntry 38677 }


    iqmux33GenlockDolbyELineUserLine525i29 OBJECT-TYPE
        SYNTAX            INTEGER
        MAX-ACCESS        read-write
        STATUS            current
        DESCRIPTION
                "CMNT: - 
                 TYPE: - Number
                 PAGE: - Genlock
                    UserLine525i29  cmdID= 38684
                    min= 1  max= 525  step= 1  format= %d  div_scale= 1  preset= 14
                    Min = 0  Max = 0  Step = 0  Preset = 0  "
        ::= { iqmux33CmdEntry 38684 }


    iqmux33GenlockDolbyELineUserLine625i25 OBJECT-TYPE
        SYNTAX            INTEGER
        MAX-ACCESS        read-write
        STATUS            current
        DESCRIPTION
                "CMNT: - 
                 TYPE: - Number
                 PAGE: - Genlock
                    UserLine625i25  cmdID= 38685
                    min= 1  max= 625  step= 1  format= %d  div_scale= 1  preset= 12
                    Min = 0  Max = 0  Step = 0  Preset = 0  "
        ::= { iqmux33CmdEntry 38685 }


    iqmux33GenlockDolbyELineUserLine720p23 OBJECT-TYPE
        SYNTAX            INTEGER
        MAX-ACCESS        read-write
        STATUS            current
        DESCRIPTION
                "CMNT: - 
                 TYPE: - Number
                 PAGE: - Genlock
                    UserLine720p23  cmdID= 38686
                    min= 1  max= 750  step= 1  format= %d  div_scale= 1  preset= 28
                    Min = 0  Max = 0  Step = 0  Preset = 0  "
        ::= { iqmux33CmdEntry 38686 }


    iqmux33GenlockDolbyELineUserLine720p24 OBJECT-TYPE
        SYNTAX            INTEGER
        MAX-ACCESS        read-write
        STATUS            current
        DESCRIPTION
                "CMNT: - 
                 TYPE: - Number
                 PAGE: - Genlock
                    UserLine720p24  cmdID= 38687
                    min= 1  max= 750  step= 1  format= %d  div_scale= 1  preset= 28
                    Min = 0  Max = 0  Step = 0  Preset = 0  "
        ::= { iqmux33CmdEntry 38687 }


    iqmux33GenlockDolbyELineUserLine720p25 OBJECT-TYPE
        SYNTAX            INTEGER
        MAX-ACCESS        read-write
        STATUS            current
        DESCRIPTION
                "CMNT: - 
                 TYPE: - Number
                 PAGE: - Genlock
                    UserLine720p25  cmdID= 38688
                    min= 1  max= 750  step= 1  format= %d  div_scale= 1  preset= 28
                    Min = 0  Max = 0  Step = 0  Preset = 0  "
        ::= { iqmux33CmdEntry 38688 }


    iqmux33GenlockDolbyELineUserLine720p29 OBJECT-TYPE
        SYNTAX            INTEGER
        MAX-ACCESS        read-write
        STATUS            current
        DESCRIPTION
                "CMNT: - 
                 TYPE: - Number
                 PAGE: - Genlock
                    UserLine720p29  cmdID= 38689
                    min= 1  max= 750  step= 1  format= %d  div_scale= 1  preset= 28
                    Min = 0  Max = 0  Step = 0  Preset = 0  "
        ::= { iqmux33CmdEntry 38689 }


    iqmux33GenlockDolbyELineUserLine720p30 OBJECT-TYPE
        SYNTAX            INTEGER
        MAX-ACCESS        read-write
        STATUS            current
        DESCRIPTION
                "CMNT: - 
                 TYPE: - Number
                 PAGE: - Genlock
                    UserLine720p30  cmdID= 38690
                    min= 1  max= 750  step= 1  format= %d  div_scale= 1  preset= 28
                    Min = 0  Max = 0  Step = 0  Preset = 0  "
        ::= { iqmux33CmdEntry 38690 }


    iqmux33GenlockDolbyELineUserLine720p50 OBJECT-TYPE
        SYNTAX            INTEGER
        MAX-ACCESS        read-write
        STATUS            current
        DESCRIPTION
                "CMNT: - 
                 TYPE: - Number
                 PAGE: - Genlock
                    UserLine720p50  cmdID= 38683
                    min= 1  max= 750  step= 1  format= %d  div_scale= 1  preset= 28
                    Min = 0  Max = 0  Step = 0  Preset = 0  "
        ::= { iqmux33CmdEntry 38683 }


    iqmux33GenlockDolbyELineUserLine720p59 OBJECT-TYPE
        SYNTAX            INTEGER
        MAX-ACCESS        read-write
        STATUS            current
        DESCRIPTION
                "CMNT: - 
                 TYPE: - Number
                 PAGE: - Genlock
                    UserLine720p59  cmdID= 38682
                    min= 1  max= 750  step= 1  format= %d  div_scale= 1  preset= 32
                    Min = 0  Max = 0  Step = 0  Preset = 0  "
        ::= { iqmux33CmdEntry 38682 }


    iqmux33GenlockDolbyELineUserLine720p60 OBJECT-TYPE
        SYNTAX            INTEGER
        MAX-ACCESS        read-write
        STATUS            current
        DESCRIPTION
                "CMNT: - 
                 TYPE: - Number
                 PAGE: - Genlock
                    UserLine720p60  cmdID= 38691
                    min= 1  max= 750  step= 1  format= %d  div_scale= 1  preset= 32
                    Min = 0  Max = 0  Step = 0  Preset = 0  "
        ::= { iqmux33CmdEntry 38691 }


    iqmux33GenlockDolbyELineUserLine1080i25 OBJECT-TYPE
        SYNTAX            INTEGER
        MAX-ACCESS        read-write
        STATUS            current
        DESCRIPTION
                "CMNT: - 
                 TYPE: - Number
                 PAGE: - Genlock
                    UserLine1080i25  cmdID= 38681
                    min= 1  max= 1125  step= 1  format= %d  div_scale= 1  preset= 21
                    Min = 0  Max = 0  Step = 0  Preset = 0  "
        ::= { iqmux33CmdEntry 38681 }


    iqmux33GenlockDolbyELineUserLine1080i29 OBJECT-TYPE
        SYNTAX            INTEGER
        MAX-ACCESS        read-write
        STATUS            current
        DESCRIPTION
                "CMNT: - 
                 TYPE: - Number
                 PAGE: - Genlock
                    UserLine1080i29  cmdID= 38680
                    min= 1  max= 1125  step= 1  format= %d  div_scale= 1  preset= 24
                    Min = 0  Max = 0  Step = 0  Preset = 0  "
        ::= { iqmux33CmdEntry 38680 }


    iqmux33GenlockDolbyELineUserLine1080i30 OBJECT-TYPE
        SYNTAX            INTEGER
        MAX-ACCESS        read-write
        STATUS            current
        DESCRIPTION
                "CMNT: - 
                 TYPE: - Number
                 PAGE: - Genlock
                    UserLine1080i30  cmdID= 38692
                    min= 1  max= 1125  step= 1  format= %d  div_scale= 1  preset= 24
                    Min = 0  Max = 0  Step = 0  Preset = 0  "
        ::= { iqmux33CmdEntry 38692 }


    iqmux33GenlockDolbyELineUserLine1080p23sf OBJECT-TYPE
        SYNTAX            INTEGER
        MAX-ACCESS        read-write
        STATUS            current
        DESCRIPTION
                "CMNT: - 
                 TYPE: - Number
                 PAGE: - Genlock
                    UserLine1080p23sf  cmdID= 38693
                    min= 1  max= 1125  step= 1  format= %d  div_scale= 1  preset= 42
                    Min = 0  Max = 0  Step = 0  Preset = 0  "
        ::= { iqmux33CmdEntry 38693 }


    iqmux33GenlockDolbyELineUserLine1080p24sf OBJECT-TYPE
        SYNTAX            INTEGER
        MAX-ACCESS        read-write
        STATUS            current
        DESCRIPTION
                "CMNT: - 
                 TYPE: - Number
                 PAGE: - Genlock
                    UserLine1080p24sf  cmdID= 38694
                    min= 1  max= 1125  step= 1  format= %d  div_scale= 1  preset= 42
                    Min = 0  Max = 0  Step = 0  Preset = 0  "
        ::= { iqmux33CmdEntry 38694 }


    iqmux33GenlockDolbyELineUserLine1080p25sf OBJECT-TYPE
        SYNTAX            INTEGER
        MAX-ACCESS        read-write
        STATUS            current
        DESCRIPTION
                "CMNT: - 
                 TYPE: - Number
                 PAGE: - Genlock
                    UserLine1080p25sf  cmdID= 38695
                    min= 1  max= 1125  step= 1  format= %d  div_scale= 1  preset= 42
                    Min = 0  Max = 0  Step = 0  Preset = 0  "
        ::= { iqmux33CmdEntry 38695 }


    iqmux33GenlockDolbyELineUserLine1080p23 OBJECT-TYPE
        SYNTAX            INTEGER
        MAX-ACCESS        read-write
        STATUS            current
        DESCRIPTION
                "CMNT: - 
                 TYPE: - Number
                 PAGE: - Genlock
                    UserLine1080p23  cmdID= 38696
                    min= 1  max= 1125  step= 1  format= %d  div_scale= 1  preset= 42
                    Min = 0  Max = 0  Step = 0  Preset = 0  "
        ::= { iqmux33CmdEntry 38696 }


    iqmux33GenlockDolbyELineUserLine1080p24 OBJECT-TYPE
        SYNTAX            INTEGER
        MAX-ACCESS        read-write
        STATUS            current
        DESCRIPTION
                "CMNT: - 
                 TYPE: - Number
                 PAGE: - Genlock
                    UserLine1080p24  cmdID= 38697
                    min= 1  max= 1125  step= 1  format= %d  div_scale= 1  preset= 42
                    Min = 0  Max = 0  Step = 0  Preset = 0  "
        ::= { iqmux33CmdEntry 38697 }


    iqmux33GenlockDolbyELineUserLine1080p25 OBJECT-TYPE
        SYNTAX            INTEGER
        MAX-ACCESS        read-write
        STATUS            current
        DESCRIPTION
                "CMNT: - 
                 TYPE: - Number
                 PAGE: - Genlock
                    UserLine1080p25  cmdID= 38698
                    min= 1  max= 1125  step= 1  format= %d  div_scale= 1  preset= 42
                    Min = 0  Max = 0  Step = 0  Preset = 0  "
        ::= { iqmux33CmdEntry 38698 }


    iqmux33GenlockDolbyELineUserLine1080p29 OBJECT-TYPE
        SYNTAX            INTEGER
        MAX-ACCESS        read-write
        STATUS            current
        DESCRIPTION
                "CMNT: - 
                 TYPE: - Number
                 PAGE: - Genlock
                    UserLine1080p29  cmdID= 38699
                    min= 1  max= 1125  step= 1  format= %d  div_scale= 1  preset= 42
                    Min = 0  Max = 0  Step = 0  Preset = 0  "
        ::= { iqmux33CmdEntry 38699 }


    iqmux33GenlockDolbyELineUserLine1080p30 OBJECT-TYPE
        SYNTAX            INTEGER
        MAX-ACCESS        read-write
        STATUS            current
        DESCRIPTION
                "CMNT: - 
                 TYPE: - Number
                 PAGE: - Genlock
                    UserLine1080p30  cmdID= 38707
                    min= 1  max= 1125  step= 1  format= %d  div_scale= 1  preset= 42
                    Min = 0  Max = 0  Step = 0  Preset = 0  "
        ::= { iqmux33CmdEntry 38707 }


    iqmux33GenlockDolbyELineUserLine1080p50 OBJECT-TYPE
        SYNTAX            INTEGER
        MAX-ACCESS        read-write
        STATUS            current
        DESCRIPTION
                "CMNT: - 
                 TYPE: - Number
                 PAGE: - Genlock
                    UserLine1080p50  cmdID= 38679
                    min= 1  max= 1125  step= 1  format= %d  div_scale= 1  preset= 42
                    Min = 0  Max = 0  Step = 0  Preset = 0  "
        ::= { iqmux33CmdEntry 38679 }


    iqmux33GenlockDolbyELineUserLine1080p59 OBJECT-TYPE
        SYNTAX            INTEGER
        MAX-ACCESS        read-write
        STATUS            current
        DESCRIPTION
                "CMNT: - 
                 TYPE: - Number
                 PAGE: - Genlock
                    UserLine1080p59  cmdID= 38780
                    min= 1  max= 1125  step= 1  format= %d  div_scale= 1  preset= 47
                    Min = 0  Max = 0  Step = 0  Preset = 0  "
        ::= { iqmux33CmdEntry 38780 }


    iqmux33GenlockDolbyELineUserLine1080p60 OBJECT-TYPE
        SYNTAX            INTEGER
        MAX-ACCESS        read-write
        STATUS            current
        DESCRIPTION
                "CMNT: - 
                 TYPE: - Number
                 PAGE: - Genlock
                    UserLine1080p60  cmdID= 38711
                    min= 1  max= 1125  step= 1  format= %d  div_scale= 1  preset= 47
                    Min = 0  Max = 0  Step = 0  Preset = 0  "
        ::= { iqmux33CmdEntry 38711 }


    iqmux33GenlockDolbyELineAutoAlign1 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign1  cmdID= 38110  "
        ::= { iqmux33CmdEntry 38110 }


    iqmux33GenlockDolbyELineAutoAlign2 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign2  cmdID= 38111  "
        ::= { iqmux33CmdEntry 38111 }


    iqmux33GenlockDolbyELineAutoAlign3 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign3  cmdID= 38112  "
        ::= { iqmux33CmdEntry 38112 }


    iqmux33GenlockDolbyELineAutoAlign4 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign4  cmdID= 38113  "
        ::= { iqmux33CmdEntry 38113 }


    iqmux33GenlockDolbyELineAutoAlign5 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign5  cmdID= 38114  "
        ::= { iqmux33CmdEntry 38114 }


    iqmux33GenlockDolbyELineAutoAlign6 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign6  cmdID= 38115  "
        ::= { iqmux33CmdEntry 38115 }


    iqmux33GenlockDolbyELineAutoAlign7 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign7  cmdID= 38116  "
        ::= { iqmux33CmdEntry 38116 }


    iqmux33GenlockDolbyELineAutoAlign8 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign8  cmdID= 38117  "
        ::= { iqmux33CmdEntry 38117 }


    iqmux33BlankingHANCVBIBlankingStandard OBJECT-TYPE
        SYNTAX            INTEGER {
                            val52529i(1),
                            val62525i(2),
                            val72023p(3),
                            val72024p(3),
                            val72025p(3),
                            val72029p(3),
                            val72030p(3),
                            val72050p(8),
                            val72059p(9),
                            val72060p(10),
                            val108025i(11),
                            val108029i(12),
                            val108030i(13),
                            val108023psf(14),
                            val108024psf(15),
                            val108025psf(16),
                            val108023p(17),
                            val108024p(18),
                            val108025p(19),
                            val108029p(20),
                            val108030p(21),
                            val108050p(22),
                            val108059p(23),
                            val108060p(24)
                            }
        MAX-ACCESS        read-write
        STATUS            current
        DESCRIPTION
                "CMNT: - Select std for VBI blank display/set
                 TYPE: - RadiobuttonList
                 PAGE: - Blanking
                    Standard  cmdID= 37200
                    525/29i  value= 1
                    625/25i  value= 2
                    720/23p  value= 3
                    720/24p  value= 3
                    720/25p  value= 3
                    720/29p  value= 3
                    720/30p  value= 3
                    720/50p  value= 8
                    720/59p  value= 9
                    720/60p  value= 10
                    1080/25i  value= 11
                    1080/29i  value= 12
                    1080/30i  value= 13
                    1080/23psf  value= 14
                    1080/24psf  value= 15
                    1080/25psf  value= 16
                    1080/23p  value= 17
                    1080/24p  value= 18
                    1080/25p  value= 19
                    1080/29p  value= 20
                    1080/30p  value= 21
                    1080/50p  value= 22
                    1080/59p  value= 23
                    1080/60p  value= 24  "
        ::= { iqmux33CmdEntry 37200 }


    iqmux33BlankingHANCVBIBlankingBlankAll OBJECT-TYPE
        SYNTAX            INTEGER { noAction(0),valBlankAll(1) }
        MAX-ACCESS        read-write
        STATUS            current
        DESCRIPTION
                "CMNT: - Blank all valid lines
                 TYPE: - Button
                 PAGE: - Blanking
                    Blank All  cmdID= 37201
                    value= 1  "
        ::= { iqmux33CmdEntry 37201 }


    iqmux33BlankingHANCVBIBlankingPassAll OBJECT-TYPE
        SYNTAX            INTEGER { noAction(0),valPassAll(1) }
        MAX-ACCESS        read-write
        STATUS            current
        DESCRIPTION
                "CMNT: - Blank no lines
                 TYPE: - Button
                 PAGE: - Blanking
                    Pass All  cmdID= 37202
                    value= 1  "
        ::= { iqmux33CmdEntry 37202 }


    iqmux33BlankingHANCVBIBlankingBlank1 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 1  cmdID= 37210  "
        ::= { iqmux33CmdEntry 37210 }


    iqmux33BlankingHANCVBIBlankingBlank2 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 2  cmdID= 37211  "
        ::= { iqmux33CmdEntry 37211 }


    iqmux33BlankingHANCVBIBlankingBlank3 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 3  cmdID= 37212  "
        ::= { iqmux33CmdEntry 37212 }


    iqmux33BlankingHANCVBIBlankingBlank4 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 4  cmdID= 37213  "
        ::= { iqmux33CmdEntry 37213 }


    iqmux33BlankingHANCVBIBlankingBlank5 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 5  cmdID= 37214  "
        ::= { iqmux33CmdEntry 37214 }


    iqmux33BlankingHANCVBIBlankingBlank6 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 6  cmdID= 37215  "
        ::= { iqmux33CmdEntry 37215 }


    iqmux33BlankingHANCVBIBlankingBlank7 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 7  cmdID= 37216  "
        ::= { iqmux33CmdEntry 37216 }


    iqmux33BlankingHANCVBIBlankingBlank8 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 8  cmdID= 37217  "
        ::= { iqmux33CmdEntry 37217 }


    iqmux33BlankingHANCVBIBlankingBlank9 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 9  cmdID= 37218  "
        ::= { iqmux33CmdEntry 37218 }


    iqmux33BlankingHANCVBIBlankingBlank10 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 10  cmdID= 37219  "
        ::= { iqmux33CmdEntry 37219 }


    iqmux33BlankingHANCVBIBlankingBlank11 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 11  cmdID= 37220  "
        ::= { iqmux33CmdEntry 37220 }


    iqmux33BlankingHANCVBIBlankingBlank12 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 12  cmdID= 37221  "
        ::= { iqmux33CmdEntry 37221 }


    iqmux33BlankingHANCVBIBlankingBlank13 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 13  cmdID= 37222  "
        ::= { iqmux33CmdEntry 37222 }


    iqmux33BlankingHANCVBIBlankingBlank14 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 14  cmdID= 37223  "
        ::= { iqmux33CmdEntry 37223 }


    iqmux33BlankingHANCVBIBlankingBlank15 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 15  cmdID= 37224  "
        ::= { iqmux33CmdEntry 37224 }


    iqmux33BlankingHANCVBIBlankingBlank16 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 16  cmdID= 37225  "
        ::= { iqmux33CmdEntry 37225 }


    iqmux33BlankingHANCVBIBlankingBlank17 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 17  cmdID= 37226  "
        ::= { iqmux33CmdEntry 37226 }


    iqmux33BlankingHANCVBIBlankingBlank18 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 18  cmdID= 37227  "
        ::= { iqmux33CmdEntry 37227 }


    iqmux33BlankingHANCVBIBlankingBlank19 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 19  cmdID= 37228  "
        ::= { iqmux33CmdEntry 37228 }


    iqmux33BlankingHANCVBIBlankingBlank20 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 20  cmdID= 37229  "
        ::= { iqmux33CmdEntry 37229 }


    iqmux33BlankingHANCVBIBlankingBlank21 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 21  cmdID= 37230  "
        ::= { iqmux33CmdEntry 37230 }


    iqmux33BlankingHANCVBIBlankingBlank22 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 22  cmdID= 37231  "
        ::= { iqmux33CmdEntry 37231 }


    iqmux33BlankingHANCVBIBlankingBlank23 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 23  cmdID= 37232  "
        ::= { iqmux33CmdEntry 37232 }


    iqmux33BlankingHANCVBIBlankingBlank24 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 24  cmdID= 37233  "
        ::= { iqmux33CmdEntry 37233 }


    iqmux33BlankingHANCVBIBlankingBlank25 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 25  cmdID= 37234  "
        ::= { iqmux33CmdEntry 37234 }


    iqmux33BlankingHANCVBIBlankingBlank26 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 26  cmdID= 37235  "
        ::= { iqmux33CmdEntry 37235 }


    iqmux33BlankingHANCVBIBlankingBlank27 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 27  cmdID= 37236  "
        ::= { iqmux33CmdEntry 37236 }


    iqmux33BlankingHANCVBIBlankingBlank28 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 28  cmdID= 37237  "
        ::= { iqmux33CmdEntry 37237 }


    iqmux33BlankingHANCVBIBlankingBlank29 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 29  cmdID= 37238  "
        ::= { iqmux33CmdEntry 37238 }


    iqmux33BlankingHANCVBIBlankingBlank30 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 30  cmdID= 37239  "
        ::= { iqmux33CmdEntry 37239 }


    iqmux33BlankingHANCVBIBlankingBlank31 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 31  cmdID= 37240  "
        ::= { iqmux33CmdEntry 37240 }


    iqmux33BlankingHANCVBIBlankingBlank32 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 32  cmdID= 37241  "
        ::= { iqmux33CmdEntry 37241 }


    iqmux33BlankingHANCVBIBlankingBlank33 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 33  cmdID= 37242  "
        ::= { iqmux33CmdEntry 37242 }


    iqmux33BlankingHANCVBIBlankingBlank34 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 34  cmdID= 37243  "
        ::= { iqmux33CmdEntry 37243 }


    iqmux33BlankingHANCVBIBlankingBlank35 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 35  cmdID= 37244  "
        ::= { iqmux33CmdEntry 37244 }


    iqmux33BlankingHANCVBIBlankingBlank36 OBJECT-TYPE
        SYNTAX            INTEGER { disable(0), enable(1)  }
        MAX-ACCESS        read-write
        STATUS            current
        DESCRIPTION
                "CMNT: - VBI Blank checkbox - depends on standard selected
                 TYPE: - Checkbox
                 PAGE: - Blanking
                    Blank 36  cmdID= 37245  "
        ::= { iqmux33CmdEntry 37245 }


    iqmux33BlankingHANCVBIBlankingBlankHANC OBJECT-TYPE
        SYNTAX            INTEGER { disable(0), enable(1)  }
        MAX-ACCESS        read-write
        STATUS            current
        DESCRIPTION
                "CMNT: - HANC Blank checkbox - depends on standard selected
                 TYPE: - Checkbox
                 PAGE: - Blanking
                    Blank HANC  cmdID= 37246  "
        ::= { iqmux33CmdEntry 37246 }


    iqmux33WSSCtrlNewNumber OBJECT-TYPE
        SYNTAX            INTEGER
        MAX-ACCESS        read-write
        STATUS            current
        DESCRIPTION
                "CMNT: - Force Input AFD store
                 TYPE: - Number
                 PAGE: - WSS Ctrl
                    New Number  cmdID= 43108
                    min= 0  max= 401  step= 1  format= %d  div_scale= 1  preset= 2
                    Min = 0  Max = 0  Step = 0  Preset = 0  "
        ::= { iqmux33CmdEntry 43108 }


    iqmux33WSSCtrlBlank62523 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank625_23  cmdID= 43228  "
        ::= { iqmux33CmdEntry 43228 }


    iqmux33WSSCtrlBlank625336 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank625_336  cmdID= 43229  "
        ::= { iqmux33CmdEntry 43229 }


    iqmux33WSSCtrlBlank52521 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_21  cmdID= 43230  "
        ::= { iqmux33CmdEntry 43230 }


    iqmux33WSSCtrlBlank52522 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_22  cmdID= 43231  "
        ::= { iqmux33CmdEntry 43231 }


    iqmux33WSSCtrlBlank525283 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_283  cmdID= 43232  "
        ::= { iqmux33CmdEntry 43232 }


    iqmux33WSSCtrlBlank525284 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_284  cmdID= 43233  "
        ::= { iqmux33CmdEntry 43233 }


    iqmux33AncillaryDataSDVBIVITCIPStatus OBJECT-TYPE
        SYNTAX            INTEGER { disable(0), enable(1)  }
        MAX-ACCESS        read-write
        STATUS            current
        DESCRIPTION
                "CMNT: - Ancillary data vertical interval time code present
                 TYPE: - Checkbox
                 PAGE: - Ancillary Data
                    VITC I/P Status  cmdID= 42742  "
        ::= { iqmux33CmdEntry 42742 }


    iqmux33AncillaryDataSDVBIWSTIPStatus OBJECT-TYPE
        SYNTAX            INTEGER { disable(0), enable(1)  }
        MAX-ACCESS        read-write
        STATUS            current
        DESCRIPTION
                "CMNT: - Ancillary data world system teletext present
                 TYPE: - Checkbox
                 PAGE: - Ancillary Data
                    WST I/P Status  cmdID= 42741  "
        ::= { iqmux33CmdEntry 42741 }


    iqmux33AncillaryDataSDVBICC608IPStatus OBJECT-TYPE
        SYNTAX            INTEGER { disable(0), enable(1)  }
        MAX-ACCESS        read-write
        STATUS            current
        DESCRIPTION
                "CMNT: - Ancillary data closed caption CC608 present
                 TYPE: - Checkbox
                 PAGE: - Ancillary Data
                    CC608 I/P Status  cmdID= 42743  "
        ::= { iqmux33CmdEntry 42743 }


    iqmux33AncillaryDataHDVANCATCEnable OBJECT-TYPE
        SYNTAX            INTEGER { disable(0), enable(1)  }
        MAX-ACCESS        read-write
        STATUS            current
        DESCRIPTION
                "CMNT: - Ancillary time code enable output
                 TYPE: - Checkbox
                 PAGE: - Ancillary Data
                    ATC Enable  cmdID= 42702  "
        ::= { iqmux33CmdEntry 42702 }


    iqmux33AncillaryDataHDVANCATCIPF1Line OBJECT-TYPE
        SYNTAX            RollCallString
        MAX-ACCESS        read-only
        STATUS            current
        DESCRIPTION
                "CMNT: - Ancillary time code input line field 1
                 TYPE: - Display
                 PAGE: - Ancillary Data
                    ATC I/P F1 Line  cmdID= 42705  "
        ::= { iqmux33CmdEntry 42705 }


    iqmux33AncillaryDataHDVANCATCOPF1Line OBJECT-TYPE
        SYNTAX            INTEGER
        MAX-ACCESS        read-write
        STATUS            current
        DESCRIPTION
                "CMNT: - Ancillary time code output line field 1
                 TYPE: - Number
                 PAGE: - Ancillary Data
                    ATC O/P F1 Line  cmdID= 42703
                    min= 0  max= 63  step= 1  format= Line %0.0f  div_scale= 1  preset= 2
                    Min = Line 0  Max = Line 63  Step = Line 1  Preset = Line 2  "
        ::= { iqmux33CmdEntry 42703 }


    iqmux33AncillaryDataHDVANCATCOPF2Line OBJECT-TYPE
        SYNTAX            INTEGER
        MAX-ACCESS        read-write
        STATUS            current
        DESCRIPTION
                "CMNT: - Ancillary time code output line field 2
                 TYPE: - Number
                 PAGE: - Ancillary Data
                    ATC O/P F2 Line  cmdID= 42748
                    min= 0  max= 31  step= 1  format= Line %0.0f  div_scale= 1  preset= 2
                    Min = Line 0  Max = Line 31  Step = Line 1  Preset = Line 2  "
        ::= { iqmux33CmdEntry 42748 }


    iqmux33AncillaryDataHDVANCATCFollow OBJECT-TYPE
        SYNTAX            INTEGER { disable(0), enable(1)  }
        MAX-ACCESS        read-write
        STATUS            current
        DESCRIPTION
                "CMNT: - Ancillary time code follow input line
                 TYPE: - Checkbox
                 PAGE: - Ancillary Data
                    ATC Follow  cmdID= 42704  "
        ::= { iqmux33CmdEntry 42704 }


    iqmux33AncillaryDataHDVANCHDCaptionEnable OBJECT-TYPE
        SYNTAX            INTEGER { disable(0), enable(1)  }
        MAX-ACCESS        read-write
        STATUS            current
        DESCRIPTION
                "CMNT: - Ancillary data closed caption CC708 enable output
                 TYPE: - Checkbox
                 PAGE: - Ancillary Data
                    HD Caption Enable  cmdID= 42701  "
        ::= { iqmux33CmdEntry 42701 }


    iqmux33AncillaryDataHDVANCHDCaptionIPLine OBJECT-TYPE
        SYNTAX            RollCallString
        MAX-ACCESS        read-only
        STATUS            current
        DESCRIPTION
                "CMNT: - Ancillary data closed caption CC708 input line
                 TYPE: - Display
                 PAGE: - Ancillary Data
                    HD Caption I/P Line  cmdID= 42726  "
        ::= { iqmux33CmdEntry 42726 }


    iqmux33AncillaryDataHDVANCHDCaptionOPLine OBJECT-TYPE
        SYNTAX            INTEGER
        MAX-ACCESS        read-write
        STATUS            current
        DESCRIPTION
                "CMNT: - Ancillary data closed caption CC708 output line
                 TYPE: - Number
                 PAGE: - Ancillary Data
                    HD Caption O/P Line  cmdID= 42725
                    min= 0  max= 63  step= 1  format= Line %0.0f  div_scale= 1  preset= 3
                    Min = Line 0  Max = Line 63  Step = Line 1  Preset = Line 3  "
        ::= { iqmux33CmdEntry 42725 }


    iqmux33HDVANCHDCaptionHDFollowIPLine OBJECT-TYPE
        SYNTAX            INTEGER { disable(0), enable(1)  }
        MAX-ACCESS        read-write
        STATUS            current
        DESCRIPTION
                "CMNT: - Ancillary data closed caption CC708 follow input
                 TYPE: - Checkbox
                 PAGE: - HD VANC
                    HD Follow I/P Line  cmdID= 42700  "
        ::= { iqmux33CmdEntry 42700 }


    iqmux33AudioInputDisembed18Disembed11procamp OBJECT-TYPE
        SYNTAX            INTEGER
        MAX-ACCESS        read-write
        STATUS            current
        DESCRIPTION
                "CMNT: - Disembed Proc Amp Gain
                 TYPE: - Number
                 PAGE: - AudioInput
                    Disembed1_1_procamp  cmdID= 40000
                    min= -801  max= 120  step= 1  format= %0.1f dB  div_scale= 10  preset= 0
                    Min = -80.1 dB  Max = 12.0 dB  Step = 0.1 dB  Preset = 0.0 dB  "
        ::= { iqmux33CmdEntry 40000 }


    iqmux33AudioInputDisembed18Disembed12procamp OBJECT-TYPE
        SYNTAX            INTEGER
        MAX-ACCESS        read-write
        STATUS            current
        DESCRIPTION
                "CMNT: - Disembed Proc Amp Gain
                 TYPE: - Number
                 PAGE: - AudioInput
                    Disembed1_2_procamp  cmdID= 40001
                    min= -801  max= 120  step= 1  format= %0.1f dB  div_scale= 10  preset= 0
                    Min = -80.1 dB  Max = 12.0 dB  Step = 0.1 dB  Preset = 0.0 dB  "
        ::= { iqmux33CmdEntry 40001 }


    iqmux33Disembed18Disembed1Mute11 OBJECT-TYPE
        SYNTAX            INTEGER { disable(0), enable(1)  }
        MAX-ACCESS        read-write
        STATUS            current
        DESCRIPTION
                "CMNT: - 
                 TYPE: - Checkbox
                 PAGE: - Disembed1-8
                    Mute1_1  cmdID= 40032  "
        ::= { iqmux33CmdEntry 40032 }


    iqmux33Disembed18Disembed1Mute12 OBJECT-TYPE
        SYNTAX            INTEGER { disable(0), enable(1)  }
        MAX-ACCESS        read-write
        STATUS            current
        DESCRIPTION
                "CMNT: - 
                 TYPE: - Checkbox
                 PAGE: - Disembed1-8
                    Mute1_2  cmdID= 40033  "
        ::= { iqmux33CmdEntry 40033 }


    iqmux33Disembed18Disembed1Stereo1 OBJECT-TYPE
        SYNTAX            INTEGER { disable(0), enable(1)  }
        MAX-ACCESS        read-write
        STATUS            current
        DESCRIPTION
                "CMNT: - 
                 TYPE: - Checkbox
                 PAGE: - Disembed1-8
                    Stereo1  cmdID= 40048  "
        ::= { iqmux33CmdEntry 40048 }


    iqmux33AudioInputDisembed18Disembed11invert OBJECT-TYPE
        SYNTAX            INTEGER { disable(0), enable(1)  }
        MAX-ACCESS        read-write
        STATUS            current
        DESCRIPTION
                "CMNT: - 
                 TYPE: - Checkbox
                 PAGE: - AudioInput
                    Disembed1_1_invert  cmdID= 40016  "
        ::= { iqmux33CmdEntry 40016 }


    iqmux33AudioInputDisembed18Disembed12invert OBJECT-TYPE
        SYNTAX            INTEGER { disable(0), enable(1)  }
        MAX-ACCESS        read-write
        STATUS            current
        DESCRIPTION
                "CMNT: - 
                 TYPE: - Checkbox
                 PAGE: - AudioInput
                    Disembed1_2_invert  cmdID= 40017  "
        ::= { iqmux33CmdEntry 40017 }


    iqmux33Disembed18Disembed1dolbyLine OBJECT-TYPE
        SYNTAX            RollCallString
        MAX-ACCESS        read-only
        STATUS            current
        DESCRIPTION
                "CMNT: - 
                 TYPE: - Display
                 PAGE: - Disembed1-8
                    dolbyLine  cmdID= 40073  "
        ::= { iqmux33CmdEntry 40073 }


    iqmux33AudioInputDisembed18Disembed21procamp OBJECT-TYPE
        SYNTAX            INTEGER
        MAX-ACCESS        read-write
        STATUS            current
        DESCRIPTION
                "CMNT: - Disembed Proc Amp Gain
                 TYPE: - Number
                 PAGE: - AudioInput
                    Disembed2_1_procamp  cmdID= 40002
                    min= -801  max= 120  step= 1  format= %0.1f dB  div_scale= 10  preset= 0
                    Min = -80.1 dB  Max = 12.0 dB  Step = 0.1 dB  Preset = 0.0 dB  "
        ::= { iqmux33CmdEntry 40002 }


    iqmux33AudioInputDisembed18Disembed22procamp OBJECT-TYPE
        SYNTAX            INTEGER
        MAX-ACCESS        read-write
        STATUS            current
        DESCRIPTION
                "CMNT: - Disembed Proc Amp Gain
                 TYPE: - Number
                 PAGE: - AudioInput
                    Disembed2_2_procamp  cmdID= 40003
                    min= -801  max= 120  step= 1  format= %0.1f dB  div_scale= 10  preset= 0
                    Min = -80.1 dB  Max = 12.0 dB  Step = 0.1 dB  Preset = 0.0 dB  "
        ::= { iqmux33CmdEntry 40003 }


    iqmux33Disembed18Disembed2Mute21 OBJECT-TYPE
        SYNTAX            INTEGER { disable(0), enable(1)  }
        MAX-ACCESS        read-write
        STATUS            current
        DESCRIPTION
                "CMNT: - 
                 TYPE: - Checkbox
                 PAGE: - Disembed1-8
                    Mute2_1  cmdID= 40034  "
        ::= { iqmux33CmdEntry 40034 }


    iqmux33Disembed18Disembed2Mute22 OBJECT-TYPE
        SYNTAX            INTEGER { disable(0), enable(1)  }
        MAX-ACCESS        read-write
        STATUS            current
        DESCRIPTION
                "CMNT: - 
                 TYPE: - Checkbox
                 PAGE: - Disembed1-8
                    Mute2_2  cmdID= 40035  "
        ::= { iqmux33CmdEntry 40035 }


    iqmux33Disembed18Disembed2Stereo2 OBJECT-TYPE
        SYNTAX            INTEGER { disable(0), enable(1)  }
        MAX-ACCESS        read-write
        STATUS            current
        DESCRIPTION
                "CMNT: - 
                 TYPE: - Checkbox
                 PAGE: - Disembed1-8
                    Stereo2  cmdID= 40049  "
        ::= { iqmux33CmdEntry 40049 }


    iqmux33AudioInputDisembed18Disembed21invert OBJECT-TYPE
        SYNTAX            INTEGER { disable(0), enable(1)  }
        MAX-ACCESS        read-write
        STATUS            current
        DESCRIPTION
                "CMNT: - 
                 TYPE: - Checkbox
                 PAGE: - AudioInput
                    Disembed2_1_invert  cmdID= 40018  "
        ::= { iqmux33CmdEntry 40018 }


    iqmux33AudioInputDisembed18Disembed22invert OBJECT-TYPE
        SYNTAX            INTEGER { disable(0), enable(1)  }
        MAX-ACCESS        read-write
        STATUS            current
        DESCRIPTION
                "CMNT: - 
                 TYPE: - Checkbox
                 PAGE: - AudioInput
                    Disembed2_2_invert  cmdID= 40019  "
        ::= { iqmux33CmdEntry 40019 }


    iqmux33Disembed18Disembed2dolbyLine OBJECT-TYPE
        SYNTAX            RollCallString
        MAX-ACCESS        read-only
        STATUS            current
        DESCRIPTION
                "CMNT: - 
                 TYPE: - Display
                 PAGE: - Disembed1-8
                    dolbyLine  cmdID= 40074  "
        ::= { iqmux33CmdEntry 40074 }


    iqmux33AudioInputDisembed18Disembed31procamp OBJECT-TYPE
        SYNTAX            INTEGER
        MAX-ACCESS        read-write
        STATUS            current
        DESCRIPTION
                "CMNT: - Disembed Proc Amp Gain
                 TYPE: - Number
                 PAGE: - AudioInput
                    Disembed3_1_procamp  cmdID= 40004
                    min= -801  max= 120  step= 1  format= %0.1f dB  div_scale= 10  preset= 0
                    Min = -80.1 dB  Max = 12.0 dB  Step = 0.1 dB  Preset = 0.0 dB  "
        ::= { iqmux33CmdEntry 40004 }


    iqmux33AudioInputDisembed18Disembed32procamp OBJECT-TYPE
        SYNTAX            INTEGER
        MAX-ACCESS        read-write
        STATUS            current
        DESCRIPTION
                "CMNT: - Disembed Proc Amp Gain
                 TYPE: - Number
                 PAGE: - AudioInput
                    Disembed3_2_procamp  cmdID= 40005
                    min= -801  max= 120  step= 1  format= %0.1f dB  div_scale= 10  preset= 0
                    Min = -80.1 dB  Max = 12.0 dB  Step = 0.1 dB  Preset = 0.0 dB  "
        ::= { iqmux33CmdEntry 40005 }


    iqmux33Disembed18Disembed3Mute31 OBJECT-TYPE
        SYNTAX            INTEGER { disable(0), enable(1)  }
        MAX-ACCESS        read-write
        STATUS            current
        DESCRIPTION
                "CMNT: - 
                 TYPE: - Checkbox
                 PAGE: - Disembed1-8
                    Mute3_1  cmdID= 40036  "
        ::= { iqmux33CmdEntry 40036 }


    iqmux33Disembed18Disembed3Mute32 OBJECT-TYPE
        SYNTAX            INTEGER { disable(0), enable(1)  }
        MAX-ACCESS        read-write
        STATUS            current
        DESCRIPTION
                "CMNT: - 
                 TYPE: - Checkbox
                 PAGE: - Disembed1-8
                    Mute3_2  cmdID= 40037  "
        ::= { iqmux33CmdEntry 40037 }


    iqmux33Disembed18Disembed3Stereo3 OBJECT-TYPE
        SYNTAX            INTEGER { disable(0), enable(1)  }
        MAX-ACCESS        read-write
        STATUS            current
        DESCRIPTION
                "CMNT: - 
                 TYPE: - Checkbox
                 PAGE: - Disembed1-8
                    Stereo3  cmdID= 40050  "
        ::= { iqmux33CmdEntry 40050 }


    iqmux33AudioInputDisembed18Disembed31invert OBJECT-TYPE
        SYNTAX            INTEGER { disable(0), enable(1)  }
        MAX-ACCESS        read-write
        STATUS            current
        DESCRIPTION
                "CMNT: - 
                 TYPE: - Checkbox
                 PAGE: - AudioInput
                    Disembed3_1_invert  cmdID= 40020  "
        ::= { iqmux33CmdEntry 40020 }


    iqmux33AudioInputDisembed18Disembed32invert OBJECT-TYPE
        SYNTAX            INTEGER { disable(0), enable(1)  }
        MAX-ACCESS        read-write
        STATUS            current
        DESCRIPTION
                "CMNT: - 
                 TYPE: - Checkbox
                 PAGE: - AudioInput
                    Disembed3_2_invert  cmdID= 40021  "
        ::= { iqmux33CmdEntry 40021 }


    iqmux33Disembed18Disembed3dolbyLine OBJECT-TYPE
        SYNTAX            RollCallString
        MAX-ACCESS        read-only
        STATUS            current
        DESCRIPTION
                "CMNT: - 
                 TYPE: - Display
                 PAGE: - Disembed1-8
                    dolbyLine  cmdID= 40075  "
        ::= { iqmux33CmdEntry 40075 }


    iqmux33AudioInputDisembed18Disembed41procamp OBJECT-TYPE
        SYNTAX            INTEGER
        MAX-ACCESS        read-write
        STATUS            current
        DESCRIPTION
                "CMNT: - Disembed Proc Amp Gain
                 TYPE: - Number
                 PAGE: - AudioInput
                    Disembed4_1_procamp  cmdID= 40006
                    min= -801  max= 120  step= 1  format= %0.1f dB  div_scale= 10  preset= 0
                    Min = -80.1 dB  Max = 12.0 dB  Step = 0.1 dB  Preset = 0.0 dB  "
        ::= { iqmux33CmdEntry 40006 }


    iqmux33AudioInputDisembed18Disembed42procamp OBJECT-TYPE
        SYNTAX            INTEGER
        MAX-ACCESS        read-write
        STATUS            current
        DESCRIPTION
                "CMNT: - Disembed Proc Amp Gain
                 TYPE: - Number
                 PAGE: - AudioInput
                    Disembed4_2_procamp  cmdID= 40007
                    min= -801  max= 120  step= 1  format= %0.1f dB  div_scale= 10  preset= 0
                    Min = -80.1 dB  Max = 12.0 dB  Step = 0.1 dB  Preset = 0.0 dB  "
        ::= { iqmux33CmdEntry 40007 }


    iqmux33Disembed18Disembed4Mute41 OBJECT-TYPE
        SYNTAX            INTEGER { disable(0), enable(1)  }
        MAX-ACCESS        read-write
        STATUS            current
        DESCRIPTION
                "CMNT: - 
                 TYPE: - Checkbox
                 PAGE: - Disembed1-8
                    Mute4_1  cmdID= 40038  "
        ::= { iqmux33CmdEntry 40038 }


    iqmux33Disembed18Disembed4Mute42 OBJECT-TYPE
        SYNTAX            INTEGER { disable(0), enable(1)  }
        MAX-ACCESS        read-write
        STATUS            current
        DESCRIPTION
                "CMNT: - 
                 TYPE: - Checkbox
                 PAGE: - Disembed1-8
                    Mute4_2  cmdID= 40039  "
        ::= { iqmux33CmdEntry 40039 }


    iqmux33Disembed18Disembed4Stereo4 OBJECT-TYPE
        SYNTAX            INTEGER { disable(0), enable(1)  }
        MAX-ACCESS        read-write
        STATUS            current
        DESCRIPTION
                "CMNT: - 
                 TYPE: - Checkbox
                 PAGE: - Disembed1-8
                    Stereo4  cmdID= 40051  "
        ::= { iqmux33CmdEntry 40051 }


    iqmux33AudioInputDisembed18Disembed41invert OBJECT-TYPE
        SYNTAX            INTEGER { disable(0), enable(1)  }
        MAX-ACCESS        read-write
        STATUS            current
        DESCRIPTION
                "CMNT: - 
                 TYPE: - Checkbox
                 PAGE: - AudioInput
                    Disembed4_1_invert  cmdID= 40022  "
        ::= { iqmux33CmdEntry 40022 }


    iqmux33AudioInputDisembed18Disembed42invert OBJECT-TYPE
        SYNTAX            INTEGER { disable(0), enable(1)  }
        MAX-ACCESS        read-write
        STATUS            current
        DESCRIPTION
                "CMNT: - 
                 TYPE: - Checkbox
                 PAGE: - AudioInput
                    Disembed4_2_invert  cmdID= 40023  "
        ::= { iqmux33CmdEntry 40023 }


    iqmux33Disembed18Disembed4dolbyLine OBJECT-TYPE
        SYNTAX            RollCallString
        MAX-ACCESS        read-only
        STATUS            current
        DESCRIPTION
                "CMNT: - 
                 TYPE: - Display
                 PAGE: - Disembed1-8
                    dolbyLine  cmdID= 40076  "
        ::= { iqmux33CmdEntry 40076 }


    iqmux33AudioInputDisembed18Disembed51procamp OBJECT-TYPE
        SYNTAX            INTEGER
        MAX-ACCESS        read-write
        STATUS            current
        DESCRIPTION
                "CMNT: - Disembed Proc Amp Gain
                 TYPE: - Number
                 PAGE: - AudioInput
                    Disembed5_1_procamp  cmdID= 40008
                    min= -801  max= 120  step= 1  format= %0.1f dB  div_scale= 10  preset= 0
                    Min = -80.1 dB  Max = 12.0 dB  Step = 0.1 dB  Preset = 0.0 dB  "
        ::= { iqmux33CmdEntry 40008 }


    iqmux33AudioInputDisembed18Disembed52procamp OBJECT-TYPE
        SYNTAX            INTEGER
        MAX-ACCESS        read-write
        STATUS            current
        DESCRIPTION
                "CMNT: - Disembed Proc Amp Gain
                 TYPE: - Number
                 PAGE: - AudioInput
                    Disembed5_2_procamp  cmdID= 40009
                    min= -801  max= 120  step= 1  format= %0.1f dB  div_scale= 10  preset= 0
                    Min = -80.1 dB  Max = 12.0 dB  Step = 0.1 dB  Preset = 0.0 dB  "
        ::= { iqmux33CmdEntry 40009 }


    iqmux33Disembed18Disembed5Mute51 OBJECT-TYPE
        SYNTAX            INTEGER { disable(0), enable(1)  }
        MAX-ACCESS        read-write
        STATUS            current
        DESCRIPTION
                "CMNT: - 
                 TYPE: - Checkbox
                 PAGE: - Disembed1-8
                    Mute5_1  cmdID= 40040  "
        ::= { iqmux33CmdEntry 40040 }


    iqmux33Disembed18Disembed5Mute52 OBJECT-TYPE
        SYNTAX            INTEGER { disable(0), enable(1)  }
        MAX-ACCESS        read-write
        STATUS            current
        DESCRIPTION
                "CMNT: - 
                 TYPE: - Checkbox
                 PAGE: - Disembed1-8
                    Mute5_2  cmdID= 40041  "
        ::= { iqmux33CmdEntry 40041 }


    iqmux33Disembed18Disembed5Stereo5 OBJECT-TYPE
        SYNTAX            INTEGER { disable(0), enable(1)  }
        MAX-ACCESS        read-write
        STATUS            current
        DESCRIPTION
                "CMNT: - 
                 TYPE: - Checkbox
                 PAGE: - Disembed1-8
                    Stereo5  cmdID= 40052  "
        ::= { iqmux33CmdEntry 40052 }


    iqmux33AudioInputDisembed18Disembed51invert OBJECT-TYPE
        SYNTAX            INTEGER { disable(0), enable(1)  }
        MAX-ACCESS        read-write
        STATUS            current
        DESCRIPTION
                "CMNT: - 
                 TYPE: - Checkbox
                 PAGE: - AudioInput
                    Disembed5_1_invert  cmdID= 40024  "
        ::= { iqmux33CmdEntry 40024 }


    iqmux33AudioInputDisembed18Disembed52invert OBJECT-TYPE
        SYNTAX            INTEGER { disable(0), enable(1)  }
        MAX-ACCESS        read-write
        STATUS            current
        DESCRIPTION
                "CMNT: - 
                 TYPE: - Checkbox
                 PAGE: - AudioInput
                    Disembed5_2_invert  cmdID= 40025  "
        ::= { iqmux33CmdEntry 40025 }


    iqmux33Disembed18Disembed5dolbyLine OBJECT-TYPE
        SYNTAX            RollCallString
        MAX-ACCESS        read-only
        STATUS            current
        DESCRIPTION
                "CMNT: - 
                 TYPE: - Display
                 PAGE: - Disembed1-8
                    dolbyLine  cmdID= 40077  "
        ::= { iqmux33CmdEntry 40077 }


    iqmux33AudioInputDisembed18Disembed61procamp OBJECT-TYPE
        SYNTAX            INTEGER
        MAX-ACCESS        read-write
        STATUS            current
        DESCRIPTION
                "CMNT: - Disembed Proc Amp Gain
                 TYPE: - Number
                 PAGE: - AudioInput
                    Disembed6_1_procamp  cmdID= 40010
                    min= -801  max= 120  step= 1  format= %0.1f dB  div_scale= 10  preset= 0
                    Min = -80.1 dB  Max = 12.0 dB  Step = 0.1 dB  Preset = 0.0 dB  "
        ::= { iqmux33CmdEntry 40010 }


    iqmux33AudioInputDisembed18Disembed62procamp OBJECT-TYPE
        SYNTAX            INTEGER
        MAX-ACCESS        read-write
        STATUS            current
        DESCRIPTION
                "CMNT: - Disembed Proc Amp Gain
                 TYPE: - Number
                 PAGE: - AudioInput
                    Disembed6_2_procamp  cmdID= 40011
                    min= -801  max= 120  step= 1  format= %0.1f dB  div_scale= 10  preset= 0
                    Min = -80.1 dB  Max = 12.0 dB  Step = 0.1 dB  Preset = 0.0 dB  "
        ::= { iqmux33CmdEntry 40011 }


    iqmux33Disembed18Disembed6Mute61 OBJECT-TYPE
        SYNTAX            INTEGER { disable(0), enable(1)  }
        MAX-ACCESS        read-write
        STATUS            current
        DESCRIPTION
                "CMNT: - 
                 TYPE: - Checkbox
                 PAGE: - Disembed1-8
                    Mute6_1  cmdID= 40042  "
        ::= { iqmux33CmdEntry 40042 }


    iqmux33Disembed18Disembed6Mute62 OBJECT-TYPE
        SYNTAX            INTEGER { disable(0), enable(1)  }
        MAX-ACCESS        read-write
        STATUS            current
        DESCRIPTION
                "CMNT: - 
                 TYPE: - Checkbox
                 PAGE: - Disembed1-8
                    Mute6_2  cmdID= 40043  "
        ::= { iqmux33CmdEntry 40043 }


    iqmux33Disembed18Disembed6Stereo6 OBJECT-TYPE
        SYNTAX            INTEGER { disable(0), enable(1)  }
        MAX-ACCESS        read-write
        STATUS            current
        DESCRIPTION
                "CMNT: - 
                 TYPE: - Checkbox
                 PAGE: - Disembed1-8
                    Stereo6  cmdID= 40053  "
        ::= { iqmux33CmdEntry 40053 }


    iqmux33AudioInputDisembed18Disembed61invert OBJECT-TYPE
        SYNTAX            INTEGER { disable(0), enable(1)  }
        MAX-ACCESS        read-write
        STATUS            current
        DESCRIPTION
                "CMNT: - 
                 TYPE: - Checkbox
                 PAGE: - AudioInput
                    Disembed6_1_invert  cmdID= 40026  "
        ::= { iqmux33CmdEntry 40026 }


    iqmux33AudioInputDisembed18Disembed62invert OBJECT-TYPE
        SYNTAX            INTEGER { disable(0), enable(1)  }
        MAX-ACCESS        read-write
        STATUS            current
        DESCRIPTION
                "CMNT: - 
                 TYPE: - Checkbox
                 PAGE: - AudioInput
                    Disembed6_2_invert  cmdID= 40027  "
        ::= { iqmux33CmdEntry 40027 }


    iqmux33Disembed18Disembed6dolbyLine OBJECT-TYPE
        SYNTAX            RollCallString
        MAX-ACCESS        read-only
        STATUS            current
        DESCRIPTION
                "CMNT: - 
                 TYPE: - Display
                 PAGE: - Disembed1-8
                    dolbyLine  cmdID= 40078  "
        ::= { iqmux33CmdEntry 40078 }


    iqmux33AudioInputDisembed18Disembed71procamp OBJECT-TYPE
        SYNTAX            INTEGER
        MAX-ACCESS        read-write
        STATUS            current
        DESCRIPTION
                "CMNT: - Disembed Proc Amp Gain
                 TYPE: - Number
                 PAGE: - AudioInput
                    Disembed7_1_procamp  cmdID= 40012
                    min= -801  max= 120  step= 1  format= %0.1f dB  div_scale= 10  preset= 0
                    Min = -80.1 dB  Max = 12.0 dB  Step = 0.1 dB  Preset = 0.0 dB  "
        ::= { iqmux33CmdEntry 40012 }


    iqmux33AudioInputDisembed18Disembed72procamp OBJECT-TYPE
        SYNTAX            INTEGER
        MAX-ACCESS        read-write
        STATUS            current
        DESCRIPTION
                "CMNT: - Disembed Proc Amp Gain
                 TYPE: - Number
                 PAGE: - AudioInput
                    Disembed7_2_procamp  cmdID= 40013
                    min= -801  max= 120  step= 1  format= %0.1f dB  div_scale= 10  preset= 0
                    Min = -80.1 dB  Max = 12.0 dB  Step = 0.1 dB  Preset = 0.0 dB  "
        ::= { iqmux33CmdEntry 40013 }


    iqmux33Disembed18Disembed7Mute71 OBJECT-TYPE
        SYNTAX            INTEGER { disable(0), enable(1)  }
        MAX-ACCESS        read-write
        STATUS            current
        DESCRIPTION
                "CMNT: - 
                 TYPE: - Checkbox
                 PAGE: - Disembed1-8
                    Mute7_1  cmdID= 40044  "
        ::= { iqmux33CmdEntry 40044 }


    iqmux33Disembed18Disembed7Mute72 OBJECT-TYPE
        SYNTAX            INTEGER { disable(0), enable(1)  }
        MAX-ACCESS        read-write
        STATUS            current
        DESCRIPTION
                "CMNT: - 
                 TYPE: - Checkbox
                 PAGE: - Disembed1-8
                    Mute7_2  cmdID= 40045  "
        ::= { iqmux33CmdEntry 40045 }


    iqmux33Disembed18Disembed7Stereo7 OBJECT-TYPE
        SYNTAX            INTEGER { disable(0), enable(1)  }
        MAX-ACCESS        read-write
        STATUS            current
        DESCRIPTION
                "CMNT: - 
                 TYPE: - Checkbox
                 PAGE: - Disembed1-8
                    Stereo7  cmdID= 40054  "
        ::= { iqmux33CmdEntry 40054 }


    iqmux33AudioInputDisembed18Disembed71invert OBJECT-TYPE
        SYNTAX            INTEGER { disable(0), enable(1)  }
        MAX-ACCESS        read-write
        STATUS            current
        DESCRIPTION
                "CMNT: - 
                 TYPE: - Checkbox
                 PAGE: - AudioInput
                    Disembed7_1_invert  cmdID= 40028  "
        ::= { iqmux33CmdEntry 40028 }


    iqmux33AudioInputDisembed18Disembed72invert OBJECT-TYPE
        SYNTAX            INTEGER { disable(0), enable(1)  }
        MAX-ACCESS        read-write
        STATUS            current
        DESCRIPTION
                "CMNT: - 
                 TYPE: - Checkbox
                 PAGE: - AudioInput
                    Disembed7_2_invert  cmdID= 40029  "
        ::= { iqmux33CmdEntry 40029 }


    iqmux33Disembed18Disembed7dolbyLine OBJECT-TYPE
        SYNTAX            RollCallString
        MAX-ACCESS        read-only
        STATUS            current
        DESCRIPTION
                "CMNT: - 
                 TYPE: - Display
                 PAGE: - Disembed1-8
                    dolbyLine  cmdID= 40079  "
        ::= { iqmux33CmdEntry 40079 }


    iqmux33AudioInputDisembed18Disembed81procamp OBJECT-TYPE
        SYNTAX            INTEGER
        MAX-ACCESS        read-write
        STATUS            current
        DESCRIPTION
                "CMNT: - Disembed Proc Amp Gain
                 TYPE: - Number
                 PAGE: - AudioInput
                    Disembed8_1_procamp  cmdID= 40014
                    min= -801  max= 120  step= 1  format= %0.1f dB  div_scale= 10  preset= 0
                    Min = -80.1 dB  Max = 12.0 dB  Step = 0.1 dB  Preset = 0.0 dB  "
        ::= { iqmux33CmdEntry 40014 }


    iqmux33AudioInputDisembed18Disembed82procamp OBJECT-TYPE
        SYNTAX            INTEGER
        MAX-ACCESS        read-write
        STATUS            current
        DESCRIPTION
                "CMNT: - Disembed Proc Amp Gain
                 TYPE: - Number
                 PAGE: - AudioInput
                    Disembed8_2_procamp  cmdID= 40015
                    min= -801  max= 120  step= 1  format= %0.1f dB  div_scale= 10  preset= 0
                    Min = -80.1 dB  Max = 12.0 dB  Step = 0.1 dB  Preset = 0.0 dB  "
        ::= { iqmux33CmdEntry 40015 }


    iqmux33Disembed18Disembed8Mute81 OBJECT-TYPE
        SYNTAX            INTEGER { disable(0), enable(1)  }
        MAX-ACCESS        read-write
        STATUS            current
        DESCRIPTION
                "CMNT: - 
                 TYPE: - Checkbox
                 PAGE: - Disembed1-8
                    Mute8_1  cmdID= 40046  "
        ::= { iqmux33CmdEntry 40046 }


    iqmux33Disembed18Disembed8Mute82 OBJECT-TYPE
        SYNTAX            INTEGER { disable(0), enable(1)  }
        MAX-ACCESS        read-write
        STATUS            current
        DESCRIPTION
                "CMNT: - 
                 TYPE: - Checkbox
                 PAGE: - Disembed1-8
                    Mute8_2  cmdID= 40047  "
        ::= { iqmux33CmdEntry 40047 }


    iqmux33Disembed18Disembed8Stereo8 OBJECT-TYPE
        SYNTAX            INTEGER { disable(0), enable(1)  }
        MAX-ACCESS        read-write
        STATUS            current
        DESCRIPTION
                "CMNT: - 
                 TYPE: - Checkbox
                 PAGE: - Disembed1-8
                    Stereo8  cmdID= 40055  "
        ::= { iqmux33CmdEntry 40055 }


    iqmux33AudioInputDisembed18Disembed81invert OBJECT-TYPE
        SYNTAX            INTEGER { disable(0), enable(1)  }
        MAX-ACCESS        read-write
        STATUS            current
        DESCRIPTION
                "CMNT: - 
                 TYPE: - Checkbox
                 PAGE: - AudioInput
                    Disembed8_1_invert  cmdID= 40030  "
        ::= { iqmux33CmdEntry 40030 }


    iqmux33AudioInputDisembed18Disembed82invert OBJECT-TYPE
        SYNTAX            INTEGER { disable(0), enable(1)  }
        MAX-ACCESS        read-write
        STATUS            current
        DESCRIPTION
                "CMNT: - 
                 TYPE: - Checkbox
                 PAGE: - AudioInput
                    Disembed8_2_invert  cmdID= 40031  "
        ::= { iqmux33CmdEntry 40031 }


    iqmux33Disembed18Disembed8dolbyLine OBJECT-TYPE
        SYNTAX            RollCallString
        MAX-ACCESS        read-only
        STATUS            current
        DESCRIPTION
                "CMNT: - 
                 TYPE: - Display
                 PAGE: - Disembed1-8
                    dolbyLine  cmdID= 40080  "
        ::= { iqmux33CmdEntry 40080 }


    iqmux33AudioInputDisembed18ProcampSaveset OBJECT-TYPE
        SYNTAX            INTEGER
        MAX-ACCESS        read-write
        STATUS            current
        DESCRIPTION
                "CMNT: - Used to correctly restore stereo procamp and mute values.
                 TYPE: - Number
                 PAGE: - AudioInput
                    ProcampSaveset  cmdID= 40072
                    min= 0  max= 1  step= 1  format= %0.0f  div_scale= 1  preset= 0
                    Min = 0  Max = 1  Step = 1  Preset = 0  "
        ::= { iqmux33CmdEntry 40072 }


    iqmux33AudioInputAESInput18AESInput11procamp OBJECT-TYPE
        SYNTAX            INTEGER
        MAX-ACCESS        read-write
        STATUS            current
        DESCRIPTION
                "CMNT: - AESInput Proc Amp Gain
                 TYPE: - Number
                 PAGE: - AudioInput
                    AESInput1_1_procamp  cmdID= 40100
                    min= -801  max= 120  step= 1  format= %0.1f dB  div_scale= 10  preset= 0
                    Min = -80.1 dB  Max = 12.0 dB  Step = 0.1 dB  Preset = 0.0 dB  "
        ::= { iqmux33CmdEntry 40100 }


    iqmux33AudioInputAESInput18AESInput12procamp OBJECT-TYPE
        SYNTAX            INTEGER
        MAX-ACCESS        read-write
        STATUS            current
        DESCRIPTION
                "CMNT: - AESInput Proc Amp Gain
                 TYPE: - Number
                 PAGE: - AudioInput
                    AESInput1_2_procamp  cmdID= 40101
                    min= -801  max= 120  step= 1  format= %0.1f dB  div_scale= 10  preset= 0
                    Min = -80.1 dB  Max = 12.0 dB  Step = 0.1 dB  Preset = 0.0 dB  "
        ::= { iqmux33CmdEntry 40101 }


    iqmux33AESInput18AESInput1Mute11 OBJECT-TYPE
        SYNTAX            INTEGER { disable(0), enable(1)  }
        MAX-ACCESS        read-write
        STATUS            current
        DESCRIPTION
                "CMNT: - 
                 TYPE: - Checkbox
                 PAGE: - AESInput1-8
                    Mute1_1  cmdID= 40132  "
        ::= { iqmux33CmdEntry 40132 }


    iqmux33AESInput18AESInput1Mute12 OBJECT-TYPE
        SYNTAX            INTEGER { disable(0), enable(1)  }
        MAX-ACCESS        read-write
        STATUS            current
        DESCRIPTION
                "CMNT: - 
                 TYPE: - Checkbox
                 PAGE: - AESInput1-8
                    Mute1_2  cmdID= 40133  "
        ::= { iqmux33CmdEntry 40133 }


    iqmux33AESInput18AESInput1Stereo1 OBJECT-TYPE
        SYNTAX            INTEGER { disable(0), enable(1)  }
        MAX-ACCESS        read-write
        STATUS            current
        DESCRIPTION
                "CMNT: - 
                 TYPE: - Checkbox
                 PAGE: - AESInput1-8
                    Stereo1  cmdID= 40148  "
        ::= { iqmux33CmdEntry 40148 }


    iqmux33AudioInputAESInput18AESInput11invert OBJECT-TYPE
        SYNTAX            INTEGER { disable(0), enable(1)  }
        MAX-ACCESS        read-write
        STATUS            current
        DESCRIPTION
                "CMNT: - 
                 TYPE: - Checkbox
                 PAGE: - AudioInput
                    AESInput1_1_invert  cmdID= 40116  "
        ::= { iqmux33CmdEntry 40116 }


    iqmux33AudioInputAESInput18AESInput12invert OBJECT-TYPE
        SYNTAX            INTEGER { disable(0), enable(1)  }
        MAX-ACCESS        read-write
        STATUS            current
        DESCRIPTION
                "CMNT: - 
                 TYPE: - Checkbox
                 PAGE: - AudioInput
                    AESInput1_2_invert  cmdID= 40117  "
        ::= { iqmux33CmdEntry 40117 }


    iqmux33AudioInputAESInput18AESInput21procamp OBJECT-TYPE
        SYNTAX            INTEGER
        MAX-ACCESS        read-write
        STATUS            current
        DESCRIPTION
                "CMNT: - AESInput Proc Amp Gain
                 TYPE: - Number
                 PAGE: - AudioInput
                    AESInput2_1_procamp  cmdID= 40102
                    min= -801  max= 120  step= 1  format= %0.1f dB  div_scale= 10  preset= 0
                    Min = -80.1 dB  Max = 12.0 dB  Step = 0.1 dB  Preset = 0.0 dB  "
        ::= { iqmux33CmdEntry 40102 }


    iqmux33AudioInputAESInput18AESInput22procamp OBJECT-TYPE
        SYNTAX            INTEGER
        MAX-ACCESS        read-write
        STATUS            current
        DESCRIPTION
                "CMNT: - AESInput Proc Amp Gain
                 TYPE: - Number
                 PAGE: - AudioInput
                    AESInput2_2_procamp  cmdID= 40103
                    min= -801  max= 120  step= 1  format= %0.1f dB  div_scale= 10  preset= 0
                    Min = -80.1 dB  Max = 12.0 dB  Step = 0.1 dB  Preset = 0.0 dB  "
        ::= { iqmux33CmdEntry 40103 }


    iqmux33AESInput18AESInput2Mute21 OBJECT-TYPE
        SYNTAX            INTEGER { disable(0), enable(1)  }
        MAX-ACCESS        read-write
        STATUS            current
        DESCRIPTION
                "CMNT: - 
                 TYPE: - Checkbox
                 PAGE: - AESInput1-8
                    Mute2_1  cmdID= 40134  "
        ::= { iqmux33CmdEntry 40134 }


    iqmux33AESInput18AESInput2Mute22 OBJECT-TYPE
        SYNTAX            INTEGER { disable(0), enable(1)  }
        MAX-ACCESS        read-write
        STATUS            current
        DESCRIPTION
                "CMNT: - 
                 TYPE: - Checkbox
                 PAGE: - AESInput1-8
                    Mute2_2  cmdID= 40135  "
        ::= { iqmux33CmdEntry 40135 }


    iqmux33AESInput18AESInput2Stereo2 OBJECT-TYPE
        SYNTAX            INTEGER { disable(0), enable(1)  }
        MAX-ACCESS        read-write
        STATUS            current
        DESCRIPTION
                "CMNT: - 
                 TYPE: - Checkbox
                 PAGE: - AESInput1-8
                    Stereo2  cmdID= 40149  "
        ::= { iqmux33CmdEntry 40149 }


    iqmux33AudioInputAESInput18AESInput21invert OBJECT-TYPE
        SYNTAX            INTEGER { disable(0), enable(1)  }
        MAX-ACCESS        read-write
        STATUS            current
        DESCRIPTION
                "CMNT: - 
                 TYPE: - Checkbox
                 PAGE: - AudioInput
                    AESInput2_1_invert  cmdID= 40118  "
        ::= { iqmux33CmdEntry 40118 }


    iqmux33AudioInputAESInput18AESInput22invert OBJECT-TYPE
        SYNTAX            INTEGER { disable(0), enable(1)  }
        MAX-ACCESS        read-write
        STATUS            current
        DESCRIPTION
                "CMNT: - 
                 TYPE: - Checkbox
                 PAGE: - AudioInput
                    AESInput2_2_invert  cmdID= 40119  "
        ::= { iqmux33CmdEntry 40119 }


    iqmux33AudioInputAESInput18AESInput31procamp OBJECT-TYPE
        SYNTAX            INTEGER
        MAX-ACCESS        read-write
        STATUS            current
        DESCRIPTION
                "CMNT: - AESInput Proc Amp Gain
                 TYPE: - Number
                 PAGE: - AudioInput
                    AESInput3_1_procamp  cmdID= 40104
                    min= -801  max= 120  step= 1  format= %0.1f dB  div_scale= 10  preset= 0
                    Min = -80.1 dB  Max = 12.0 dB  Step = 0.1 dB  Preset = 0.0 dB  "
        ::= { iqmux33CmdEntry 40104 }


    iqmux33AudioInputAESInput18AESInput32procamp OBJECT-TYPE
        SYNTAX            INTEGER
        MAX-ACCESS        read-write
        STATUS            current
        DESCRIPTION
                "CMNT: - AESInput Proc Amp Gain
                 TYPE: - Number
                 PAGE: - AudioInput
                    AESInput3_2_procamp  cmdID= 40105
                    min= -801  max= 120  step= 1  format= %0.1f dB  div_scale= 10  preset= 0
                    Min = -80.1 dB  Max = 12.0 dB  Step = 0.1 dB  Preset = 0.0 dB  "
        ::= { iqmux33CmdEntry 40105 }


    iqmux33AESInput18AESInput3Mute31 OBJECT-TYPE
        SYNTAX            INTEGER { disable(0), enable(1)  }
        MAX-ACCESS        read-write
        STATUS            current
        DESCRIPTION
                "CMNT: - 
                 TYPE: - Checkbox
                 PAGE: - AESInput1-8
                    Mute3_1  cmdID= 40136  "
        ::= { iqmux33CmdEntry 40136 }


    iqmux33AESInput18AESInput3Mute32 OBJECT-TYPE
        SYNTAX            INTEGER { disable(0), enable(1)  }
        MAX-ACCESS        read-write
        STATUS            current
        DESCRIPTION
                "CMNT: - 
                 TYPE: - Checkbox
                 PAGE: - AESInput1-8
                    Mute3_2  cmdID= 40137  "
        ::= { iqmux33CmdEntry 40137 }


    iqmux33AESInput18AESInput3Stereo3 OBJECT-TYPE
        SYNTAX            INTEGER { disable(0), enable(1)  }
        MAX-ACCESS        read-write
        STATUS            current
        DESCRIPTION
                "CMNT: - 
                 TYPE: - Checkbox
                 PAGE: - AESInput1-8
                    Stereo3  cmdID= 40150  "
        ::= { iqmux33CmdEntry 40150 }


    iqmux33AudioInputAESInput18AESInput31invert OBJECT-TYPE
        SYNTAX            INTEGER { disable(0), enable(1)  }
        MAX-ACCESS        read-write
        STATUS            current
        DESCRIPTION
                "CMNT: - 
                 TYPE: - Checkbox
                 PAGE: - AudioInput
                    AESInput3_1_invert  cmdID= 40120  "
        ::= { iqmux33CmdEntry 40120 }


    iqmux33AudioInputAESInput18AESInput32invert OBJECT-TYPE
        SYNTAX            INTEGER { disable(0), enable(1)  }
        MAX-ACCESS        read-write
        STATUS            current
        DESCRIPTION
                "CMNT: - 
                 TYPE: - Checkbox
                 PAGE: - AudioInput
                    AESInput3_2_invert  cmdID= 40121  "
        ::= { iqmux33CmdEntry 40121 }


    iqmux33AudioInputAESInput18AESInput41procamp OBJECT-TYPE
        SYNTAX            INTEGER
        MAX-ACCESS        read-write
        STATUS            current
        DESCRIPTION
                "CMNT: - AESInput Proc Amp Gain
                 TYPE: - Number
                 PAGE: - AudioInput
                    AESInput4_1_procamp  cmdID= 40106
                    min= -801  max= 120  step= 1  format= %0.1f dB  div_scale= 10  preset= 0
                    Min = -80.1 dB  Max = 12.0 dB  Step = 0.1 dB  Preset = 0.0 dB  "
        ::= { iqmux33CmdEntry 40106 }


    iqmux33AudioInputAESInput18AESInput42procamp OBJECT-TYPE
        SYNTAX            INTEGER
        MAX-ACCESS        read-write
        STATUS            current
        DESCRIPTION
                "CMNT: - AESInput Proc Amp Gain
                 TYPE: - Number
                 PAGE: - AudioInput
                    AESInput4_2_procamp  cmdID= 40107
                    min= -801  max= 120  step= 1  format= %0.1f dB  div_scale= 10  preset= 0
                    Min = -80.1 dB  Max = 12.0 dB  Step = 0.1 dB  Preset = 0.0 dB  "
        ::= { iqmux33CmdEntry 40107 }


    iqmux33AESInput18AESInput4Mute41 OBJECT-TYPE
        SYNTAX            INTEGER { disable(0), enable(1)  }
        MAX-ACCESS        read-write
        STATUS            current
        DESCRIPTION
                "CMNT: - 
                 TYPE: - Checkbox
                 PAGE: - AESInput1-8
                    Mute4_1  cmdID= 40138  "
        ::= { iqmux33CmdEntry 40138 }


    iqmux33AESInput18AESInput4Mute42 OBJECT-TYPE
        SYNTAX            INTEGER { disable(0), enable(1)  }
        MAX-ACCESS        read-write
        STATUS            current
        DESCRIPTION
                "CMNT: - 
                 TYPE: - Checkbox
                 PAGE: - AESInput1-8
                    Mute4_2  cmdID= 40139  "
        ::= { iqmux33CmdEntry 40139 }


    iqmux33AESInput18AESInput4Stereo4 OBJECT-TYPE
        SYNTAX            INTEGER { disable(0), enable(1)  }
        MAX-ACCESS        read-write
        STATUS            current
        DESCRIPTION
                "CMNT: - 
                 TYPE: - Checkbox
                 PAGE: - AESInput1-8
                    Stereo4  cmdID= 40151  "
        ::= { iqmux33CmdEntry 40151 }


    iqmux33AudioInputAESInput18AESInput41invert OBJECT-TYPE
        SYNTAX            INTEGER { disable(0), enable(1)  }
        MAX-ACCESS        read-write
        STATUS            current
        DESCRIPTION
                "CMNT: - 
                 TYPE: - Checkbox
                 PAGE: - AudioInput
                    AESInput4_1_invert  cmdID= 40122  "
        ::= { iqmux33CmdEntry 40122 }


    iqmux33AudioInputAESInput18AESInput42invert OBJECT-TYPE
        SYNTAX            INTEGER { disable(0), enable(1)  }
        MAX-ACCESS        read-write
        STATUS            current
        DESCRIPTION
                "CMNT: - 
                 TYPE: - Checkbox
                 PAGE: - AudioInput
                    AESInput4_2_invert  cmdID= 40123  "
        ::= { iqmux33CmdEntry 40123 }


    iqmux33AudioInputAESInput18AESInput51procamp OBJECT-TYPE
        SYNTAX            INTEGER
        MAX-ACCESS        read-write
        STATUS            current
        DESCRIPTION
                "CMNT: - AESInput Proc Amp Gain
                 TYPE: - Number
                 PAGE: - AudioInput
                    AESInput5_1_procamp  cmdID= 40108
                    min= -801  max= 120  step= 1  format= %0.1f dB  div_scale= 10  preset= 0
                    Min = -80.1 dB  Max = 12.0 dB  Step = 0.1 dB  Preset = 0.0 dB  "
        ::= { iqmux33CmdEntry 40108 }


    iqmux33AudioInputAESInput18AESInput52procamp OBJECT-TYPE
        SYNTAX            INTEGER
        MAX-ACCESS        read-write
        STATUS            current
        DESCRIPTION
                "CMNT: - AESInput Proc Amp Gain
                 TYPE: - Number
                 PAGE: - AudioInput
                    AESInput5_2_procamp  cmdID= 40109
                    min= -801  max= 120  step= 1  format= %0.1f dB  div_scale= 10  preset= 0
                    Min = -80.1 dB  Max = 12.0 dB  Step = 0.1 dB  Preset = 0.0 dB  "
        ::= { iqmux33CmdEntry 40109 }


    iqmux33AESInput18AESInput5Mute51 OBJECT-TYPE
        SYNTAX            INTEGER { disable(0), enable(1)  }
        MAX-ACCESS        read-write
        STATUS            current
        DESCRIPTION
                "CMNT: - 
                 TYPE: - Checkbox
                 PAGE: - AESInput1-8
                    Mute5_1  cmdID= 40140  "
        ::= { iqmux33CmdEntry 40140 }


    iqmux33AESInput18AESInput5Mute52 OBJECT-TYPE
        SYNTAX            INTEGER { disable(0), enable(1)  }
        MAX-ACCESS        read-write
        STATUS            current
        DESCRIPTION
                "CMNT: - 
                 TYPE: - Checkbox
                 PAGE: - AESInput1-8
                    Mute5_2  cmdID= 40141  "
        ::= { iqmux33CmdEntry 40141 }


    iqmux33AESInput18AESInput5Stereo5 OBJECT-TYPE
        SYNTAX            INTEGER { disable(0), enable(1)  }
        MAX-ACCESS        read-write
        STATUS            current
        DESCRIPTION
                "CMNT: - 
                 TYPE: - Checkbox
                 PAGE: - AESInput1-8
                    Stereo5  cmdID= 40152  "
        ::= { iqmux33CmdEntry 40152 }


    iqmux33AudioInputAESInput18AESInput51invert OBJECT-TYPE
        SYNTAX            INTEGER { disable(0), enable(1)  }
        MAX-ACCESS        read-write
        STATUS            current
        DESCRIPTION
                "CMNT: - 
                 TYPE: - Checkbox
                 PAGE: - AudioInput
                    AESInput5_1_invert  cmdID= 40124  "
        ::= { iqmux33CmdEntry 40124 }


    iqmux33AudioInputAESInput18AESInput52invert OBJECT-TYPE
        SYNTAX            INTEGER { disable(0), enable(1)  }
        MAX-ACCESS        read-write
        STATUS            current
        DESCRIPTION
                "CMNT: - 
                 TYPE: - Checkbox
                 PAGE: - AudioInput
                    AESInput5_2_invert  cmdID= 40125  "
        ::= { iqmux33CmdEntry 40125 }


    iqmux33AudioInputAESInput18AESInput61procamp OBJECT-TYPE
        SYNTAX            INTEGER
        MAX-ACCESS        read-write
        STATUS            current
        DESCRIPTION
                "CMNT: - AESInput Proc Amp Gain
                 TYPE: - Number
                 PAGE: - AudioInput
                    AESInput6_1_procamp  cmdID= 40110
                    min= -801  max= 120  step= 1  format= %0.1f dB  div_scale= 10  preset= 0
                    Min = -80.1 dB  Max = 12.0 dB  Step = 0.1 dB  Preset = 0.0 dB  "
        ::= { iqmux33CmdEntry 40110 }


    iqmux33AudioInputAESInput18AESInput62procamp OBJECT-TYPE
        SYNTAX            INTEGER
        MAX-ACCESS        read-write
        STATUS            current
        DESCRIPTION
                "CMNT: - AESInput Proc Amp Gain
                 TYPE: - Number
                 PAGE: - AudioInput
                    AESInput6_2_procamp  cmdID= 40111
                    min= -801  max= 120  step= 1  format= %0.1f dB  div_scale= 10  preset= 0
                    Min = -80.1 dB  Max = 12.0 dB  Step = 0.1 dB  Preset = 0.0 dB  "
        ::= { iqmux33CmdEntry 40111 }


    iqmux33AESInput18AESInput6Mute61 OBJECT-TYPE
        SYNTAX            INTEGER { disable(0), enable(1)  }
        MAX-ACCESS        read-write
        STATUS            current
        DESCRIPTION
                "CMNT: - 
                 TYPE: - Checkbox
                 PAGE: - AESInput1-8
                    Mute6_1  cmdID= 40142  "
        ::= { iqmux33CmdEntry 40142 }


    iqmux33AESInput18AESInput6Mute62 OBJECT-TYPE
        SYNTAX            INTEGER { disable(0), enable(1)  }
        MAX-ACCESS        read-write
        STATUS            current
        DESCRIPTION
                "CMNT: - 
                 TYPE: - Checkbox
                 PAGE: - AESInput1-8
                    Mute6_2  cmdID= 40143  "
        ::= { iqmux33CmdEntry 40143 }


    iqmux33AESInput18AESInput6Stereo6 OBJECT-TYPE
        SYNTAX            INTEGER { disable(0), enable(1)  }
        MAX-ACCESS        read-write
        STATUS            current
        DESCRIPTION
                "CMNT: - 
                 TYPE: - Checkbox
                 PAGE: - AESInput1-8
                    Stereo6  cmdID= 40153  "
        ::= { iqmux33CmdEntry 40153 }


    iqmux33AudioInputAESInput18AESInput61invert OBJECT-TYPE
        SYNTAX            INTEGER { disable(0), enable(1)  }
        MAX-ACCESS        read-write
        STATUS            current
        DESCRIPTION
                "CMNT: - 
                 TYPE: - Checkbox
                 PAGE: - AudioInput
                    AESInput6_1_invert  cmdID= 40126  "
        ::= { iqmux33CmdEntry 40126 }


    iqmux33AudioInputAESInput18AESInput62invert OBJECT-TYPE
        SYNTAX            INTEGER { disable(0), enable(1)  }
        MAX-ACCESS        read-write
        STATUS            current
        DESCRIPTION
                "CMNT: - 
                 TYPE: - Checkbox
                 PAGE: - AudioInput
                    AESInput6_2_invert  cmdID= 40127  "
        ::= { iqmux33CmdEntry 40127 }


    iqmux33AudioInputAESInput18AESInput71procamp OBJECT-TYPE
        SYNTAX            INTEGER
        MAX-ACCESS        read-write
        STATUS            current
        DESCRIPTION
                "CMNT: - AESInput Proc Amp Gain
                 TYPE: - Number
                 PAGE: - AudioInput
                    AESInput7_1_procamp  cmdID= 40112
                    min= -801  max= 120  step= 1  format= %0.1f dB  div_scale= 10  preset= 0
                    Min = -80.1 dB  Max = 12.0 dB  Step = 0.1 dB  Preset = 0.0 dB  "
        ::= { iqmux33CmdEntry 40112 }


    iqmux33AudioInputAESInput18AESInput72procamp OBJECT-TYPE
        SYNTAX            INTEGER
        MAX-ACCESS        read-write
        STATUS            current
        DESCRIPTION
                "CMNT: - AESInput Proc Amp Gain
                 TYPE: - Number
                 PAGE: - AudioInput
                    AESInput7_2_procamp  cmdID= 40113
                    min= -801  max= 120  step= 1  format= %0.1f dB  div_scale= 10  preset= 0
                    Min = -80.1 dB  Max = 12.0 dB  Step = 0.1 dB  Preset = 0.0 dB  "
        ::= { iqmux33CmdEntry 40113 }


    iqmux33AESInput18AESInput7Mute71 OBJECT-TYPE
        SYNTAX            INTEGER { disable(0), enable(1)  }
        MAX-ACCESS        read-write
        STATUS            current
        DESCRIPTION
                "CMNT: - 
                 TYPE: - Checkbox
                 PAGE: - AESInput1-8
                    Mute7_1  cmdID= 40144  "
        ::= { iqmux33CmdEntry 40144 }


    iqmux33AESInput18AESInput7Mute72 OBJECT-TYPE
        SYNTAX            INTEGER { disable(0), enable(1)  }
        MAX-ACCESS        read-write
        STATUS            current
        DESCRIPTION
                "CMNT: - 
                 TYPE: - Checkbox
                 PAGE: - AESInput1-8
                    Mute7_2  cmdID= 40145  "
        ::= { iqmux33CmdEntry 40145 }


    iqmux33AESInput18AESInput7Stereo7 OBJECT-TYPE
        SYNTAX            INTEGER { disable(0), enable(1)  }
        MAX-ACCESS        read-write
        STATUS            current
        DESCRIPTION
                "CMNT: - 
                 TYPE: - Checkbox
                 PAGE: - AESInput1-8
                    Stereo7  cmdID= 40154  "
        ::= { iqmux33CmdEntry 40154 }


    iqmux33AudioInputAESInput18AESInput71invert OBJECT-TYPE
        SYNTAX            INTEGER { disable(0), enable(1)  }
        MAX-ACCESS        read-write
        STATUS            current
        DESCRIPTION
                "CMNT: - 
                 TYPE: - Checkbox
                 PAGE: - AudioInput
                    AESInput7_1_invert  cmdID= 40128  "
        ::= { iqmux33CmdEntry 40128 }


    iqmux33AudioInputAESInput18AESInput72invert OBJECT-TYPE
        SYNTAX            INTEGER { disable(0), enable(1)  }
        MAX-ACCESS        read-write
        STATUS            current
        DESCRIPTION
                "CMNT: - 
                 TYPE: - Checkbox
                 PAGE: - AudioInput
                    AESInput7_2_invert  cmdID= 40129  "
        ::= { iqmux33CmdEntry 40129 }


    iqmux33AudioInputAESInput18AESInput81procamp OBJECT-TYPE
        SYNTAX            INTEGER
        MAX-ACCESS        read-write
        STATUS            current
        DESCRIPTION
                "CMNT: - AESInput Proc Amp Gain
                 TYPE: - Number
                 PAGE: - AudioInput
                    AESInput8_1_procamp  cmdID= 40114
                    min= -801  max= 120  step= 1  format= %0.1f dB  div_scale= 10  preset= 0
                    Min = -80.1 dB  Max = 12.0 dB  Step = 0.1 dB  Preset = 0.0 dB  "
        ::= { iqmux33CmdEntry 40114 }


    iqmux33AudioInputAESInput18AESInput82procamp OBJECT-TYPE
        SYNTAX            INTEGER
        MAX-ACCESS        read-write
        STATUS            current
        DESCRIPTION
                "CMNT: - AESInput Proc Amp Gain
                 TYPE: - Number
                 PAGE: - AudioInput
                    AESInput8_2_procamp  cmdID= 40115
                    min= -801  max= 120  step= 1  format= %0.1f dB  div_scale= 10  preset= 0
                    Min = -80.1 dB  Max = 12.0 dB  Step = 0.1 dB  Preset = 0.0 dB  "
        ::= { iqmux33CmdEntry 40115 }


    iqmux33AESInput18AESInput8Mute81 OBJECT-TYPE
        SYNTAX            INTEGER { disable(0), enable(1)  }
        MAX-ACCESS        read-write
        STATUS            current
        DESCRIPTION
                "CMNT: - 
                 TYPE: - Checkbox
                 PAGE: - AESInput1-8
                    Mute8_1  cmdID= 40146  "
        ::= { iqmux33CmdEntry 40146 }


    iqmux33AESInput18AESInput8Mute82 OBJECT-TYPE
        SYNTAX            INTEGER { disable(0), enable(1)  }
        MAX-ACCESS        read-write
        STATUS            current
        DESCRIPTION
                "CMNT: - 
                 TYPE: - Checkbox
                 PAGE: - AESInput1-8
                    Mute8_2  cmdID= 40147  "
        ::= { iqmux33CmdEntry 40147 }


    iqmux33AESInput18AESInput8Stereo8 OBJECT-TYPE
        SYNTAX            INTEGER { disable(0), enable(1)  }
        MAX-ACCESS        read-write
        STATUS            current
        DESCRIPTION
                "CMNT: - 
                 TYPE: - Checkbox
                 PAGE: - AESInput1-8
                    Stereo8  cmdID= 40155  "
        ::= { iqmux33CmdEntry 40155 }


    iqmux33AudioInputAESInput18AESInput81invert OBJECT-TYPE
        SYNTAX            INTEGER { disable(0), enable(1)  }
        MAX-ACCESS        read-write
        STATUS            current
        DESCRIPTION
                "CMNT: - 
                 TYPE: - Checkbox
                 PAGE: - AudioInput
                    AESInput8_1_invert  cmdID= 40130  "
        ::= { iqmux33CmdEntry 40130 }


    iqmux33AudioInputAESInput18AESInput82invert OBJECT-TYPE
        SYNTAX            INTEGER { disable(0), enable(1)  }
        MAX-ACCESS        read-write
        STATUS            current
        DESCRIPTION
                "CMNT: - 
                 TYPE: - Checkbox
                 PAGE: - AudioInput
                    AESInput8_2_invert  cmdID= 40131  "
        ::= { iqmux33CmdEntry 40131 }


    iqmux33AudioInputAnalogInput12AnalogInput11procamp OBJECT-TYPE
        SYNTAX            INTEGER
        MAX-ACCESS        read-write
        STATUS            current
        DESCRIPTION
                "CMNT: - AnalogInput Proc Amp Gain
                 TYPE: - Number
                 PAGE: - AudioInput
                    AnalogInput1_1_procamp  cmdID= 40181
                    min= -801  max= 120  step= 1  format= %0.1f dB  div_scale= 10  preset= 0
                    Min = -80.1 dB  Max = 12.0 dB  Step = 0.1 dB  Preset = 0.0 dB  "
        ::= { iqmux33CmdEntry 40181 }


    iqmux33AudioInputAnalogInput12AnalogInput12procamp OBJECT-TYPE
        SYNTAX            INTEGER
        MAX-ACCESS        read-write
        STATUS            current
        DESCRIPTION
                "CMNT: - AnalogInput Proc Amp Gain
                 TYPE: - Number
                 PAGE: - AudioInput
                    AnalogInput1_2_procamp  cmdID= 40182
                    min= -801  max= 120  step= 1  format= %0.1f dB  div_scale= 10  preset= 0
                    Min = -80.1 dB  Max = 12.0 dB  Step = 0.1 dB  Preset = 0.0 dB  "
        ::= { iqmux33CmdEntry 40182 }


    iqmux33AnalogInput12AnalogInput1Mute11 OBJECT-TYPE
        SYNTAX            INTEGER { disable(0), enable(1)  }
        MAX-ACCESS        read-write
        STATUS            current
        DESCRIPTION
                "CMNT: - 
                 TYPE: - Checkbox
                 PAGE: - AnalogInput1-2
                    Mute1_1  cmdID= 40189  "
        ::= { iqmux33CmdEntry 40189 }


    iqmux33AnalogInput12AnalogInput1Mute12 OBJECT-TYPE
        SYNTAX            INTEGER { disable(0), enable(1)  }
        MAX-ACCESS        read-write
        STATUS            current
        DESCRIPTION
                "CMNT: - 
                 TYPE: - Checkbox
                 PAGE: - AnalogInput1-2
                    Mute1_2  cmdID= 40190  "
        ::= { iqmux33CmdEntry 40190 }


    iqmux33AnalogInput12AnalogInput1Stereo1 OBJECT-TYPE
        SYNTAX            INTEGER { disable(0), enable(1)  }
        MAX-ACCESS        read-write
        STATUS            current
        DESCRIPTION
                "CMNT: - 
                 TYPE: - Checkbox
                 PAGE: - AnalogInput1-2
                    Stereo1  cmdID= 40193  "
        ::= { iqmux33CmdEntry 40193 }


    iqmux33AudioInputAnalogInput12AnalogInput11invert OBJECT-TYPE
        SYNTAX            INTEGER { disable(0), enable(1)  }
        MAX-ACCESS        read-write
        STATUS            current
        DESCRIPTION
                "CMNT: - 
                 TYPE: - Checkbox
                 PAGE: - AudioInput
                    AnalogInput1_1_invert  cmdID= 40185  "
        ::= { iqmux33CmdEntry 40185 }


    iqmux33AudioInputAnalogInput12AnalogInput12invert OBJECT-TYPE
        SYNTAX            INTEGER { disable(0), enable(1)  }
        MAX-ACCESS        read-write
        STATUS            current
        DESCRIPTION
                "CMNT: - 
                 TYPE: - Checkbox
                 PAGE: - AudioInput
                    AnalogInput1_2_invert  cmdID= 40186  "
        ::= { iqmux33CmdEntry 40186 }


    iqmux33AudioInputAnalogInput12AnalogInput21procamp OBJECT-TYPE
        SYNTAX            INTEGER
        MAX-ACCESS        read-write
        STATUS            current
        DESCRIPTION
                "CMNT: - AnalogInput Proc Amp Gain
                 TYPE: - Number
                 PAGE: - AudioInput
                    AnalogInput2_1_procamp  cmdID= 40183
                    min= -801  max= 120  step= 1  format= %0.1f dB  div_scale= 10  preset= 0
                    Min = -80.1 dB  Max = 12.0 dB  Step = 0.1 dB  Preset = 0.0 dB  "
        ::= { iqmux33CmdEntry 40183 }


    iqmux33AudioInputAnalogInput12AnalogInput22procamp OBJECT-TYPE
        SYNTAX            INTEGER
        MAX-ACCESS        read-write
        STATUS            current
        DESCRIPTION
                "CMNT: - AnalogInput Proc Amp Gain
                 TYPE: - Number
                 PAGE: - AudioInput
                    AnalogInput2_2_procamp  cmdID= 40184
                    min= -801  max= 120  step= 1  format= %0.1f dB  div_scale= 10  preset= 0
                    Min = -80.1 dB  Max = 12.0 dB  Step = 0.1 dB  Preset = 0.0 dB  "
        ::= { iqmux33CmdEntry 40184 }


    iqmux33AnalogInput12AnalogInput2Mute21 OBJECT-TYPE
        SYNTAX            INTEGER { disable(0), enable(1)  }
        MAX-ACCESS        read-write
        STATUS            current
        DESCRIPTION
                "CMNT: - 
                 TYPE: - Checkbox
                 PAGE: - AnalogInput1-2
                    Mute2_1  cmdID= 40191  "
        ::= { iqmux33CmdEntry 40191 }


    iqmux33AnalogInput12AnalogInput2Mute22 OBJECT-TYPE
        SYNTAX            INTEGER { disable(0), enable(1)  }
        MAX-ACCESS        read-write
        STATUS            current
        DESCRIPTION
                "CMNT: - 
                 TYPE: - Checkbox
                 PAGE: - AnalogInput1-2
                    Mute2_2  cmdID= 40192  "
        ::= { iqmux33CmdEntry 40192 }


    iqmux33AnalogInput12AnalogInput2Stereo2 OBJECT-TYPE
        SYNTAX            INTEGER { disable(0), enable(1)  }
        MAX-ACCESS        read-write
        STATUS            current
        DESCRIPTION
                "CMNT: - 
                 TYPE: - Checkbox
                 PAGE: - AnalogInput1-2
                    Stereo2  cmdID= 40194  "
        ::= { iqmux33CmdEntry 40194 }


    iqmux33AudioInputAnalogInput12AnalogInput21invert OBJECT-TYPE
        SYNTAX            INTEGER { disable(0), enable(1)  }
        MAX-ACCESS        read-write
        STATUS            current
        DESCRIPTION
                "CMNT: - 
                 TYPE: - Checkbox
                 PAGE: - AudioInput
                    AnalogInput2_1_invert  cmdID= 40187  "
        ::= { iqmux33CmdEntry 40187 }


    iqmux33AudioInputAnalogInput12AnalogInput22invert OBJECT-TYPE
        SYNTAX            INTEGER { disable(0), enable(1)  }
        MAX-ACCESS        read-write
        STATUS            current
        DESCRIPTION
                "CMNT: - 
                 TYPE: - Checkbox
                 PAGE: - AudioInput
                    AnalogInput2_2_invert  cmdID= 40188  "
        ::= { iqmux33CmdEntry 40188 }


    iqmux33AudioOutputEmbed18Embed11procamp OBJECT-TYPE
        SYNTAX            INTEGER
        MAX-ACCESS        read-write
        STATUS            current
        DESCRIPTION
                "CMNT: - Embed Proc Amp Gain
                 TYPE: - Number
                 PAGE: - AudioOutput
                    Embed1_1_procamp  cmdID= 40400
                    min= -801  max= 120  step= 1  format= %0.1f dB  div_scale= 10  preset= 0
                    Min = -80.1 dB  Max = 12.0 dB  Step = 0.1 dB  Preset = 0.0 dB  "
        ::= { iqmux33CmdEntry 40400 }


    iqmux33AudioOutputEmbed18Embed12procamp OBJECT-TYPE
        SYNTAX            INTEGER
        MAX-ACCESS        read-write
        STATUS            current
        DESCRIPTION
                "CMNT: - Embed Proc Amp Gain
                 TYPE: - Number
                 PAGE: - AudioOutput
                    Embed1_2_procamp  cmdID= 40401
                    min= -801  max= 120  step= 1  format= %0.1f dB  div_scale= 10  preset= 0
                    Min = -80.1 dB  Max = 12.0 dB  Step = 0.1 dB  Preset = 0.0 dB  "
        ::= { iqmux33CmdEntry 40401 }


    iqmux33Embed18Embed1Mute11 OBJECT-TYPE
        SYNTAX            INTEGER { disable(0), enable(1)  }
        MAX-ACCESS        read-write
        STATUS            current
        DESCRIPTION
                "CMNT: - 
                 TYPE: - Checkbox
                 PAGE: - Embed1-8
                    Mute1_1  cmdID= 40432  "
        ::= { iqmux33CmdEntry 40432 }


    iqmux33Embed18Embed1Mute12 OBJECT-TYPE
        SYNTAX            INTEGER { disable(0), enable(1)  }
        MAX-ACCESS        read-write
        STATUS            current
        DESCRIPTION
                "CMNT: - 
                 TYPE: - Checkbox
                 PAGE: - Embed1-8
                    Mute1_2  cmdID= 40433  "
        ::= { iqmux33CmdEntry 40433 }


    iqmux33Embed18Embed1Stereo1 OBJECT-TYPE
        SYNTAX            INTEGER { disable(0), enable(1)  }
        MAX-ACCESS        read-write
        STATUS            current
        DESCRIPTION
                "CMNT: - 
                 TYPE: - Checkbox
                 PAGE: - Embed1-8
                    Stereo1  cmdID= 40448  "
        ::= { iqmux33CmdEntry 40448 }


    iqmux33Embed18Embed1dolbyLine OBJECT-TYPE
        SYNTAX            RollCallString
        MAX-ACCESS        read-only
        STATUS            current
        DESCRIPTION
                "CMNT: - 
                 TYPE: - Display
                 PAGE: - Embed1-8
                    dolbyLine  cmdID= 40081  "
        ::= { iqmux33CmdEntry 40081 }


    iqmux33AudioOutputEmbed18Embed21procamp OBJECT-TYPE
        SYNTAX            INTEGER
        MAX-ACCESS        read-write
        STATUS            current
        DESCRIPTION
                "CMNT: - Embed Proc Amp Gain
                 TYPE: - Number
                 PAGE: - AudioOutput
                    Embed2_1_procamp  cmdID= 40402
                    min= -801  max= 120  step= 1  format= %0.1f dB  div_scale= 10  preset= 0
                    Min = -80.1 dB  Max = 12.0 dB  Step = 0.1 dB  Preset = 0.0 dB  "
        ::= { iqmux33CmdEntry 40402 }


    iqmux33AudioOutputEmbed18Embed22procamp OBJECT-TYPE
        SYNTAX            INTEGER
        MAX-ACCESS        read-write
        STATUS            current
        DESCRIPTION
                "CMNT: - Embed Proc Amp Gain
                 TYPE: - Number
                 PAGE: - AudioOutput
                    Embed2_2_procamp  cmdID= 40403
                    min= -801  max= 120  step= 1  format= %0.1f dB  div_scale= 10  preset= 0
                    Min = -80.1 dB  Max = 12.0 dB  Step = 0.1 dB  Preset = 0.0 dB  "
        ::= { iqmux33CmdEntry 40403 }


    iqmux33Embed18Embed2Mute21 OBJECT-TYPE
        SYNTAX            INTEGER { disable(0), enable(1)  }
        MAX-ACCESS        read-write
        STATUS            current
        DESCRIPTION
                "CMNT: - 
                 TYPE: - Checkbox
                 PAGE: - Embed1-8
                    Mute2_1  cmdID= 40434  "
        ::= { iqmux33CmdEntry 40434 }


    iqmux33Embed18Embed2Mute22 OBJECT-TYPE
        SYNTAX            INTEGER { disable(0), enable(1)  }
        MAX-ACCESS        read-write
        STATUS            current
        DESCRIPTION
                "CMNT: - 
                 TYPE: - Checkbox
                 PAGE: - Embed1-8
                    Mute2_2  cmdID= 40435  "
        ::= { iqmux33CmdEntry 40435 }


    iqmux33Embed18Embed2Stereo2 OBJECT-TYPE
        SYNTAX            INTEGER { disable(0), enable(1)  }
        MAX-ACCESS        read-write
        STATUS            current
        DESCRIPTION
                "CMNT: - 
                 TYPE: - Checkbox
                 PAGE: - Embed1-8
                    Stereo2  cmdID= 40449  "
        ::= { iqmux33CmdEntry 40449 }


    iqmux33Embed18Embed2dolbyLine OBJECT-TYPE
        SYNTAX            RollCallString
        MAX-ACCESS        read-only
        STATUS            current
        DESCRIPTION
                "CMNT: - 
                 TYPE: - Display
                 PAGE: - Embed1-8
                    dolbyLine  cmdID= 40082  "
        ::= { iqmux33CmdEntry 40082 }


    iqmux33AudioOutputEmbed18Embed31procamp OBJECT-TYPE
        SYNTAX            INTEGER
        MAX-ACCESS        read-write
        STATUS            current
        DESCRIPTION
                "CMNT: - Embed Proc Amp Gain
                 TYPE: - Number
                 PAGE: - AudioOutput
                    Embed3_1_procamp  cmdID= 40404
                    min= -801  max= 120  step= 1  format= %0.1f dB  div_scale= 10  preset= 0
                    Min = -80.1 dB  Max = 12.0 dB  Step = 0.1 dB  Preset = 0.0 dB  "
        ::= { iqmux33CmdEntry 40404 }


    iqmux33AudioOutputEmbed18Embed32procamp OBJECT-TYPE
        SYNTAX            INTEGER
        MAX-ACCESS        read-write
        STATUS            current
        DESCRIPTION
                "CMNT: - Embed Proc Amp Gain
                 TYPE: - Number
                 PAGE: - AudioOutput
                    Embed3_2_procamp  cmdID= 40405
                    min= -801  max= 120  step= 1  format= %0.1f dB  div_scale= 10  preset= 0
                    Min = -80.1 dB  Max = 12.0 dB  Step = 0.1 dB  Preset = 0.0 dB  "
        ::= { iqmux33CmdEntry 40405 }


    iqmux33Embed18Embed3Mute31 OBJECT-TYPE
        SYNTAX            INTEGER { disable(0), enable(1)  }
        MAX-ACCESS        read-write
        STATUS            current
        DESCRIPTION
                "CMNT: - 
                 TYPE: - Checkbox
                 PAGE: - Embed1-8
                    Mute3_1  cmdID= 40436  "
        ::= { iqmux33CmdEntry 40436 }


    iqmux33Embed18Embed3Mute32 OBJECT-TYPE
        SYNTAX            INTEGER { disable(0), enable(1)  }
        MAX-ACCESS        read-write
        STATUS            current
        DESCRIPTION
                "CMNT: - 
                 TYPE: - Checkbox
                 PAGE: - Embed1-8
                    Mute3_2  cmdID= 40437  "
        ::= { iqmux33CmdEntry 40437 }


    iqmux33Embed18Embed3Stereo3 OBJECT-TYPE
        SYNTAX            INTEGER { disable(0), enable(1)  }
        MAX-ACCESS        read-write
        STATUS            current
        DESCRIPTION
                "CMNT: - 
                 TYPE: - Checkbox
                 PAGE: - Embed1-8
                    Stereo3  cmdID= 40450  "
        ::= { iqmux33CmdEntry 40450 }


    iqmux33Embed18Embed3dolbyLine OBJECT-TYPE
        SYNTAX            RollCallString
        MAX-ACCESS        read-only
        STATUS            current
        DESCRIPTION
                "CMNT: - 
                 TYPE: - Display
                 PAGE: - Embed1-8
                    dolbyLine  cmdID= 40083  "
        ::= { iqmux33CmdEntry 40083 }


    iqmux33AudioOutputEmbed18Embed41procamp OBJECT-TYPE
        SYNTAX            INTEGER
        MAX-ACCESS        read-write
        STATUS            current
        DESCRIPTION
                "CMNT: - Embed Proc Amp Gain
                 TYPE: - Number
                 PAGE: - AudioOutput
                    Embed4_1_procamp  cmdID= 40406
                    min= -801  max= 120  step= 1  format= %0.1f dB  div_scale= 10  preset= 0
                    Min = -80.1 dB  Max = 12.0 dB  Step = 0.1 dB  Preset = 0.0 dB  "
        ::= { iqmux33CmdEntry 40406 }


    iqmux33AudioOutputEmbed18Embed42procamp OBJECT-TYPE
        SYNTAX            INTEGER
        MAX-ACCESS        read-write
        STATUS            current
        DESCRIPTION
                "CMNT: - Embed Proc Amp Gain
                 TYPE: - Number
                 PAGE: - AudioOutput
                    Embed4_2_procamp  cmdID= 40407
                    min= -801  max= 120  step= 1  format= %0.1f dB  div_scale= 10  preset= 0
                    Min = -80.1 dB  Max = 12.0 dB  Step = 0.1 dB  Preset = 0.0 dB  "
        ::= { iqmux33CmdEntry 40407 }


    iqmux33Embed18Embed4Mute41 OBJECT-TYPE
        SYNTAX            INTEGER { disable(0), enable(1)  }
        MAX-ACCESS        read-write
        STATUS            current
        DESCRIPTION
                "CMNT: - 
                 TYPE: - Checkbox
                 PAGE: - Embed1-8
                    Mute4_1  cmdID= 40438  "
        ::= { iqmux33CmdEntry 40438 }


    iqmux33Embed18Embed4Mute42 OBJECT-TYPE
        SYNTAX            INTEGER { disable(0), enable(1)  }
        MAX-ACCESS        read-write
        STATUS            current
        DESCRIPTION
                "CMNT: - 
                 TYPE: - Checkbox
                 PAGE: - Embed1-8
                    Mute4_2  cmdID= 40439  "
        ::= { iqmux33CmdEntry 40439 }


    iqmux33Embed18Embed4Stereo4 OBJECT-TYPE
        SYNTAX            INTEGER { disable(0), enable(1)  }
        MAX-ACCESS        read-write
        STATUS            current
        DESCRIPTION
                "CMNT: - 
                 TYPE: - Checkbox
                 PAGE: - Embed1-8
                    Stereo4  cmdID= 40451  "
        ::= { iqmux33CmdEntry 40451 }


    iqmux33Embed18Embed4dolbyLine OBJECT-TYPE
        SYNTAX            RollCallString
        MAX-ACCESS        read-only
        STATUS            current
        DESCRIPTION
                "CMNT: - 
                 TYPE: - Display
                 PAGE: - Embed1-8
                    dolbyLine  cmdID= 40084  "
        ::= { iqmux33CmdEntry 40084 }


    iqmux33AudioOutputEmbed18Embed51procamp OBJECT-TYPE
        SYNTAX            INTEGER
        MAX-ACCESS        read-write
        STATUS            current
        DESCRIPTION
                "CMNT: - Embed Proc Amp Gain
                 TYPE: - Number
                 PAGE: - AudioOutput
                    Embed5_1_procamp  cmdID= 40408
                    min= -801  max= 120  step= 1  format= %0.1f dB  div_scale= 10  preset= 0
                    Min = -80.1 dB  Max = 12.0 dB  Step = 0.1 dB  Preset = 0.0 dB  "
        ::= { iqmux33CmdEntry 40408 }


    iqmux33AudioOutputEmbed18Embed52procamp OBJECT-TYPE
        SYNTAX            INTEGER
        MAX-ACCESS        read-write
        STATUS            current
        DESCRIPTION
                "CMNT: - Embed Proc Amp Gain
                 TYPE: - Number
                 PAGE: - AudioOutput
                    Embed5_2_procamp  cmdID= 40409
                    min= -801  max= 120  step= 1  format= %0.1f dB  div_scale= 10  preset= 0
                    Min = -80.1 dB  Max = 12.0 dB  Step = 0.1 dB  Preset = 0.0 dB  "
        ::= { iqmux33CmdEntry 40409 }


    iqmux33Embed18Embed5Mute51 OBJECT-TYPE
        SYNTAX            INTEGER { disable(0), enable(1)  }
        MAX-ACCESS        read-write
        STATUS            current
        DESCRIPTION
                "CMNT: - 
                 TYPE: - Checkbox
                 PAGE: - Embed1-8
                    Mute5_1  cmdID= 40440  "
        ::= { iqmux33CmdEntry 40440 }


    iqmux33Embed18Embed5Mute52 OBJECT-TYPE
        SYNTAX            INTEGER { disable(0), enable(1)  }
        MAX-ACCESS        read-write
        STATUS            current
        DESCRIPTION
                "CMNT: - 
                 TYPE: - Checkbox
                 PAGE: - Embed1-8
                    Mute5_2  cmdID= 40441  "
        ::= { iqmux33CmdEntry 40441 }


    iqmux33Embed18Embed5Stereo5 OBJECT-TYPE
        SYNTAX            INTEGER { disable(0), enable(1)  }
        MAX-ACCESS        read-write
        STATUS            current
        DESCRIPTION
                "CMNT: - 
                 TYPE: - Checkbox
                 PAGE: - Embed1-8
                    Stereo5  cmdID= 40452  "
        ::= { iqmux33CmdEntry 40452 }


    iqmux33Embed18Embed5dolbyLine OBJECT-TYPE
        SYNTAX            RollCallString
        MAX-ACCESS        read-only
        STATUS            current
        DESCRIPTION
                "CMNT: - 
                 TYPE: - Display
                 PAGE: - Embed1-8
                    dolbyLine  cmdID= 40085  "
        ::= { iqmux33CmdEntry 40085 }


    iqmux33AudioOutputEmbed18Embed61procamp OBJECT-TYPE
        SYNTAX            INTEGER
        MAX-ACCESS        read-write
        STATUS            current
        DESCRIPTION
                "CMNT: - Embed Proc Amp Gain
                 TYPE: - Number
                 PAGE: - AudioOutput
                    Embed6_1_procamp  cmdID= 40410
                    min= -801  max= 120  step= 1  format= %0.1f dB  div_scale= 10  preset= 0
                    Min = -80.1 dB  Max = 12.0 dB  Step = 0.1 dB  Preset = 0.0 dB  "
        ::= { iqmux33CmdEntry 40410 }


    iqmux33AudioOutputEmbed18Embed62procamp OBJECT-TYPE
        SYNTAX            INTEGER
        MAX-ACCESS        read-write
        STATUS            current
        DESCRIPTION
                "CMNT: - Embed Proc Amp Gain
                 TYPE: - Number
                 PAGE: - AudioOutput
                    Embed6_2_procamp  cmdID= 40411
                    min= -801  max= 120  step= 1  format= %0.1f dB  div_scale= 10  preset= 0
                    Min = -80.1 dB  Max = 12.0 dB  Step = 0.1 dB  Preset = 0.0 dB  "
        ::= { iqmux33CmdEntry 40411 }


    iqmux33Embed18Embed6Mute61 OBJECT-TYPE
        SYNTAX            INTEGER { disable(0), enable(1)  }
        MAX-ACCESS        read-write
        STATUS            current
        DESCRIPTION
                "CMNT: - 
                 TYPE: - Checkbox
                 PAGE: - Embed1-8
                    Mute6_1  cmdID= 40442  "
        ::= { iqmux33CmdEntry 40442 }


    iqmux33Embed18Embed6Mute62 OBJECT-TYPE
        SYNTAX            INTEGER { disable(0), enable(1)  }
        MAX-ACCESS        read-write
        STATUS            current
        DESCRIPTION
                "CMNT: - 
                 TYPE: - Checkbox
                 PAGE: - Embed1-8
                    Mute6_2  cmdID= 40443  "
        ::= { iqmux33CmdEntry 40443 }


    iqmux33Embed18Embed6Stereo6 OBJECT-TYPE
        SYNTAX            INTEGER { disable(0), enable(1)  }
        MAX-ACCESS        read-write
        STATUS            current
        DESCRIPTION
                "CMNT: - 
                 TYPE: - Checkbox
                 PAGE: - Embed1-8
                    Stereo6  cmdID= 40453  "
        ::= { iqmux33CmdEntry 40453 }


    iqmux33Embed18Embed6dolbyLine OBJECT-TYPE
        SYNTAX            RollCallString
        MAX-ACCESS        read-only
        STATUS            current
        DESCRIPTION
                "CMNT: - 
                 TYPE: - Display
                 PAGE: - Embed1-8
                    dolbyLine  cmdID= 40086  "
        ::= { iqmux33CmdEntry 40086 }


    iqmux33AudioOutputEmbed18Embed71procamp OBJECT-TYPE
        SYNTAX            INTEGER
        MAX-ACCESS        read-write
        STATUS            current
        DESCRIPTION
                "CMNT: - Embed Proc Amp Gain
                 TYPE: - Number
                 PAGE: - AudioOutput
                    Embed7_1_procamp  cmdID= 40412
                    min= -801  max= 120  step= 1  format= %0.1f dB  div_scale= 10  preset= 0
                    Min = -80.1 dB  Max = 12.0 dB  Step = 0.1 dB  Preset = 0.0 dB  "
        ::= { iqmux33CmdEntry 40412 }


    iqmux33AudioOutputEmbed18Embed72procamp OBJECT-TYPE
        SYNTAX            INTEGER
        MAX-ACCESS        read-write
        STATUS            current
        DESCRIPTION
                "CMNT: - Embed Proc Amp Gain
                 TYPE: - Number
                 PAGE: - AudioOutput
                    Embed7_2_procamp  cmdID= 40413
                    min= -801  max= 120  step= 1  format= %0.1f dB  div_scale= 10  preset= 0
                    Min = -80.1 dB  Max = 12.0 dB  Step = 0.1 dB  Preset = 0.0 dB  "
        ::= { iqmux33CmdEntry 40413 }


    iqmux33Embed18Embed7Mute71 OBJECT-TYPE
        SYNTAX            INTEGER { disable(0), enable(1)  }
        MAX-ACCESS        read-write
        STATUS            current
        DESCRIPTION
                "CMNT: - 
                 TYPE: - Checkbox
                 PAGE: - Embed1-8
                    Mute7_1  cmdID= 40444  "
        ::= { iqmux33CmdEntry 40444 }


    iqmux33Embed18Embed7Mute72 OBJECT-TYPE
        SYNTAX            INTEGER { disable(0), enable(1)  }
        MAX-ACCESS        read-write
        STATUS            current
        DESCRIPTION
                "CMNT: - 
                 TYPE: - Checkbox
                 PAGE: - Embed1-8
                    Mute7_2  cmdID= 40445  "
        ::= { iqmux33CmdEntry 40445 }


    iqmux33Embed18Embed7Stereo7 OBJECT-TYPE
        SYNTAX            INTEGER { disable(0), enable(1)  }
        MAX-ACCESS        read-write
        STATUS            current
        DESCRIPTION
                "CMNT: - 
                 TYPE: - Checkbox
                 PAGE: - Embed1-8
                    Stereo7  cmdID= 40454  "
        ::= { iqmux33CmdEntry 40454 }


    iqmux33Embed18Embed7dolbyLine OBJECT-TYPE
        SYNTAX            RollCallString
        MAX-ACCESS        read-only
        STATUS            current
        DESCRIPTION
                "CMNT: - 
                 TYPE: - Display
                 PAGE: - Embed1-8
                    dolbyLine  cmdID= 40087  "
        ::= { iqmux33CmdEntry 40087 }


    iqmux33AudioOutputEmbed18Embed81procamp OBJECT-TYPE
        SYNTAX            INTEGER
        MAX-ACCESS        read-write
        STATUS            current
        DESCRIPTION
                "CMNT: - Embed Proc Amp Gain
                 TYPE: - Number
                 PAGE: - AudioOutput
                    Embed8_1_procamp  cmdID= 40414
                    min= -801  max= 120  step= 1  format= %0.1f dB  div_scale= 10  preset= 0
                    Min = -80.1 dB  Max = 12.0 dB  Step = 0.1 dB  Preset = 0.0 dB  "
        ::= { iqmux33CmdEntry 40414 }


    iqmux33AudioOutputEmbed18Embed82procamp OBJECT-TYPE
        SYNTAX            INTEGER
        MAX-ACCESS        read-write
        STATUS            current
        DESCRIPTION
                "CMNT: - Embed Proc Amp Gain
                 TYPE: - Number
                 PAGE: - AudioOutput
                    Embed8_2_procamp  cmdID= 40415
                    min= -801  max= 120  step= 1  format= %0.1f dB  div_scale= 10  preset= 0
                    Min = -80.1 dB  Max = 12.0 dB  Step = 0.1 dB  Preset = 0.0 dB  "
        ::= { iqmux33CmdEntry 40415 }


    iqmux33Embed18Embed8Mute81 OBJECT-TYPE
        SYNTAX            INTEGER { disable(0), enable(1)  }
        MAX-ACCESS        read-write
        STATUS            current
        DESCRIPTION
                "CMNT: - 
                 TYPE: - Checkbox
                 PAGE: - Embed1-8
                    Mute8_1  cmdID= 40446  "
        ::= { iqmux33CmdEntry 40446 }


    iqmux33Embed18Embed8Mute82 OBJECT-TYPE
        SYNTAX            INTEGER { disable(0), enable(1)  }
        MAX-ACCESS        read-write
        STATUS            current
        DESCRIPTION
                "CMNT: - 
                 TYPE: - Checkbox
                 PAGE: - Embed1-8
                    Mute8_2  cmdID= 40447  "
        ::= { iqmux33CmdEntry 40447 }


    iqmux33Embed18Embed8Stereo8 OBJECT-TYPE
        SYNTAX            INTEGER { disable(0), enable(1)  }
        MAX-ACCESS        read-write
        STATUS            current
        DESCRIPTION
                "CMNT: - 
                 TYPE: - Checkbox
                 PAGE: - Embed1-8
                    Stereo8  cmdID= 40455  "
        ::= { iqmux33CmdEntry 40455 }


    iqmux33Embed18Embed8dolbyLine OBJECT-TYPE
        SYNTAX            RollCallString
        MAX-ACCESS        read-only
        STATUS            current
        DESCRIPTION
                "CMNT: - 
                 TYPE: - Display
                 PAGE: - Embed1-8
                    dolbyLine  cmdID= 40088  "
        ::= { iqmux33CmdEntry 40088 }


    iqmux33Embed18GroupEmbGroup1 OBJECT-TYPE
        SYNTAX            INTEGER { disable(0), enable(1)  }
        MAX-ACCESS        read-write
        STATUS            current
        DESCRIPTION
                "CMNT: - Audio group 1 enable
                 TYPE: - Checkbox
                 PAGE: - Embed1-8
                    EmbGroup1  cmdID= 36139  "
        ::= { iqmux33CmdEntry 36139 }


    iqmux33Embed18GroupEmbGroup2 OBJECT-TYPE
        SYNTAX            INTEGER { disable(0), enable(1)  }
        MAX-ACCESS        read-write
        STATUS            current
        DESCRIPTION
                "CMNT: - Audio group 2 enable
                 TYPE: - Checkbox
                 PAGE: - Embed1-8
                    EmbGroup2  cmdID= 36140  "
        ::= { iqmux33CmdEntry 36140 }


    iqmux33Embed18GroupEmbGroup3 OBJECT-TYPE
        SYNTAX            INTEGER { disable(0), enable(1)  }
        MAX-ACCESS        read-write
        STATUS            current
        DESCRIPTION
                "CMNT: - Audio group 3 enable
                 TYPE: - Checkbox
                 PAGE: - Embed1-8
                    EmbGroup3  cmdID= 36141  "
        ::= { iqmux33CmdEntry 36141 }


    iqmux33Embed18GroupEmbGroup4 OBJECT-TYPE
        SYNTAX            INTEGER { disable(0), enable(1)  }
        MAX-ACCESS        read-write
        STATUS            current
        DESCRIPTION
                "CMNT: - Audio group 4 enable
                 TYPE: - Checkbox
                 PAGE: - Embed1-8
                    EmbGroup4  cmdID= 36142  "
        ::= { iqmux33CmdEntry 36142 }


    iqmux33AudSetupDelaySelectTotalDelayBus1 OBJECT-TYPE
        SYNTAX            RollCallString
        MAX-ACCESS        read-only
        STATUS            current
        DESCRIPTION
                "CMNT: - Set Manual delay
                 TYPE: - Display
                 PAGE: - AudSetup
                    TotalDelayBus1  cmdID= 40656  "
        ::= { iqmux33CmdEntry 40656 }


    iqmux33AudSetupDelaySelectTotalDelayBus2 OBJECT-TYPE
        SYNTAX            RollCallString
        MAX-ACCESS        read-only
        STATUS            current
        DESCRIPTION
                "CMNT: - Set Manual delay
                 TYPE: - Display
                 PAGE: - AudSetup
                    TotalDelayBus2  cmdID= 40657  "
        ::= { iqmux33CmdEntry 40657 }


    iqmux33AudSetupDelaySelectTotalDelayBus3 OBJECT-TYPE
        SYNTAX            RollCallString
        MAX-ACCESS        read-only
        STATUS            current
        DESCRIPTION
                "CMNT: - Set Manual delay
                 TYPE: - Display
                 PAGE: - AudSetup
                    TotalDelayBus3  cmdID= 40658  "
        ::= { iqmux33CmdEntry 40658 }


    iqmux33AudSetupDelaySelectTotalDelayBus4 OBJECT-TYPE
        SYNTAX            RollCallString
        MAX-ACCESS        read-only
        STATUS            current
        DESCRIPTION
                "CMNT: - Set Manual delay
                 TYPE: - Display
                 PAGE: - AudSetup
                    TotalDelayBus4  cmdID= 40659  "
        ::= { iqmux33CmdEntry 40659 }


    iqmux33AudSetupDelaySelectTotalDelayBus5 OBJECT-TYPE
        SYNTAX            RollCallString
        MAX-ACCESS        read-only
        STATUS            current
        DESCRIPTION
                "CMNT: - Set Manual delay
                 TYPE: - Display
                 PAGE: - AudSetup
                    TotalDelayBus5  cmdID= 40660  "
        ::= { iqmux33CmdEntry 40660 }


    iqmux33AudSetupDelaySelectTotalDelayBus6 OBJECT-TYPE
        SYNTAX            RollCallString
        MAX-ACCESS        read-only
        STATUS            current
        DESCRIPTION
                "CMNT: - Set Manual delay
                 TYPE: - Display
                 PAGE: - AudSetup
                    TotalDelayBus6  cmdID= 40661  "
        ::= { iqmux33CmdEntry 40661 }


    iqmux33AudSetupDelaySelectTotalDelayBus7 OBJECT-TYPE
        SYNTAX            RollCallString
        MAX-ACCESS        read-only
        STATUS            current
        DESCRIPTION
                "CMNT: - Set Manual delay
                 TYPE: - Display
                 PAGE: - AudSetup
                    TotalDelayBus7  cmdID= 40662  "
        ::= { iqmux33CmdEntry 40662 }


    iqmux33AudSetupDelaySelectTotalDelayBus8 OBJECT-TYPE
        SYNTAX            RollCallString
        MAX-ACCESS        read-only
        STATUS            current
        DESCRIPTION
                "CMNT: - Set Manual delay
                 TYPE: - Display
                 PAGE: - AudSetup
                    TotalDelayBus8  cmdID= 40663  "
        ::= { iqmux33CmdEntry 40663 }


    iqmux33AudSetupDelaySelectBus1Delay OBJECT-TYPE
        SYNTAX            INTEGER
        MAX-ACCESS        read-write
        STATUS            current
        DESCRIPTION
                "CMNT: - Set Manual delay
                 TYPE: - Number
                 PAGE: - AudSetup
                    Bus 1 Delay  cmdID= 40648
                    min= -1995  max= 1995  step= 1  format= %d  div_scale= 1  preset= 0
                    Min = 0  Max = 0  Step = 0  Preset = 0  "
        ::= { iqmux33CmdEntry 40648 }


    iqmux33AudSetupDelaySelectBus2Delay OBJECT-TYPE
        SYNTAX            INTEGER
        MAX-ACCESS        read-write
        STATUS            current
        DESCRIPTION
                "CMNT: - Set Manual delay
                 TYPE: - Number
                 PAGE: - AudSetup
                    Bus 2 Delay  cmdID= 40649
                    min= -1995  max= 1995  step= 1  format= %d  div_scale= 1  preset= 0
                    Min = 0  Max = 0  Step = 0  Preset = 0  "
        ::= { iqmux33CmdEntry 40649 }


    iqmux33AudSetupDelaySelectBus3Delay OBJECT-TYPE
        SYNTAX            INTEGER
        MAX-ACCESS        read-write
        STATUS            current
        DESCRIPTION
                "CMNT: - Set Manual delay
                 TYPE: - Number
                 PAGE: - AudSetup
                    Bus 3 Delay  cmdID= 40650
                    min= -1995  max= 1995  step= 1  format= %d  div_scale= 1  preset= 0
                    Min = 0  Max = 0  Step = 0  Preset = 0  "
        ::= { iqmux33CmdEntry 40650 }


    iqmux33AudSetupDelaySelectBus4Delay OBJECT-TYPE
        SYNTAX            INTEGER
        MAX-ACCESS        read-write
        STATUS            current
        DESCRIPTION
                "CMNT: - Set Manual delay
                 TYPE: - Number
                 PAGE: - AudSetup
                    Bus 4 Delay  cmdID= 40651
                    min= -1995  max= 1995  step= 1  format= %d  div_scale= 1  preset= 0
                    Min = 0  Max = 0  Step = 0  Preset = 0  "
        ::= { iqmux33CmdEntry 40651 }


    iqmux33AudSetupDelaySelectBus5Delay OBJECT-TYPE
        SYNTAX            INTEGER
        MAX-ACCESS        read-write
        STATUS            current
        DESCRIPTION
                "CMNT: - Set Manual delay
                 TYPE: - Number
                 PAGE: - AudSetup
                    Bus 5 Delay  cmdID= 40652
                    min= -1995  max= 1995  step= 1  format= %d  div_scale= 1  preset= 0
                    Min = 0  Max = 0  Step = 0  Preset = 0  "
        ::= { iqmux33CmdEntry 40652 }


    iqmux33AudSetupDelaySelectBus6Delay OBJECT-TYPE
        SYNTAX            INTEGER
        MAX-ACCESS        read-write
        STATUS            current
        DESCRIPTION
                "CMNT: - Set Manual delay
                 TYPE: - Number
                 PAGE: - AudSetup
                    Bus 6 Delay  cmdID= 40653
                    min= -1995  max= 1995  step= 1  format= %d  div_scale= 1  preset= 0
                    Min = 0  Max = 0  Step = 0  Preset = 0  "
        ::= { iqmux33CmdEntry 40653 }


    iqmux33AudSetupDelaySelectBus7Delay OBJECT-TYPE
        SYNTAX            INTEGER
        MAX-ACCESS        read-write
        STATUS            current
        DESCRIPTION
                "CMNT: - Set Manual delay
                 TYPE: - Number
                 PAGE: - AudSetup
                    Bus 7 Delay  cmdID= 40654
                    min= -1995  max= 1995  step= 1  format= %d  div_scale= 1  preset= 0
                    Min = 0  Max = 0  Step = 0  Preset = 0  "
        ::= { iqmux33CmdEntry 40654 }


    iqmux33AudSetupDelaySelectBus8Delay OBJECT-TYPE
        SYNTAX            INTEGER
        MAX-ACCESS        read-write
        STATUS            current
        DESCRIPTION
                "CMNT: - Set Manual delay
                 TYPE: - Number
                 PAGE: - AudSetup
                    Bus 8 Delay  cmdID= 40655
                    min= -1995  max= 1995  step= 1  format= %d  div_scale= 1  preset= 0
                    Min = 0  Max = 0  Step = 0  Preset = 0  "
        ::= { iqmux33CmdEntry 40655 }


    iqmux33AudSetupDelaySelectBus1Fine OBJECT-TYPE
        SYNTAX            INTEGER
        MAX-ACCESS        read-write
        STATUS            current
        DESCRIPTION
                "CMNT: - Set Manual delay
                 TYPE: - Number
                 PAGE: - AudSetup
                    Bus 1 Fine  cmdID= 36165
                    min= -240  max= 240  step= 1  format= %d  div_scale= 1  preset= 0
                    Min = 0  Max = 0  Step = 0  Preset = 0  "
        ::= { iqmux33CmdEntry 36165 }


    iqmux33AudSetupDelaySelectBus2Fine OBJECT-TYPE
        SYNTAX            INTEGER
        MAX-ACCESS        read-write
        STATUS            current
        DESCRIPTION
                "CMNT: - Set Manual delay
                 TYPE: - Number
                 PAGE: - AudSetup
                    Bus 2 Fine  cmdID= 36166
                    min= -240  max= 240  step= 1  format= %d  div_scale= 1  preset= 0
                    Min = 0  Max = 0  Step = 0  Preset = 0  "
        ::= { iqmux33CmdEntry 36166 }


    iqmux33AudSetupDelaySelectBus3Fine OBJECT-TYPE
        SYNTAX            INTEGER
        MAX-ACCESS        read-write
        STATUS            current
        DESCRIPTION
                "CMNT: - Set Manual delay
                 TYPE: - Number
                 PAGE: - AudSetup
                    Bus 3 Fine  cmdID= 36167
                    min= -240  max= 240  step= 1  format= %d  div_scale= 1  preset= 0
                    Min = 0  Max = 0  Step = 0  Preset = 0  "
        ::= { iqmux33CmdEntry 36167 }


    iqmux33AudSetupDelaySelectBus4Fine OBJECT-TYPE
        SYNTAX            INTEGER
        MAX-ACCESS        read-write
        STATUS            current
        DESCRIPTION
                "CMNT: - Set Manual delay
                 TYPE: - Number
                 PAGE: - AudSetup
                    Bus 4 Fine  cmdID= 36168
                    min= -240  max= 240  step= 1  format= %d  div_scale= 1  preset= 0
                    Min = 0  Max = 0  Step = 0  Preset = 0  "
        ::= { iqmux33CmdEntry 36168 }


    iqmux33AudSetupDelaySelectBus5Fine OBJECT-TYPE
        SYNTAX            INTEGER
        MAX-ACCESS        read-write
        STATUS            current
        DESCRIPTION
                "CMNT: - Set Manual delay
                 TYPE: - Number
                 PAGE: - AudSetup
                    Bus 5 Fine  cmdID= 36169
                    min= -240  max= 240  step= 1  format= %d  div_scale= 1  preset= 0
                    Min = 0  Max = 0  Step = 0  Preset = 0  "
        ::= { iqmux33CmdEntry 36169 }


    iqmux33AudSetupDelaySelectBus6Fine OBJECT-TYPE
        SYNTAX            INTEGER
        MAX-ACCESS        read-write
        STATUS            current
        DESCRIPTION
                "CMNT: - Set Manual delay
                 TYPE: - Number
                 PAGE: - AudSetup
                    Bus 6 Fine  cmdID= 36170
                    min= -240  max= 240  step= 1  format= %d  div_scale= 1  preset= 0
                    Min = 0  Max = 0  Step = 0  Preset = 0  "
        ::= { iqmux33CmdEntry 36170 }


    iqmux33AudSetupDelaySelectBus7Fine OBJECT-TYPE
        SYNTAX            INTEGER
        MAX-ACCESS        read-write
        STATUS            current
        DESCRIPTION
                "CMNT: - Set Manual delay
                 TYPE: - Number
                 PAGE: - AudSetup
                    Bus 7 Fine  cmdID= 36171
                    min= -240  max= 240  step= 1  format= %d  div_scale= 1  preset= 0
                    Min = 0  Max = 0  Step = 0  Preset = 0  "
        ::= { iqmux33CmdEntry 36171 }


    iqmux33AudSetupDelaySelectBus8Fine OBJECT-TYPE
        SYNTAX            INTEGER
        MAX-ACCESS        read-write
        STATUS            current
        DESCRIPTION
                "CMNT: - Set Manual delay
                 TYPE: - Number
                 PAGE: - AudSetup
                    Bus 8 Fine  cmdID= 36172
                    min= -240  max= 240  step= 1  format= %d  div_scale= 1  preset= 0
                    Min = 0  Max = 0  Step = 0  Preset = 0  "
        ::= { iqmux33CmdEntry 36172 }


    iqmux33AudSetupDelaySelectBusBulkDelay OBJECT-TYPE
        SYNTAX            INTEGER
        MAX-ACCESS        read-write
        STATUS            current
        DESCRIPTION
                "CMNT: - Set Bulk delay
                 TYPE: - Number
                 PAGE: - AudSetup
                    Bus Bulk Delay  cmdID= 40647
                    min= -3210  max= 12000  step= 1  format= %d  div_scale= 1  preset= 0
                    Min = 0  Max = 0  Step = 0  Preset = 0  "
        ::= { iqmux33CmdEntry 40647 }


    iqmux33AudSetupDelaySelectThreshold OBJECT-TYPE
        SYNTAX            INTEGER
        MAX-ACCESS        read-write
        STATUS            current
        DESCRIPTION
                "CMNT: - Set DELAY Threshold
                 TYPE: - Number
                 PAGE: - AudSetup
                    Threshold  cmdID= 40646
                    min= 240  max= 3840  step= 1  format= %d  div_scale= 1  preset= 3840
                    Min = 0  Max = 0  Step = 0  Preset = 0  "
        ::= { iqmux33CmdEntry 40646 }


    iqmux33AudSetupDelaySelectRtrack14 OBJECT-TYPE
        SYNTAX            INTEGER { disable(0), enable(1)  }
        MAX-ACCESS        read-write
        STATUS            current
        DESCRIPTION
                "CMNT: - Use rolltrack14 data for delay
                 TYPE: - Checkbox
                 PAGE: - AudSetup
                    Rtrack14  cmdID= 40600  "
        ::= { iqmux33CmdEntry 40600 }


    iqmux33AudSetupDelaySelectRtrack15 OBJECT-TYPE
        SYNTAX            INTEGER { disable(0), enable(1)  }
        MAX-ACCESS        read-write
        STATUS            current
        DESCRIPTION
                "CMNT: - Use rolltrack15 data for delay
                 TYPE: - Checkbox
                 PAGE: - AudSetup
                    Rtrack15  cmdID= 40608  "
        ::= { iqmux33CmdEntry 40608 }


    iqmux33AudSetupDelaySelectRtrack16 OBJECT-TYPE
        SYNTAX            INTEGER { disable(0), enable(1)  }
        MAX-ACCESS        read-write
        STATUS            current
        DESCRIPTION
                "CMNT: - Use rolltrack16 data for delay
                 TYPE: - Checkbox
                 PAGE: - AudSetup
                    Rtrack16  cmdID= 40616  "
        ::= { iqmux33CmdEntry 40616 }


    iqmux33AudSetupDelaySelectRtrack17 OBJECT-TYPE
        SYNTAX            INTEGER { disable(0), enable(1)  }
        MAX-ACCESS        read-write
        STATUS            current
        DESCRIPTION
                "CMNT: - Use rolltrack17 data for delay
                 TYPE: - Checkbox
                 PAGE: - AudSetup
                    Rtrack17  cmdID= 40624  "
        ::= { iqmux33CmdEntry 40624 }


    iqmux33AudSetupDelaySelectEnableBulk OBJECT-TYPE
        SYNTAX            INTEGER { disable(0), enable(1)  }
        MAX-ACCESS        read-write
        STATUS            current
        DESCRIPTION
                "CMNT: - Use BULK data for delay
                 TYPE: - Checkbox
                 PAGE: - AudSetup
                    EnableBulk  cmdID= 40625  "
        ::= { iqmux33CmdEntry 40625 }


    iqmux33AudSetupDelaySelectEnableVideo OBJECT-TYPE
        SYNTAX            INTEGER { disable(0), enable(1)  }
        MAX-ACCESS        read-write
        STATUS            current
        DESCRIPTION
                "CMNT: - Use BULK data for delay
                 TYPE: - Checkbox
                 PAGE: - AudSetup
                    EnableVideo  cmdID= 40632  "
        ::= { iqmux33CmdEntry 40632 }


    iqmux33AudioAudSetupRollTrack14 OBJECT-TYPE
        SYNTAX            RollCallString
        MAX-ACCESS        read-only
        STATUS            current
        DESCRIPTION
                "CMNT: - Rolltrack input command for delays
                 TYPE: - Display
                 PAGE: - Audio
                    RollTrack14  cmdID= 14  "
        ::= { iqmux33CmdEntry 14 }


    iqmux33AudioAudSetupRollTrack15 OBJECT-TYPE
        SYNTAX            RollCallString
        MAX-ACCESS        read-only
        STATUS            current
        DESCRIPTION
                "CMNT: - Rolltrack input command for delays
                 TYPE: - Display
                 PAGE: - Audio
                    RollTrack15  cmdID= 15  "
        ::= { iqmux33CmdEntry 15 }


    iqmux33AudioAudSetupRollTrack16 OBJECT-TYPE
        SYNTAX            RollCallString
        MAX-ACCESS        read-only
        STATUS            current
        DESCRIPTION
                "CMNT: - Rolltrack input command for delays
                 TYPE: - Display
                 PAGE: - Audio
                    RollTrack16  cmdID= 16  "
        ::= { iqmux33CmdEntry 16 }


    iqmux33AudioAudSetupRollTrack17 OBJECT-TYPE
        SYNTAX            RollCallString
        MAX-ACCESS        read-only
        STATUS            current
        DESCRIPTION
                "CMNT: - Rolltrack input command for delays
                 TYPE: - Display
                 PAGE: - Audio
                    RollTrack17  cmdID= 17  "
        ::= { iqmux33CmdEntry 17 }


    iqmux33AudioAudSetupCurrentVidDelay OBJECT-TYPE
        SYNTAX            RollCallString
        MAX-ACCESS        read-only
        STATUS            current
        DESCRIPTION
                "CMNT: - Internal Video Delay for Synchroniser modules
                 TYPE: - Display
                 PAGE: - Audio
                    CurrentVidDelay  cmdID= 33030  "
        ::= { iqmux33CmdEntry 33030 }


    iqmux33AudioAudSetupMinVidAudDelay OBJECT-TYPE
        SYNTAX            RollCallString
        MAX-ACCESS        read-only
        STATUS            current
        DESCRIPTION
                "CMNT: - Internal Video Delay for Synchroniser modules
                 TYPE: - Display
                 PAGE: - Audio
                    MinVidAudDelay  cmdID= 33043  "
        ::= { iqmux33CmdEntry 33043 }


    iqmux33AudioAudSetupCurrRTrack14Delay OBJECT-TYPE
        SYNTAX            RollCallString
        MAX-ACCESS        read-only
        STATUS            current
        DESCRIPTION
                "CMNT: - Current Delay for Rolltrack 14
                 TYPE: - Display
                 PAGE: - Audio
                    CurrRTrack14Delay  cmdID= 40665  "
        ::= { iqmux33CmdEntry 40665 }


    iqmux33AudioAudSetupCurrRlTrack15Delay OBJECT-TYPE
        SYNTAX            RollCallString
        MAX-ACCESS        read-only
        STATUS            current
        DESCRIPTION
                "CMNT: - Current Delay for Rolltrack 15
                 TYPE: - Display
                 PAGE: - Audio
                    CurrRlTrack15Delay  cmdID= 40666  "
        ::= { iqmux33CmdEntry 40666 }


    iqmux33AudioAudSetupCurrRTrack16Delay OBJECT-TYPE
        SYNTAX            RollCallString
        MAX-ACCESS        read-only
        STATUS            current
        DESCRIPTION
                "CMNT: - Current Delay for Rolltrack 16
                 TYPE: - Display
                 PAGE: - Audio
                    CurrRTrack16Delay  cmdID= 40667  "
        ::= { iqmux33CmdEntry 40667 }


    iqmux33AudioAudSetupCurrRTrack17Delay OBJECT-TYPE
        SYNTAX            RollCallString
        MAX-ACCESS        read-only
        STATUS            current
        DESCRIPTION
                "CMNT: - Current Delay for Rolltrack 17
                 TYPE: - Display
                 PAGE: - Audio
                    CurrRTrack17Delay  cmdID= 40668  "
        ::= { iqmux33CmdEntry 40668 }


    iqmux33AudSetupTonesFreq0 OBJECT-TYPE
        SYNTAX            INTEGER
        MAX-ACCESS        read-write
        STATUS            current
        DESCRIPTION
                "CMNT: - 
                 TYPE: - Number
                 PAGE: - AudSetup
                    Freq0  cmdID= 42600
                    min= 1  max= 160  step= 1  format= %d  div_scale= 1  preset= 4
                    Min = 0  Max = 0  Step = 0  Preset = 0  "
        ::= { iqmux33CmdEntry 42600 }


    iqmux33AudSetupTonesFreq1 OBJECT-TYPE
        SYNTAX            INTEGER
        MAX-ACCESS        read-write
        STATUS            current
        DESCRIPTION
                "CMNT: - 
                 TYPE: - Number
                 PAGE: - AudSetup
                    Freq1  cmdID= 42601
                    min= 1  max= 160  step= 1  format= %d  div_scale= 1  preset= 8
                    Min = 0  Max = 0  Step = 0  Preset = 0  "
        ::= { iqmux33CmdEntry 42601 }


    iqmux33AudSetupTonesFreq2 OBJECT-TYPE
        SYNTAX            INTEGER
        MAX-ACCESS        read-write
        STATUS            current
        DESCRIPTION
                "CMNT: - 
                 TYPE: - Number
                 PAGE: - AudSetup
                    Freq2  cmdID= 42602
                    min= 1  max= 160  step= 1  format= %d  div_scale= 1  preset= 16
                    Min = 0  Max = 0  Step = 0  Preset = 0  "
        ::= { iqmux33CmdEntry 42602 }


    iqmux33AudSetupTonesFreq3 OBJECT-TYPE
        SYNTAX            INTEGER
        MAX-ACCESS        read-write
        STATUS            current
        DESCRIPTION
                "CMNT: - 
                 TYPE: - Number
                 PAGE: - AudSetup
                    Freq3  cmdID= 42603
                    min= 1  max= 160  step= 1  format= %d  div_scale= 1  preset= 32
                    Min = 0  Max = 0  Step = 0  Preset = 0  "
        ::= { iqmux33CmdEntry 42603 }


    iqmux33AudSetupTonesFreq4 OBJECT-TYPE
        SYNTAX            INTEGER
        MAX-ACCESS        read-write
        STATUS            current
        DESCRIPTION
                "CMNT: - 
                 TYPE: - Number
                 PAGE: - AudSetup
                    Freq4  cmdID= 42604
                    min= 1  max= 160  step= 1  format= %d  div_scale= 1  preset= 6
                    Min = 0  Max = 0  Step = 0  Preset = 0  "
        ::= { iqmux33CmdEntry 42604 }


    iqmux33AudSetupTonesFreq5 OBJECT-TYPE
        SYNTAX            INTEGER
        MAX-ACCESS        read-write
        STATUS            current
        DESCRIPTION
                "CMNT: - 
                 TYPE: - Number
                 PAGE: - AudSetup
                    Freq5  cmdID= 42605
                    min= 1  max= 160  step= 1  format= %d  div_scale= 1  preset= 12
                    Min = 0  Max = 0  Step = 0  Preset = 0  "
        ::= { iqmux33CmdEntry 42605 }


    iqmux33AudSetupTonesFreq6 OBJECT-TYPE
        SYNTAX            INTEGER
        MAX-ACCESS        read-write
        STATUS            current
        DESCRIPTION
                "CMNT: - 
                 TYPE: - Number
                 PAGE: - AudSetup
                    Freq6  cmdID= 42606
                    min= 1  max= 160  step= 1  format= %d  div_scale= 1  preset= 24
                    Min = 0  Max = 0  Step = 0  Preset = 0  "
        ::= { iqmux33CmdEntry 42606 }


    iqmux33AudSetupTonesFreq7 OBJECT-TYPE
        SYNTAX            INTEGER
        MAX-ACCESS        read-write
        STATUS            current
        DESCRIPTION
                "CMNT: - 
                 TYPE: - Number
                 PAGE: - AudSetup
                    Freq7  cmdID= 42607
                    min= 1  max= 160  step= 1  format= %d  div_scale= 1  preset= 48
                    Min = 0  Max = 0  Step = 0  Preset = 0  "
        ::= { iqmux33CmdEntry 42607 }


    iqmux33AudSetupTonesIdent0 OBJECT-TYPE
        SYNTAX            INTEGER { disable(0), enable(1)  }
        MAX-ACCESS        read-write
        STATUS            current
        DESCRIPTION
                "CMNT: - 
                 TYPE: - Checkbox
                 PAGE: - AudSetup
                    Ident0  cmdID= 42610  "
        ::= { iqmux33CmdEntry 42610 }


    iqmux33AudSetupTonesIdent1 OBJECT-TYPE
        SYNTAX            INTEGER { disable(0), enable(1)  }
        MAX-ACCESS        read-write
        STATUS            current
        DESCRIPTION
                "CMNT: - 
                 TYPE: - Checkbox
                 PAGE: - AudSetup
                    Ident1  cmdID= 42611  "
        ::= { iqmux33CmdEntry 42611 }


    iqmux33AudSetupTonesIdent2 OBJECT-TYPE
        SYNTAX            INTEGER { disable(0), enable(1)  }
        MAX-ACCESS        read-write
        STATUS            current
        DESCRIPTION
                "CMNT: - 
                 TYPE: - Checkbox
                 PAGE: - AudSetup
                    Ident2  cmdID= 42612  "
        ::= { iqmux33CmdEntry 42612 }


    iqmux33AudSetupTonesIdent3 OBJECT-TYPE
        SYNTAX            INTEGER { disable(0), enable(1)  }
        MAX-ACCESS        read-write
        STATUS            current
        DESCRIPTION
                "CMNT: - 
                 TYPE: - Checkbox
                 PAGE: - AudSetup
                    Ident3  cmdID= 42613  "
        ::= { iqmux33CmdEntry 42613 }


    iqmux33AudSetupTonesIdent4 OBJECT-TYPE
        SYNTAX            INTEGER { disable(0), enable(1)  }
        MAX-ACCESS        read-write
        STATUS            current
        DESCRIPTION
                "CMNT: - 
                 TYPE: - Checkbox
                 PAGE: - AudSetup
                    Ident4  cmdID= 42614  "
        ::= { iqmux33CmdEntry 42614 }


    iqmux33AudSetupTonesIdent5 OBJECT-TYPE
        SYNTAX            INTEGER { disable(0), enable(1)  }
        MAX-ACCESS        read-write
        STATUS            current
        DESCRIPTION
                "CMNT: - 
                 TYPE: - Checkbox
                 PAGE: - AudSetup
                    Ident5  cmdID= 42615  "
        ::= { iqmux33CmdEntry 42615 }


    iqmux33AudSetupTonesIdent6 OBJECT-TYPE
        SYNTAX            INTEGER { disable(0), enable(1)  }
        MAX-ACCESS        read-write
        STATUS            current
        DESCRIPTION
                "CMNT: - 
                 TYPE: - Checkbox
                 PAGE: - AudSetup
                    Ident6  cmdID= 42616  "
        ::= { iqmux33CmdEntry 42616 }


    iqmux33AudSetupTonesIdent7 OBJECT-TYPE
        SYNTAX            INTEGER { disable(0), enable(1)  }
        MAX-ACCESS        read-write
        STATUS            current
        DESCRIPTION
                "CMNT: - 
                 TYPE: - Checkbox
                 PAGE: - AudSetup
                    Ident7  cmdID= 42617  "
        ::= { iqmux33CmdEntry 42617 }


    iqmux33AudioAudSetupNeg1Frame OBJECT-TYPE
        SYNTAX            INTEGER { noAction(0),valNeg1Frame(1) }
        MAX-ACCESS        read-write
        STATUS            current
        DESCRIPTION
                "CMNT: - 
                 TYPE: - Button
                 PAGE: - Audio
                    Neg1Frame  cmdID= 40626
                    value= 1  "
        ::= { iqmux33CmdEntry 40626 }


    iqmux33AudioAudSetupNeg1ms OBJECT-TYPE
        SYNTAX            INTEGER { noAction(0),valNeg1ms(1) }
        MAX-ACCESS        read-write
        STATUS            current
        DESCRIPTION
                "CMNT: - 
                 TYPE: - Button
                 PAGE: - Audio
                    Neg1ms  cmdID= 40627
                    value= 1  "
        ::= { iqmux33CmdEntry 40627 }


    iqmux33AudioAudSetupNeg4samp OBJECT-TYPE
        SYNTAX            INTEGER { noAction(0),valNeg4samp(1) }
        MAX-ACCESS        read-write
        STATUS            current
        DESCRIPTION
                "CMNT: - 
                 TYPE: - Button
                 PAGE: - Audio
                    Neg4samp  cmdID= 40628
                    value= 1  "
        ::= { iqmux33CmdEntry 40628 }


    iqmux33AudioAudSetupPos4samp OBJECT-TYPE
        SYNTAX            INTEGER { noAction(0),valPos4samp(1) }
        MAX-ACCESS        read-write
        STATUS            current
        DESCRIPTION
                "CMNT: - 
                 TYPE: - Button
                 PAGE: - Audio
                    Pos4samp  cmdID= 40629
                    value= 1  "
        ::= { iqmux33CmdEntry 40629 }


    iqmux33AudioAudSetupPos1ms OBJECT-TYPE
        SYNTAX            INTEGER { noAction(0),valPos1ms(1) }
        MAX-ACCESS        read-write
        STATUS            current
        DESCRIPTION
                "CMNT: - 
                 TYPE: - Button
                 PAGE: - Audio
                    Pos1ms  cmdID= 40630
                    value= 1  "
        ::= { iqmux33CmdEntry 40630 }


    iqmux33AudioAudSetupPos1Frame OBJECT-TYPE
        SYNTAX            INTEGER { noAction(0),valPos1Frame(1) }
        MAX-ACCESS        read-write
        STATUS            current
        DESCRIPTION
                "CMNT: - 
                 TYPE: - Button
                 PAGE: - Audio
                    Pos1Frame  cmdID= 40631
                    value= 1  "
        ::= { iqmux33CmdEntry 40631 }


    iqmux33AudioAudSetupSilentLevel OBJECT-TYPE
        SYNTAX            INTEGER
        MAX-ACCESS        read-write
        STATUS            current
        DESCRIPTION
                "CMNT: - Set Audio Silent level
                 TYPE: - Number
                 PAGE: - Audio
                    SilentLevel  cmdID= 3061
                    min= -100  max= -2  step= 1  format= %0.0f dBFS  div_scale= 1  preset= -70
                    Min = -100 dBFS  Max = -2 dBFS  Step = 1 dBFS  Preset = -70 dBFS  "
        ::= { iqmux33CmdEntry 3061 }


    iqmux33AudioAudSetupOverloadLevel OBJECT-TYPE
        SYNTAX            INTEGER
        MAX-ACCESS        read-write
        STATUS            current
        DESCRIPTION
                "CMNT: - Set Audio Overload level
                 TYPE: - Number
                 PAGE: - Audio
                    OverloadLevel  cmdID= 3064
                    min= -99  max= -1  step= 1  format= %0.0f dBFS  div_scale= 1  preset= -1
                    Min = -99 dBFS  Max = -1 dBFS  Step = 1 dBFS  Preset = -1 dBFS  "
        ::= { iqmux33CmdEntry 3064 }


    iqmux33AudioAudSetupLevelTimeout OBJECT-TYPE
        SYNTAX            INTEGER
        MAX-ACCESS        read-write
        STATUS            current
        DESCRIPTION
                "CMNT: - Set Audio level timeout
                 TYPE: - Number
                 PAGE: - Audio
                    LevelTimeout  cmdID= 3065
                    min= 1  max= 20  step= 1  format= %d  div_scale= 1  preset= 10
                    Min = 0  Max = 0  Step = 0  Preset = 0  "
        ::= { iqmux33CmdEntry 3065 }


    iqmux33AudioAudSetupLevelUpdateEnb OBJECT-TYPE
        SYNTAX            INTEGER { disable(0), enable(1)  }
        MAX-ACCESS        read-write
        STATUS            current
        DESCRIPTION
                "CMNT: - Enable Audio level updates to rollmap
                 TYPE: - Checkbox
                 PAGE: - Audio
                    LevelUpdateEnb  cmdID= 38275  "
        ::= { iqmux33CmdEntry 38275 }


    iqmux33AudioAudSetupAudLevel OBJECT-TYPE
        SYNTAX            RollCallString
        MAX-ACCESS        read-only
        STATUS            current
        DESCRIPTION
                "CMNT: - Audio level updates to rollmap
                 TYPE: - Display
                 PAGE: - Audio
                    AudLevel  cmdID= 38276  "
        ::= { iqmux33CmdEntry 38276 }


    iqmux33AudioAudSetupHeadroomIn OBJECT-TYPE
        SYNTAX            INTEGER
        MAX-ACCESS        read-write
        STATUS            current
        DESCRIPTION
                "CMNT: - Set Audio level Headroom
                 TYPE: - Number
                 PAGE: - Audio
                    HeadroomIn  cmdID= 3066
                    min= 4  max= 24  step= 1  format= %0.0fdB  div_scale= 1  preset= 18
                    Min = 4dB  Max = 24dB  Step = 1dB  Preset = 18dB  "
        ::= { iqmux33CmdEntry 3066 }


    iqmux33AudioAudSetupLineupIn OBJECT-TYPE
        SYNTAX            INTEGER
        MAX-ACCESS        read-write
        STATUS            current
        DESCRIPTION
                "CMNT: - Set Audio level Lineup
                 TYPE: - Number
                 PAGE: - Audio
                    LineupIn  cmdID= 3067
                    min= -20  max= 20  step= 1  format= %0.0fdBu  div_scale= 1  preset= 0
                    Min = -20dBu  Max = 20dBu  Step = 1dBu  Preset = 0dBu  "
        ::= { iqmux33CmdEntry 3067 }


    iqmux33AudioRoutingInputRouteDest1 OBJECT-TYPE
        SYNTAX            INTEGER
        MAX-ACCESS        read-write
        STATUS            current
        DESCRIPTION
                "CMNT: - 
                 TYPE: - Number
                 PAGE: - Audio
                    Input Route Dest 1  cmdID= 40223
                    min= 0  max= 22  step= 1  format= 0  div_scale= 1  preset= 0
                    Min = 0  Max = 0  Step = 0  Preset = 0  "
        ::= { iqmux33CmdEntry 40223 }


    iqmux33AudioRoutingInputRouteDest2 OBJECT-TYPE
        SYNTAX            INTEGER
        MAX-ACCESS        read-write
        STATUS            current
        DESCRIPTION
                "CMNT: - 
                 TYPE: - Number
                 PAGE: - Audio
                    Input Route Dest 2  cmdID= 40224
                    min= 0  max= 22  step= 1  format= 0  div_scale= 1  preset= 1
                    Min = 0  Max = 0  Step = 0  Preset = 0  "
        ::= { iqmux33CmdEntry 40224 }


    iqmux33AudioRoutingInputRouteDest3 OBJECT-TYPE
        SYNTAX            INTEGER
        MAX-ACCESS        read-write
        STATUS            current
        DESCRIPTION
                "CMNT: - 
                 TYPE: - Number
                 PAGE: - Audio
                    Input Route Dest 3  cmdID= 40225
                    min= 0  max= 22  step= 1  format= 0  div_scale= 1  preset= 2
                    Min = 0  Max = 0  Step = 0  Preset = 0  "
        ::= { iqmux33CmdEntry 40225 }


    iqmux33AudioRoutingInputRouteDest4 OBJECT-TYPE
        SYNTAX            INTEGER
        MAX-ACCESS        read-write
        STATUS            current
        DESCRIPTION
                "CMNT: - 
                 TYPE: - Number
                 PAGE: - Audio
                    Input Route Dest 4  cmdID= 40226
                    min= 0  max= 22  step= 1  format= 0  div_scale= 1  preset= 3
                    Min = 0  Max = 0  Step = 0  Preset = 0  "
        ::= { iqmux33CmdEntry 40226 }


    iqmux33AudioRoutingInputRouteDest5 OBJECT-TYPE
        SYNTAX            INTEGER
        MAX-ACCESS        read-write
        STATUS            current
        DESCRIPTION
                "CMNT: - 
                 TYPE: - Number
                 PAGE: - Audio
                    Input Route Dest 5  cmdID= 40227
                    min= 0  max= 22  step= 1  format= 0  div_scale= 1  preset= 4
                    Min = 0  Max = 0  Step = 0  Preset = 0  "
        ::= { iqmux33CmdEntry 40227 }


    iqmux33AudioRoutingInputRouteDest6 OBJECT-TYPE
        SYNTAX            INTEGER
        MAX-ACCESS        read-write
        STATUS            current
        DESCRIPTION
                "CMNT: - 
                 TYPE: - Number
                 PAGE: - Audio
                    Input Route Dest 6  cmdID= 40228
                    min= 0  max= 22  step= 1  format= 0  div_scale= 1  preset= 5
                    Min = 0  Max = 0  Step = 0  Preset = 0  "
        ::= { iqmux33CmdEntry 40228 }


    iqmux33AudioRoutingInputRouteDest7 OBJECT-TYPE
        SYNTAX            INTEGER
        MAX-ACCESS        read-write
        STATUS            current
        DESCRIPTION
                "CMNT: - 
                 TYPE: - Number
                 PAGE: - Audio
                    Input Route Dest 7  cmdID= 40229
                    min= 0  max= 22  step= 1  format= 0  div_scale= 1  preset= 6
                    Min = 0  Max = 0  Step = 0  Preset = 0  "
        ::= { iqmux33CmdEntry 40229 }


    iqmux33AudioRoutingInputRouteDest8 OBJECT-TYPE
        SYNTAX            INTEGER
        MAX-ACCESS        read-write
        STATUS            current
        DESCRIPTION
                "CMNT: - 
                 TYPE: - Number
                 PAGE: - Audio
                    Input Route Dest 8  cmdID= 40230
                    min= 0  max= 22  step= 1  format= 0  div_scale= 1  preset= 7
                    Min = 0  Max = 0  Step = 0  Preset = 0  "
        ::= { iqmux33CmdEntry 40230 }


    iqmux33AudioRoutingInputNameAnalog OBJECT-TYPE
        SYNTAX            RollCallString
        MAX-ACCESS        read-only
        STATUS            current
        DESCRIPTION
                "CMNT: - 
                 TYPE: - Display
                 PAGE: - Audio
                    Input Name Analog  cmdID= 40216  "
        ::= { iqmux33CmdEntry 40216 }


    iqmux33AudioRoutingInputNameDlby1 OBJECT-TYPE
        SYNTAX            RollCallString
        MAX-ACCESS        read-only
        STATUS            current
        DESCRIPTION
                "CMNT: - 
                 TYPE: - Display
                 PAGE: - Audio
                    Input Name Dlby 1  cmdID= 40218  "
        ::= { iqmux33CmdEntry 40218 }


    iqmux33AudioRoutingInputNameDlby2 OBJECT-TYPE
        SYNTAX            RollCallString
        MAX-ACCESS        read-only
        STATUS            current
        DESCRIPTION
                "CMNT: - 
                 TYPE: - Display
                 PAGE: - Audio
                    Input Name Dlby 2  cmdID= 40219  "
        ::= { iqmux33CmdEntry 40219 }


    iqmux33AudioRoutingInputNameDlby3 OBJECT-TYPE
        SYNTAX            RollCallString
        MAX-ACCESS        read-only
        STATUS            current
        DESCRIPTION
                "CMNT: - 
                 TYPE: - Display
                 PAGE: - Audio
                    Input Name Dlby 3  cmdID= 40220  "
        ::= { iqmux33CmdEntry 40220 }


    iqmux33AudioRoutingInputNameDlby4 OBJECT-TYPE
        SYNTAX            RollCallString
        MAX-ACCESS        read-only
        STATUS            current
        DESCRIPTION
                "CMNT: - 
                 TYPE: - Display
                 PAGE: - Audio
                    Input Name Dlby 4  cmdID= 40221  "
        ::= { iqmux33CmdEntry 40221 }


    iqmux33AudioRoutingInputNameDlby5 OBJECT-TYPE
        SYNTAX            RollCallString
        MAX-ACCESS        read-only
        STATUS            current
        DESCRIPTION
                "CMNT: - 
                 TYPE: - Display
                 PAGE: - Audio
                    Input Name Dlby 5  cmdID= 40222  "
        ::= { iqmux33CmdEntry 40222 }


    iqmux33AudioRoutingInputHideAES1 OBJECT-TYPE
        SYNTAX            RollCallString
        MAX-ACCESS        read-only
        STATUS            current
        DESCRIPTION
                "CMNT: - 
                 TYPE: - Display
                 PAGE: - Audio
                    Input Hide AES 1  cmdID= 40233  "
        ::= { iqmux33CmdEntry 40233 }


    iqmux33AudioRoutingInputHideAES2 OBJECT-TYPE
        SYNTAX            RollCallString
        MAX-ACCESS        read-only
        STATUS            current
        DESCRIPTION
                "CMNT: - 
                 TYPE: - Display
                 PAGE: - Audio
                    Input Hide AES 2  cmdID= 40234  "
        ::= { iqmux33CmdEntry 40234 }


    iqmux33AudioRoutingInputHideAES3 OBJECT-TYPE
        SYNTAX            RollCallString
        MAX-ACCESS        read-only
        STATUS            current
        DESCRIPTION
                "CMNT: - 
                 TYPE: - Display
                 PAGE: - Audio
                    Input Hide AES 3  cmdID= 40235  "
        ::= { iqmux33CmdEntry 40235 }


    iqmux33AudioRoutingInputHideAES4 OBJECT-TYPE
        SYNTAX            RollCallString
        MAX-ACCESS        read-only
        STATUS            current
        DESCRIPTION
                "CMNT: - 
                 TYPE: - Display
                 PAGE: - Audio
                    Input Hide AES 4  cmdID= 40236  "
        ::= { iqmux33CmdEntry 40236 }


    iqmux33AudioRoutingInputHideAES5 OBJECT-TYPE
        SYNTAX            RollCallString
        MAX-ACCESS        read-only
        STATUS            current
        DESCRIPTION
                "CMNT: - 
                 TYPE: - Display
                 PAGE: - Audio
                    Input Hide AES 5  cmdID= 40237  "
        ::= { iqmux33CmdEntry 40237 }


    iqmux33AudioRoutingInputHideAES6 OBJECT-TYPE
        SYNTAX            RollCallString
        MAX-ACCESS        read-only
        STATUS            current
        DESCRIPTION
                "CMNT: - 
                 TYPE: - Display
                 PAGE: - Audio
                    Input Hide AES 6  cmdID= 40238  "
        ::= { iqmux33CmdEntry 40238 }


    iqmux33AudioRoutingInputHideAES7 OBJECT-TYPE
        SYNTAX            RollCallString
        MAX-ACCESS        read-only
        STATUS            current
        DESCRIPTION
                "CMNT: - 
                 TYPE: - Display
                 PAGE: - Audio
                    Input Hide AES 7  cmdID= 40239  "
        ::= { iqmux33CmdEntry 40239 }


    iqmux33AudioRoutingInputHideAES8 OBJECT-TYPE
        SYNTAX            RollCallString
        MAX-ACCESS        read-only
        STATUS            current
        DESCRIPTION
                "CMNT: - 
                 TYPE: - Display
                 PAGE: - Audio
                    Input Hide AES 8  cmdID= 40240  "
        ::= { iqmux33CmdEntry 40240 }


    iqmux33AudioRoutingOutputHideAES1 OBJECT-TYPE
        SYNTAX            RollCallString
        MAX-ACCESS        read-only
        STATUS            current
        DESCRIPTION
                "CMNT: - 
                 TYPE: - Display
                 PAGE: - Audio
                    Output Hide AES 1  cmdID= 40250  "
        ::= { iqmux33CmdEntry 40250 }


    iqmux33AudioRoutingOutputHideAES2 OBJECT-TYPE
        SYNTAX            RollCallString
        MAX-ACCESS        read-only
        STATUS            current
        DESCRIPTION
                "CMNT: - 
                 TYPE: - Display
                 PAGE: - Audio
                    Output Hide AES 2  cmdID= 40251  "
        ::= { iqmux33CmdEntry 40251 }


    iqmux33AudioRoutingOutputHideAES3 OBJECT-TYPE
        SYNTAX            RollCallString
        MAX-ACCESS        read-only
        STATUS            current
        DESCRIPTION
                "CMNT: - 
                 TYPE: - Display
                 PAGE: - Audio
                    Output Hide AES 3  cmdID= 40252  "
        ::= { iqmux33CmdEntry 40252 }


    iqmux33AudioRoutingOutputHideAES4 OBJECT-TYPE
        SYNTAX            RollCallString
        MAX-ACCESS        read-only
        STATUS            current
        DESCRIPTION
                "CMNT: - 
                 TYPE: - Display
                 PAGE: - Audio
                    Output Hide AES 4  cmdID= 40253  "
        ::= { iqmux33CmdEntry 40253 }


    iqmux33AudioRoutingOutputHideAES5 OBJECT-TYPE
        SYNTAX            RollCallString
        MAX-ACCESS        read-only
        STATUS            current
        DESCRIPTION
                "CMNT: - 
                 TYPE: - Display
                 PAGE: - Audio
                    Output Hide AES 5  cmdID= 40254  "
        ::= { iqmux33CmdEntry 40254 }


    iqmux33AudioRoutingOutputHideAES6 OBJECT-TYPE
        SYNTAX            RollCallString
        MAX-ACCESS        read-only
        STATUS            current
        DESCRIPTION
                "CMNT: - 
                 TYPE: - Display
                 PAGE: - Audio
                    Output Hide AES 6  cmdID= 40255  "
        ::= { iqmux33CmdEntry 40255 }


    iqmux33AudioRoutingOutputHideAES7 OBJECT-TYPE
        SYNTAX            RollCallString
        MAX-ACCESS        read-only
        STATUS            current
        DESCRIPTION
                "CMNT: - 
                 TYPE: - Display
                 PAGE: - Audio
                    Output Hide AES 7  cmdID= 40256  "
        ::= { iqmux33CmdEntry 40256 }


    iqmux33AudioRoutingOutputHideAES8 OBJECT-TYPE
        SYNTAX            RollCallString
        MAX-ACCESS        read-only
        STATUS            current
        DESCRIPTION
                "CMNT: - 
                 TYPE: - Display
                 PAGE: - Audio
                    Output Hide AES 8  cmdID= 40257  "
        ::= { iqmux33CmdEntry 40257 }


    iqmux33AudioRoutingDolbyDecodeSource OBJECT-TYPE
        SYNTAX            INTEGER {
                            valDisembed1(0),
                            valDisembed2(1),
                            valDisembed3(2),
                            valDisembed4(3),
                            valDisembed5(4),
                            valDisembed6(5),
                            valDisembed7(6),
                            valDisembed8(7),
                            valAes1(8),
                            valAes2(9),
                            valAes3(10),
                            valAes4(11),
                            valAes5(12),
                            valAes6(13),
                            valAes7(14),
                            valAes8(15)
                            }
        MAX-ACCESS        read-write
        STATUS            current
        DESCRIPTION
                "CMNT: - 
                 TYPE: - RadiobuttonList
                 PAGE: - Audio
                    DolbyDecode Source  cmdID= 40241
                    Disembed 1  value= 0
                    Disembed 2  value= 1
                    Disembed 3  value= 2
                    Disembed 4  value= 3
                    Disembed 5  value= 4
                    Disembed 6  value= 5
                    Disembed 7  value= 6
                    Disembed 8  value= 7
                    Aes 1  value= 8
                    Aes 2  value= 9
                    Aes 3  value= 10
                    Aes 4  value= 11
                    Aes 5  value= 12
                    Aes 6  value= 13
                    Aes 7  value= 14
                    Aes 8  value= 15  "
        ::= { iqmux33CmdEntry 40241 }


    iqmux33AudioRoutingDolbyDecodeNum OBJECT-TYPE
        SYNTAX            INTEGER
        MAX-ACCESS        read-write
        STATUS            current
        DESCRIPTION
                "CMNT: - 
                 TYPE: - Number
                 PAGE: - Audio
                    DolbyDecodeNum  cmdID= 40242
                    min= 0  max= 1  step= 1  format= 0  div_scale= 1  preset= 0
                    Min = 0  Max = 0  Step = 0  Preset = 0  "
        ::= { iqmux33CmdEntry 40242 }


    iqmux33AudioOutputRoutingOutDest1 OBJECT-TYPE
        SYNTAX            INTEGER
        MAX-ACCESS        read-write
        STATUS            current
        DESCRIPTION
                "CMNT: - 
                 TYPE: - Number
                 PAGE: - Audio
                    OutDest1  cmdID= 40293
                    min= 0  max= 47  step= 1  format= %d  div_scale= 1  preset= 0
                    Min = 0  Max = 0  Step = 0  Preset = 0  "
        ::= { iqmux33CmdEntry 40293 }


    iqmux33AudioOutputRoutingOutDest2 OBJECT-TYPE
        SYNTAX            INTEGER
        MAX-ACCESS        read-write
        STATUS            current
        DESCRIPTION
                "CMNT: - 
                 TYPE: - Number
                 PAGE: - Audio
                    OutDest2  cmdID= 40294
                    min= 0  max= 47  step= 1  format= %d  div_scale= 1  preset= 1
                    Min = 0  Max = 0  Step = 0  Preset = 0  "
        ::= { iqmux33CmdEntry 40294 }


    iqmux33AudioOutputRoutingOutDest3 OBJECT-TYPE
        SYNTAX            INTEGER
        MAX-ACCESS        read-write
        STATUS            current
        DESCRIPTION
                "CMNT: - 
                 TYPE: - Number
                 PAGE: - Audio
                    OutDest3  cmdID= 40295
                    min= 0  max= 47  step= 1  format= %d  div_scale= 1  preset= 2
                    Min = 0  Max = 0  Step = 0  Preset = 0  "
        ::= { iqmux33CmdEntry 40295 }


    iqmux33AudioOutputRoutingOutDest4 OBJECT-TYPE
        SYNTAX            INTEGER
        MAX-ACCESS        read-write
        STATUS            current
        DESCRIPTION
                "CMNT: - 
                 TYPE: - Number
                 PAGE: - Audio
                    OutDest4  cmdID= 40296
                    min= 0  max= 47  step= 1  format= %d  div_scale= 1  preset= 3
                    Min = 0  Max = 0  Step = 0  Preset = 0  "
        ::= { iqmux33CmdEntry 40296 }


    iqmux33AudioOutputRoutingOutDest5 OBJECT-TYPE
        SYNTAX            INTEGER
        MAX-ACCESS        read-write
        STATUS            current
        DESCRIPTION
                "CMNT: - 
                 TYPE: - Number
                 PAGE: - Audio
                    OutDest5  cmdID= 40297
                    min= 0  max= 47  step= 1  format= %d  div_scale= 1  preset= 4
                    Min = 0  Max = 0  Step = 0  Preset = 0  "
        ::= { iqmux33CmdEntry 40297 }


    iqmux33AudioOutputRoutingOutDest6 OBJECT-TYPE
        SYNTAX            INTEGER
        MAX-ACCESS        read-write
        STATUS            current
        DESCRIPTION
                "CMNT: - 
                 TYPE: - Number
                 PAGE: - Audio
                    OutDest6  cmdID= 40298
                    min= 0  max= 47  step= 1  format= %d  div_scale= 1  preset= 5
                    Min = 0  Max = 0  Step = 0  Preset = 0  "
        ::= { iqmux33CmdEntry 40298 }


    iqmux33AudioOutputRoutingOutDest7 OBJECT-TYPE
        SYNTAX            INTEGER
        MAX-ACCESS        read-write
        STATUS            current
        DESCRIPTION
                "CMNT: - 
                 TYPE: - Number
                 PAGE: - Audio
                    OutDest7  cmdID= 40299
                    min= 0  max= 47  step= 1  format= %d  div_scale= 1  preset= 6
                    Min = 0  Max = 0  Step = 0  Preset = 0  "
        ::= { iqmux33CmdEntry 40299 }


    iqmux33AudioOutputRoutingOutDest8 OBJECT-TYPE
        SYNTAX            INTEGER
        MAX-ACCESS        read-write
        STATUS            current
        DESCRIPTION
                "CMNT: - 
                 TYPE: - Number
                 PAGE: - Audio
                    OutDest8  cmdID= 40300
                    min= 0  max= 47  step= 1  format= %d  div_scale= 1  preset= 7
                    Min = 0  Max = 0  Step = 0  Preset = 0  "
        ::= { iqmux33CmdEntry 40300 }


    iqmux33AudioOutputRoutingOutDest9 OBJECT-TYPE
        SYNTAX            INTEGER
        MAX-ACCESS        read-write
        STATUS            current
        DESCRIPTION
                "CMNT: - 
                 TYPE: - Number
                 PAGE: - Audio
                    OutDest9  cmdID= 40301
                    min= 0  max= 47  step= 1  format= %d  div_scale= 1  preset= 8
                    Min = 0  Max = 0  Step = 0  Preset = 0  "
        ::= { iqmux33CmdEntry 40301 }


    iqmux33AudioOutputRoutingOutDest10 OBJECT-TYPE
        SYNTAX            INTEGER
        MAX-ACCESS        read-write
        STATUS            current
        DESCRIPTION
                "CMNT: - 
                 TYPE: - Number
                 PAGE: - Audio
                    OutDest10  cmdID= 40302
                    min= 0  max= 47  step= 1  format= %d  div_scale= 1  preset= 9
                    Min = 0  Max = 0  Step = 0  Preset = 0  "
        ::= { iqmux33CmdEntry 40302 }


    iqmux33AudioOutputRoutingOutDest11 OBJECT-TYPE
        SYNTAX            INTEGER
        MAX-ACCESS        read-write
        STATUS            current
        DESCRIPTION
                "CMNT: - 
                 TYPE: - Number
                 PAGE: - Audio
                    OutDest11  cmdID= 40303
                    min= 0  max= 47  step= 1  format= %d  div_scale= 1  preset= 10
                    Min = 0  Max = 0  Step = 0  Preset = 0  "
        ::= { iqmux33CmdEntry 40303 }


    iqmux33AudioOutputRoutingOutDest12 OBJECT-TYPE
        SYNTAX            INTEGER
        MAX-ACCESS        read-write
        STATUS            current
        DESCRIPTION
                "CMNT: - 
                 TYPE: - Number
                 PAGE: - Audio
                    OutDest12  cmdID= 40304
                    min= 0  max= 47  step= 1  format= %d  div_scale= 1  preset= 11
                    Min = 0  Max = 0  Step = 0  Preset = 0  "
        ::= { iqmux33CmdEntry 40304 }


    iqmux33AudioOutputRoutingOutDest13 OBJECT-TYPE
        SYNTAX            INTEGER
        MAX-ACCESS        read-write
        STATUS            current
        DESCRIPTION
                "CMNT: - 
                 TYPE: - Number
                 PAGE: - Audio
                    OutDest13  cmdID= 40305
                    min= 0  max= 47  step= 1  format= %d  div_scale= 1  preset= 12
                    Min = 0  Max = 0  Step = 0  Preset = 0  "
        ::= { iqmux33CmdEntry 40305 }


    iqmux33AudioOutputRoutingOutDest14 OBJECT-TYPE
        SYNTAX            INTEGER
        MAX-ACCESS        read-write
        STATUS            current
        DESCRIPTION
                "CMNT: - 
                 TYPE: - Number
                 PAGE: - Audio
                    OutDest14  cmdID= 40306
                    min= 0  max= 47  step= 1  format= %d  div_scale= 1  preset= 13
                    Min = 0  Max = 0  Step = 0  Preset = 0  "
        ::= { iqmux33CmdEntry 40306 }


    iqmux33AudioOutputRoutingOutDest15 OBJECT-TYPE
        SYNTAX            INTEGER
        MAX-ACCESS        read-write
        STATUS            current
        DESCRIPTION
                "CMNT: - 
                 TYPE: - Number
                 PAGE: - Audio
                    OutDest15  cmdID= 40307
                    min= 0  max= 47  step= 1  format= %d  div_scale= 1  preset= 14
                    Min = 0  Max = 0  Step = 0  Preset = 0  "
        ::= { iqmux33CmdEntry 40307 }


    iqmux33AudioOutputRoutingOutDest16 OBJECT-TYPE
        SYNTAX            INTEGER
        MAX-ACCESS        read-write
        STATUS            current
        DESCRIPTION
                "CMNT: - 
                 TYPE: - Number
                 PAGE: - Audio
                    OutDest16  cmdID= 40308
                    min= 0  max= 47  step= 1  format= %d  div_scale= 1  preset= 15
                    Min = 0  Max = 0  Step = 0  Preset = 0  "
        ::= { iqmux33CmdEntry 40308 }


    iqmux33AudioOutputRoutingDolbyEncEnb OBJECT-TYPE
        SYNTAX            RollCallString
        MAX-ACCESS        read-only
        STATUS            current
        DESCRIPTION
                "CMNT: - 
                 TYPE: - Display
                 PAGE: - Audio
                    DolbyEncEnb  cmdID= 40214  "
        ::= { iqmux33CmdEntry 40214 }


    iqmux33AudioOutputRoutingUpmixEnb OBJECT-TYPE
        SYNTAX            RollCallString
        MAX-ACCESS        read-only
        STATUS            current
        DESCRIPTION
                "CMNT: - 
                 TYPE: - Display
                 PAGE: - Audio
                    UpmixEnb  cmdID= 40213  "
        ::= { iqmux33CmdEntry 40213 }


    iqmux33AudioProcDefaultEmbed OBJECT-TYPE
        SYNTAX            INTEGER {
                            valCustom(3),
                            valRampp2dB(0),
                            valRampn2dB(1),
                            valLevel0dB(2)
                            }
        MAX-ACCESS        read-write
        STATUS            current
        DESCRIPTION
                "CMNT: - Procamp default
                 TYPE: - RadiobuttonList
                 PAGE: - Audio
                    Embed  cmdID= 43105
                    Custom  value= 3
                    Ramp +2dB  value= 0
                    Ramp -2dB  value= 1
                    Level 0dB  value= 2  "
        ::= { iqmux33CmdEntry 43105 }


    iqmux33AudioRoutingMatrixBus1audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 1 aud sel  cmdID= 40200
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iqmux33CmdEntry 40200 }


    iqmux33AudioRoutingMatrixBus2audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 2 aud sel  cmdID= 40201
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iqmux33CmdEntry 40201 }


    iqmux33AudioRoutingMatrixBus3audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 3 aud sel  cmdID= 40202
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iqmux33CmdEntry 40202 }


    iqmux33AudioRoutingMatrixBus4audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 4 aud sel  cmdID= 40203
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iqmux33CmdEntry 40203 }


    iqmux33AudioRoutingMatrixBus5audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 5 aud sel  cmdID= 40204
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iqmux33CmdEntry 40204 }


    iqmux33AudioRoutingMatrixBus6audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 6 aud sel  cmdID= 40205
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iqmux33CmdEntry 40205 }


    iqmux33AudioRoutingMatrixBus7audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 7 aud sel  cmdID= 40206
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iqmux33CmdEntry 40206 }


    iqmux33AudioRoutingMatrixBus8audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valAesInput1(8),
                            valAesInput2(9),
                            valAesInput3(10),
                            valAesInput4(11),
                            valAesInput5(12),
                            valAesInput6(13),
                            valAesInput7(14),
                            valAesInput8(15),
                            valAnglInput1(16),
                            valAnlgInput2(17),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 8 aud sel  cmdID= 40207
                    Disemb1  value= 0
                    Disemb2  value= 1
                    Disemb3  value= 2
                    Disemb4  value= 3
                    Disemb5  value= 4
                    Disemb6  value= 5
                    Disemb7  value= 6
                    Disemb8  value= 7
                    AesInput1  value= 8
                    AesInput2  value= 9
                    AesInput3  value= 10
                    AesInput4  value= 11
                    AesInput5  value= 12
                    AesInput6  value= 13
                    AesInput7  value= 14
                    AesInput8  value= 15
                    AnglInput1  value= 16
                    AnlgInput2  value= 17
                    DolbyDec1  value= 18
                    DolbyDec2  value= 19
                    DolbyDec3  value= 20
                    DolbyDec4  value= 21
                    DolbyDec5  value= 22  "
        ::= { iqmux33CmdEntry 40207 }


    iqmux33AudioOutRouteMatrixEmbed12MatrixEmbed11audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed1_1 aud sel  cmdID= 40329
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40329 }


    iqmux33AudioOutRouteMatrixEmbed12MatrixEmbed12audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed1_2 aud sel  cmdID= 40330
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40330 }


    iqmux33AudioOutRouteMatrixEmbed12MatrixEmbed21audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed2_1 aud sel  cmdID= 40331
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40331 }


    iqmux33AudioOutRouteMatrixEmbed12MatrixEmbed22audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed2_2 aud sel  cmdID= 40332
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40332 }


    iqmux33AudioOutRouteMatrixEmbed34MatrixEmbed31audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed3_1 aud sel  cmdID= 40333
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40333 }


    iqmux33AudioOutRouteMatrixEmbed34MatrixEmbed32audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed3_2 aud sel  cmdID= 40334
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40334 }


    iqmux33AudioOutRouteMatrixEmbed34MatrixEmbed41audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed4_1 aud sel  cmdID= 40335
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40335 }


    iqmux33AudioOutRouteMatrixEmbed34MatrixEmbed42audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed4_2 aud sel  cmdID= 40336
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40336 }


    iqmux33AudioOutRouteMatrixEmbed56MatrixEmbed51audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed5_1 aud sel  cmdID= 40337
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40337 }


    iqmux33AudioOutRouteMatrixEmbed56MatrixEmbed52audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed5_2 aud sel  cmdID= 40338
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40338 }


    iqmux33AudioOutRouteMatrixEmbed56MatrixEmbed61audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed6_1 aud sel  cmdID= 40339
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40339 }


    iqmux33AudioOutRouteMatrixEmbed56MatrixEmbed62audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed6_2 aud sel  cmdID= 40340
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40340 }


    iqmux33AudioOutRouteMatrixEmbed78MatrixEmbed71audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed7_1 aud sel  cmdID= 40341
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40341 }


    iqmux33AudioOutRouteMatrixEmbed78MatrixEmbed72audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed7_2 aud sel  cmdID= 40342
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40342 }


    iqmux33AudioOutRouteMatrixEmbed78MatrixEmbed81audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed8_1 aud sel  cmdID= 40343
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40343 }


    iqmux33AudioOutRouteMatrixEmbed78MatrixEmbed82audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed8_2 aud sel  cmdID= 40344
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqmux33CmdEntry 40344 }


    iqmux33AudioOutRouteMatrixDefaultsEmbOut OBJECT-TYPE
        SYNTAX            INTEGER {
                            valCustom(10),
                            valEmbedPassthrough(0),
                            valAESPassthrough(1),
                            valDisEm1n4(2),
                            valDisEm1n4AESin1n4(3),
                            valDisEm1n4AESin5n8(4),
                            valAESin1n4(5),
                            valAESin5n8(6),
                            valAnlgin1n2(7),
                            valTone1n2(8),
                            valSilent(9)
                            }
        MAX-ACCESS        read-write
        STATUS            current
        DESCRIPTION
                "CMNT: - 
                 TYPE: - RadiobuttonList
                 PAGE: - AudioOut RouteMatrix
                    Emb Out  cmdID= 40365
                    Custom  value= 10
                    Embed Passthrough  value= 0
                    AES Passthrough  value= 1
                    DisEm1-4  value= 2
                    DisEm1-4 & AESin1-4  value= 3
                    DisEm1-4 & AESin5-8  value= 4
                    AESin1-4  value= 5
                    AESin5-8  value= 6
                    Anlg in 1-2  value= 7
                    Tone 1-2  value= 8
                    Silent  value= 9  "
        ::= { iqmux33CmdEntry 40365 }


    iqmux33UpMixerLoud14Source1ProcGain OBJECT-TYPE
        SYNTAX            INTEGER
        MAX-ACCESS        read-write
        STATUS            current
        DESCRIPTION
                "CMNT: - Mix_1 Proc Amp Gain
                 TYPE: - Number
                 PAGE: - UpMixerLoud1_4
                    ProcGain  cmdID= 40834
                    min= -801  max= 120  step= 1  format= %0.1f dB  div_scale= 10  preset= 0
                    Min = -80.1 dB  Max = 12.0 dB  Step = 0.1 dB  Preset = 0.0 dB  "
        ::= { iqmux33CmdEntry 40834 }


    iqmux33UpMixerLoud14Source1Mute OBJECT-TYPE
        SYNTAX            INTEGER { disable(0), enable(1)  }
        MAX-ACCESS        read-write
        STATUS            current
        DESCRIPTION
                "CMNT: - Mix_1 Mute
                 TYPE: - Checkbox
                 PAGE: - UpMixerLoud1_4
                    Mute  cmdID= 40840  "
        ::= { iqmux33CmdEntry 40840 }


    iqmux33UpMixerLoud14Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_1 source
                 TYPE: - RadiobuttonList
                 PAGE: - UpMixerLoud1_4
                    Src  cmdID= 40846
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqmux33CmdEntry 40846 }


    iqmux33UpMixerLoud14Source2ProcGain OBJECT-TYPE
        SYNTAX            INTEGER
        MAX-ACCESS        read-write
        STATUS            current
        DESCRIPTION
                "CMNT: - Mix_2 Proc Amp Gain
                 TYPE: - Number
                 PAGE: - UpMixerLoud1_4
                    ProcGain  cmdID= 40835
                    min= -801  max= 120  step= 1  format= %0.1f dB  div_scale= 10  preset= 0
                    Min = -80.1 dB  Max = 12.0 dB  Step = 0.1 dB  Preset = 0.0 dB  "
        ::= { iqmux33CmdEntry 40835 }


    iqmux33UpMixerLoud14Source2Mute OBJECT-TYPE
        SYNTAX            INTEGER { disable(0), enable(1)  }
        MAX-ACCESS        read-write
        STATUS            current
        DESCRIPTION
                "CMNT: - Mix_2 Mute
                 TYPE: - Checkbox
                 PAGE: - UpMixerLoud1_4
                    Mute  cmdID= 40841  "
        ::= { iqmux33CmdEntry 40841 }


    iqmux33UpMixerLoud14Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_2 source
                 TYPE: - RadiobuttonList
                 PAGE: - UpMixerLoud1_4
                    Src  cmdID= 40847
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqmux33CmdEntry 40847 }


    iqmux33UpMixerLoud14Source3ProcGain OBJECT-TYPE
        SYNTAX            INTEGER
        MAX-ACCESS        read-write
        STATUS            current
        DESCRIPTION
                "CMNT: - Mix_3 Proc Amp Gain
                 TYPE: - Number
                 PAGE: - UpMixerLoud1_4
                    ProcGain  cmdID= 40836
                    min= -801  max= 120  step= 1  format= %0.1f dB  div_scale= 10  preset= 0
                    Min = -80.1 dB  Max = 12.0 dB  Step = 0.1 dB  Preset = 0.0 dB  "
        ::= { iqmux33CmdEntry 40836 }


    iqmux33UpMixerLoud14Source3Mute OBJECT-TYPE
        SYNTAX            INTEGER { disable(0), enable(1)  }
        MAX-ACCESS        read-write
        STATUS            current
        DESCRIPTION
                "CMNT: - Mix_3 Mute
                 TYPE: - Checkbox
                 PAGE: - UpMixerLoud1_4
                    Mute  cmdID= 40842  "
        ::= { iqmux33CmdEntry 40842 }


    iqmux33UpMixerLoud14Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_3 source
                 TYPE: - RadiobuttonList
                 PAGE: - UpMixerLoud1_4
                    Src  cmdID= 40848
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqmux33CmdEntry 40848 }


    iqmux33UpMixerLoud14Source4ProcGain OBJECT-TYPE
        SYNTAX            INTEGER
        MAX-ACCESS        read-write
        STATUS            current
        DESCRIPTION
                "CMNT: - Mix_4 Proc Amp Gain
                 TYPE: - Number
                 PAGE: - UpMixerLoud1_4
                    ProcGain  cmdID= 40837
                    min= -801  max= 120  step= 1  format= %0.1f dB  div_scale= 10  preset= 0
                    Min = -80.1 dB  Max = 12.0 dB  Step = 0.1 dB  Preset = 0.0 dB  "
        ::= { iqmux33CmdEntry 40837 }


    iqmux33UpMixerLoud14Source4Mute OBJECT-TYPE
        SYNTAX            INTEGER { disable(0), enable(1)  }
        MAX-ACCESS        read-write
        STATUS            current
        DESCRIPTION
                "CMNT: - Mix_4 Mute
                 TYPE: - Checkbox
                 PAGE: - UpMixerLoud1_4
                    Mute  cmdID= 40843  "
        ::= { iqmux33CmdEntry 40843 }


    iqmux33UpMixerLoud14Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_4 source
                 TYPE: - RadiobuttonList
                 PAGE: - UpMixerLoud1_4
                    Src  cmdID= 40849
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqmux33CmdEntry 40849 }


    iqmux33UpMixerLoud14Mode OBJECT-TYPE
        SYNTAX            INTEGER {
                            valAuto(0),
                            valAlwaysUpmix(1),
                            valBypass(2)
                            }
        MAX-ACCESS        read-write
        STATUS            current
        DESCRIPTION
                "CMNT: - UpMixer mode
                 TYPE: - RadiobuttonList
                 PAGE: - UpMixerLoud1_4
                    Mode  cmdID= 40854
                    Auto  value= 0
                    Always Upmix  value= 1
                    Bypass  value= 2  "
        ::= { iqmux33CmdEntry 40854 }


    iqmux33UpMixerLoud14Status OBJECT-TYPE
        SYNTAX            RollCallString
        MAX-ACCESS        read-only
        STATUS            current
        DESCRIPTION
                "CMNT: - UpMixer status
                 TYPE: - Display
                 PAGE: - UpMixerLoud1_4
                    Status  cmdID= 40855  "
        ::= { iqmux33CmdEntry 40855 }


    iqmux33UpMixerLoud14XfadeBypass OBJECT-TYPE
        SYNTAX            INTEGER {
                            valVerySlow(0),
                            valSlow(1),
                            valMedium(2),
                            valFast(3),
                            valVeryFast(4),
                            valInstant(5)
                            }
        MAX-ACCESS        read-write
        STATUS            current
        DESCRIPTION
                "CMNT: - UpMixer Xfade to bypass
                 TYPE: - RadiobuttonList
                 PAGE: - UpMixerLoud1_4
                    XfadeBypass  cmdID= 40856
                    Very Slow  value= 0
                    Slow  value= 1
                    Medium  value= 2
                    Fast  value= 3
                    Very Fast  value= 4
                    Instant  value= 5  "
        ::= { iqmux33CmdEntry 40856 }


    iqmux33UpMixerLoud14XfadeUpmix OBJECT-TYPE
        SYNTAX            INTEGER {
                            valVerySlow(0),
                            valSlow(1),
                            valMedium(2),
                            valFast(3),
                            valVeryFast(4),
                            valInstant(5)
                            }
        MAX-ACCESS        read-write
        STATUS            current
        DESCRIPTION
                "CMNT: - UpMixer Xfade to upmix
                 TYPE: - RadiobuttonList
                 PAGE: - UpMixerLoud1_4
                    XfadeUpmix  cmdID= 40857
                    Very Slow  value= 0
                    Slow  value= 1
                    Medium  value= 2
                    Fast  value= 3
                    Very Fast  value= 4
                    Instant  value= 5  "
        ::= { iqmux33CmdEntry 40857 }


    iqmux33UpMixerLoud14Detect OBJECT-TYPE
        SYNTAX            INTEGER
        MAX-ACCESS        read-write
        STATUS            current
        DESCRIPTION
                "CMNT: - UpMixer Detection threshold
                 TYPE: - Number
                 PAGE: - UpMixerLoud1_4
                    Detect  cmdID= 40858
                    min= -1500  max= 0  step= 1  format= %0.1f dB  div_scale= 10  preset= -600
                    Min = -150.0 dB  Max = 0.0 dB  Step = 0.1 dB  Preset = -60.0 dB  "
        ::= { iqmux33CmdEntry 40858 }


    iqmux33UpMixerLoud14CenterWidth OBJECT-TYPE
        SYNTAX            INTEGER
        MAX-ACCESS        read-write
        STATUS            current
        DESCRIPTION
                "CMNT: - UpMixer Center width
                 TYPE: - Number
                 PAGE: - UpMixerLoud1_4
                    CenterWidth  cmdID= 40859
                    min= 0  max= 1000  step= 1  format= %0.1f%%  div_scale= 10  preset= 0
                    Min = 0.0%  Max = 100.0%  Step = 0.1%  Preset = 0.0%  "
        ::= { iqmux33CmdEntry 40859 }


    iqmux33UpMixerLoud14Surround OBJECT-TYPE
        SYNTAX            INTEGER
        MAX-ACCESS        read-write
        STATUS            current
        DESCRIPTION
                "CMNT: - UpMixer Surround Depth
                 TYPE: - Number
                 PAGE: - UpMixerLoud1_4
                    Surround  cmdID= 40860
                    min= 0  max= 1000  step= 1  format= %0.1f%%  div_scale= 10  preset= 1000
                    Min = 0.0%  Max = 100.0%  Step = 0.1%  Preset = 100.0%  "
        ::= { iqmux33CmdEntry 40860 }


    iqmux33UpMixerLoud14AlgorithmType OBJECT-TYPE
        SYNTAX            INTEGER {
                            valUpmix(0),
                            valLoudness51(1),
                            valLoudness1p2(2),
                            valLoudness1(3),
                            valUpmixLoudA(5)
                            }
        MAX-ACCESS        read-write
        STATUS            current
        DESCRIPTION
                "CMNT: - Linear Acoustic Algorithm Type
                 TYPE: - RadiobuttonList
                 PAGE: - UpMixerLoud1_4
                    Algorithm Type  cmdID= 36148
                    Upmix  value= 0
                    Loudness5.1  value= 1
                    Loudness1+2  value= 2
                    Loudness1  value= 3
                    UpmixLoudA  value= 5  "
        ::= { iqmux33CmdEntry 36148 }


    iqmux33UpMixerLoud58LoudnessPreset1 OBJECT-TYPE
        SYNTAX            INTEGER {
                            valGeneral(0),
                            valLight(1),
                            valHeavy(2),
                            valLoud(3),
                            valLoudLimit(4),
                            valProtectionLimit(5),
                            valCustom1(6),
                            valCustom2(7)
                            }
        MAX-ACCESS        read-write
        STATUS            current
        DESCRIPTION
                "CMNT: - Linear Acoustic Preset 1
                 TYPE: - RadiobuttonList
                 PAGE: - UpMixerLoud5_8
                    Preset1  cmdID= 36151
                    General  value= 0
                    Light  value= 1
                    Heavy  value= 2
                    Loud  value= 3
                    Loud Limit  value= 4
                    Protection Limit  value= 5
                    Custom 1  value= 6
                    Custom 2  value= 7  "
        ::= { iqmux33CmdEntry 36151 }


    iqmux33UpMixerLoud58LoudnessMasterLevel1 OBJECT-TYPE
        SYNTAX            INTEGER
        MAX-ACCESS        read-write
        STATUS            current
        DESCRIPTION
                "CMNT: - Linear Acoustic Master level 1
                 TYPE: - Number
                 PAGE: - UpMixerLoud5_8
                    MasterLevel1  cmdID= 36149
                    min= -310  max= 0  step= 1  format= %0.1f dB  div_scale= 10  preset= -110
                    Min = -31.0 dB  Max = 0.0 dB  Step = 0.1 dB  Preset = -11.0 dB  "
        ::= { iqmux33CmdEntry 36149 }


    iqmux33UpMixerLoud58LoudnessName1 OBJECT-TYPE
        SYNTAX            RollCallString
        MAX-ACCESS        read-only
        STATUS            current
        DESCRIPTION
                "CMNT: - Linear Acoustic Name 1
                 TYPE: - Display
                 PAGE: - UpMixerLoud5_8
                    Name1  cmdID= 36153  "
        ::= { iqmux33CmdEntry 36153 }


    iqmux33UpMixerLoud58LoudnessBypass1 OBJECT-TYPE
        SYNTAX            INTEGER { disable(0), enable(1)  }
        MAX-ACCESS        read-write
        STATUS            current
        DESCRIPTION
                "CMNT: - Linear Acoustic Bypass 1
                 TYPE: - Checkbox
                 PAGE: - UpMixerLoud5_8
                    Bypass 1  cmdID= 36173  "
        ::= { iqmux33CmdEntry 36173 }


    iqmux33UpMixerLoud58LoudnessPreset2 OBJECT-TYPE
        SYNTAX            INTEGER {
                            valGeneral(0),
                            valLight(1),
                            valHeavy(2),
                            valLoud(3),
                            valLoudLimit(4),
                            valProtectionLimit(5),
                            valCustom1(6),
                            valCustom2(7)
                            }
        MAX-ACCESS        read-write
        STATUS            current
        DESCRIPTION
                "CMNT: - Linear Acoustic Preset 2
                 TYPE: - RadiobuttonList
                 PAGE: - UpMixerLoud5_8
                    Preset2  cmdID= 36152
                    General  value= 0
                    Light  value= 1
                    Heavy  value= 2
                    Loud  value= 3
                    Loud Limit  value= 4
                    Protection Limit  value= 5
                    Custom 1  value= 6
                    Custom 2  value= 7  "
        ::= { iqmux33CmdEntry 36152 }


    iqmux33UpMixerLoud58LoudnessMasterLevel2 OBJECT-TYPE
        SYNTAX            INTEGER
        MAX-ACCESS        read-write
        STATUS            current
        DESCRIPTION
                "CMNT: - Linear Acoustic Master level 2
                 TYPE: - Number
                 PAGE: - UpMixerLoud5_8
                    MasterLevel2  cmdID= 36150
                    min= -310  max= 0  step= 1  format= %0.1f dB  div_scale= 10  preset= -110
                    Min = -31.0 dB  Max = 0.0 dB  Step = 0.1 dB  Preset = -11.0 dB  "
        ::= { iqmux33CmdEntry 36150 }


    iqmux33UpMixerLoud58LoudnessName2 OBJECT-TYPE
        SYNTAX            RollCallString
        MAX-ACCESS        read-only
        STATUS            current
        DESCRIPTION
                "CMNT: - Linear Acoustic Name 2
                 TYPE: - Display
                 PAGE: - UpMixerLoud5_8
                    Name2  cmdID= 36154  "
        ::= { iqmux33CmdEntry 36154 }


    iqmux33UpMixerLoud58LoudnessBypass2 OBJECT-TYPE
        SYNTAX            INTEGER { disable(0), enable(1)  }
        MAX-ACCESS        read-write
        STATUS            current
        DESCRIPTION
                "CMNT: - Linear Acoustic Bypass 2
                 TYPE: - Checkbox
                 PAGE: - UpMixerLoud5_8
                    Bypass 2  cmdID= 36174  "
        ::= { iqmux33CmdEntry 36174 }


    iqmux33UpMixerLoud58Source5ProcGain OBJECT-TYPE
        SYNTAX            INTEGER
        MAX-ACCESS        read-write
        STATUS            current
        DESCRIPTION
                "CMNT: - Mix_5 Proc Amp Gain
                 TYPE: - Number
                 PAGE: - UpMixerLoud5_8
                    ProcGain  cmdID= 40838
                    min= -801  max= 120  step= 1  format= %0.1f dB  div_scale= 10  preset= 0
                    Min = -80.1 dB  Max = 12.0 dB  Step = 0.1 dB  Preset = 0.0 dB  "
        ::= { iqmux33CmdEntry 40838 }


    iqmux33UpMixerLoud58Source5Mute OBJECT-TYPE
        SYNTAX            INTEGER { disable(0), enable(1)  }
        MAX-ACCESS        read-write
        STATUS            current
        DESCRIPTION
                "CMNT: - Mix_5 Mute
                 TYPE: - Checkbox
                 PAGE: - UpMixerLoud5_8
                    Mute  cmdID= 40844  "
        ::= { iqmux33CmdEntry 40844 }


    iqmux33UpMixerLoud58Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_5 source
                 TYPE: - RadiobuttonList
                 PAGE: - UpMixerLoud5_8
                    Src  cmdID= 40850
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqmux33CmdEntry 40850 }


    iqmux33UpMixerLoud58Source6ProcGain OBJECT-TYPE
        SYNTAX            INTEGER
        MAX-ACCESS        read-write
        STATUS            current
        DESCRIPTION
                "CMNT: - Mix_6 Proc Amp Gain
                 TYPE: - Number
                 PAGE: - UpMixerLoud5_8
                    ProcGain  cmdID= 40839
                    min= -801  max= 120  step= 1  format= %0.1f dB  div_scale= 10  preset= 0
                    Min = -80.1 dB  Max = 12.0 dB  Step = 0.1 dB  Preset = 0.0 dB  "
        ::= { iqmux33CmdEntry 40839 }


    iqmux33UpMixerLoud58Source6Mute OBJECT-TYPE
        SYNTAX            INTEGER { disable(0), enable(1)  }
        MAX-ACCESS        read-write
        STATUS            current
        DESCRIPTION
                "CMNT: - Mix_6 Mute
                 TYPE: - Checkbox
                 PAGE: - UpMixerLoud5_8
                    Mute  cmdID= 40845  "
        ::= { iqmux33CmdEntry 40845 }


    iqmux33UpMixerLoud58Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_6 source
                 TYPE: - RadiobuttonList
                 PAGE: - UpMixerLoud5_8
                    Src  cmdID= 40851
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqmux33CmdEntry 40851 }


    iqmux33UpMixerLoud58Source7ProcGain OBJECT-TYPE
        SYNTAX            INTEGER
        MAX-ACCESS        read-write
        STATUS            current
        DESCRIPTION
                "CMNT: - Mix_7 Proc Amp Gain
                 TYPE: - Number
                 PAGE: - UpMixerLoud5_8
                    ProcGain  cmdID= 40873
                    min= -801  max= 120  step= 1  format= %0.1f dB  div_scale= 10  preset= 0
                    Min = -80.1 dB  Max = 12.0 dB  Step = 0.1 dB  Preset = 0.0 dB  "
        ::= { iqmux33CmdEntry 40873 }


    iqmux33UpMixerLoud58Source7Mute OBJECT-TYPE
        SYNTAX            INTEGER { disable(0), enable(1)  }
        MAX-ACCESS        read-write
        STATUS            current
        DESCRIPTION
                "CMNT: - Mix_7 Mute
                 TYPE: - Checkbox
                 PAGE: - UpMixerLoud5_8
                    Mute  cmdID= 40875  "
        ::= { iqmux33CmdEntry 40875 }


    iqmux33UpMixerLoud58Source7Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_7 source
                 TYPE: - RadiobuttonList
                 PAGE: - UpMixerLoud5_8
                    Src  cmdID= 40877
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqmux33CmdEntry 40877 }


    iqmux33UpMixerLoud58Source8ProcGain OBJECT-TYPE
        SYNTAX            INTEGER
        MAX-ACCESS        read-write
        STATUS            current
        DESCRIPTION
                "CMNT: - Mix_8 Proc Amp Gain
                 TYPE: - Number
                 PAGE: - UpMixerLoud5_8
                    ProcGain  cmdID= 40874
                    min= -801  max= 120  step= 1  format= %0.1f dB  div_scale= 10  preset= 0
                    Min = -80.1 dB  Max = 12.0 dB  Step = 0.1 dB  Preset = 0.0 dB  "
        ::= { iqmux33CmdEntry 40874 }


    iqmux33UpMixerLoud58Source8Mute OBJECT-TYPE
        SYNTAX            INTEGER { disable(0), enable(1)  }
        MAX-ACCESS        read-write
        STATUS            current
        DESCRIPTION
                "CMNT: - Mix_8 Mute
                 TYPE: - Checkbox
                 PAGE: - UpMixerLoud5_8
                    Mute  cmdID= 40876  "
        ::= { iqmux33CmdEntry 40876 }


    iqmux33UpMixerLoud58Source8Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_8 source
                 TYPE: - RadiobuttonList
                 PAGE: - UpMixerLoud5_8
                    Src  cmdID= 40878
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqmux33CmdEntry 40878 }


    iqmux33UpMixerLoud58UpmixHide OBJECT-TYPE
        SYNTAX            RollCallString
        MAX-ACCESS        read-only
        STATUS            current
        DESCRIPTION
                "CMNT: - Hide Upmix
                 TYPE: - Display
                 PAGE: - UpMixerLoud5_8
                    UpmixHide  cmdID= 36155  "
        ::= { iqmux33CmdEntry 36155 }


    iqmux33UpMixerLoud58Chan1Name OBJECT-TYPE
        SYNTAX            RollCallString
        MAX-ACCESS        read-only
        STATUS            current
        DESCRIPTION
                "CMNT: - Linear Acoustic Chan Name 1
                 TYPE: - Display
                 PAGE: - UpMixerLoud5_8
                    Chan1Name  cmdID= 36158  "
        ::= { iqmux33CmdEntry 36158 }


    iqmux33UpMixerLoud58Chan2Name OBJECT-TYPE
        SYNTAX            RollCallString
        MAX-ACCESS        read-only
        STATUS            current
        DESCRIPTION
                "CMNT: - Linear Acoustic Chan Name 2
                 TYPE: - Display
                 PAGE: - UpMixerLoud5_8
                    Chan2Name  cmdID= 36159  "
        ::= { iqmux33CmdEntry 36159 }


    iqmux33UpMixerLoud58Chan3Name OBJECT-TYPE
        SYNTAX            RollCallString
        MAX-ACCESS        read-only
        STATUS            current
        DESCRIPTION
                "CMNT: - Linear Acoustic Chan Name 3
                 TYPE: - Display
                 PAGE: - UpMixerLoud5_8
                    Chan3Name  cmdID= 36160  "
        ::= { iqmux33CmdEntry 36160 }


    iqmux33UpMixerLoud58Chan4Name OBJECT-TYPE
        SYNTAX            RollCallString
        MAX-ACCESS        read-only
        STATUS            current
        DESCRIPTION
                "CMNT: - Linear Acoustic Chan Name 4
                 TYPE: - Display
                 PAGE: - UpMixerLoud5_8
                    Chan4Name  cmdID= 36161  "
        ::= { iqmux33CmdEntry 36161 }


    iqmux33UpMixerLoud58Chan5Name OBJECT-TYPE
        SYNTAX            RollCallString
        MAX-ACCESS        read-only
        STATUS            current
        DESCRIPTION
                "CMNT: - Linear Acoustic Chan Name 5
                 TYPE: - Display
                 PAGE: - UpMixerLoud5_8
                    Chan5Name  cmdID= 36162  "
        ::= { iqmux33CmdEntry 36162 }


    iqmux33UpMixerLoud58Chan6Name OBJECT-TYPE
        SYNTAX            RollCallString
        MAX-ACCESS        read-only
        STATUS            current
        DESCRIPTION
                "CMNT: - Linear Acoustic Chan Name 6
                 TYPE: - Display
                 PAGE: - UpMixerLoud5_8
                    Chan6Name  cmdID= 36163  "
        ::= { iqmux33CmdEntry 36163 }


    iqmux33UpMixerLoud58Chan7Name OBJECT-TYPE
        SYNTAX            RollCallString
        MAX-ACCESS        read-only
        STATUS            current
        DESCRIPTION
                "CMNT: - Linear Acoustic Chan Name 7
                 TYPE: - Display
                 PAGE: - UpMixerLoud5_8
                    Chan7Name  cmdID= 36183  "
        ::= { iqmux33CmdEntry 36183 }


    iqmux33UpMixerLoud58Chan8Name OBJECT-TYPE
        SYNTAX            RollCallString
        MAX-ACCESS        read-only
        STATUS            current
        DESCRIPTION
                "CMNT: - Linear Acoustic Chan Name 8
                 TYPE: - Display
                 PAGE: - UpMixerLoud5_8
                    Chan8Name  cmdID= 36184  "
        ::= { iqmux33CmdEntry 36184 }


    iqmux33UpMixerLoud58Chan1NameIn OBJECT-TYPE
        SYNTAX            RollCallString
        MAX-ACCESS        read-only
        STATUS            current
        DESCRIPTION
                "CMNT: - Linear Acoustic Chan Name 1
                 TYPE: - Display
                 PAGE: - UpMixerLoud5_8
                    Chan1NameIn  cmdID= 36175  "
        ::= { iqmux33CmdEntry 36175 }


    iqmux33UpMixerLoud58Chan2NameIn OBJECT-TYPE
        SYNTAX            RollCallString
        MAX-ACCESS        read-only
        STATUS            current
        DESCRIPTION
                "CMNT: - Linear Acoustic Chan Name 2
                 TYPE: - Display
                 PAGE: - UpMixerLoud5_8
                    Chan2NameIn  cmdID= 36176  "
        ::= { iqmux33CmdEntry 36176 }


    iqmux33UpMixerLoud58Chan3NameIn OBJECT-TYPE
        SYNTAX            RollCallString
        MAX-ACCESS        read-only
        STATUS            current
        DESCRIPTION
                "CMNT: - Linear Acoustic Chan Name 3
                 TYPE: - Display
                 PAGE: - UpMixerLoud5_8
                    Chan3NameIn  cmdID= 36177  "
        ::= { iqmux33CmdEntry 36177 }


    iqmux33UpMixerLoud58Chan4NameIn OBJECT-TYPE
        SYNTAX            RollCallString
        MAX-ACCESS        read-only
        STATUS            current
        DESCRIPTION
                "CMNT: - Linear Acoustic Chan Name 4
                 TYPE: - Display
                 PAGE: - UpMixerLoud5_8
                    Chan4NameIn  cmdID= 36178  "
        ::= { iqmux33CmdEntry 36178 }


    iqmux33UpMixerLoud58Chan5NameIn OBJECT-TYPE
        SYNTAX            RollCallString
        MAX-ACCESS        read-only
        STATUS            current
        DESCRIPTION
                "CMNT: - Linear Acoustic Chan Name 5
                 TYPE: - Display
                 PAGE: - UpMixerLoud5_8
                    Chan5NameIn  cmdID= 36179  "
        ::= { iqmux33CmdEntry 36179 }


    iqmux33UpMixerLoud58Chan6NameIn OBJECT-TYPE
        SYNTAX            RollCallString
        MAX-ACCESS        read-only
        STATUS            current
        DESCRIPTION
                "CMNT: - Linear Acoustic Chan Name 6
                 TYPE: - Display
                 PAGE: - UpMixerLoud5_8
                    Chan6NameIn  cmdID= 36180  "
        ::= { iqmux33CmdEntry 36180 }


    iqmux33UpMixerLoud58Chan7NameIn OBJECT-TYPE
        SYNTAX            RollCallString
        MAX-ACCESS        read-only
        STATUS            current
        DESCRIPTION
                "CMNT: - Linear Acoustic Chan Name 7
                 TYPE: - Display
                 PAGE: - UpMixerLoud5_8
                    Chan7NameIn  cmdID= 36181  "
        ::= { iqmux33CmdEntry 36181 }


    iqmux33UpMixerLoud58Chan8NameIn OBJECT-TYPE
        SYNTAX            RollCallString
        MAX-ACCESS        read-only
        STATUS            current
        DESCRIPTION
                "CMNT: - Linear Acoustic Chan Name 8
                 TYPE: - Display
                 PAGE: - UpMixerLoud5_8
                    Chan8NameIn  cmdID= 36182  "
        ::= { iqmux33CmdEntry 36182 }


    iqmux33UpMixerLoud58DialogHide OBJECT-TYPE
        SYNTAX            RollCallString
        MAX-ACCESS        read-only
        STATUS            current
        DESCRIPTION
                "CMNT: - Hide Upmix DIALOG
                 TYPE: - Display
                 PAGE: - UpMixerLoud5_8
                    DialogHide  cmdID= 36164  "
        ::= { iqmux33CmdEntry 36164 }


    iqmux33LoudCustomBlock1Name OBJECT-TYPE
        SYNTAX            RollCallString
        MAX-ACCESS        read-write
        STATUS            current
        DESCRIPTION
                "CMNT: - Linear Acoustic MB Block1 Name
                 TYPE: - Editstring
                 PAGE: - LoudCustom
                    Name  cmdID= 36304
                    preset= Custom Block 1"
        ::= { iqmux33CmdEntry 36304 }


    iqmux33LoudCustomBlock1inagcfreeze OBJECT-TYPE
        SYNTAX            INTEGER
        MAX-ACCESS        read-write
        STATUS            current
        DESCRIPTION
                "CMNT: - Linear Acoustic InAGC Block1 Freeze Threshold
                 TYPE: - Number
                 PAGE: - LoudCustom
                    inagc freeze  cmdID= 36200
                    min= -180  max= 0  step= 1  format= %0.1f dBFS  div_scale= 2  preset= -62
                    Min = -90.0 dBFS  Max = 0.0 dBFS  Step = 0.5 dBFS  Preset = -31.0 dBFS  "
        ::= { iqmux33CmdEntry 36200 }


    iqmux33LoudCustomBlock1inagcgate OBJECT-TYPE
        SYNTAX            INTEGER
        MAX-ACCESS        read-write
        STATUS            current
        DESCRIPTION
                "CMNT: - Linear Acoustic InAGC Block1 Gate Threshold
                 TYPE: - Number
                 PAGE: - LoudCustom
                    inagc gate  cmdID= 36202
                    min= -180  max= 0  step= 1  format= %0.1f dBFS  div_scale= 2  preset= -42
                    Min = -90.0 dBFS  Max = 0.0 dBFS  Step = 0.5 dBFS  Preset = -21.0 dBFS  "
        ::= { iqmux33CmdEntry 36202 }


    iqmux33LoudCustomBlock1inagcratio OBJECT-TYPE
        SYNTAX            INTEGER
        MAX-ACCESS        read-write
        STATUS            current
        DESCRIPTION
                "CMNT: - Linear Acoustic InAGC Block1 Ratio
                 TYPE: - Number
                 PAGE: - LoudCustom
                    inagc ratio  cmdID= 36208
                    min= 0  max= 100  step= 1  format= %0.0f  div_scale= 1  preset= 91
                    Min = 0  Max = 100  Step = 1  Preset = 91  "
        ::= { iqmux33CmdEntry 36208 }


    iqmux33LoudCustomBlock1inagcrange OBJECT-TYPE
        SYNTAX            INTEGER
        MAX-ACCESS        read-write
        STATUS            current
        DESCRIPTION
                "CMNT: - Linear Acoustic InAGC Block1 Range
                 TYPE: - Number
                 PAGE: - LoudCustom
                    inagc range  cmdID= 36206
                    min= 0  max= 180  step= 1  format= %0.1f dB  div_scale= 5  preset= 125
                    Min = 0.0 dB  Max = 36.0 dB  Step = 0.2 dB  Preset = 25.0 dB  "
        ::= { iqmux33CmdEntry 36206 }


    iqmux33LoudCustomBlock1inagcthresh OBJECT-TYPE
        SYNTAX            INTEGER
        MAX-ACCESS        read-write
        STATUS            current
        DESCRIPTION
                "CMNT: - Linear Acoustic InAGC Block1 Threshold
                 TYPE: - Number
                 PAGE: - LoudCustom
                    inagc thresh  cmdID= 36204
                    min= -180  max= 0  step= 1  format= %0.1f dBFS  div_scale= 10  preset= -140
                    Min = -18.0 dBFS  Max = 0.0 dBFS  Step = 0.1 dBFS  Preset = -14.0 dBFS  "
        ::= { iqmux33CmdEntry 36204 }


    iqmux33LoudCustomBlock1inagcattack OBJECT-TYPE
        SYNTAX            INTEGER
        MAX-ACCESS        read-write
        STATUS            current
        DESCRIPTION
                "CMNT: - Linear Acoustic InAGC Block1 Attack
                 TYPE: - Number
                 PAGE: - LoudCustom
                    inagc attack  cmdID= 36210
                    min= 1  max= 100  step= 1  format= %0.0f  div_scale= 1  preset= 24
                    Min = 1  Max = 100  Step = 1  Preset = 24  "
        ::= { iqmux33CmdEntry 36210 }


    iqmux33LoudCustomBlock1inagcrelease OBJECT-TYPE
        SYNTAX            INTEGER
        MAX-ACCESS        read-write
        STATUS            current
        DESCRIPTION
                "CMNT: - Linear Acoustic InAGC Block1 Release
                 TYPE: - Number
                 PAGE: - LoudCustom
                    inagc release  cmdID= 36212
                    min= 1  max= 100  step= 1  format= %0.0f  div_scale= 1  preset= 42
                    Min = 1  Max = 100  Step = 1  Preset = 42  "
        ::= { iqmux33CmdEntry 36212 }


    iqmux33LoudCustomBlock1peqfreq1 OBJECT-TYPE
        SYNTAX            INTEGER
        MAX-ACCESS        read-write
        STATUS            current
        DESCRIPTION
                "CMNT: - Linear Acoustic PEQ Block1 Index 1 Frequency
                 TYPE: - Number
                 PAGE: - LoudCustom
                    peq freq 1  cmdID= 36276
                    min= 20  max= 20000  step= 1  format= %0.0f Hz  div_scale= 1  preset= 1000
                    Min = 20 Hz  Max = 20000 Hz  Step = 1 Hz  Preset = 1000 Hz  "
        ::= { iqmux33CmdEntry 36276 }


    iqmux33LoudCustomBlock1peqq1 OBJECT-TYPE
        SYNTAX            INTEGER
        MAX-ACCESS        read-write
        STATUS            current
        DESCRIPTION
                "CMNT: - Linear Acoustic PEQ Block1 Index 1 Q
                 TYPE: - Number
                 PAGE: - LoudCustom
                    peq q 1  cmdID= 36282
                    min= 1  max= 200  step= 1  format= %0.2f  div_scale= 20  preset= 20
                    Min = 0.05  Max = 10.00  Step = 0.05  Preset = 1.00  "
        ::= { iqmux33CmdEntry 36282 }


    iqmux33LoudCustomBlock1peqlevel1 OBJECT-TYPE
        SYNTAX            INTEGER
        MAX-ACCESS        read-write
        STATUS            current
        DESCRIPTION
                "CMNT: - Linear Acoustic PEQ Block1 Index 1 Level
                 TYPE: - Number
                 PAGE: - LoudCustom
                    peq level 1  cmdID= 36288
                    min= -90  max= 90  step= 1  format= %0.1f dB  div_scale= 5  preset= 0
                    Min = -18.0 dB  Max = 18.0 dB  Step = 0.2 dB  Preset = 0.0 dB  "
        ::= { iqmux33CmdEntry 36288 }


    iqmux33LoudCustomBlock1peqfreq2 OBJECT-TYPE
        SYNTAX            INTEGER
        MAX-ACCESS        read-write
        STATUS            current
        DESCRIPTION
                "CMNT: - Linear Acoustic PEQ Block1 Index 2 Frequency
                 TYPE: - Number
                 PAGE: - LoudCustom
                    peq freq 2  cmdID= 36277
                    min= 20  max= 20000  step= 1  format= %0.0f Hz  div_scale= 1  preset= 1000
                    Min = 20 Hz  Max = 20000 Hz  Step = 1 Hz  Preset = 1000 Hz  "
        ::= { iqmux33CmdEntry 36277 }


    iqmux33LoudCustomBlock1peqq2 OBJECT-TYPE
        SYNTAX            INTEGER
        MAX-ACCESS        read-write
        STATUS            current
        DESCRIPTION
                "CMNT: - Linear Acoustic PEQ Block1 Index 2 Q
                 TYPE: - Number
                 PAGE: - LoudCustom
                    peq q 2  cmdID= 36283
                    min= 1  max= 200  step= 1  format= %0.2f  div_scale= 20  preset= 20
                    Min = 0.05  Max = 10.00  Step = 0.05  Preset = 1.00  "
        ::= { iqmux33CmdEntry 36283 }


    iqmux33LoudCustomBlock1peqlevel2 OBJECT-TYPE
        SYNTAX            INTEGER
        MAX-ACCESS        read-write
        STATUS            current
        DESCRIPTION
                "CMNT: - Linear Acoustic PEQ Block1 Index 2 Level
                 TYPE: - Number
                 PAGE: - LoudCustom
                    peq level 2  cmdID= 36289
                    min= -90  max= 90  step= 1  format= %0.1f dB  div_scale= 5  preset= 0
                    Min = -18.0 dB  Max = 18.0 dB  Step = 0.2 dB  Preset = 0.0 dB  "
        ::= { iqmux33CmdEntry 36289 }


    iqmux33LoudCustomBlock1peqfreq3 OBJECT-TYPE
        SYNTAX            INTEGER
        MAX-ACCESS        read-write
        STATUS            current
        DESCRIPTION
                "CMNT: - Linear Acoustic PEQ Block1 Index 3 Frequency
                 TYPE: - Number
                 PAGE: - LoudCustom
                    peq freq 3  cmdID= 36278
                    min= 20  max= 20000  step= 1  format= %0.0f Hz  div_scale= 1  preset= 1000
                    Min = 20 Hz  Max = 20000 Hz  Step = 1 Hz  Preset = 1000 Hz  "
        ::= { iqmux33CmdEntry 36278 }


    iqmux33LoudCustomBlock1peqq3 OBJECT-TYPE
        SYNTAX            INTEGER
        MAX-ACCESS        read-write
        STATUS            current
        DESCRIPTION
                "CMNT: - Linear Acoustic PEQ Block1 Index 3 Q
                 TYPE: - Number
                 PAGE: - LoudCustom
                    peq q 3  cmdID= 36284
                    min= 1  max= 200  step= 1  format= %0.2f  div_scale= 20  preset= 20
                    Min = 0.05  Max = 10.00  Step = 0.05  Preset = 1.00  "
        ::= { iqmux33CmdEntry 36284 }


    iqmux33LoudCustomBlock1peqlevel3 OBJECT-TYPE
        SYNTAX            INTEGER
        MAX-ACCESS        read-write
        STATUS            current
        DESCRIPTION
                "CMNT: - Linear Acoustic PEQ Block1 Index 3 Level
                 TYPE: - Number
                 PAGE: - LoudCustom
                    peq level 3  cmdID= 36290
                    min= -90  max= 90  step= 1  format= %0.1f dB  div_scale= 5  preset= 0
                    Min = -18.0 dB  Max = 18.0 dB  Step = 0.2 dB  Preset = 0.0 dB  "
        ::= { iqmux33CmdEntry 36290 }


    iqmux33LoudCustomBlock1mbagcatk1 OBJECT-TYPE
        SYNTAX            INTEGER
        MAX-ACCESS        read-write
        STATUS            current
        DESCRIPTION
                "CMNT: - Linear Acoustic MBAGC Block1 Index 1 Attack
                 TYPE: - Number
                 PAGE: - LoudCustom
                    mbagc atk 1  cmdID= 36236
                    min= 0  max= 100  step= 1  format= %0.0f  div_scale= 1  preset= 24
                    Min = 0  Max = 100  Step = 1  Preset = 24  "
        ::= { iqmux33CmdEntry 36236 }


    iqmux33LoudCustomBlock1mbagcrel1 OBJECT-TYPE
        SYNTAX            INTEGER
        MAX-ACCESS        read-write
        STATUS            current
        DESCRIPTION
                "CMNT: - Linear Acoustic MBAGC Block1 Index 1 Release
                 TYPE: - Number
                 PAGE: - LoudCustom
                    mbagc rel 1  cmdID= 36226
                    min= 0  max= 100  step= 1  format= %0.0f  div_scale= 1  preset= 42
                    Min = 0  Max = 100  Step = 1  Preset = 42  "
        ::= { iqmux33CmdEntry 36226 }


    iqmux33LoudCustomBlock1mbagcthresh1 OBJECT-TYPE
        SYNTAX            INTEGER
        MAX-ACCESS        read-write
        STATUS            current
        DESCRIPTION
                "CMNT: - Linear Acoustic MBAGC Block1 Index 1 Threshold
                 TYPE: - Number
                 PAGE: - LoudCustom
                    mbagc thresh 1  cmdID= 36246
                    min= -120  max= 120  step= 1  format= %0.1f dB  div_scale= 10  preset= 0
                    Min = -12.0 dB  Max = 12.0 dB  Step = 0.1 dB  Preset = 0.0 dB  "
        ::= { iqmux33CmdEntry 36246 }


    iqmux33LoudCustomBlock1mbagcoutlev1 OBJECT-TYPE
        SYNTAX            INTEGER
        MAX-ACCESS        read-write
        STATUS            current
        DESCRIPTION
                "CMNT: - Linear Acoustic MBAGC Block1 Index 1 OutLevel
                 TYPE: - Number
                 PAGE: - LoudCustom
                    mbagc outlev 1  cmdID= 36266
                    min= -120  max= 120  step= 1  format= %0.1f dB  div_scale= 10  preset= 0
                    Min = -12.0 dB  Max = 12.0 dB  Step = 0.1 dB  Preset = 0.0 dB  "
        ::= { iqmux33CmdEntry 36266 }


    iqmux33LoudCustomBlock1mbagclimthresh1 OBJECT-TYPE
        SYNTAX            INTEGER
        MAX-ACCESS        read-write
        STATUS            current
        DESCRIPTION
                "CMNT: - Linear Acoustic MBAGC Block1 Index 1 Limit Threshold
                 TYPE: - Number
                 PAGE: - LoudCustom
                    mbagc limthresh 1  cmdID= 36256
                    min= 0  max= 180  step= 1  format= %0.1f dB  div_scale= 10  preset= 0
                    Min = 0.0 dB  Max = 18.0 dB  Step = 0.1 dB  Preset = 0.0 dB  "
        ::= { iqmux33CmdEntry 36256 }


    iqmux33LoudCustomBlock1mbagcinfthr1 OBJECT-TYPE
        SYNTAX            INTEGER { disable(0), enable(1)  }
        MAX-ACCESS        read-write
        STATUS            current
        DESCRIPTION
                "CMNT: - Linear Acoustic MBAGC Block1 Index 1 InfThr
                 TYPE: - Checkbox
                 PAGE: - LoudCustom
                    mbagc infthr 1  cmdID= 36294  "
        ::= { iqmux33CmdEntry 36294 }


    iqmux33LoudCustomBlock1mbagcatk2 OBJECT-TYPE
        SYNTAX            INTEGER
        MAX-ACCESS        read-write
        STATUS            current
        DESCRIPTION
                "CMNT: - Linear Acoustic MBAGC Block1 Index 2 Attack
                 TYPE: - Number
                 PAGE: - LoudCustom
                    mbagc atk 2  cmdID= 36237
                    min= 0  max= 100  step= 1  format= %0.0f  div_scale= 1  preset= 24
                    Min = 0  Max = 100  Step = 1  Preset = 24  "
        ::= { iqmux33CmdEntry 36237 }


    iqmux33LoudCustomBlock1mbagcrel2 OBJECT-TYPE
        SYNTAX            INTEGER
        MAX-ACCESS        read-write
        STATUS            current
        DESCRIPTION
                "CMNT: - Linear Acoustic MBAGC Block1 Index 2 Release
                 TYPE: - Number
                 PAGE: - LoudCustom
                    mbagc rel 2  cmdID= 36227
                    min= 0  max= 100  step= 1  format= %0.0f  div_scale= 1  preset= 42
                    Min = 0  Max = 100  Step = 1  Preset = 42  "
        ::= { iqmux33CmdEntry 36227 }


    iqmux33LoudCustomBlock1mbagcthresh2 OBJECT-TYPE
        SYNTAX            INTEGER
        MAX-ACCESS        read-write
        STATUS            current
        DESCRIPTION
                "CMNT: - Linear Acoustic MBAGC Block1 Index 2 Threshold
                 TYPE: - Number
                 PAGE: - LoudCustom
                    mbagc thresh 2  cmdID= 36247
                    min= -120  max= 120  step= 1  format= %0.1f dB  div_scale= 10  preset= 0
                    Min = -12.0 dB  Max = 12.0 dB  Step = 0.1 dB  Preset = 0.0 dB  "
        ::= { iqmux33CmdEntry 36247 }


    iqmux33LoudCustomBlock1mbagcoutlev2 OBJECT-TYPE
        SYNTAX            INTEGER
        MAX-ACCESS        read-write
        STATUS            current
        DESCRIPTION
                "CMNT: - Linear Acoustic MBAGC Block1 Index 2 OutLevel
                 TYPE: - Number
                 PAGE: - LoudCustom
                    mbagc outlev 2  cmdID= 36267
                    min= -120  max= 120  step= 1  format= %0.1f dB  div_scale= 10  preset= 0
                    Min = -12.0 dB  Max = 12.0 dB  Step = 0.1 dB  Preset = 0.0 dB  "
        ::= { iqmux33CmdEntry 36267 }


    iqmux33LoudCustomBlock1mbagclimthresh2 OBJECT-TYPE
        SYNTAX            INTEGER
        MAX-ACCESS        read-write
        STATUS            current
        DESCRIPTION
                "CMNT: - Linear Acoustic MBAGC Block1 Index 2 Limit Threshold
                 TYPE: - Number
                 PAGE: - LoudCustom
                    mbagc limthresh 2  cmdID= 36257
                    min= 0  max= 180  step= 1  format= %0.1f dB  div_scale= 10  preset= 0
                    Min = 0.0 dB  Max = 18.0 dB  Step = 0.1 dB  Preset = 0.0 dB  "
        ::= { iqmux33CmdEntry 36257 }


    iqmux33LoudCustomBlock1mbagcinfthr2 OBJECT-TYPE
        SYNTAX            INTEGER { disable(0), enable(1)  }
        MAX-ACCESS        read-write
        STATUS            current
        DESCRIPTION
                "CMNT: - Linear Acoustic MBAGC Block1 Index 2 InfThr
                 TYPE: - Checkbox
                 PAGE: - LoudCustom
                    mbagc infthr 2  cmdID= 36295  "
        ::= { iqmux33CmdEntry 36295 }


    iqmux33LoudCustomBlock1mbagcatk3 OBJECT-TYPE
        SYNTAX            INTEGER
        MAX-ACCESS        read-write
        STATUS            current
        DESCRIPTION
                "CMNT: - Linear Acoustic MBAGC Block1 Index 3 Attack
                 TYPE: - Number
                 PAGE: - LoudCustom
                    mbagc atk 3  cmdID= 36238
                    min= 0  max= 100  step= 1  format= %0.0f  div_scale= 1  preset= 24
                    Min = 0  Max = 100  Step = 1  Preset = 24  "
        ::= { iqmux33CmdEntry 36238 }


    iqmux33LoudCustomBlock1mbagcrel3 OBJECT-TYPE
        SYNTAX            INTEGER
        MAX-ACCESS        read-write
        STATUS            current
        DESCRIPTION
                "CMNT: - Linear Acoustic MBAGC Block1 Index 3 Release
                 TYPE: - Number
                 PAGE: - LoudCustom
                    mbagc rel 3  cmdID= 36228
                    min= 0  max= 100  step= 1  format= %0.0f  div_scale= 1  preset= 42
                    Min = 0  Max = 100  Step = 1  Preset = 42  "
        ::= { iqmux33CmdEntry 36228 }


    iqmux33LoudCustomBlock1mbagcthresh3 OBJECT-TYPE
        SYNTAX            INTEGER
        MAX-ACCESS        read-write
        STATUS            current
        DESCRIPTION
                "CMNT: - Linear Acoustic MBAGC Block1 Index 3 Threshold
                 TYPE: - Number
                 PAGE: - LoudCustom
                    mbagc thresh 3  cmdID= 36248
                    min= -120  max= 120  step= 1  format= %0.1f dB  div_scale= 10  preset= 0
                    Min = -12.0 dB  Max = 12.0 dB  Step = 0.1 dB  Preset = 0.0 dB  "
        ::= { iqmux33CmdEntry 36248 }


    iqmux33LoudCustomBlock1mbagcoutlev3 OBJECT-TYPE
        SYNTAX            INTEGER
        MAX-ACCESS        read-write
        STATUS            current
        DESCRIPTION
                "CMNT: - Linear Acoustic MBAGC Block1 Index 3 OutLevel
                 TYPE: - Number
                 PAGE: - LoudCustom
                    mbagc outlev 3  cmdID= 36268
                    min= -120  max= 120  step= 1  format= %0.1f dB  div_scale= 10  preset= 0
                    Min = -12.0 dB  Max = 12.0 dB  Step = 0.1 dB  Preset = 0.0 dB  "
        ::= { iqmux33CmdEntry 36268 }


    iqmux33LoudCustomBlock1mbagclimthresh3 OBJECT-TYPE
        SYNTAX            INTEGER
        MAX-ACCESS        read-write
        STATUS            current
        DESCRIPTION
                "CMNT: - Linear Acoustic MBAGC Block1 Index 3 Limit Threshold
                 TYPE: - Number
                 PAGE: - LoudCustom
                    mbagc limthresh 3  cmdID= 36258
                    min= 0  max= 180  step= 1  format= %0.1f dB  div_scale= 10  preset= 0
                    Min = 0.0 dB  Max = 18.0 dB  Step = 0.1 dB  Preset = 0.0 dB  "
        ::= { iqmux33CmdEntry 36258 }


    iqmux33LoudCustomBlock1mbagcinfthr3 OBJECT-TYPE
        SYNTAX            INTEGER { disable(0), enable(1)  }
        MAX-ACCESS        read-write
        STATUS            current
        DESCRIPTION
                "CMNT: - Linear Acoustic MBAGC Block1 Index 3 InfThr
                 TYPE: - Checkbox
                 PAGE: - LoudCustom
                    mbagc infthr 3  cmdID= 36296  "
        ::= { iqmux33CmdEntry 36296 }


    iqmux33LoudCustomBlock1mbagcatk4 OBJECT-TYPE
        SYNTAX            INTEGER
        MAX-ACCESS        read-write
        STATUS            current
        DESCRIPTION
                "CMNT: - Linear Acoustic MBAGC Block1 Index 4 Attack
                 TYPE: - Number
                 PAGE: - LoudCustom
                    mbagc atk 4  cmdID= 36239
                    min= 0  max= 100  step= 1  format= %0.0f  div_scale= 1  preset= 24
                    Min = 0  Max = 100  Step = 1  Preset = 24  "
        ::= { iqmux33CmdEntry 36239 }


    iqmux33LoudCustomBlock1mbagcrel4 OBJECT-TYPE
        SYNTAX            INTEGER
        MAX-ACCESS        read-write
        STATUS            current
        DESCRIPTION
                "CMNT: - Linear Acoustic MBAGC Block1 Index 4 Release
                 TYPE: - Number
                 PAGE: - LoudCustom
                    mbagc rel 4  cmdID= 36229
                    min= 0  max= 100  step= 1  format= %0.0f  div_scale= 1  preset= 42
                    Min = 0  Max = 100  Step = 1  Preset = 42  "
        ::= { iqmux33CmdEntry 36229 }


    iqmux33LoudCustomBlock1mbagcthresh4 OBJECT-TYPE
        SYNTAX            INTEGER
        MAX-ACCESS        read-write
        STATUS            current
        DESCRIPTION
                "CMNT: - Linear Acoustic MBAGC Block1 Index 4 Threshold
                 TYPE: - Number
                 PAGE: - LoudCustom
                    mbagc thresh 4  cmdID= 36249
                    min= -120  max= 120  step= 1  format= %0.1f dB  div_scale= 10  preset= 0
                    Min = -12.0 dB  Max = 12.0 dB  Step = 0.1 dB  Preset = 0.0 dB  "
        ::= { iqmux33CmdEntry 36249 }


    iqmux33LoudCustomBlock1mbagcoutlev4 OBJECT-TYPE
        SYNTAX            INTEGER
        MAX-ACCESS        read-write
        STATUS            current
        DESCRIPTION
                "CMNT: - Linear Acoustic MBAGC Block1 Index 4 OutLevel
                 TYPE: - Number
                 PAGE: - LoudCustom
                    mbagc outlev 4  cmdID= 36269
                    min= -120  max= 120  step= 1  format= %0.1f dB  div_scale= 10  preset= 0
                    Min = -12.0 dB  Max = 12.0 dB  Step = 0.1 dB  Preset = 0.0 dB  "
        ::= { iqmux33CmdEntry 36269 }


    iqmux33LoudCustomBlock1mbagclimthresh4 OBJECT-TYPE
        SYNTAX            INTEGER
        MAX-ACCESS        read-write
        STATUS            current
        DESCRIPTION
                "CMNT: - Linear Acoustic MBAGC Block1 Index 4 Limit Threshold
                 TYPE: - Number
                 PAGE: - LoudCustom
                    mbagc limthresh 4  cmdID= 36259
                    min= 0  max= 180  step= 1  format= %0.1f dB  div_scale= 10  preset= 0
                    Min = 0.0 dB  Max = 18.0 dB  Step = 0.1 dB  Preset = 0.0 dB  "
        ::= { iqmux33CmdEntry 36259 }


    iqmux33LoudCustomBlock1mbagcinfthr4 OBJECT-TYPE
        SYNTAX            INTEGER { disable(0), enable(1)  }
        MAX-ACCESS        read-write
        STATUS            current
        DESCRIPTION
                "CMNT: - Linear Acoustic MBAGC Block1 Index 4 InfThr
                 TYPE: - Checkbox
                 PAGE: - LoudCustom
                    mbagc infthr 4  cmdID= 36297  "
        ::= { iqmux33CmdEntry 36297 }


    iqmux33LoudCustomBlock1mbagcatk5 OBJECT-TYPE
        SYNTAX            INTEGER
        MAX-ACCESS        read-write
        STATUS            current
        DESCRIPTION
                "CMNT: - Linear Acoustic MBAGC Block1 Index 5 Attack
                 TYPE: - Number
                 PAGE: - LoudCustom
                    mbagc atk 5  cmdID= 36240
                    min= 0  max= 100  step= 1  format= %0.0f  div_scale= 1  preset= 24
                    Min = 0  Max = 100  Step = 1  Preset = 24  "
        ::= { iqmux33CmdEntry 36240 }


    iqmux33LoudCustomBlock1mbagcrel5 OBJECT-TYPE
        SYNTAX            INTEGER
        MAX-ACCESS        read-write
        STATUS            current
        DESCRIPTION
                "CMNT: - Linear Acoustic MBAGC Block1 Index 5 Release
                 TYPE: - Number
                 PAGE: - LoudCustom
                    mbagc rel 5  cmdID= 36230
                    min= 0  max= 100  step= 1  format= %0.0f  div_scale= 1  preset= 42
                    Min = 0  Max = 100  Step = 1  Preset = 42  "
        ::= { iqmux33CmdEntry 36230 }


    iqmux33LoudCustomBlock1mbagcthresh5 OBJECT-TYPE
        SYNTAX            INTEGER
        MAX-ACCESS        read-write
        STATUS            current
        DESCRIPTION
                "CMNT: - Linear Acoustic MBAGC Block1 Index 5 Threshold
                 TYPE: - Number
                 PAGE: - LoudCustom
                    mbagc thresh 5  cmdID= 36250
                    min= -120  max= 120  step= 1  format= %0.1f dB  div_scale= 10  preset= 0
                    Min = -12.0 dB  Max = 12.0 dB  Step = 0.1 dB  Preset = 0.0 dB  "
        ::= { iqmux33CmdEntry 36250 }


    iqmux33LoudCustomBlock1mbagcoutlev5 OBJECT-TYPE
        SYNTAX            INTEGER
        MAX-ACCESS        read-write
        STATUS            current
        DESCRIPTION
                "CMNT: - Linear Acoustic MBAGC Block1 Index 5 OutLevel
                 TYPE: - Number
                 PAGE: - LoudCustom
                    mbagc outlev 5  cmdID= 36270
                    min= -120  max= 120  step= 1  format= %0.1f dB  div_scale= 10  preset= 0
                    Min = -12.0 dB  Max = 12.0 dB  Step = 0.1 dB  Preset = 0.0 dB  "
        ::= { iqmux33CmdEntry 36270 }


    iqmux33LoudCustomBlock1mbagclimthresh5 OBJECT-TYPE
        SYNTAX            INTEGER
        MAX-ACCESS        read-write
        STATUS            current
        DESCRIPTION
                "CMNT: - Linear Acoustic MBAGC Block1 Index 5 Limit Threshold
                 TYPE: - Number
                 PAGE: - LoudCustom
                    mbagc limthresh 5  cmdID= 36260
                    min= 0  max= 180  step= 1  format= %0.1f dB  div_scale= 10  preset= 0
                    Min = 0.0 dB  Max = 18.0 dB  Step = 0.1 dB  Preset = 0.0 dB  "
        ::= { iqmux33CmdEntry 36260 }


    iqmux33LoudCustomBlock1mbagcinfthr5 OBJECT-TYPE
        SYNTAX            INTEGER { disable(0), enable(1)  }
        MAX-ACCESS        read-write
        STATUS            current
        DESCRIPTION
                "CMNT: - Linear Acoustic MBAGC Block1 Index 5 InfThr
                 TYPE: - Checkbox
                 PAGE: - LoudCustom
                    mbagc infthr 5  cmdID= 36298  "
        ::= { iqmux33CmdEntry 36298 }


    iqmux33LoudCustomBlock1mbrange OBJECT-TYPE
        SYNTAX            INTEGER
        MAX-ACCESS        read-write
        STATUS            current
        DESCRIPTION
                "CMNT: - Linear Acoustic MB Block1 Range
                 TYPE: - Number
                 PAGE: - LoudCustom
                    mb range  cmdID= 36216
                    min= 0  max= 180  step= 1  format= %0.1f dB  div_scale= 5  preset= 90
                    Min = 0.0 dB  Max = 36.0 dB  Step = 0.2 dB  Preset = 18.0 dB  "
        ::= { iqmux33CmdEntry 36216 }


    iqmux33LoudCustomBlock1mbprogrise OBJECT-TYPE
        SYNTAX            INTEGER
        MAX-ACCESS        read-write
        STATUS            current
        DESCRIPTION
                "CMNT: - Linear Acoustic MB Block1 Progressive Rise
                 TYPE: - Number
                 PAGE: - LoudCustom
                    mb progrise  cmdID= 36214
                    min= 0  max= 100  step= 1  format= %0.0f  div_scale= 1  preset= 1
                    Min = 0  Max = 100  Step = 1  Preset = 1  "
        ::= { iqmux33CmdEntry 36214 }


    iqmux33LoudCustomBlock1mbsoftclip1 OBJECT-TYPE
        SYNTAX            INTEGER
        MAX-ACCESS        read-write
        STATUS            current
        DESCRIPTION
                "CMNT: - Linear Acoustic MB Block1 SoftClip1
                 TYPE: - Number
                 PAGE: - LoudCustom
                    mb softclip1  cmdID= 36218
                    min= 0  max= 180  step= 1  format= %0.1f dB  div_scale= 10  preset= 180
                    Min = 0.0 dB  Max = 18.0 dB  Step = 0.1 dB  Preset = 18.0 dB  "
        ::= { iqmux33CmdEntry 36218 }


    iqmux33LoudCustomBlock1mbsoftclip2 OBJECT-TYPE
        SYNTAX            INTEGER
        MAX-ACCESS        read-write
        STATUS            current
        DESCRIPTION
                "CMNT: - Linear Acoustic MB Block1 SoftClip2
                 TYPE: - Number
                 PAGE: - LoudCustom
                    mb softclip2  cmdID= 36220
                    min= 0  max= 180  step= 1  format= %0.1f dB  div_scale= 10  preset= 180
                    Min = 0.0 dB  Max = 18.0 dB  Step = 0.1 dB  Preset = 18.0 dB  "
        ::= { iqmux33CmdEntry 36220 }


    iqmux33LoudCustomBlock1mbratio OBJECT-TYPE
        SYNTAX            INTEGER
        MAX-ACCESS        read-write
        STATUS            current
        DESCRIPTION
                "CMNT: - Linear Acoustic MB Block1 Ratio
                 TYPE: - Number
                 PAGE: - LoudCustom
                    mb ratio  cmdID= 36222
                    min= 0  max= 100  step= 1  format= %0.0f  div_scale= 1  preset= 63
                    Min = 0  Max = 100  Step = 1  Preset = 63  "
        ::= { iqmux33CmdEntry 36222 }


    iqmux33LoudCustomBlock1mblimdrive OBJECT-TYPE
        SYNTAX            INTEGER
        MAX-ACCESS        read-write
        STATUS            current
        DESCRIPTION
                "CMNT: - Linear Acoustic MB Block1 OutLimDrive
                 TYPE: - Number
                 PAGE: - LoudCustom
                    mb lim drive  cmdID= 36224
                    min= -60  max= 60  step= 1  format= %0.1f dB  div_scale= 10  preset= -50
                    Min = -6.0 dB  Max = 6.0 dB  Step = 0.1 dB  Preset = -5.0 dB  "
        ::= { iqmux33CmdEntry 36224 }


    iqmux33LoudCustomBlock1CustomPreset OBJECT-TYPE
        SYNTAX            INTEGER {
                            valGeneral(0),
                            valLight(1),
                            valHeavy(2),
                            valLoud(3),
                            valLoudLimit(4),
                            valProtectionLimit(5),
                            valDefaults(6),
                            valCustom(7)
                            }
        MAX-ACCESS        read-write
        STATUS            current
        DESCRIPTION
                "CMNT: - Linear Acoustic Cust Preset 1
                 TYPE: - RadiobuttonList
                 PAGE: - LoudCustom
                    CustomPreset  cmdID= 36306
                    General  value= 0
                    Light  value= 1
                    Heavy  value= 2
                    Loud  value= 3
                    LoudLimit  value= 4
                    ProtectionLimit  value= 5
                    Defaults  value= 6
                    Custom  value= 7  "
        ::= { iqmux33CmdEntry 36306 }


    iqmux33LoudCustomBlock1Copyto2 OBJECT-TYPE
        SYNTAX            INTEGER { noAction(0),valCopyto2(1) }
        MAX-ACCESS        read-write
        STATUS            current
        DESCRIPTION
                "CMNT: - Linear Acoustic Cust Preset COPY 1 to 2
                 TYPE: - Button
                 PAGE: - LoudCustom
                    Copy to 2  cmdID= 36309
                    value= 1  "
        ::= { iqmux33CmdEntry 36309 }


    iqmux33LoudCustomBlock2Name OBJECT-TYPE
        SYNTAX            RollCallString
        MAX-ACCESS        read-write
        STATUS            current
        DESCRIPTION
                "CMNT: - Linear Acoustic MB Block2 Name
                 TYPE: - Editstring
                 PAGE: - LoudCustom
                    Name  cmdID= 36305
                    preset= Custom Block 2"
        ::= { iqmux33CmdEntry 36305 }


    iqmux33LoudCustomBlock2inagcfreeze OBJECT-TYPE
        SYNTAX            INTEGER
        MAX-ACCESS        read-write
        STATUS            current
        DESCRIPTION
                "CMNT: - Linear Acoustic InAGC Block2 Freeze Threshold
                 TYPE: - Number
                 PAGE: - LoudCustom
                    inagc freeze  cmdID= 36201
                    min= -180  max= 0  step= 1  format= %0.1f dBFS  div_scale= 2  preset= -62
                    Min = -90.0 dBFS  Max = 0.0 dBFS  Step = 0.5 dBFS  Preset = -31.0 dBFS  "
        ::= { iqmux33CmdEntry 36201 }


    iqmux33LoudCustomBlock2inagcgate OBJECT-TYPE
        SYNTAX            INTEGER
        MAX-ACCESS        read-write
        STATUS            current
        DESCRIPTION
                "CMNT: - Linear Acoustic InAGC Block2 Gate Threshold
                 TYPE: - Number
                 PAGE: - LoudCustom
                    inagc gate  cmdID= 36203
                    min= -180  max= 0  step= 1  format= %0.1f dBFS  div_scale= 2  preset= -42
                    Min = -90.0 dBFS  Max = 0.0 dBFS  Step = 0.5 dBFS  Preset = -21.0 dBFS  "
        ::= { iqmux33CmdEntry 36203 }


    iqmux33LoudCustomBlock2inagcratio OBJECT-TYPE
        SYNTAX            INTEGER
        MAX-ACCESS        read-write
        STATUS            current
        DESCRIPTION
                "CMNT: - Linear Acoustic InAGC Block2 Ratio
                 TYPE: - Number
                 PAGE: - LoudCustom
                    inagc ratio  cmdID= 36209
                    min= 0  max= 100  step= 1  format= %0.0f  div_scale= 1  preset= 91
                    Min = 0  Max = 100  Step = 1  Preset = 91  "
        ::= { iqmux33CmdEntry 36209 }


    iqmux33LoudCustomBlock2inagcrange OBJECT-TYPE
        SYNTAX            INTEGER
        MAX-ACCESS        read-write
        STATUS            current
        DESCRIPTION
                "CMNT: - Linear Acoustic InAGC Block2 Range
                 TYPE: - Number
                 PAGE: - LoudCustom
                    inagc range  cmdID= 36207
                    min= 0  max= 180  step= 1  format= %0.1f dB  div_scale= 5  preset= 125
                    Min = 0.0 dB  Max = 36.0 dB  Step = 0.2 dB  Preset = 25.0 dB  "
        ::= { iqmux33CmdEntry 36207 }


    iqmux33LoudCustomBlock2inagcthresh OBJECT-TYPE
        SYNTAX            INTEGER
        MAX-ACCESS        read-write
        STATUS            current
        DESCRIPTION
                "CMNT: - Linear Acoustic InAGC Block2 Threshold
                 TYPE: - Number
                 PAGE: - LoudCustom
                    inagc thresh  cmdID= 36205
                    min= -180  max= 0  step= 1  format= %0.1f dBFS  div_scale= 10  preset= -140
                    Min = -18.0 dBFS  Max = 0.0 dBFS  Step = 0.1 dBFS  Preset = -14.0 dBFS  "
        ::= { iqmux33CmdEntry 36205 }


    iqmux33LoudCustomBlock2inagcattack OBJECT-TYPE
        SYNTAX            INTEGER
        MAX-ACCESS        read-write
        STATUS            current
        DESCRIPTION
                "CMNT: - Linear Acoustic InAGC Block2 Attack
                 TYPE: - Number
                 PAGE: - LoudCustom
                    inagc attack  cmdID= 36211
                    min= 1  max= 100  step= 1  format= %0.0f  div_scale= 1  preset= 24
                    Min = 1  Max = 100  Step = 1  Preset = 24  "
        ::= { iqmux33CmdEntry 36211 }


    iqmux33LoudCustomBlock2inagcrelease OBJECT-TYPE
        SYNTAX            INTEGER
        MAX-ACCESS        read-write
        STATUS            current
        DESCRIPTION
                "CMNT: - Linear Acoustic InAGC Block2 Release
                 TYPE: - Number
                 PAGE: - LoudCustom
                    inagc release  cmdID= 36213
                    min= 1  max= 100  step= 1  format= %0.0f  div_scale= 1  preset= 42
                    Min = 1  Max = 100  Step = 1  Preset = 42  "
        ::= { iqmux33CmdEntry 36213 }


    iqmux33LoudCustomBlock2peqfreq1 OBJECT-TYPE
        SYNTAX            INTEGER
        MAX-ACCESS        read-write
        STATUS            current
        DESCRIPTION
                "CMNT: - Linear Acoustic PEQ Block2 Index 1 Frequency
                 TYPE: - Number
                 PAGE: - LoudCustom
                    peq freq 1  cmdID= 36279
                    min= 20  max= 20000  step= 1  format= %0.0f Hz  div_scale= 1  preset= 1000
                    Min = 20 Hz  Max = 20000 Hz  Step = 1 Hz  Preset = 1000 Hz  "
        ::= { iqmux33CmdEntry 36279 }


    iqmux33LoudCustomBlock2peqq1 OBJECT-TYPE
        SYNTAX            INTEGER
        MAX-ACCESS        read-write
        STATUS            current
        DESCRIPTION
                "CMNT: - Linear Acoustic PEQ Block2 Index 1 Q
                 TYPE: - Number
                 PAGE: - LoudCustom
                    peq q 1  cmdID= 36285
                    min= 1  max= 200  step= 1  format= %0.2f  div_scale= 20  preset= 20
                    Min = 0.05  Max = 10.00  Step = 0.05  Preset = 1.00  "
        ::= { iqmux33CmdEntry 36285 }


    iqmux33LoudCustomBlock2peqlevel1 OBJECT-TYPE
        SYNTAX            INTEGER
        MAX-ACCESS        read-write
        STATUS            current
        DESCRIPTION
                "CMNT: - Linear Acoustic PEQ Block2 Index 1 Level
                 TYPE: - Number
                 PAGE: - LoudCustom
                    peq level 1  cmdID= 36291
                    min= -90  max= 90  step= 1  format= %0.1f dB  div_scale= 5  preset= 0
                    Min = -18.0 dB  Max = 18.0 dB  Step = 0.2 dB  Preset = 0.0 dB  "
        ::= { iqmux33CmdEntry 36291 }


    iqmux33LoudCustomBlock2peqfreq2 OBJECT-TYPE
        SYNTAX            INTEGER
        MAX-ACCESS        read-write
        STATUS            current
        DESCRIPTION
                "CMNT: - Linear Acoustic PEQ Block2 Index 2 Frequency
                 TYPE: - Number
                 PAGE: - LoudCustom
                    peq freq 2  cmdID= 36280
                    min= 20  max= 20000  step= 1  format= %0.0f Hz  div_scale= 1  preset= 1000
                    Min = 20 Hz  Max = 20000 Hz  Step = 1 Hz  Preset = 1000 Hz  "
        ::= { iqmux33CmdEntry 36280 }


    iqmux33LoudCustomBlock2peqq2 OBJECT-TYPE
        SYNTAX            INTEGER
        MAX-ACCESS        read-write
        STATUS            current
        DESCRIPTION
                "CMNT: - Linear Acoustic PEQ Block2 Index 2 Q
                 TYPE: - Number
                 PAGE: - LoudCustom
                    peq q 2  cmdID= 36286
                    min= 1  max= 200  step= 1  format= %0.2f  div_scale= 20  preset= 20
                    Min = 0.05  Max = 10.00  Step = 0.05  Preset = 1.00  "
        ::= { iqmux33CmdEntry 36286 }


    iqmux33LoudCustomBlock2peqlevel2 OBJECT-TYPE
        SYNTAX            INTEGER
        MAX-ACCESS        read-write
        STATUS            current
        DESCRIPTION
                "CMNT: - Linear Acoustic PEQ Block2 Index 2 Level
                 TYPE: - Number
                 PAGE: - LoudCustom
                    peq level 2  cmdID= 36292
                    min= -90  max= 90  step= 1  format= %0.1f dB  div_scale= 5  preset= 0
                    Min = -18.0 dB  Max = 18.0 dB  Step = 0.2 dB  Preset = 0.0 dB  "
        ::= { iqmux33CmdEntry 36292 }


    iqmux33LoudCustomBlock2peqfreq3 OBJECT-TYPE
        SYNTAX            INTEGER
        MAX-ACCESS        read-write
        STATUS            current
        DESCRIPTION
                "CMNT: - Linear Acoustic PEQ Block2 Index 3 Frequency
                 TYPE: - Number
                 PAGE: - LoudCustom
                    peq freq 3  cmdID= 36281
                    min= 20  max= 20000  step= 1  format= %0.0f Hz  div_scale= 1  preset= 1000
                    Min = 20 Hz  Max = 20000 Hz  Step = 1 Hz  Preset = 1000 Hz  "
        ::= { iqmux33CmdEntry 36281 }


    iqmux33LoudCustomBlock2peqq3 OBJECT-TYPE
        SYNTAX            INTEGER
        MAX-ACCESS        read-write
        STATUS            current
        DESCRIPTION
                "CMNT: - Linear Acoustic PEQ Block2 Index 3 Q
                 TYPE: - Number
                 PAGE: - LoudCustom
                    peq q 3  cmdID= 36287
                    min= 1  max= 200  step= 1  format= %0.2f  div_scale= 20  preset= 20
                    Min = 0.05  Max = 10.00  Step = 0.05  Preset = 1.00  "
        ::= { iqmux33CmdEntry 36287 }


    iqmux33LoudCustomBlock2peqlevel3 OBJECT-TYPE
        SYNTAX            INTEGER
        MAX-ACCESS        read-write
        STATUS            current
        DESCRIPTION
                "CMNT: - Linear Acoustic PEQ Block2 Index 3 Level
                 TYPE: - Number
                 PAGE: - LoudCustom
                    peq level 3  cmdID= 36293
                    min= -90  max= 90  step= 1  format= %0.1f dB  div_scale= 5  preset= 0
                    Min = -18.0 dB  Max = 18.0 dB  Step = 0.2 dB  Preset = 0.0 dB  "
        ::= { iqmux33CmdEntry 36293 }


    iqmux33LoudCustomBlock2mbagcatk1 OBJECT-TYPE
        SYNTAX            INTEGER
        MAX-ACCESS        read-write
        STATUS            current
        DESCRIPTION
                "CMNT: - Linear Acoustic MBAGC Block2 Index 1 Attack
                 TYPE: - Number
                 PAGE: - LoudCustom
                    mbagc atk 1  cmdID= 36241
                    min= 0  max= 100  step= 1  format= %0.0f  div_scale= 1  preset= 24
                    Min = 0  Max = 100  Step = 1  Preset = 24  "
        ::= { iqmux33CmdEntry 36241 }


    iqmux33LoudCustomBlock2mbagcrel1 OBJECT-TYPE
        SYNTAX            INTEGER
        MAX-ACCESS        read-write
        STATUS            current
        DESCRIPTION
                "CMNT: - Linear Acoustic MBAGC Block2 Index 1 Release
                 TYPE: - Number
                 PAGE: - LoudCustom
                    mbagc rel 1  cmdID= 36231
                    min= 0  max= 100  step= 1  format= %0.0f  div_scale= 1  preset= 42
                    Min = 0  Max = 100  Step = 1  Preset = 42  "
        ::= { iqmux33CmdEntry 36231 }


    iqmux33LoudCustomBlock2mbagcthresh1 OBJECT-TYPE
        SYNTAX            INTEGER
        MAX-ACCESS        read-write
        STATUS            current
        DESCRIPTION
                "CMNT: - Linear Acoustic MBAGC Block2 Index 1 Threshold
                 TYPE: - Number
                 PAGE: - LoudCustom
                    mbagc thresh 1  cmdID= 36251
                    min= -120  max= 120  step= 1  format= %0.1f dB  div_scale= 10  preset= 0
                    Min = -12.0 dB  Max = 12.0 dB  Step = 0.1 dB  Preset = 0.0 dB  "
        ::= { iqmux33CmdEntry 36251 }


    iqmux33LoudCustomBlock2mbagcoutlev1 OBJECT-TYPE
        SYNTAX            INTEGER
        MAX-ACCESS        read-write
        STATUS            current
        DESCRIPTION
                "CMNT: - Linear Acoustic MBAGC Block2 Index 1 OutLevel
                 TYPE: - Number
                 PAGE: - LoudCustom
                    mbagc outlev 1  cmdID= 36271
                    min= -120  max= 120  step= 1  format= %0.1f dB  div_scale= 10  preset= 0
                    Min = -12.0 dB  Max = 12.0 dB  Step = 0.1 dB  Preset = 0.0 dB  "
        ::= { iqmux33CmdEntry 36271 }


    iqmux33LoudCustomBlock2mbagclimthresh1 OBJECT-TYPE
        SYNTAX            INTEGER
        MAX-ACCESS        read-write
        STATUS            current
        DESCRIPTION
                "CMNT: - Linear Acoustic MBAGC Block2 Index 1 Limit Threshold
                 TYPE: - Number
                 PAGE: - LoudCustom
                    mbagc limthresh 1  cmdID= 36261
                    min= 0  max= 180  step= 1  format= %0.1f dB  div_scale= 10  preset= 0
                    Min = 0.0 dB  Max = 18.0 dB  Step = 0.1 dB  Preset = 0.0 dB  "
        ::= { iqmux33CmdEntry 36261 }


    iqmux33LoudCustomBlock2mbagcinfthr1 OBJECT-TYPE
        SYNTAX            INTEGER { disable(0), enable(1)  }
        MAX-ACCESS        read-write
        STATUS            current
        DESCRIPTION
                "CMNT: - Linear Acoustic MBAGC Block2 Index 1 InfThr
                 TYPE: - Checkbox
                 PAGE: - LoudCustom
                    mbagc infthr 1  cmdID= 36299  "
        ::= { iqmux33CmdEntry 36299 }


    iqmux33LoudCustomBlock2mbagcatk2 OBJECT-TYPE
        SYNTAX            INTEGER
        MAX-ACCESS        read-write
        STATUS            current
        DESCRIPTION
                "CMNT: - Linear Acoustic MBAGC Block2 Index 2 Attack
                 TYPE: - Number
                 PAGE: - LoudCustom
                    mbagc atk 2  cmdID= 36242
                    min= 0  max= 100  step= 1  format= %0.0f  div_scale= 1  preset= 24
                    Min = 0  Max = 100  Step = 1  Preset = 24  "
        ::= { iqmux33CmdEntry 36242 }


    iqmux33LoudCustomBlock2mbagcrel2 OBJECT-TYPE
        SYNTAX            INTEGER
        MAX-ACCESS        read-write
        STATUS            current
        DESCRIPTION
                "CMNT: - Linear Acoustic MBAGC Block2 Index 2 Release
                 TYPE: - Number
                 PAGE: - LoudCustom
                    mbagc rel 2  cmdID= 36232
                    min= 0  max= 100  step= 1  format= %0.0f  div_scale= 1  preset= 42
                    Min = 0  Max = 100  Step = 1  Preset = 42  "
        ::= { iqmux33CmdEntry 36232 }


    iqmux33LoudCustomBlock2mbagcthresh2 OBJECT-TYPE
        SYNTAX            INTEGER
        MAX-ACCESS        read-write
        STATUS            current
        DESCRIPTION
                "CMNT: - Linear Acoustic MBAGC Block2 Index 2 Threshold
                 TYPE: - Number
                 PAGE: - LoudCustom
                    mbagc thresh 2  cmdID= 36252
                    min= -120  max= 120  step= 1  format= %0.1f dB  div_scale= 10  preset= 0
                    Min = -12.0 dB  Max = 12.0 dB  Step = 0.1 dB  Preset = 0.0 dB  "
        ::= { iqmux33CmdEntry 36252 }


    iqmux33LoudCustomBlock2mbagcoutlev2 OBJECT-TYPE
        SYNTAX            INTEGER
        MAX-ACCESS        read-write
        STATUS            current
        DESCRIPTION
                "CMNT: - Linear Acoustic MBAGC Block2 Index 2 OutLevel
                 TYPE: - Number
                 PAGE: - LoudCustom
                    mbagc outlev 2  cmdID= 36272
                    min= -120  max= 120  step= 1  format= %0.1f dB  div_scale= 10  preset= 0
                    Min = -12.0 dB  Max = 12.0 dB  Step = 0.1 dB  Preset = 0.0 dB  "
        ::= { iqmux33CmdEntry 36272 }


    iqmux33LoudCustomBlock2mbagclimthresh2 OBJECT-TYPE
        SYNTAX            INTEGER
        MAX-ACCESS        read-write
        STATUS            current
        DESCRIPTION
                "CMNT: - Linear Acoustic MBAGC Block2 Index 2 Limit Threshold
                 TYPE: - Number
                 PAGE: - LoudCustom
                    mbagc limthresh 2  cmdID= 36262
                    min= 0  max= 180  step= 1  format= %0.1f dB  div_scale= 10  preset= 0
                    Min = 0.0 dB  Max = 18.0 dB  Step = 0.1 dB  Preset = 0.0 dB  "
        ::= { iqmux33CmdEntry 36262 }


    iqmux33LoudCustomBlock2mbagcinfthr2 OBJECT-TYPE
        SYNTAX            INTEGER { disable(0), enable(1)  }
        MAX-ACCESS        read-write
        STATUS            current
        DESCRIPTION
                "CMNT: - Linear Acoustic MBAGC Block2 Index 2 InfThr
                 TYPE: - Checkbox
                 PAGE: - LoudCustom
                    mbagc infthr 2  cmdID= 36300  "
        ::= { iqmux33CmdEntry 36300 }


    iqmux33LoudCustomBlock2mbagcatk3 OBJECT-TYPE
        SYNTAX            INTEGER
        MAX-ACCESS        read-write
        STATUS            current
        DESCRIPTION
                "CMNT: - Linear Acoustic MBAGC Block2 Index 3 Attack
                 TYPE: - Number
                 PAGE: - LoudCustom
                    mbagc atk 3  cmdID= 36243
                    min= 0  max= 100  step= 1  format= %0.0f  div_scale= 1  preset= 24
                    Min = 0  Max = 100  Step = 1  Preset = 24  "
        ::= { iqmux33CmdEntry 36243 }


    iqmux33LoudCustomBlock2mbagcrel3 OBJECT-TYPE
        SYNTAX            INTEGER
        MAX-ACCESS        read-write
        STATUS            current
        DESCRIPTION
                "CMNT: - Linear Acoustic MBAGC Block2 Index 3 Release
                 TYPE: - Number
                 PAGE: - LoudCustom
                    mbagc rel 3  cmdID= 36233
                    min= 0  max= 100  step= 1  format= %0.0f  div_scale= 1  preset= 42
                    Min = 0  Max = 100  Step = 1  Preset = 42  "
        ::= { iqmux33CmdEntry 36233 }


    iqmux33LoudCustomBlock2mbagcthresh3 OBJECT-TYPE
        SYNTAX            INTEGER
        MAX-ACCESS        read-write
        STATUS            current
        DESCRIPTION
                "CMNT: - Linear Acoustic MBAGC Block2 Index 3 Threshold
                 TYPE: - Number
                 PAGE: - LoudCustom
                    mbagc thresh 3  cmdID= 36253
                    min= -120  max= 120  step= 1  format= %0.1f dB  div_scale= 10  preset= 0
                    Min = -12.0 dB  Max = 12.0 dB  Step = 0.1 dB  Preset = 0.0 dB  "
        ::= { iqmux33CmdEntry 36253 }


    iqmux33LoudCustomBlock2mbagcoutlev3 OBJECT-TYPE
        SYNTAX            INTEGER
        MAX-ACCESS        read-write
        STATUS            current
        DESCRIPTION
                "CMNT: - Linear Acoustic MBAGC Block2 Index 3 OutLevel
                 TYPE: - Number
                 PAGE: - LoudCustom
                    mbagc outlev 3  cmdID= 36273
                    min= -120  max= 120  step= 1  format= %0.1f dB  div_scale= 10  preset= 0
                    Min = -12.0 dB  Max = 12.0 dB  Step = 0.1 dB  Preset = 0.0 dB  "
        ::= { iqmux33CmdEntry 36273 }


    iqmux33LoudCustomBlock2mbagclimthresh3 OBJECT-TYPE
        SYNTAX            INTEGER
        MAX-ACCESS        read-write
        STATUS            current
        DESCRIPTION
                "CMNT: - Linear Acoustic MBAGC Block2 Index 3 Limit Threshold
                 TYPE: - Number
                 PAGE: - LoudCustom
                    mbagc limthresh 3  cmdID= 36263
                    min= 0  max= 180  step= 1  format= %0.1f dB  div_scale= 10  preset= 0
                    Min = 0.0 dB  Max = 18.0 dB  Step = 0.1 dB  Preset = 0.0 dB  "
        ::= { iqmux33CmdEntry 36263 }


    iqmux33LoudCustomBlock2mbagcinfthr3 OBJECT-TYPE
        SYNTAX            INTEGER { disable(0), enable(1)  }
        MAX-ACCESS        read-write
        STATUS            current
        DESCRIPTION
                "CMNT: - Linear Acoustic MBAGC Block2 Index 3 InfThr
                 TYPE: - Checkbox
                 PAGE: - LoudCustom
                    mbagc infthr 3  cmdID= 36301  "
        ::= { iqmux33CmdEntry 36301 }


    iqmux33LoudCustomBlock2mbagcatk4 OBJECT-TYPE
        SYNTAX            INTEGER
        MAX-ACCESS        read-write
        STATUS            current
        DESCRIPTION
                "CMNT: - Linear Acoustic MBAGC Block2 Index 4 Attack
                 TYPE: - Number
                 PAGE: - LoudCustom
                    mbagc atk 4  cmdID= 36244
                    min= 0  max= 100  step= 1  format= %0.0f  div_scale= 1  preset= 24
                    Min = 0  Max = 100  Step = 1  Preset = 24  "
        ::= { iqmux33CmdEntry 36244 }


    iqmux33LoudCustomBlock2mbagcrel4 OBJECT-TYPE
        SYNTAX            INTEGER
        MAX-ACCESS        read-write
        STATUS            current
        DESCRIPTION
                "CMNT: - Linear Acoustic MBAGC Block2 Index 4 Release
                 TYPE: - Number
                 PAGE: - LoudCustom
                    mbagc rel 4  cmdID= 36234
                    min= 0  max= 100  step= 1  format= %0.0f  div_scale= 1  preset= 42
                    Min = 0  Max = 100  Step = 1  Preset = 42  "
        ::= { iqmux33CmdEntry 36234 }


    iqmux33LoudCustomBlock2mbagcthresh4 OBJECT-TYPE
        SYNTAX            INTEGER
        MAX-ACCESS        read-write
        STATUS            current
        DESCRIPTION
                "CMNT: - Linear Acoustic MBAGC Block2 Index 4 Threshold
                 TYPE: - Number
                 PAGE: - LoudCustom
                    mbagc thresh 4  cmdID= 36254
                    min= -120  max= 120  step= 1  format= %0.1f dB  div_scale= 10  preset= 0
                    Min = -12.0 dB  Max = 12.0 dB  Step = 0.1 dB  Preset = 0.0 dB  "
        ::= { iqmux33CmdEntry 36254 }


    iqmux33LoudCustomBlock2mbagcoutlev4 OBJECT-TYPE
        SYNTAX            INTEGER
        MAX-ACCESS        read-write
        STATUS            current
        DESCRIPTION
                "CMNT: - Linear Acoustic MBAGC Block2 Index 4 OutLevel
                 TYPE: - Number
                 PAGE: - LoudCustom
                    mbagc outlev 4  cmdID= 36274
                    min= -120  max= 120  step= 1  format= %0.1f dB  div_scale= 10  preset= 0
                    Min = -12.0 dB  Max = 12.0 dB  Step = 0.1 dB  Preset = 0.0 dB  "
        ::= { iqmux33CmdEntry 36274 }


    iqmux33LoudCustomBlock2mbagclimthresh4 OBJECT-TYPE
        SYNTAX            INTEGER
        MAX-ACCESS        read-write
        STATUS            current
        DESCRIPTION
                "CMNT: - Linear Acoustic MBAGC Block2 Index 4 Limit Threshold
                 TYPE: - Number
                 PAGE: - LoudCustom
                    mbagc limthresh 4  cmdID= 36264
                    min= 0  max= 180  step= 1  format= %0.1f dB  div_scale= 10  preset= 0
                    Min = 0.0 dB  Max = 18.0 dB  Step = 0.1 dB  Preset = 0.0 dB  "
        ::= { iqmux33CmdEntry 36264 }


    iqmux33LoudCustomBlock2mbagcinfthr4 OBJECT-TYPE
        SYNTAX            INTEGER { disable(0), enable(1)  }
        MAX-ACCESS        read-write
        STATUS            current
        DESCRIPTION
                "CMNT: - Linear Acoustic MBAGC Block2 Index 4 InfThr
                 TYPE: - Checkbox
                 PAGE: - LoudCustom
                    mbagc infthr 4  cmdID= 36302  "
        ::= { iqmux33CmdEntry 36302 }


    iqmux33LoudCustomBlock2mbagcatk5 OBJECT-TYPE
        SYNTAX            INTEGER
        MAX-ACCESS        read-write
        STATUS            current
        DESCRIPTION
                "CMNT: - Linear Acoustic MBAGC Block2 Index 5 Attack
                 TYPE: - Number
                 PAGE: - LoudCustom
                    mbagc atk 5  cmdID= 36245
                    min= 0  max= 100  step= 1  format= %0.0f  div_scale= 1  preset= 24
                    Min = 0  Max = 100  Step = 1  Preset = 24  "
        ::= { iqmux33CmdEntry 36245 }


    iqmux33LoudCustomBlock2mbagcrel5 OBJECT-TYPE
        SYNTAX            INTEGER
        MAX-ACCESS        read-write
        STATUS            current
        DESCRIPTION
                "CMNT: - Linear Acoustic MBAGC Block2 Index 5 Release
                 TYPE: - Number
                 PAGE: - LoudCustom
                    mbagc rel 5  cmdID= 36235
                    min= 0  max= 100  step= 1  format= %0.0f  div_scale= 1  preset= 42
                    Min = 0  Max = 100  Step = 1  Preset = 42  "
        ::= { iqmux33CmdEntry 36235 }


    iqmux33LoudCustomBlock2mbagcthresh5 OBJECT-TYPE
        SYNTAX            INTEGER
        MAX-ACCESS        read-write
        STATUS            current
        DESCRIPTION
                "CMNT: - Linear Acoustic MBAGC Block2 Index 5 Threshold
                 TYPE: - Number
                 PAGE: - LoudCustom
                    mbagc thresh 5  cmdID= 36255
                    min= -120  max= 120  step= 1  format= %0.1f dB  div_scale= 10  preset= 0
                    Min = -12.0 dB  Max = 12.0 dB  Step = 0.1 dB  Preset = 0.0 dB  "
        ::= { iqmux33CmdEntry 36255 }


    iqmux33LoudCustomBlock2mbagcoutlev5 OBJECT-TYPE
        SYNTAX            INTEGER
        MAX-ACCESS        read-write
        STATUS            current
        DESCRIPTION
                "CMNT: - Linear Acoustic MBAGC Block2 Index 5 OutLevel
                 TYPE: - Number
                 PAGE: - LoudCustom
                    mbagc outlev 5  cmdID= 36275
                    min= -120  max= 120  step= 1  format= %0.1f dB  div_scale= 10  preset= 0
                    Min = -12.0 dB  Max = 12.0 dB  Step = 0.1 dB  Preset = 0.0 dB  "
        ::= { iqmux33CmdEntry 36275 }


    iqmux33LoudCustomBlock2mbagclimthresh5 OBJECT-TYPE
        SYNTAX            INTEGER
        MAX-ACCESS        read-write
        STATUS            current
        DESCRIPTION
                "CMNT: - Linear Acoustic MBAGC Block2 Index 5 Limit Threshold
                 TYPE: - Number
                 PAGE: - LoudCustom
                    mbagc limthresh 5  cmdID= 36265
                    min= 0  max= 180  step= 1  format= %0.1f dB  div_scale= 10  preset= 0
                    Min = 0.0 dB  Max = 18.0 dB  Step = 0.1 dB  Preset = 0.0 dB  "
        ::= { iqmux33CmdEntry 36265 }


    iqmux33LoudCustomBlock2mbagcinfthr5 OBJECT-TYPE
        SYNTAX            INTEGER { disable(0), enable(1)  }
        MAX-ACCESS        read-write
        STATUS            current
        DESCRIPTION
                "CMNT: - Linear Acoustic MBAGC Block2 Index 5 InfThr
                 TYPE: - Checkbox
                 PAGE: - LoudCustom
                    mbagc infthr 5  cmdID= 36303  "
        ::= { iqmux33CmdEntry 36303 }


    iqmux33LoudCustomBlock2mbrange OBJECT-TYPE
        SYNTAX            INTEGER
        MAX-ACCESS        read-write
        STATUS            current
        DESCRIPTION
                "CMNT: - Linear Acoustic MB Block2 Range
                 TYPE: - Number
                 PAGE: - LoudCustom
                    mb range  cmdID= 36217
                    min= 0  max= 180  step= 1  format= %0.1f dB  div_scale= 5  preset= 90
                    Min = 0.0 dB  Max = 36.0 dB  Step = 0.2 dB  Preset = 18.0 dB  "
        ::= { iqmux33CmdEntry 36217 }


    iqmux33LoudCustomBlock2mbprogrise OBJECT-TYPE
        SYNTAX            INTEGER
        MAX-ACCESS        read-write
        STATUS            current
        DESCRIPTION
                "CMNT: - Linear Acoustic MB Block2 Progressive Rise
                 TYPE: - Number
                 PAGE: - LoudCustom
                    mb progrise  cmdID= 36215
                    min= 0  max= 100  step= 1  format= %0.0f  div_scale= 1  preset= 1
                    Min = 0  Max = 100  Step = 1  Preset = 1  "
        ::= { iqmux33CmdEntry 36215 }


    iqmux33LoudCustomBlock2mbsoftclip1 OBJECT-TYPE
        SYNTAX            INTEGER
        MAX-ACCESS        read-write
        STATUS            current
        DESCRIPTION
                "CMNT: - Linear Acoustic MB Block2 SoftClip1
                 TYPE: - Number
                 PAGE: - LoudCustom
                    mb softclip1  cmdID= 36219
                    min= 0  max= 180  step= 1  format= %0.1f dB  div_scale= 10  preset= 180
                    Min = 0.0 dB  Max = 18.0 dB  Step = 0.1 dB  Preset = 18.0 dB  "
        ::= { iqmux33CmdEntry 36219 }


    iqmux33LoudCustomBlock2mbsoftclip2 OBJECT-TYPE
        SYNTAX            INTEGER
        MAX-ACCESS        read-write
        STATUS            current
        DESCRIPTION
                "CMNT: - Linear Acoustic MB Block2 SoftClip2
                 TYPE: - Number
                 PAGE: - LoudCustom
                    mb softclip2  cmdID= 36221
                    min= 0  max= 180  step= 1  format= %0.1f dB  div_scale= 10  preset= 180
                    Min = 0.0 dB  Max = 18.0 dB  Step = 0.1 dB  Preset = 18.0 dB  "
        ::= { iqmux33CmdEntry 36221 }


    iqmux33LoudCustomBlock2mbratio OBJECT-TYPE
        SYNTAX            INTEGER
        MAX-ACCESS        read-write
        STATUS            current
        DESCRIPTION
                "CMNT: - Linear Acoustic MB Block2 Ratio
                 TYPE: - Number
                 PAGE: - LoudCustom
                    mb ratio  cmdID= 36223
                    min= 0  max= 100  step= 1  format= %0.0f  div_scale= 1  preset= 63
                    Min = 0  Max = 100  Step = 1  Preset = 63  "
        ::= { iqmux33CmdEntry 36223 }


    iqmux33LoudCustomBlock2mblimdrive OBJECT-TYPE
        SYNTAX            INTEGER
        MAX-ACCESS        read-write
        STATUS            current
        DESCRIPTION
                "CMNT: - Linear Acoustic MB Block2 OutLimDrive
                 TYPE: - Number
                 PAGE: - LoudCustom
                    mb lim drive  cmdID= 36225
                    min= -60  max= 60  step= 1  format= %0.1f dB  div_scale= 10  preset= -50
                    Min = -6.0 dB  Max = 6.0 dB  Step = 0.1 dB  Preset = -5.0 dB  "
        ::= { iqmux33CmdEntry 36225 }


    iqmux33LoudCustomBlock2CustomPreset OBJECT-TYPE
        SYNTAX            INTEGER {
                            valGeneral(0),
                            valLight(1),
                            valHeavy(2),
                            valLoud(3),
                            valLoudLimit(4),
                            valProtectionLimit(5),
                            valDefaults(6),
                            valCustom(7)
                            }
        MAX-ACCESS        read-write
        STATUS            current
        DESCRIPTION
                "CMNT: - Linear Acoustic Cust Preset 2
                 TYPE: - RadiobuttonList
                 PAGE: - LoudCustom
                    CustomPreset  cmdID= 36307
                    General  value= 0
                    Light  value= 1
                    Heavy  value= 2
                    Loud  value= 3
                    LoudLimit  value= 4
                    ProtectionLimit  value= 5
                    Defaults  value= 6
                    Custom  value= 7  "
        ::= { iqmux33CmdEntry 36307 }


    iqmux33LoudCustomBlock2Copyto1 OBJECT-TYPE
        SYNTAX            INTEGER { noAction(0),valCopyto1(1) }
        MAX-ACCESS        read-write
        STATUS            current
        DESCRIPTION
                "CMNT: - Linear Acoustic Cust Preset COPY 2 to 1
                 TYPE: - Button
                 PAGE: - LoudCustom
                    Copy to 1  cmdID= 36308
                    value= 1  "
        ::= { iqmux33CmdEntry 36308 }


    iqmux33LoudCustomMasterLevelCustom1 OBJECT-TYPE
        SYNTAX            INTEGER
        MAX-ACCESS        read-write
        STATUS            current
        DESCRIPTION
                "CMNT: - Linear Acoustic CUSTOM1 Master Level 
                 TYPE: - Number
                 PAGE: - LoudCustom
                    Custom1  cmdID= 36328
                    min= -310  max= 0  step= 1  format= %0.1f dB  div_scale= 10  preset= -110
                    Min = -31.0 dB  Max = 0.0 dB  Step = 0.1 dB  Preset = -11.0 dB  "
        ::= { iqmux33CmdEntry 36328 }


    iqmux33LoudCustomMasterLevelCustom2 OBJECT-TYPE
        SYNTAX            INTEGER
        MAX-ACCESS        read-write
        STATUS            current
        DESCRIPTION
                "CMNT: - Linear Acoustic CUSTOM2 Master Level 
                 TYPE: - Number
                 PAGE: - LoudCustom
                    Custom2  cmdID= 36329
                    min= -310  max= 0  step= 1  format= %0.1f dB  div_scale= 10  preset= -110
                    Min = -31.0 dB  Max = 0.0 dB  Step = 0.1 dB  Preset = -11.0 dB  "
        ::= { iqmux33CmdEntry 36329 }


    iqmux33LoudCustomMasterLevelGen51 OBJECT-TYPE
        SYNTAX            INTEGER
        MAX-ACCESS        read-write
        STATUS            current
        DESCRIPTION
                "CMNT: - Linear Acoustic 5.1 Master Level General
                 TYPE: - Number
                 PAGE: - LoudCustom
                    Gen_51  cmdID= 36310
                    min= -310  max= 0  step= 1  format= %0.1f dB  div_scale= 10  preset= -110
                    Min = -31.0 dB  Max = 0.0 dB  Step = 0.1 dB  Preset = -11.0 dB  "
        ::= { iqmux33CmdEntry 36310 }


    iqmux33LoudCustomMasterLevelLight51 OBJECT-TYPE
        SYNTAX            INTEGER
        MAX-ACCESS        read-write
        STATUS            current
        DESCRIPTION
                "CMNT: - Linear Acoustic 5.1 Master Level Light
                 TYPE: - Number
                 PAGE: - LoudCustom
                    Light_51  cmdID= 36311
                    min= -310  max= 0  step= 1  format= %0.1f dB  div_scale= 10  preset= -110
                    Min = -31.0 dB  Max = 0.0 dB  Step = 0.1 dB  Preset = -11.0 dB  "
        ::= { iqmux33CmdEntry 36311 }


    iqmux33LoudCustomMasterLevelHeavy51 OBJECT-TYPE
        SYNTAX            INTEGER
        MAX-ACCESS        read-write
        STATUS            current
        DESCRIPTION
                "CMNT: - Linear Acoustic 5.1 Master Level Heavy
                 TYPE: - Number
                 PAGE: - LoudCustom
                    Heavy_51  cmdID= 36312
                    min= -310  max= 0  step= 1  format= %0.1f dB  div_scale= 10  preset= -110
                    Min = -31.0 dB  Max = 0.0 dB  Step = 0.1 dB  Preset = -11.0 dB  "
        ::= { iqmux33CmdEntry 36312 }


    iqmux33LoudCustomMasterLevelLoud51 OBJECT-TYPE
        SYNTAX            INTEGER
        MAX-ACCESS        read-write
        STATUS            current
        DESCRIPTION
                "CMNT: - Linear Acoustic 5.1 Master Level Loud
                 TYPE: - Number
                 PAGE: - LoudCustom
                    Loud_51  cmdID= 36313
                    min= -310  max= 0  step= 1  format= %0.1f dB  div_scale= 10  preset= -110
                    Min = -31.0 dB  Max = 0.0 dB  Step = 0.1 dB  Preset = -11.0 dB  "
        ::= { iqmux33CmdEntry 36313 }


    iqmux33LoudCustomMasterLevelLoudLimit51 OBJECT-TYPE
        SYNTAX            INTEGER
        MAX-ACCESS        read-write
        STATUS            current
        DESCRIPTION
                "CMNT: - Linear Acoustic 5.1 Master Level LoudLimit
                 TYPE: - Number
                 PAGE: - LoudCustom
                    LoudLimit_51  cmdID= 36314
                    min= -310  max= 0  step= 1  format= %0.1f dB  div_scale= 10  preset= -60
                    Min = -31.0 dB  Max = 0.0 dB  Step = 0.1 dB  Preset = -6.0 dB  "
        ::= { iqmux33CmdEntry 36314 }


    iqmux33LoudCustomMasterLevelProtect51 OBJECT-TYPE
        SYNTAX            INTEGER
        MAX-ACCESS        read-write
        STATUS            current
        DESCRIPTION
                "CMNT: - Linear Acoustic 5.1 Master Level Protection
                 TYPE: - Number
                 PAGE: - LoudCustom
                    Protect_51  cmdID= 36315
                    min= -310  max= 0  step= 1  format= %0.1f dB  div_scale= 10  preset= -30
                    Min = -31.0 dB  Max = 0.0 dB  Step = 0.1 dB  Preset = -3.0 dB  "
        ::= { iqmux33CmdEntry 36315 }


    iqmux33LoudCustomMasterLevelGenSterA OBJECT-TYPE
        SYNTAX            INTEGER
        MAX-ACCESS        read-write
        STATUS            current
        DESCRIPTION
                "CMNT: - Linear Acoustic StereoA Master Level General
                 TYPE: - Number
                 PAGE: - LoudCustom
                    Gen_SterA  cmdID= 36316
                    min= -310  max= 0  step= 1  format= %0.1f dB  div_scale= 10  preset= -110
                    Min = -31.0 dB  Max = 0.0 dB  Step = 0.1 dB  Preset = -11.0 dB  "
        ::= { iqmux33CmdEntry 36316 }


    iqmux33LoudCustomMasterLevelLightSterA OBJECT-TYPE
        SYNTAX            INTEGER
        MAX-ACCESS        read-write
        STATUS            current
        DESCRIPTION
                "CMNT: - Linear Acoustic StereoA Master Level Light
                 TYPE: - Number
                 PAGE: - LoudCustom
                    Light_SterA  cmdID= 36317
                    min= -310  max= 0  step= 1  format= %0.1f dB  div_scale= 10  preset= -110
                    Min = -31.0 dB  Max = 0.0 dB  Step = 0.1 dB  Preset = -11.0 dB  "
        ::= { iqmux33CmdEntry 36317 }


    iqmux33LoudCustomMasterLevelHeavySterA OBJECT-TYPE
        SYNTAX            INTEGER
        MAX-ACCESS        read-write
        STATUS            current
        DESCRIPTION
                "CMNT: - Linear Acoustic StereoA Master Level Heavy
                 TYPE: - Number
                 PAGE: - LoudCustom
                    Heavy_SterA  cmdID= 36318
                    min= -310  max= 0  step= 1  format= %0.1f dB  div_scale= 10  preset= -110
                    Min = -31.0 dB  Max = 0.0 dB  Step = 0.1 dB  Preset = -11.0 dB  "
        ::= { iqmux33CmdEntry 36318 }


    iqmux33LoudCustomMasterLevelLoudSterA OBJECT-TYPE
        SYNTAX            INTEGER
        MAX-ACCESS        read-write
        STATUS            current
        DESCRIPTION
                "CMNT: - Linear Acoustic StereoA Master Level Loud
                 TYPE: - Number
                 PAGE: - LoudCustom
                    Loud_SterA  cmdID= 36319
                    min= -310  max= 0  step= 1  format= %0.1f dB  div_scale= 10  preset= -110
                    Min = -31.0 dB  Max = 0.0 dB  Step = 0.1 dB  Preset = -11.0 dB  "
        ::= { iqmux33CmdEntry 36319 }


    iqmux33LoudCustomMasterLevelLoudLimitSterA OBJECT-TYPE
        SYNTAX            INTEGER
        MAX-ACCESS        read-write
        STATUS            current
        DESCRIPTION
                "CMNT: - Linear Acoustic StereoA Master Level LoudLimit
                 TYPE: - Number
                 PAGE: - LoudCustom
                    LoudLimit_SterA  cmdID= 36320
                    min= -310  max= 0  step= 1  format= %0.1f dB  div_scale= 10  preset= -60
                    Min = -31.0 dB  Max = 0.0 dB  Step = 0.1 dB  Preset = -6.0 dB  "
        ::= { iqmux33CmdEntry 36320 }


    iqmux33LoudCustomMasterLevelProtectSterA OBJECT-TYPE
        SYNTAX            INTEGER
        MAX-ACCESS        read-write
        STATUS            current
        DESCRIPTION
                "CMNT: - Linear Acoustic StereoA Master Level Protection
                 TYPE: - Number
                 PAGE: - LoudCustom
                    Protect_SterA  cmdID= 36321
                    min= -310  max= 0  step= 1  format= %0.1f dB  div_scale= 10  preset= -30
                    Min = -31.0 dB  Max = 0.0 dB  Step = 0.1 dB  Preset = -3.0 dB  "
        ::= { iqmux33CmdEntry 36321 }


    iqmux33LoudCustomMasterLevelGenSterB OBJECT-TYPE
        SYNTAX            INTEGER
        MAX-ACCESS        read-write
        STATUS            current
        DESCRIPTION
                "CMNT: - Linear Acoustic StereoB Master Level General
                 TYPE: - Number
                 PAGE: - LoudCustom
                    Gen_SterB  cmdID= 36322
                    min= -310  max= 0  step= 1  format= %0.1f dB  div_scale= 10  preset= -110
                    Min = -31.0 dB  Max = 0.0 dB  Step = 0.1 dB  Preset = -11.0 dB  "
        ::= { iqmux33CmdEntry 36322 }


    iqmux33LoudCustomMasterLevelLightSterB OBJECT-TYPE
        SYNTAX            INTEGER
        MAX-ACCESS        read-write
        STATUS            current
        DESCRIPTION
                "CMNT: - Linear Acoustic StereoB Master Level Light
                 TYPE: - Number
                 PAGE: - LoudCustom
                    Light_SterB  cmdID= 36323
                    min= -310  max= 0  step= 1  format= %0.1f dB  div_scale= 10  preset= -110
                    Min = -31.0 dB  Max = 0.0 dB  Step = 0.1 dB  Preset = -11.0 dB  "
        ::= { iqmux33CmdEntry 36323 }


    iqmux33LoudCustomMasterLevelHeavySterB OBJECT-TYPE
        SYNTAX            INTEGER
        MAX-ACCESS        read-write
        STATUS            current
        DESCRIPTION
                "CMNT: - Linear Acoustic StereoB Master Level Heavy
                 TYPE: - Number
                 PAGE: - LoudCustom
                    Heavy_SterB  cmdID= 36324
                    min= -310  max= 0  step= 1  format= %0.1f dB  div_scale= 10  preset= -110
                    Min = -31.0 dB  Max = 0.0 dB  Step = 0.1 dB  Preset = -11.0 dB  "
        ::= { iqmux33CmdEntry 36324 }


    iqmux33LoudCustomMasterLevelLoudSterB OBJECT-TYPE
        SYNTAX            INTEGER
        MAX-ACCESS        read-write
        STATUS            current
        DESCRIPTION
                "CMNT: - Linear Acoustic StereoB Master Level Loud
                 TYPE: - Number
                 PAGE: - LoudCustom
                    Loud_SterB  cmdID= 36325
                    min= -310  max= 0  step= 1  format= %0.1f dB  div_scale= 10  preset= -110
                    Min = -31.0 dB  Max = 0.0 dB  Step = 0.1 dB  Preset = -11.0 dB  "
        ::= { iqmux33CmdEntry 36325 }


    iqmux33LoudCustomMasterLevelLoudLimitSterB OBJECT-TYPE
        SYNTAX            INTEGER
        MAX-ACCESS        read-write
        STATUS            current
        DESCRIPTION
                "CMNT: - Linear Acoustic StereoB Master Level LoudLimit
                 TYPE: - Number
                 PAGE: - LoudCustom
                    LoudLimit_SterB  cmdID= 36326
                    min= -310  max= 0  step= 1  format= %0.1f dB  div_scale= 10  preset= -60
                    Min = -31.0 dB  Max = 0.0 dB  Step = 0.1 dB  Preset = -6.0 dB  "
        ::= { iqmux33CmdEntry 36326 }


    iqmux33LoudCustomMasterLevelProtectSterB OBJECT-TYPE
        SYNTAX            INTEGER
        MAX-ACCESS        read-write
        STATUS            current
        DESCRIPTION
                "CMNT: - Linear Acoustic StereoB Master Level Protection
                 TYPE: - Number
                 PAGE: - LoudCustom
                    Protect_SterB  cmdID= 36327
                    min= -310  max= 0  step= 1  format= %0.1f dB  div_scale= 10  preset= -30
                    Min = -31.0 dB  Max = 0.0 dB  Step = 0.1 dB  Preset = -3.0 dB  "
        ::= { iqmux33CmdEntry 36327 }


    iqmux33Mixers13Select OBJECT-TYPE
        SYNTAX            INTEGER {
                            valMixer1(0),
                            valMixer2(1),
                            valMixer3(2),
                            valMixer4(3),
                            valDownmix1n1(4),
                            valDownmix1n2(5)
                            }
        MAX-ACCESS        read-write
        STATUS            current
        DESCRIPTION
                "CMNT: - Mixer select
                 TYPE: - RadiobuttonList
                 PAGE: - Mixers1_3
                    Select  cmdID= 40825
                    Mixer1  value= 0
                    Mixer2  value= 1
                    Mixer3  value= 2
                    Mixer4  value= 3
                    Downmix1-1  value= 4
                    Downmix1-2  value= 5  "
        ::= { iqmux33CmdEntry 40825 }


    iqmux33Mixers13Source1ProcGain OBJECT-TYPE
        SYNTAX            INTEGER
        MAX-ACCESS        read-write
        STATUS            current
        DESCRIPTION
                "CMNT: - Mix_1 Proc Amp Gain
                 TYPE: - Number
                 PAGE: - Mixers1_3
                    ProcGain  cmdID= 40800
                    min= -801  max= 120  step= 1  format= %0.1f dB  div_scale= 10  preset= 0
                    Min = -80.1 dB  Max = 12.0 dB  Step = 0.1 dB  Preset = 0.0 dB  "
        ::= { iqmux33CmdEntry 40800 }


    iqmux33Mixers13Source1Invert OBJECT-TYPE
        SYNTAX            INTEGER { disable(0), enable(1)  }
        MAX-ACCESS        read-write
        STATUS            current
        DESCRIPTION
                "CMNT: - Mix_1 Invert
                 TYPE: - Checkbox
                 PAGE: - Mixers1_3
                    Invert  cmdID= 40806  "
        ::= { iqmux33CmdEntry 40806 }


    iqmux33Mixers13Source1Mute OBJECT-TYPE
        SYNTAX            INTEGER { disable(0), enable(1)  }
        MAX-ACCESS        read-write
        STATUS            current
        DESCRIPTION
                "CMNT: - Mix_1 Mute
                 TYPE: - Checkbox
                 PAGE: - Mixers1_3
                    Mute  cmdID= 40812  "
        ::= { iqmux33CmdEntry 40812 }


    iqmux33Mixers13Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_1 source
                 TYPE: - RadiobuttonList
                 PAGE: - Mixers1_3
                    Src  cmdID= 40818
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqmux33CmdEntry 40818 }


    iqmux33Mixers13Source1Name OBJECT-TYPE
        SYNTAX            RollCallString
        MAX-ACCESS        read-only
        STATUS            current
        DESCRIPTION
                "CMNT: - Mix_1 name
                 TYPE: - Display
                 PAGE: - Mixers1_3
                    Name  cmdID= 40826  "
        ::= { iqmux33CmdEntry 40826 }


    iqmux33Mixers13Source2ProcGain OBJECT-TYPE
        SYNTAX            INTEGER
        MAX-ACCESS        read-write
        STATUS            current
        DESCRIPTION
                "CMNT: - Mix_2 Proc Amp Gain
                 TYPE: - Number
                 PAGE: - Mixers1_3
                    ProcGain  cmdID= 40801
                    min= -801  max= 120  step= 1  format= %0.1f dB  div_scale= 10  preset= 0
                    Min = -80.1 dB  Max = 12.0 dB  Step = 0.1 dB  Preset = 0.0 dB  "
        ::= { iqmux33CmdEntry 40801 }


    iqmux33Mixers13Source2Invert OBJECT-TYPE
        SYNTAX            INTEGER { disable(0), enable(1)  }
        MAX-ACCESS        read-write
        STATUS            current
        DESCRIPTION
                "CMNT: - Mix_2 Invert
                 TYPE: - Checkbox
                 PAGE: - Mixers1_3
                    Invert  cmdID= 40807  "
        ::= { iqmux33CmdEntry 40807 }


    iqmux33Mixers13Source2Mute OBJECT-TYPE
        SYNTAX            INTEGER { disable(0), enable(1)  }
        MAX-ACCESS        read-write
        STATUS            current
        DESCRIPTION
                "CMNT: - Mix_2 Mute
                 TYPE: - Checkbox
                 PAGE: - Mixers1_3
                    Mute  cmdID= 40813  "
        ::= { iqmux33CmdEntry 40813 }


    iqmux33Mixers13Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_2 source
                 TYPE: - RadiobuttonList
                 PAGE: - Mixers1_3
                    Src  cmdID= 40819
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqmux33CmdEntry 40819 }


    iqmux33Mixers13Source2Name OBJECT-TYPE
        SYNTAX            RollCallString
        MAX-ACCESS        read-only
        STATUS            current
        DESCRIPTION
                "CMNT: - Mix_2 name
                 TYPE: - Display
                 PAGE: - Mixers1_3
                    Name  cmdID= 40827  "
        ::= { iqmux33CmdEntry 40827 }


    iqmux33Mixers13Source3ProcGain OBJECT-TYPE
        SYNTAX            INTEGER
        MAX-ACCESS        read-write
        STATUS            current
        DESCRIPTION
                "CMNT: - Mix_3 Proc Amp Gain
                 TYPE: - Number
                 PAGE: - Mixers1_3
                    ProcGain  cmdID= 40802
                    min= -801  max= 120  step= 1  format= %0.1f dB  div_scale= 10  preset= 0
                    Min = -80.1 dB  Max = 12.0 dB  Step = 0.1 dB  Preset = 0.0 dB  "
        ::= { iqmux33CmdEntry 40802 }


    iqmux33Mixers13Source3Invert OBJECT-TYPE
        SYNTAX            INTEGER { disable(0), enable(1)  }
        MAX-ACCESS        read-write
        STATUS            current
        DESCRIPTION
                "CMNT: - Mix_3 Invert
                 TYPE: - Checkbox
                 PAGE: - Mixers1_3
                    Invert  cmdID= 40808  "
        ::= { iqmux33CmdEntry 40808 }


    iqmux33Mixers13Source3Mute OBJECT-TYPE
        SYNTAX            INTEGER { disable(0), enable(1)  }
        MAX-ACCESS        read-write
        STATUS            current
        DESCRIPTION
                "CMNT: - Mix_3 Mute
                 TYPE: - Checkbox
                 PAGE: - Mixers1_3
                    Mute  cmdID= 40814  "
        ::= { iqmux33CmdEntry 40814 }


    iqmux33Mixers13Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_3 source
                 TYPE: - RadiobuttonList
                 PAGE: - Mixers1_3
                    Src  cmdID= 40820
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqmux33CmdEntry 40820 }


    iqmux33Mixers13Source3Name OBJECT-TYPE
        SYNTAX            RollCallString
        MAX-ACCESS        read-only
        STATUS            current
        DESCRIPTION
                "CMNT: - Mix_3 name
                 TYPE: - Display
                 PAGE: - Mixers1_3
                    Name  cmdID= 40828  "
        ::= { iqmux33CmdEntry 40828 }


    iqmux33Mixers13MixerLoRo OBJECT-TYPE
        SYNTAX            INTEGER {
                            valCustom(0),
                            valn3dBCpLsRs(1),
                            valn3dBCn3dBLsRs(2),
                            valn3dBCn6dBLsRs(3),
                            valn3dBCn9dBLsRs(4)
                            }
        MAX-ACCESS        read-write
        STATUS            current
        DESCRIPTION
                "CMNT: - DownMixLoRo
                 TYPE: - RadiobuttonList
                 PAGE: - Mixers1_3
                    MixerLoRo  cmdID= 40832
                    Custom  value= 0
                    -3dB C + Ls/Rs  value= 1
                    -3dB C -3dB Ls/Rs  value= 2
                    -3dB C -6dB Ls/Rs  value= 3
                    -3dB C -9dB Ls/Rs  value= 4  "
        ::= { iqmux33CmdEntry 40832 }


    iqmux33Mixers46Source4ProcGain OBJECT-TYPE
        SYNTAX            INTEGER
        MAX-ACCESS        read-write
        STATUS            current
        DESCRIPTION
                "CMNT: - Mix_4 Proc Amp Gain
                 TYPE: - Number
                 PAGE: - Mixers4_6
                    ProcGain  cmdID= 40803
                    min= -801  max= 120  step= 1  format= %0.1f dB  div_scale= 10  preset= 0
                    Min = -80.1 dB  Max = 12.0 dB  Step = 0.1 dB  Preset = 0.0 dB  "
        ::= { iqmux33CmdEntry 40803 }


    iqmux33Mixers46Source4Invert OBJECT-TYPE
        SYNTAX            INTEGER { disable(0), enable(1)  }
        MAX-ACCESS        read-write
        STATUS            current
        DESCRIPTION
                "CMNT: - Mix_4 Invert
                 TYPE: - Checkbox
                 PAGE: - Mixers4_6
                    Invert  cmdID= 40809  "
        ::= { iqmux33CmdEntry 40809 }


    iqmux33Mixers46Source4Mute OBJECT-TYPE
        SYNTAX            INTEGER { disable(0), enable(1)  }
        MAX-ACCESS        read-write
        STATUS            current
        DESCRIPTION
                "CMNT: - Mix_4 Mute
                 TYPE: - Checkbox
                 PAGE: - Mixers4_6
                    Mute  cmdID= 40815  "
        ::= { iqmux33CmdEntry 40815 }


    iqmux33Mixers46Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_4 source
                 TYPE: - RadiobuttonList
                 PAGE: - Mixers4_6
                    Src  cmdID= 40821
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqmux33CmdEntry 40821 }


    iqmux33Mixers46Source4Name OBJECT-TYPE
        SYNTAX            RollCallString
        MAX-ACCESS        read-only
        STATUS            current
        DESCRIPTION
                "CMNT: - Mix_4 name
                 TYPE: - Display
                 PAGE: - Mixers4_6
                    Name  cmdID= 40829  "
        ::= { iqmux33CmdEntry 40829 }


    iqmux33Mixers46Source5ProcGain OBJECT-TYPE
        SYNTAX            INTEGER
        MAX-ACCESS        read-write
        STATUS            current
        DESCRIPTION
                "CMNT: - Mix_5 Proc Amp Gain
                 TYPE: - Number
                 PAGE: - Mixers4_6
                    ProcGain  cmdID= 40804
                    min= -801  max= 120  step= 1  format= %0.1f dB  div_scale= 10  preset= 0
                    Min = -80.1 dB  Max = 12.0 dB  Step = 0.1 dB  Preset = 0.0 dB  "
        ::= { iqmux33CmdEntry 40804 }


    iqmux33Mixers46Source5Invert OBJECT-TYPE
        SYNTAX            INTEGER { disable(0), enable(1)  }
        MAX-ACCESS        read-write
        STATUS            current
        DESCRIPTION
                "CMNT: - Mix_5 Invert
                 TYPE: - Checkbox
                 PAGE: - Mixers4_6
                    Invert  cmdID= 40810  "
        ::= { iqmux33CmdEntry 40810 }


    iqmux33Mixers46Source5Mute OBJECT-TYPE
        SYNTAX            INTEGER { disable(0), enable(1)  }
        MAX-ACCESS        read-write
        STATUS            current
        DESCRIPTION
                "CMNT: - Mix_5 Mute
                 TYPE: - Checkbox
                 PAGE: - Mixers4_6
                    Mute  cmdID= 40816  "
        ::= { iqmux33CmdEntry 40816 }


    iqmux33Mixers46Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_5 source
                 TYPE: - RadiobuttonList
                 PAGE: - Mixers4_6
                    Src  cmdID= 40822
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqmux33CmdEntry 40822 }


    iqmux33Mixers46Source5Name OBJECT-TYPE
        SYNTAX            RollCallString
        MAX-ACCESS        read-only
        STATUS            current
        DESCRIPTION
                "CMNT: - Mix_5 name
                 TYPE: - Display
                 PAGE: - Mixers4_6
                    Name  cmdID= 40830  "
        ::= { iqmux33CmdEntry 40830 }


    iqmux33Mixers46Source6ProcGain OBJECT-TYPE
        SYNTAX            INTEGER
        MAX-ACCESS        read-write
        STATUS            current
        DESCRIPTION
                "CMNT: - Mix_6 Proc Amp Gain
                 TYPE: - Number
                 PAGE: - Mixers4_6
                    ProcGain  cmdID= 40805
                    min= -801  max= 120  step= 1  format= %0.1f dB  div_scale= 10  preset= 0
                    Min = -80.1 dB  Max = 12.0 dB  Step = 0.1 dB  Preset = 0.0 dB  "
        ::= { iqmux33CmdEntry 40805 }


    iqmux33Mixers46Source6Invert OBJECT-TYPE
        SYNTAX            INTEGER { disable(0), enable(1)  }
        MAX-ACCESS        read-write
        STATUS            current
        DESCRIPTION
                "CMNT: - Mix_6 Invert
                 TYPE: - Checkbox
                 PAGE: - Mixers4_6
                    Invert  cmdID= 40811  "
        ::= { iqmux33CmdEntry 40811 }


    iqmux33Mixers46Source6Mute OBJECT-TYPE
        SYNTAX            INTEGER { disable(0), enable(1)  }
        MAX-ACCESS        read-write
        STATUS            current
        DESCRIPTION
                "CMNT: - Mix_6 Mute
                 TYPE: - Checkbox
                 PAGE: - Mixers4_6
                    Mute  cmdID= 40817  "
        ::= { iqmux33CmdEntry 40817 }


    iqmux33Mixers46Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_6 source
                 TYPE: - RadiobuttonList
                 PAGE: - Mixers4_6
                    Src  cmdID= 40823
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqmux33CmdEntry 40823 }


    iqmux33Mixers46Source6Name OBJECT-TYPE
        SYNTAX            RollCallString
        MAX-ACCESS        read-only
        STATUS            current
        DESCRIPTION
                "CMNT: - Mix_6 name
                 TYPE: - Display
                 PAGE: - Mixers4_6
                    Name  cmdID= 40831  "
        ::= { iqmux33CmdEntry 40831 }


    iqmux33DolbyDecodeDolbyDecoderDetectMode OBJECT-TYPE
        SYNTAX            INTEGER {
                            valAuto(0),
                            valDolbyEorMute(1),
                            valDolbyDigitalorMute(2),
                            valMute(3)
                            }
        MAX-ACCESS        read-write
        STATUS            current
        DESCRIPTION
                "CMNT: - Dolby decoder detect mode
                 TYPE: - RadiobuttonList
                 PAGE: - DolbyDecode
                    Detect Mode  cmdID= 42401
                    Auto  value= 0
                    Dolby E or Mute  value= 1
                    Dolby Digital or Mute  value= 2
                    Mute  value= 3  "
        ::= { iqmux33CmdEntry 42401 }


    iqmux33DolbyDecodeDolbyDecoderAESChannelSelect OBJECT-TYPE
        SYNTAX            INTEGER {
                            valChannel1(0),
                            valChannel2(1)
                            }
        MAX-ACCESS        read-write
        STATUS            current
        DESCRIPTION
                "CMNT: - Dolby Digital Pro 16 AES channel select
                 TYPE: - RadiobuttonList
                 PAGE: - DolbyDecode
                    AES Channel Select  cmdID= 42402
                    Channel 1  value= 0
                    Channel 2  value= 1  "
        ::= { iqmux33CmdEntry 42402 }


    iqmux33DolbyDecodeDolbyDecoderPCMLatency OBJECT-TYPE
        SYNTAX            INTEGER {
                            valSingleVideoFrame(0),
                            valMinimum(1)
                            }
        MAX-ACCESS        read-write
        STATUS            current
        DESCRIPTION
                "CMNT: - Dolby decoder PCM latency
                 TYPE: - RadiobuttonList
                 PAGE: - DolbyDecode
                    PCM Latency  cmdID= 42403
                    Single Video Frame  value= 0
                    Minimum  value= 1  "
        ::= { iqmux33CmdEntry 42403 }


    iqmux33DolbyDecodeDolbyDecoderListeningModeDolbyD OBJECT-TYPE
        SYNTAX            INTEGER {
                            valFull(0),
                            valEX(1),
                            val3Stereo(2),
                            valPhantom(3),
                            valStereo(4),
                            valMono(5)
                            }
        MAX-ACCESS        read-write
        STATUS            current
        DESCRIPTION
                "CMNT: - Dolby decoder listening mode
                 TYPE: - RadiobuttonList
                 PAGE: - DolbyDecode
                    Listening Mode Dolby D  cmdID= 42404
                    Full  value= 0
                    EX  value= 1
                    3 Stereo  value= 2
                    Phantom  value= 3
                    Stereo  value= 4
                    Mono  value= 5  "
        ::= { iqmux33CmdEntry 42404 }


    iqmux33DolbyDecodeDolbyDecoderDynamicRange OBJECT-TYPE
        SYNTAX            INTEGER {
                            valLineMode(0),
                            valRFMode(1),
                            valBypassMode(3)
                            }
        MAX-ACCESS        read-write
        STATUS            current
        DESCRIPTION
                "CMNT: - Dolby decoder dynamic range
                 TYPE: - RadiobuttonList
                 PAGE: - DolbyDecode
                    Dynamic Range   cmdID= 42405
                    Line Mode  value= 0
                    RF Mode  value= 1
                    Bypass Mode  value= 3  "
        ::= { iqmux33CmdEntry 42405 }


    iqmux33DolbyDecoderAuxChannelProgramSelect OBJECT-TYPE
        SYNTAX            INTEGER {
                            valProgram1(0),
                            valProgram2(1),
                            valProgram3(2),
                            valProgram4(3),
                            valProgram5(4),
                            valProgram6(5),
                            valProgram7(6),
                            valProgram8(7)
                            }
        MAX-ACCESS        read-write
        STATUS            current
        DESCRIPTION
                "CMNT: - Dolby decoder auxiliary channel program select
                 TYPE: - RadiobuttonList
                 PAGE: - Dolby Decoder
                    Program Select  cmdID= 42406
                    Program 1  value= 0
                    Program 2  value= 1
                    Program 3  value= 2
                    Program 4  value= 3
                    Program 5  value= 4
                    Program 6  value= 5
                    Program 7  value= 6
                    Program 8  value= 7  "
        ::= { iqmux33CmdEntry 42406 }


    iqmux33DolbyDecoderAuxChannelDynamicRange OBJECT-TYPE
        SYNTAX            INTEGER {
                            valLineMode(0),
                            valRFMode(1)
                            }
        MAX-ACCESS        read-write
        STATUS            current
        DESCRIPTION
                "CMNT: - Dolby decoder auxiliary channel dynamic range
                 TYPE: - RadiobuttonList
                 PAGE: - Dolby Decoder
                    Dynamic Range  cmdID= 42407
                    Line Mode  value= 0
                    RF Mode  value= 1  "
        ::= { iqmux33CmdEntry 42407 }


    iqmux33DolbyDecoderAuxChannelOutputMode OBJECT-TYPE
        SYNTAX            INTEGER {
                            valLtRt(0),
                            valLoRo(1),
                            valMono(2),
                            valMute(3)
                            }
        MAX-ACCESS        read-write
        STATUS            current
        DESCRIPTION
                "CMNT: - Dolby decoder auxiliary channel output mode
                 TYPE: - RadiobuttonList
                 PAGE: - Dolby Decoder
                    Output Mode  cmdID= 42408
                    Lt/Rt  value= 0
                    Lo/Ro  value= 1
                    Mono  value= 2
                    Mute  value= 3  "
        ::= { iqmux33CmdEntry 42408 }


    iqmux33DolbyDecoderDecoderStatusBitstreamFormat OBJECT-TYPE
        SYNTAX            RollCallString
        MAX-ACCESS        read-only
        STATUS            current
        DESCRIPTION
                "CMNT: - Dolby decoder I/P bitstream format
                 TYPE: - Display
                 PAGE: - Dolby Decoder
                    Bitstream Format  cmdID= 42409  "
        ::= { iqmux33CmdEntry 42409 }


    iqmux33DolbyDecoderDecoderStatusBitstreamStatus OBJECT-TYPE
        SYNTAX            RollCallString
        MAX-ACCESS        read-only
        STATUS            current
        DESCRIPTION
                "CMNT: - Dolby decoder I/P bitstream status
                 TYPE: - Display
                 PAGE: - Dolby Decoder
                    Bitstream Status  cmdID= 42410  "
        ::= { iqmux33CmdEntry 42410 }


    iqmux33DolbyDecoderDecoderStatusDCRCErrorCount OBJECT-TYPE
        SYNTAX            RollCallString
        MAX-ACCESS        read-only
        STATUS            current
        DESCRIPTION
                "CMNT: - Dolby D decoder CRC error count
                 TYPE: - Display
                 PAGE: - Dolby Decoder
                    D CRC Error Count  cmdID= 42505  "
        ::= { iqmux33CmdEntry 42505 }


    iqmux33DolbyDecoderDecoderStatusDCRCErrorTime OBJECT-TYPE
        SYNTAX            RollCallString
        MAX-ACCESS        read-only
        STATUS            current
        DESCRIPTION
                "CMNT: - Dolby D decoder CRC error time
                 TYPE: - Display
                 PAGE: - Dolby Decoder
                    D CRC Error Time  cmdID= 42504  "
        ::= { iqmux33CmdEntry 42504 }


    iqmux33DolbyDecoderDecoderStatusECRCErrorCount OBJECT-TYPE
        SYNTAX            RollCallString
        MAX-ACCESS        read-only
        STATUS            current
        DESCRIPTION
                "CMNT: - Dolby E decoder CRC error count
                 TYPE: - Display
                 PAGE: - Dolby Decoder
                    E CRC Error Count  cmdID= 42507  "
        ::= { iqmux33CmdEntry 42507 }


    iqmux33DolbyDecoderDecoderStatusECRCErrorTime OBJECT-TYPE
        SYNTAX            RollCallString
        MAX-ACCESS        read-only
        STATUS            current
        DESCRIPTION
                "CMNT: - Dolby E decoder CRC error time
                 TYPE: - Display
                 PAGE: - Dolby Decoder
                    E CRC Error Time  cmdID= 42506  "
        ::= { iqmux33CmdEntry 42506 }


    iqmux33DolbyDecoderDecoderStatusResetErrors OBJECT-TYPE
        SYNTAX            INTEGER { noAction(0),valResetErrors(1) }
        MAX-ACCESS        read-write
        STATUS            current
        DESCRIPTION
                "CMNT: - Dolby decoder CRC error reset
                 TYPE: - Button
                 PAGE: - Dolby Decoder
                    Reset Errors  cmdID= 42502
                    value= 1  "
        ::= { iqmux33CmdEntry 42502 }


    iqmux33DolbyDecoderDecoderStatusResetTime OBJECT-TYPE
        SYNTAX            RollCallString
        MAX-ACCESS        read-only
        STATUS            current
        DESCRIPTION
                "CMNT: - Dolby decoder CRC error reset time
                 TYPE: - Display
                 PAGE: - Dolby Decoder
                    Reset Time  cmdID= 42503  "
        ::= { iqmux33CmdEntry 42503 }


    iqmux33DolbyDecoderOutputsA1A2A1Gain OBJECT-TYPE
        SYNTAX            INTEGER
        MAX-ACCESS        read-write
        STATUS            current
        DESCRIPTION
                "CMNT: - Dolby decoder O/P A1 gain
                 TYPE: - Number
                 PAGE: - Dolby Decoder Outputs
                    A1 Gain  cmdID= 42558
                    min= -801  max= 120  step= 1  format= %0.1f dB  div_scale= 10  preset= 0
                    Min = -80.1 dB  Max = 12.0 dB  Step = 0.1 dB  Preset = 0.0 dB  "
        ::= { iqmux33CmdEntry 42558 }


    iqmux33DolbyDecoderOutputsA1A2A2Gain OBJECT-TYPE
        SYNTAX            INTEGER
        MAX-ACCESS        read-write
        STATUS            current
        DESCRIPTION
                "CMNT: - Dolby decoder O/P A2 gain
                 TYPE: - Number
                 PAGE: - Dolby Decoder Outputs
                    A2 Gain  cmdID= 42559
                    min= -801  max= 120  step= 1  format= %0.1f dB  div_scale= 10  preset= 0
                    Min = -80.1 dB  Max = 12.0 dB  Step = 0.1 dB  Preset = 0.0 dB  "
        ::= { iqmux33CmdEntry 42559 }


    iqmux33DolbyDecoderOutputsA1A2MuteA1 OBJECT-TYPE
        SYNTAX            INTEGER { disable(0), enable(1)  }
        MAX-ACCESS        read-write
        STATUS            current
        DESCRIPTION
                "CMNT: - Dolby decoder O/P A1 mute
                 TYPE: - Checkbox
                 PAGE: - Dolby Decoder Outputs
                    Mute A1  cmdID= 42568  "
        ::= { iqmux33CmdEntry 42568 }


    iqmux33DolbyDecoderOutputsA1A2MuteA2 OBJECT-TYPE
        SYNTAX            INTEGER { disable(0), enable(1)  }
        MAX-ACCESS        read-write
        STATUS            current
        DESCRIPTION
                "CMNT: - Dolby decoder O/P A2 mute
                 TYPE: - Checkbox
                 PAGE: - Dolby Decoder Outputs
                    Mute A2  cmdID= 42569  "
        ::= { iqmux33CmdEntry 42569 }


    iqmux33DolbyDecoderOutputsA1A2StereoA OBJECT-TYPE
        SYNTAX            INTEGER { disable(0), enable(1)  }
        MAX-ACCESS        read-write
        STATUS            current
        DESCRIPTION
                "CMNT: - Dolby decoder O/P A stereo
                 TYPE: - Checkbox
                 PAGE: - Dolby Decoder Outputs
                    Stereo A  cmdID= 42578  "
        ::= { iqmux33CmdEntry 42578 }


    iqmux33DolbyDecoderOutputsB3B4B3Gain OBJECT-TYPE
        SYNTAX            INTEGER
        MAX-ACCESS        read-write
        STATUS            current
        DESCRIPTION
                "CMNT: - Dolby decoder O/P B3 gain
                 TYPE: - Number
                 PAGE: - Dolby Decoder Outputs
                    B3 Gain  cmdID= 42560
                    min= -801  max= 120  step= 1  format= %0.1f dB  div_scale= 10  preset= 0
                    Min = -80.1 dB  Max = 12.0 dB  Step = 0.1 dB  Preset = 0.0 dB  "
        ::= { iqmux33CmdEntry 42560 }


    iqmux33DolbyDecoderOutputsB3B4B4Gain OBJECT-TYPE
        SYNTAX            INTEGER
        MAX-ACCESS        read-write
        STATUS            current
        DESCRIPTION
                "CMNT: - Dolby decoder O/P B4 gain
                 TYPE: - Number
                 PAGE: - Dolby Decoder Outputs
                    B4 Gain  cmdID= 42561
                    min= -801  max= 120  step= 1  format= %0.1f dB  div_scale= 10  preset= 0
                    Min = -80.1 dB  Max = 12.0 dB  Step = 0.1 dB  Preset = 0.0 dB  "
        ::= { iqmux33CmdEntry 42561 }


    iqmux33DolbyDecoderOutputsB3B4MuteB3 OBJECT-TYPE
        SYNTAX            INTEGER { disable(0), enable(1)  }
        MAX-ACCESS        read-write
        STATUS            current
        DESCRIPTION
                "CMNT: - Dolby decoder O/P B3 mute
                 TYPE: - Checkbox
                 PAGE: - Dolby Decoder Outputs
                    Mute B3  cmdID= 42570  "
        ::= { iqmux33CmdEntry 42570 }


    iqmux33DolbyDecoderOutputsB3B4MuteB4 OBJECT-TYPE
        SYNTAX            INTEGER { disable(0), enable(1)  }
        MAX-ACCESS        read-write
        STATUS            current
        DESCRIPTION
                "CMNT: - Dolby decoder O/P B4 mute
                 TYPE: - Checkbox
                 PAGE: - Dolby Decoder Outputs
                    Mute B4  cmdID= 42571  "
        ::= { iqmux33CmdEntry 42571 }


    iqmux33DolbyDecoderOutputsB3B4StereoB OBJECT-TYPE
        SYNTAX            INTEGER { disable(0), enable(1)  }
        MAX-ACCESS        read-write
        STATUS            current
        DESCRIPTION
                "CMNT: - Dolby decoder O/P B stereo
                 TYPE: - Checkbox
                 PAGE: - Dolby Decoder Outputs
                    Stereo B  cmdID= 42579  "
        ::= { iqmux33CmdEntry 42579 }


    iqmux33DolbyDecoderOutputsC5C6C5Gain OBJECT-TYPE
        SYNTAX            INTEGER
        MAX-ACCESS        read-write
        STATUS            current
        DESCRIPTION
                "CMNT: - Dolby decoder O/P C5 gain
                 TYPE: - Number
                 PAGE: - Dolby Decoder Outputs
                    C5 Gain  cmdID= 42562
                    min= -801  max= 120  step= 1  format= %0.1f dB  div_scale= 10  preset= 0
                    Min = -80.1 dB  Max = 12.0 dB  Step = 0.1 dB  Preset = 0.0 dB  "
        ::= { iqmux33CmdEntry 42562 }


    iqmux33DolbyDecoderOutputsC5C6C6Gain OBJECT-TYPE
        SYNTAX            INTEGER
        MAX-ACCESS        read-write
        STATUS            current
        DESCRIPTION
                "CMNT: - Dolby decoder O/P C6 gain
                 TYPE: - Number
                 PAGE: - Dolby Decoder Outputs
                    C6 Gain  cmdID= 42563
                    min= -801  max= 120  step= 1  format= %0.1f dB  div_scale= 10  preset= 0
                    Min = -80.1 dB  Max = 12.0 dB  Step = 0.1 dB  Preset = 0.0 dB  "
        ::= { iqmux33CmdEntry 42563 }


    iqmux33DolbyDecoderOutputsC5C6MuteC5 OBJECT-TYPE
        SYNTAX            INTEGER { disable(0), enable(1)  }
        MAX-ACCESS        read-write
        STATUS            current
        DESCRIPTION
                "CMNT: - Dolby decoder O/P C5 mute
                 TYPE: - Checkbox
                 PAGE: - Dolby Decoder Outputs
                    Mute C5  cmdID= 42572  "
        ::= { iqmux33CmdEntry 42572 }


    iqmux33DolbyDecoderOutputsC5C6MuteC6 OBJECT-TYPE
        SYNTAX            INTEGER { disable(0), enable(1)  }
        MAX-ACCESS        read-write
        STATUS            current
        DESCRIPTION
                "CMNT: - Dolby decoder O/P C6 mute
                 TYPE: - Checkbox
                 PAGE: - Dolby Decoder Outputs
                    Mute C6  cmdID= 42573  "
        ::= { iqmux33CmdEntry 42573 }


    iqmux33DolbyDecoderOutputsC5C6StereoC OBJECT-TYPE
        SYNTAX            INTEGER { disable(0), enable(1)  }
        MAX-ACCESS        read-write
        STATUS            current
        DESCRIPTION
                "CMNT: - Dolby decoder O/P C stereo
                 TYPE: - Checkbox
                 PAGE: - Dolby Decoder Outputs
                    Stereo C  cmdID= 42580  "
        ::= { iqmux33CmdEntry 42580 }


    iqmux33DolbyDecoderOutputsD7D8D7Gain OBJECT-TYPE
        SYNTAX            INTEGER
        MAX-ACCESS        read-write
        STATUS            current
        DESCRIPTION
                "CMNT: - Dolby decoder O/P D7 gain
                 TYPE: - Number
                 PAGE: - Dolby Decoder Outputs
                    D7 Gain  cmdID= 42564
                    min= -801  max= 120  step= 1  format= %0.1f dB  div_scale= 10  preset= 0
                    Min = -80.1 dB  Max = 12.0 dB  Step = 0.1 dB  Preset = 0.0 dB  "
        ::= { iqmux33CmdEntry 42564 }


    iqmux33DolbyDecoderOutputsD7D8D8Gain OBJECT-TYPE
        SYNTAX            INTEGER
        MAX-ACCESS        read-write
        STATUS            current
        DESCRIPTION
                "CMNT: - Dolby decoder O/P D8 gain
                 TYPE: - Number
                 PAGE: - Dolby Decoder Outputs
                    D8 Gain  cmdID= 42565
                    min= -801  max= 120  step= 1  format= %0.1f dB  div_scale= 10  preset= 0
                    Min = -80.1 dB  Max = 12.0 dB  Step = 0.1 dB  Preset = 0.0 dB  "
        ::= { iqmux33CmdEntry 42565 }


    iqmux33DolbyDecoderOutputsD7D8MuteD7 OBJECT-TYPE
        SYNTAX            INTEGER { disable(0), enable(1)  }
        MAX-ACCESS        read-write
        STATUS            current
        DESCRIPTION
                "CMNT: - Dolby decoder O/P D7 mute
                 TYPE: - Checkbox
                 PAGE: - Dolby Decoder Outputs
                    Mute D7  cmdID= 42574  "
        ::= { iqmux33CmdEntry 42574 }


    iqmux33DolbyDecoderOutputsD7D8MuteD8 OBJECT-TYPE
        SYNTAX            INTEGER { disable(0), enable(1)  }
        MAX-ACCESS        read-write
        STATUS            current
        DESCRIPTION
                "CMNT: - Dolby decoder O/P D8 mute
                 TYPE: - Checkbox
                 PAGE: - Dolby Decoder Outputs
                    Mute D8  cmdID= 42575  "
        ::= { iqmux33CmdEntry 42575 }


    iqmux33DolbyDecoderOutputsD7D8StereoD OBJECT-TYPE
        SYNTAX            INTEGER { disable(0), enable(1)  }
        MAX-ACCESS        read-write
        STATUS            current
        DESCRIPTION
                "CMNT: - Dolby decoder O/P D stereo
                 TYPE: - Checkbox
                 PAGE: - Dolby Decoder Outputs
                    Stereo D  cmdID= 42581  "
        ::= { iqmux33CmdEntry 42581 }


    iqmux33DolbyDecoderOutputsMLMRMLGain OBJECT-TYPE
        SYNTAX            INTEGER
        MAX-ACCESS        read-write
        STATUS            current
        DESCRIPTION
                "CMNT: - Dolby decoder downmix O/P L gain
                 TYPE: - Number
                 PAGE: - Dolby Decoder Outputs
                    ML Gain  cmdID= 42566
                    min= -801  max= 120  step= 1  format= %0.1f dB  div_scale= 10  preset= 0
                    Min = -80.1 dB  Max = 12.0 dB  Step = 0.1 dB  Preset = 0.0 dB  "
        ::= { iqmux33CmdEntry 42566 }


    iqmux33DolbyDecoderOutputsMLMRMRGain OBJECT-TYPE
        SYNTAX            INTEGER
        MAX-ACCESS        read-write
        STATUS            current
        DESCRIPTION
                "CMNT: - Dolby decoder downmix O/P R gain
                 TYPE: - Number
                 PAGE: - Dolby Decoder Outputs
                    MR Gain  cmdID= 42567
                    min= -801  max= 120  step= 1  format= %0.1f dB  div_scale= 10  preset= 0
                    Min = -80.1 dB  Max = 12.0 dB  Step = 0.1 dB  Preset = 0.0 dB  "
        ::= { iqmux33CmdEntry 42567 }


    iqmux33DolbyDecoderOutputsMLMRMuteML OBJECT-TYPE
        SYNTAX            INTEGER { disable(0), enable(1)  }
        MAX-ACCESS        read-write
        STATUS            current
        DESCRIPTION
                "CMNT: - Dolby decoder downmix O/P L mute
                 TYPE: - Checkbox
                 PAGE: - Dolby Decoder Outputs
                    Mute ML  cmdID= 42576  "
        ::= { iqmux33CmdEntry 42576 }


    iqmux33DolbyDecoderOutputsMLMRMuteMR OBJECT-TYPE
        SYNTAX            INTEGER { disable(0), enable(1)  }
        MAX-ACCESS        read-write
        STATUS            current
        DESCRIPTION
                "CMNT: - Dolby decoder downmix O/P R mute
                 TYPE: - Checkbox
                 PAGE: - Dolby Decoder Outputs
                    Mute MR  cmdID= 42577  "
        ::= { iqmux33CmdEntry 42577 }


    iqmux33DolbyDecoderOutputsMLMRStereoM OBJECT-TYPE
        SYNTAX            INTEGER { disable(0), enable(1)  }
        MAX-ACCESS        read-write
        STATUS            current
        DESCRIPTION
                "CMNT: - Dolby decoder downmix O/P stereo
                 TYPE: - Checkbox
                 PAGE: - Dolby Decoder Outputs
                    Stereo M  cmdID= 42582  "
        ::= { iqmux33CmdEntry 42582 }


    iqmux33DolbyDecodeDolbyDecoderOutputsMasterGain OBJECT-TYPE
        SYNTAX            INTEGER
        MAX-ACCESS        read-write
        STATUS            current
        DESCRIPTION
                "CMNT: - Dolby decoder O/P master gain
                 TYPE: - Number
                 PAGE: - DolbyDecode
                    Master Gain  cmdID= 42556
                    min= -801  max= 120  step= 1  format= %0.1f dB  div_scale= 10  preset= 0
                    Min = -80.1 dB  Max = 12.0 dB  Step = 0.1 dB  Preset = 0.0 dB  "
        ::= { iqmux33CmdEntry 42556 }


    iqmux33DolbyDecodeDolbyDecoderOutputsMasterMute OBJECT-TYPE
        SYNTAX            INTEGER { disable(0), enable(1)  }
        MAX-ACCESS        read-write
        STATUS            current
        DESCRIPTION
                "CMNT: - Dolby decoder O/P master mute
                 TYPE: - Checkbox
                 PAGE: - DolbyDecode
                    Master Mute  cmdID= 42557  "
        ::= { iqmux33CmdEntry 42557 }


    iqmux33DolbyEncInp14Source1ProcGain OBJECT-TYPE
        SYNTAX            INTEGER
        MAX-ACCESS        read-write
        STATUS            current
        DESCRIPTION
                "CMNT: - Dolby encoder A1 input gain
                 TYPE: - Number
                 PAGE: - Dolby Enc Inp1_4
                    ProcGain  cmdID= 42520
                    min= -801  max= 120  step= 1  format= %0.1f dB  div_scale= 10  preset= 0
                    Min = -80.1 dB  Max = 12.0 dB  Step = 0.1 dB  Preset = 0.0 dB  "
        ::= { iqmux33CmdEntry 42520 }


    iqmux33DolbyEncInp14Source1Mute OBJECT-TYPE
        SYNTAX            INTEGER { disable(0), enable(1)  }
        MAX-ACCESS        read-write
        STATUS            current
        DESCRIPTION
                "CMNT: - Dolby encoder A1 input mute
                 TYPE: - Checkbox
                 PAGE: - Dolby Enc Inp1_4
                    Mute  cmdID= 42528  "
        ::= { iqmux33CmdEntry 42528 }


    iqmux33DolbyEncInp14Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder A1 input source
                 TYPE: - RadiobuttonList
                 PAGE: - Dolby Enc Inp1_4
                    Src  cmdID= 42536
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqmux33CmdEntry 42536 }


    iqmux33DolbyEncInp14Source2ProcGain OBJECT-TYPE
        SYNTAX            INTEGER
        MAX-ACCESS        read-write
        STATUS            current
        DESCRIPTION
                "CMNT: - Dolby encoder A2 input gain
                 TYPE: - Number
                 PAGE: - Dolby Enc Inp1_4
                    ProcGain  cmdID= 42521
                    min= -801  max= 120  step= 1  format= %0.1f dB  div_scale= 10  preset= 0
                    Min = -80.1 dB  Max = 12.0 dB  Step = 0.1 dB  Preset = 0.0 dB  "
        ::= { iqmux33CmdEntry 42521 }


    iqmux33DolbyEncInp14Source2Mute OBJECT-TYPE
        SYNTAX            INTEGER { disable(0), enable(1)  }
        MAX-ACCESS        read-write
        STATUS            current
        DESCRIPTION
                "CMNT: - Dolby encoder A2 input mute
                 TYPE: - Checkbox
                 PAGE: - Dolby Enc Inp1_4
                    Mute  cmdID= 42529  "
        ::= { iqmux33CmdEntry 42529 }


    iqmux33DolbyEncInp14Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder A2 input source
                 TYPE: - RadiobuttonList
                 PAGE: - Dolby Enc Inp1_4
                    Src  cmdID= 42537
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqmux33CmdEntry 42537 }


    iqmux33DolbyEncInp14Source3ProcGain OBJECT-TYPE
        SYNTAX            INTEGER
        MAX-ACCESS        read-write
        STATUS            current
        DESCRIPTION
                "CMNT: - Dolby encoder B3 input gain
                 TYPE: - Number
                 PAGE: - Dolby Enc Inp1_4
                    ProcGain  cmdID= 42522
                    min= -801  max= 120  step= 1  format= %0.1f dB  div_scale= 10  preset= 0
                    Min = -80.1 dB  Max = 12.0 dB  Step = 0.1 dB  Preset = 0.0 dB  "
        ::= { iqmux33CmdEntry 42522 }


    iqmux33DolbyEncInp14Source3Mute OBJECT-TYPE
        SYNTAX            INTEGER { disable(0), enable(1)  }
        MAX-ACCESS        read-write
        STATUS            current
        DESCRIPTION
                "CMNT: - Dolby encoder B3 input mute
                 TYPE: - Checkbox
                 PAGE: - Dolby Enc Inp1_4
                    Mute  cmdID= 42530  "
        ::= { iqmux33CmdEntry 42530 }


    iqmux33DolbyEncInp14Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder B3 input source
                 TYPE: - RadiobuttonList
                 PAGE: - Dolby Enc Inp1_4
                    Src  cmdID= 42538
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqmux33CmdEntry 42538 }


    iqmux33DolbyEncInp14Source4ProcGain OBJECT-TYPE
        SYNTAX            INTEGER
        MAX-ACCESS        read-write
        STATUS            current
        DESCRIPTION
                "CMNT: - Dolby encoder B4 input gain
                 TYPE: - Number
                 PAGE: - Dolby Enc Inp1_4
                    ProcGain  cmdID= 42523
                    min= -801  max= 120  step= 1  format= %0.1f dB  div_scale= 10  preset= 0
                    Min = -80.1 dB  Max = 12.0 dB  Step = 0.1 dB  Preset = 0.0 dB  "
        ::= { iqmux33CmdEntry 42523 }


    iqmux33DolbyEncInp14Source4Mute OBJECT-TYPE
        SYNTAX            INTEGER { disable(0), enable(1)  }
        MAX-ACCESS        read-write
        STATUS            current
        DESCRIPTION
                "CMNT: - Dolby encoder B4 input mute
                 TYPE: - Checkbox
                 PAGE: - Dolby Enc Inp1_4
                    Mute  cmdID= 42531  "
        ::= { iqmux33CmdEntry 42531 }


    iqmux33DolbyEncInp14Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder B4 input source
                 TYPE: - RadiobuttonList
                 PAGE: - Dolby Enc Inp1_4
                    Src  cmdID= 42539
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqmux33CmdEntry 42539 }


    iqmux33DolbyEncInp58Source5ProcGain OBJECT-TYPE
        SYNTAX            INTEGER
        MAX-ACCESS        read-write
        STATUS            current
        DESCRIPTION
                "CMNT: - Dolby encoder C5 input gain
                 TYPE: - Number
                 PAGE: - Dolby Enc Inp5_8
                    ProcGain  cmdID= 42524
                    min= -801  max= 120  step= 1  format= %0.1f dB  div_scale= 10  preset= 0
                    Min = -80.1 dB  Max = 12.0 dB  Step = 0.1 dB  Preset = 0.0 dB  "
        ::= { iqmux33CmdEntry 42524 }


    iqmux33DolbyEncInp58Source5Mute OBJECT-TYPE
        SYNTAX            INTEGER { disable(0), enable(1)  }
        MAX-ACCESS        read-write
        STATUS            current
        DESCRIPTION
                "CMNT: - Dolby encoder C5 input mute
                 TYPE: - Checkbox
                 PAGE: - Dolby Enc Inp5_8
                    Mute  cmdID= 42532  "
        ::= { iqmux33CmdEntry 42532 }


    iqmux33DolbyEncInp58Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder C5 input source
                 TYPE: - RadiobuttonList
                 PAGE: - Dolby Enc Inp5_8
                    Src  cmdID= 42540
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqmux33CmdEntry 42540 }


    iqmux33DolbyEncInp58Source6ProcGain OBJECT-TYPE
        SYNTAX            INTEGER
        MAX-ACCESS        read-write
        STATUS            current
        DESCRIPTION
                "CMNT: - Dolby encoder C6 input gain
                 TYPE: - Number
                 PAGE: - Dolby Enc Inp5_8
                    ProcGain  cmdID= 42525
                    min= -801  max= 120  step= 1  format= %0.1f dB  div_scale= 10  preset= 0
                    Min = -80.1 dB  Max = 12.0 dB  Step = 0.1 dB  Preset = 0.0 dB  "
        ::= { iqmux33CmdEntry 42525 }


    iqmux33DolbyEncInp58Source6Mute OBJECT-TYPE
        SYNTAX            INTEGER { disable(0), enable(1)  }
        MAX-ACCESS        read-write
        STATUS            current
        DESCRIPTION
                "CMNT: - Dolby encoder C6 input mute
                 TYPE: - Checkbox
                 PAGE: - Dolby Enc Inp5_8
                    Mute  cmdID= 42533  "
        ::= { iqmux33CmdEntry 42533 }


    iqmux33DolbyEncInp58Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder C6 input source
                 TYPE: - RadiobuttonList
                 PAGE: - Dolby Enc Inp5_8
                    Src  cmdID= 42541
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqmux33CmdEntry 42541 }


    iqmux33DolbyEncInp58Source7ProcGain OBJECT-TYPE
        SYNTAX            INTEGER
        MAX-ACCESS        read-write
        STATUS            current
        DESCRIPTION
                "CMNT: - Dolby encoder D7 input gain
                 TYPE: - Number
                 PAGE: - Dolby Enc Inp5_8
                    ProcGain  cmdID= 42526
                    min= -801  max= 120  step= 1  format= %0.1f dB  div_scale= 10  preset= 0
                    Min = -80.1 dB  Max = 12.0 dB  Step = 0.1 dB  Preset = 0.0 dB  "
        ::= { iqmux33CmdEntry 42526 }


    iqmux33DolbyEncInp58Source7Mute OBJECT-TYPE
        SYNTAX            INTEGER { disable(0), enable(1)  }
        MAX-ACCESS        read-write
        STATUS            current
        DESCRIPTION
                "CMNT: - Dolby encoder D7 input mute
                 TYPE: - Checkbox
                 PAGE: - Dolby Enc Inp5_8
                    Mute  cmdID= 42534  "
        ::= { iqmux33CmdEntry 42534 }


    iqmux33DolbyEncInp58Source7Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder D7 input source
                 TYPE: - RadiobuttonList
                 PAGE: - Dolby Enc Inp5_8
                    Src  cmdID= 42542
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqmux33CmdEntry 42542 }


    iqmux33DolbyEncInp58Source8ProcGain OBJECT-TYPE
        SYNTAX            INTEGER
        MAX-ACCESS        read-write
        STATUS            current
        DESCRIPTION
                "CMNT: - Dolby encoder D8 input gain
                 TYPE: - Number
                 PAGE: - Dolby Enc Inp5_8
                    ProcGain  cmdID= 42527
                    min= -801  max= 120  step= 1  format= %0.1f dB  div_scale= 10  preset= 0
                    Min = -80.1 dB  Max = 12.0 dB  Step = 0.1 dB  Preset = 0.0 dB  "
        ::= { iqmux33CmdEntry 42527 }


    iqmux33DolbyEncInp58Source8Mute OBJECT-TYPE
        SYNTAX            INTEGER { disable(0), enable(1)  }
        MAX-ACCESS        read-write
        STATUS            current
        DESCRIPTION
                "CMNT: - Dolby encoder D8 input mute
                 TYPE: - Checkbox
                 PAGE: - Dolby Enc Inp5_8
                    Mute  cmdID= 42535  "
        ::= { iqmux33CmdEntry 42535 }


    iqmux33DolbyEncInp58Source8Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder D8 input source
                 TYPE: - RadiobuttonList
                 PAGE: - Dolby Enc Inp5_8
                    Src  cmdID= 42543
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqmux33CmdEntry 42543 }


    iqmux33DolbyControlDolbyEncoderControlSampleRateConversion OBJECT-TYPE
        SYNTAX            INTEGER {
                            valEnabled(0),
                            valDisabled(1)
                            }
        MAX-ACCESS        read-write
        STATUS            current
        DESCRIPTION
                "CMNT: - Dolby encoder sample rate converter
                 TYPE: - RadiobuttonList
                 PAGE: - DolbyControl
                    Sample Rate Conversion  cmdID= 42451
                    Enabled  value= 0
                    Disabled  value= 1  "
        ::= { iqmux33CmdEntry 42451 }


    iqmux33DolbyControlDolbyEncoderControlMetaRevertMode OBJECT-TYPE
        SYNTAX            INTEGER {
                            valLastused(0),
                            valInternal(1)
                            }
        MAX-ACCESS        read-write
        STATUS            current
        DESCRIPTION
                "CMNT: - Dolby encoder metadata revert mode
                 TYPE: - RadiobuttonList
                 PAGE: - DolbyControl
                    Meta Revert Mode  cmdID= 42452
                    Last used  value= 0
                    Internal  value= 1  "
        ::= { iqmux33CmdEntry 42452 }


    iqmux33DolbyControlDolbyEncoderControlEncodingMode OBJECT-TYPE
        SYNTAX            INTEGER {
                            valEncode(0),
                            valPassThrough(1)
                            }
        MAX-ACCESS        read-write
        STATUS            current
        DESCRIPTION
                "CMNT: - Dolby encoding mode
                 TYPE: - RadiobuttonList
                 PAGE: - DolbyControl
                    Encoding Mode  cmdID= 42450
                    Encode  value= 0
                    Pass Through  value= 1  "
        ::= { iqmux33CmdEntry 42450 }


    iqmux33DolbyControlDolbyEEncoderCntrlBitDepth OBJECT-TYPE
        SYNTAX            INTEGER {
                            val20bit(0),
                            val16bit(1)
                            }
        MAX-ACCESS        read-write
        STATUS            current
        DESCRIPTION
                "CMNT: - Dolby E encoder bit depth
                 TYPE: - RadiobuttonList
                 PAGE: - DolbyControl
                    Bit Depth  cmdID= 42453
                    20 bit  value= 0
                    16 bit  value= 1  "
        ::= { iqmux33CmdEntry 42453 }


    iqmux33DolbyControlDolbyEEncoderCntrlMetadataSource OBJECT-TYPE
        SYNTAX            INTEGER {
                            valExternal(0),
                            valInternal(1)
                            }
        MAX-ACCESS        read-write
        STATUS            current
        DESCRIPTION
                "CMNT: - Dolby E encoder metadata sample rate converter
                 TYPE: - RadiobuttonList
                 PAGE: - DolbyControl
                    Metadata Source  cmdID= 42456
                    External  value= 0
                    Internal  value= 1  "
        ::= { iqmux33CmdEntry 42456 }


    iqmux33DolbyControlDolbyEEncoderCntrlInternalConfig OBJECT-TYPE
        SYNTAX            INTEGER {
                            val51p2(0),
                            val51p2x1(1),
                            val4p4(2),
                            val4p2x2(3),
                            val4p2p2x1(4),
                            val4p4x1(5),
                            val4x2(6),
                            val3x2p2x1(7),
                            val2x2p4x1(8),
                            val2p6x1(9),
                            val8x1(10),
                            val51(11),
                            val4p2(12),
                            val4p2x1(13),
                            val3x2(14),
                            val2x2p2x1(15),
                            val2p4x1(16),
                            val6x1(17),
                            val4(18),
                            val2p2(19),
                            val2p2x1(20),
                            val4x1(21),
                            val71(22),
                            val71Screen(23)
                            }
        MAX-ACCESS        read-write
        STATUS            current
        DESCRIPTION
                "CMNT: - Dolby E encoder internal program configuration
                 TYPE: - RadiobuttonList
                 PAGE: - DolbyControl
                    Internal Config  cmdID= 42455
                    5.1+2  value= 0
                    5.1+2x1  value= 1
                    4+4  value= 2
                    4+2x2  value= 3
                    4+2+2x1  value= 4
                    4+4x1  value= 5
                    4x2  value= 6
                    3x2+2x1  value= 7
                    2x2+4x1  value= 8
                    2+6x1  value= 9
                    8x1  value= 10
                    5.1  value= 11
                    4+2  value= 12
                    4+2x1  value= 13
                    3x2  value= 14
                    2x2+2x1  value= 15
                    2+4x1  value= 16
                    6x1  value= 17
                    4  value= 18
                    2+2  value= 19
                    2+2x1  value= 20
                    4x1  value= 21
                    7.1  value= 22
                    7.1 Screen  value= 23  "
        ::= { iqmux33CmdEntry 42455 }


    iqmux33DolbyControlDolbyEEncoderCntrlDefaultAllMeta OBJECT-TYPE
        SYNTAX            INTEGER { noAction(0),valDefaultAllMeta(3) }
        MAX-ACCESS        read-write
        STATUS            current
        DESCRIPTION
                "CMNT: - Dolby encoder default all internal metadata
                 TYPE: - Button
                 PAGE: - DolbyControl
                    Default All Meta  cmdID= 42514
                    value= 3  "
        ::= { iqmux33CmdEntry 42514 }


    iqmux33DolbyControlDolbyIntMetaCntrlCopyExtMetadata OBJECT-TYPE
        SYNTAX            INTEGER { noAction(0),valCopyExtMetadata(1) }
        MAX-ACCESS        read-write
        STATUS            current
        DESCRIPTION
                "CMNT: - Dolby encoder copy external metadata to internal
                 TYPE: - Button
                 PAGE: - DolbyControl
                    Copy Ext Metadata  cmdID= 42512
                    value= 1  "
        ::= { iqmux33CmdEntry 42512 }


    iqmux33DolbyControlDolbyIntMetaCntrlDefaultProgramMeta OBJECT-TYPE
        SYNTAX            INTEGER { noAction(0),valDefaultProgramMeta(2) }
        MAX-ACCESS        read-write
        STATUS            current
        DESCRIPTION
                "CMNT: - Dolby encoder default internal metadata
                 TYPE: - Button
                 PAGE: - DolbyControl
                    Default Program Meta  cmdID= 42513
                    value= 2  "
        ::= { iqmux33CmdEntry 42513 }


    iqmux33DolbyControlDolbyIntMetaCntrlDialogueNorm OBJECT-TYPE
        SYNTAX            INTEGER
        MAX-ACCESS        read-write
        STATUS            current
        DESCRIPTION
                "CMNT: - Dolby encoder internal metadata AC-3 dialogue normalisation
                 TYPE: - Number
                 PAGE: - DolbyControl
                    Dialogue Norm  cmdID= 42468
                    min= 1  max= 31  step= 1  format= -%0.0f dBFS  div_scale= 1  preset= 27
                    Min = -1 dBFS  Max = -31 dBFS  Step = -1 dBFS  Preset = -27 dBFS  "
        ::= { iqmux33CmdEntry 42468 }


    iqmux33DolbyControlDolbyIntMetaCntrlChannelMode OBJECT-TYPE
        SYNTAX            INTEGER {
                            val10C(1),
                            val20LR(2),
                            val30LCR(3),
                            val21LRS(4),
                            val31LCRS(5),
                            val22LRSLSR(6),
                            val32LCRSLSR(7)
                            }
        MAX-ACCESS        read-write
        STATUS            current
        DESCRIPTION
                "CMNT: - Dolby encoder internal metadata AC-3 channel (coding) mode
                 TYPE: - RadiobuttonList
                 PAGE: - DolbyControl
                    Channel Mode  cmdID= 42461
                    1/0 (C)  value= 1
                    2/0 (L R)  value= 2
                    3/0 (L C R)  value= 3
                    2/1 (L R S)  value= 4
                    3/1 (L C R S)  value= 5
                    2/2 (L R SL SR)  value= 6
                    3/2 (L C R SL SR)  value= 7  "
        ::= { iqmux33CmdEntry 42461 }


    iqmux33DolbyControlDolbyIntMetaCntrlLFEChannel OBJECT-TYPE
        SYNTAX            INTEGER { disable(0), enable(1)  }
        MAX-ACCESS        read-write
        STATUS            current
        DESCRIPTION
                "CMNT: - Dolby encoder internal metadata AC-3 low frequency effect channel
                 TYPE: - Checkbox
                 PAGE: - DolbyControl
                    LFE Channel  cmdID= 42467  "
        ::= { iqmux33CmdEntry 42467 }


    iqmux33DolbyControlDolbyIntMetaCntrlBitstreamMode OBJECT-TYPE
        SYNTAX            INTEGER {
                            valCompleteMain(0),
                            valMusicEffects(1),
                            valVisuallyImpaired(2),
                            valHearingImpaired(3),
                            valDialogue(4),
                            valCommentary(5),
                            valEmergency(6),
                            valVoiceOverKaraoke(7)
                            }
        MAX-ACCESS        read-write
        STATUS            current
        DESCRIPTION
                "CMNT: - Dolby encoder internal metadata AC-3 bitstream mode
                 TYPE: - RadiobuttonList
                 PAGE: - DolbyControl
                    Bitstream Mode  cmdID= 42460
                    Complete Main  value= 0
                    Music & Effects  value= 1
                    Visually Impaired  value= 2
                    Hearing Impaired  value= 3
                    Dialogue  value= 4
                    Commentary  value= 5
                    Emergency  value= 6
                    Voice Over/Karaoke  value= 7  "
        ::= { iqmux33CmdEntry 42460 }


    iqmux33DolbyControlDolbyIntMetaCntrlRFMode OBJECT-TYPE
        SYNTAX            INTEGER {
                            valNone(0),
                            valFilmStandard(1),
                            valFilmLight(2),
                            valMusicStandard(3),
                            valMusicLight(4),
                            valSpeech(5)
                            }
        MAX-ACCESS        read-write
        STATUS            current
        DESCRIPTION
                "CMNT: - Dolby encoder internal metadata AC-3 RF mode
                 TYPE: - RadiobuttonList
                 PAGE: - DolbyControl
                    RF Mode  cmdID= 42463
                    None  value= 0
                    Film Standard  value= 1
                    Film Light  value= 2
                    Music Standard  value= 3
                    Music Light  value= 4
                    Speech  value= 5  "
        ::= { iqmux33CmdEntry 42463 }


    iqmux33DolbyControlDolbyIntMetaCntrlLineMode OBJECT-TYPE
        SYNTAX            INTEGER {
                            valNone(0),
                            valFilmStandard(1),
                            valFilmLight(2),
                            valMusicStandard(3),
                            valMusicLight(4),
                            valSpeech(5)
                            }
        MAX-ACCESS        read-write
        STATUS            current
        DESCRIPTION
                "CMNT: - Dolby encoder internal metadata AC-3 line mode
                 TYPE: - RadiobuttonList
                 PAGE: - DolbyControl
                    Line Mode  cmdID= 42462
                    None  value= 0
                    Film Standard  value= 1
                    Film Light  value= 2
                    Music Standard  value= 3
                    Music Light  value= 4
                    Speech  value= 5  "
        ::= { iqmux33CmdEntry 42462 }


    iqmux33DolbyIntMetaCntrlAudioProductionInfoExists OBJECT-TYPE
        SYNTAX            INTEGER { disable(0), enable(1)  }
        MAX-ACCESS        read-write
        STATUS            current
        DESCRIPTION
                "CMNT: - Dolby encoder internal metadata AC-3 audio production information exists
                 TYPE: - Checkbox
                 PAGE: - Dolby Int Meta Cntrl
                    Exists  cmdID= 42469  "
        ::= { iqmux33CmdEntry 42469 }


    iqmux33DolbyIntMetaCntrlAudioProductionInfoMixLevel OBJECT-TYPE
        SYNTAX            INTEGER
        MAX-ACCESS        read-write
        STATUS            current
        DESCRIPTION
                "CMNT: - Dolby encoder internal metadata AC-3 audio production mix level
                 TYPE: - Number
                 PAGE: - Dolby Int Meta Cntrl
                    Mix Level  cmdID= 42470
                    min= 80  max= 111  step= 1  format= %0.0f dB SPL  div_scale= 1  preset= 105
                    Min = 80 dB SPL  Max = 111 dB SPL  Step = 1 dB SPL  Preset = 105 dB SPL  "
        ::= { iqmux33CmdEntry 42470 }


    iqmux33DolbyIntMetaCntrlAudioProductionInfoRoomType OBJECT-TYPE
        SYNTAX            INTEGER {
                            valNotindicated(0),
                            valLarge(1),
                            valSmall(2)
                            }
        MAX-ACCESS        read-write
        STATUS            current
        DESCRIPTION
                "CMNT: - Dolby encoder internal metadata AC-3 audio production room type
                 TYPE: - RadiobuttonList
                 PAGE: - Dolby Int Meta Cntrl
                    Room Type  cmdID= 42471
                    Not indicated  value= 0
                    Large  value= 1
                    Small  value= 2  "
        ::= { iqmux33CmdEntry 42471 }


    iqmux33DolbyControlDolbyIntMetaCntrlCentreMixLevel OBJECT-TYPE
        SYNTAX            INTEGER {
                            valn30dB(0),
                            valn45dB(1),
                            valn60dB(2)
                            }
        MAX-ACCESS        read-write
        STATUS            current
        DESCRIPTION
                "CMNT: - Dolby encoder internal metadata AC-3 centre mix level
                 TYPE: - RadiobuttonList
                 PAGE: - DolbyControl
                    Centre Mix Level  cmdID= 42464
                    -3.0dB  value= 0
                    -4.5dB  value= 1
                    -6.0dB  value= 2  "
        ::= { iqmux33CmdEntry 42464 }


    iqmux33DolbyControlDolbyIntMetaCntrlSurroundMixLevel OBJECT-TYPE
        SYNTAX            INTEGER {
                            valn30dB(0),
                            valn60dB(1),
                            valOff(2)
                            }
        MAX-ACCESS        read-write
        STATUS            current
        DESCRIPTION
                "CMNT: - Dolby encoder internal metadata AC-3 surround mix level
                 TYPE: - RadiobuttonList
                 PAGE: - DolbyControl
                    Surround Mix Level  cmdID= 42465
                    -3.0dB  value= 0
                    -6.0dB  value= 1
                    Off  value= 2  "
        ::= { iqmux33CmdEntry 42465 }


    iqmux33DolbyControlDolbyIntMetaCntrlSurroundMode OBJECT-TYPE
        SYNTAX            INTEGER {
                            valNotindicated(0),
                            valOff(1),
                            valOn(2)
                            }
        MAX-ACCESS        read-write
        STATUS            current
        DESCRIPTION
                "CMNT: - Dolby encoder internal metadata AC-3 surround mode
                 TYPE: - RadiobuttonList
                 PAGE: - DolbyControl
                    Surround Mode  cmdID= 42466
                    Not indicated  value= 0
                    Off  value= 1
                    On  value= 2  "
        ::= { iqmux33CmdEntry 42466 }


    iqmux33DolbyControlDolbyIntMetaCntrlCopyright OBJECT-TYPE
        SYNTAX            INTEGER { disable(0), enable(1)  }
        MAX-ACCESS        read-write
        STATUS            current
        DESCRIPTION
                "CMNT: - Dolby encoder internal metadata AC-3 copyright
                 TYPE: - Checkbox
                 PAGE: - DolbyControl
                    Copyright  cmdID= 42384  "
        ::= { iqmux33CmdEntry 42384 }


    iqmux33DolbyIntMetaCntrlExtendedBSI1Exists OBJECT-TYPE
        SYNTAX            INTEGER { disable(0), enable(1)  }
        MAX-ACCESS        read-write
        STATUS            current
        DESCRIPTION
                "CMNT: - Dolby encoder internal metadata AC-3 BSI 1 exists
                 TYPE: - Checkbox
                 PAGE: - Dolby Int Meta Cntrl
                    Exists  cmdID= 42472  "
        ::= { iqmux33CmdEntry 42472 }


    iqmux33DolbyIntMetaCntrlExtendedBSI1StereoDownmixMode OBJECT-TYPE
        SYNTAX            INTEGER {
                            valNotindicated(0),
                            valLtRtPreferred(1),
                            valLoRoPreferred(2)
                            }
        MAX-ACCESS        read-write
        STATUS            current
        DESCRIPTION
                "CMNT: - Dolby encoder internal metadata AC-3 BSI 1 preferred stereo downmix mode
                 TYPE: - RadiobuttonList
                 PAGE: - Dolby Int Meta Cntrl
                    Stereo Downmix Mode  cmdID= 42473
                    Not indicated  value= 0
                    LtRt Preferred  value= 1
                    LoRo Preferred  value= 2  "
        ::= { iqmux33CmdEntry 42473 }


    iqmux33DolbyIntMetaCntrlExtendedBSI1LtRtCentreMixLevel OBJECT-TYPE
        SYNTAX            INTEGER {
                            valp30dB(0),
                            valp15dB(1),
                            valp00dB(2),
                            valn15dB(3),
                            valn30dB(4),
                            valn45dB(5),
                            valn60dB(6),
                            valOff(7)
                            }
        MAX-ACCESS        read-write
        STATUS            current
        DESCRIPTION
                "CMNT: - Dolby encoder internal metadata AC-3 BSI 1 LtRt centre mix level
                 TYPE: - RadiobuttonList
                 PAGE: - Dolby Int Meta Cntrl
                    Lt/Rt Centre Mix Level  cmdID= 42474
                    +3.0dB  value= 0
                    +1.5dB  value= 1
                    +0.0dB  value= 2
                    -1.5dB  value= 3
                    -3.0dB  value= 4
                    -4.5dB  value= 5
                    -6.0dB  value= 6
                    Off  value= 7  "
        ::= { iqmux33CmdEntry 42474 }


    iqmux33DolbyIntMetaCntrlExtendedBSI1LtRtSurrMixLevel OBJECT-TYPE
        SYNTAX            INTEGER {
                            valn15dB(3),
                            valn30dB(4),
                            valn45dB(5),
                            valn60dB(6),
                            valOff(7)
                            }
        MAX-ACCESS        read-write
        STATUS            current
        DESCRIPTION
                "CMNT: - Dolby encoder internal metadata AC-3 BSI 1 LtRt surround mix level
                 TYPE: - RadiobuttonList
                 PAGE: - Dolby Int Meta Cntrl
                    Lt/Rt Surr Mix Level  cmdID= 42475
                    -1.5dB  value= 3
                    -3.0dB  value= 4
                    -4.5dB  value= 5
                    -6.0dB  value= 6
                    Off  value= 7  "
        ::= { iqmux33CmdEntry 42475 }


    iqmux33DolbyIntMetaCntrlExtendedBSI1LoRoCentreMixLevel OBJECT-TYPE
        SYNTAX            INTEGER {
                            valp30dB(0),
                            valp15dB(1),
                            valp00dB(2),
                            valn15dB(3),
                            valn30dB(4),
                            valn45dB(5),
                            valn60dB(6),
                            valOff(7)
                            }
        MAX-ACCESS        read-write
        STATUS            current
        DESCRIPTION
                "CMNT: - Dolby encoder internal metadata AC-3 BSI 1 LoRo centre mix level
                 TYPE: - RadiobuttonList
                 PAGE: - Dolby Int Meta Cntrl
                    Lo/Ro Centre Mix Level  cmdID= 42476
                    +3.0dB  value= 0
                    +1.5dB  value= 1
                    +0.0dB  value= 2
                    -1.5dB  value= 3
                    -3.0dB  value= 4
                    -4.5dB  value= 5
                    -6.0dB  value= 6
                    Off  value= 7  "
        ::= { iqmux33CmdEntry 42476 }


    iqmux33DolbyIntMetaCntrlExtendedBSI1LoRoSurrMixLevel OBJECT-TYPE
        SYNTAX            INTEGER {
                            valn15dB(3),
                            valn30dB(4),
                            valn45dB(5),
                            valn60dB(6),
                            valOff(7)
                            }
        MAX-ACCESS        read-write
        STATUS            current
        DESCRIPTION
                "CMNT: - Dolby encoder internal metadata AC-3 BSI 1 LoRo surround mix level
                 TYPE: - RadiobuttonList
                 PAGE: - Dolby Int Meta Cntrl
                    Lo/Ro Surr Mix Level  cmdID= 42477
                    -1.5dB  value= 3
                    -3.0dB  value= 4
                    -4.5dB  value= 5
                    -6.0dB  value= 6
                    Off  value= 7  "
        ::= { iqmux33CmdEntry 42477 }


    iqmux33DolbyIntMetaCntrlExtendedBSI2Exists OBJECT-TYPE
        SYNTAX            INTEGER { disable(0), enable(1)  }
        MAX-ACCESS        read-write
        STATUS            current
        DESCRIPTION
                "CMNT: - Dolby encoder internal metadata AC-3 BSI 2 exists
                 TYPE: - Checkbox
                 PAGE: - Dolby Int Meta Cntrl
                    Exists  cmdID= 42478  "
        ::= { iqmux33CmdEntry 42478 }


    iqmux33DolbyIntMetaCntrlExtendedBSI2SurroundEXMode OBJECT-TYPE
        SYNTAX            INTEGER {
                            valNotindicated(0),
                            valOff(1),
                            valOn(2)
                            }
        MAX-ACCESS        read-write
        STATUS            current
        DESCRIPTION
                "CMNT: - Dolby encoder internal metadata AC-3 BSI 2 surround EX mode
                 TYPE: - RadiobuttonList
                 PAGE: - Dolby Int Meta Cntrl
                    Surround EX Mode  cmdID= 42479
                    Not indicated  value= 0
                    Off  value= 1
                    On  value= 2  "
        ::= { iqmux33CmdEntry 42479 }


    iqmux33DolbyIntMetaCntrlExtendedBSI2LowpassFilter OBJECT-TYPE
        SYNTAX            INTEGER { disable(0), enable(1)  }
        MAX-ACCESS        read-write
        STATUS            current
        DESCRIPTION
                "CMNT: - Dolby encoder internal metadata AC-3 BSI 2 lowpass filter
                 TYPE: - Checkbox
                 PAGE: - Dolby Int Meta Cntrl
                    Lowpass Filter  cmdID= 42480  "
        ::= { iqmux33CmdEntry 42480 }


    iqmux33DolbyIntMetaCntrlExtendedBSI2LFEFIlter OBJECT-TYPE
        SYNTAX            INTEGER { disable(0), enable(1)  }
        MAX-ACCESS        read-write
        STATUS            current
        DESCRIPTION
                "CMNT: - Dolby encoder internal metadata AC-3 BSI 2 LFE filter
                 TYPE: - Checkbox
                 PAGE: - Dolby Int Meta Cntrl
                    LFE FIlter  cmdID= 42481  "
        ::= { iqmux33CmdEntry 42481 }


    iqmux33DolbyIntMetaCntrlExtendedBSI2SurrPhaseShiftFltr OBJECT-TYPE
        SYNTAX            INTEGER { disable(0), enable(1)  }
        MAX-ACCESS        read-write
        STATUS            current
        DESCRIPTION
                "CMNT: - Dolby encoder internal metadata AC-3 BSI 2 surround 90deg phase shift filter
                 TYPE: - Checkbox
                 PAGE: - Dolby Int Meta Cntrl
                    Surr Phase Shift Fltr  cmdID= 42482  "
        ::= { iqmux33CmdEntry 42482 }


    iqmux33DolbyIntMetaCntrlExtendedBSI2Surr3dBAttenuator OBJECT-TYPE
        SYNTAX            INTEGER { disable(0), enable(1)  }
        MAX-ACCESS        read-write
        STATUS            current
        DESCRIPTION
                "CMNT: - Dolby encoder internal metadata AC-3 BSI 2 3dB surround channel attenuator
                 TYPE: - Checkbox
                 PAGE: - Dolby Int Meta Cntrl
                    Surr 3dB Attenuator  cmdID= 42483  "
        ::= { iqmux33CmdEntry 42483 }


    iqmux33DolbyControlDolbyIntMetaCntrlProgramDescriptionL OBJECT-TYPE
        SYNTAX            RollCallString
        MAX-ACCESS        read-write
        STATUS            current
        DESCRIPTION
                "CMNT: - Dolby encoder internal metadata text description (LH part)
                 TYPE: - Editstring
                 PAGE: - DolbyControl
                    Program Description L  cmdID= 42510
                    preset= Prog"
        ::= { iqmux33CmdEntry 42510 }


    iqmux33DolbyControlDolbyIntMetaCntrlProgramDescriptionR OBJECT-TYPE
        SYNTAX            RollCallString
        MAX-ACCESS        read-write
        STATUS            current
        DESCRIPTION
                "CMNT: - Dolby encoder internal metadata text description (RH part)
                 TYPE: - Editstring
                 PAGE: - DolbyControl
                    Program Description R  cmdID= 42511
                    preset= Prog"
        ::= { iqmux33CmdEntry 42511 }


    iqmux33DolbyControlDolbyIntMetaCntrlIntMetaSaveset OBJECT-TYPE
        SYNTAX            INTEGER
        MAX-ACCESS        read-write
        STATUS            current
        DESCRIPTION
                "CMNT: - Used to save 8 internal metadata programs through RollCall
                 TYPE: - Number
                 PAGE: - DolbyControl
                    Int Meta Saveset  cmdID= 42590
                    min= 0  max= 8  step= 1  format= %0.0f  div_scale= 1  preset= 0
                    Min = 0  Max = 8  Step = 1  Preset = 0  "
        ::= { iqmux33CmdEntry 42590 }


    iqmux33DolbyControlDolbyDEncoderCntrlInternalMode OBJECT-TYPE
        SYNTAX            INTEGER {
                            valFilmSurround(0),
                            valFilmStereo(1),
                            valMusicSurround(2),
                            valMusicStereo(3),
                            valManual(4)
                            }
        MAX-ACCESS        read-write
        STATUS            current
        DESCRIPTION
                "CMNT: - Dolby Digital encoder internal metadata mode
                 TYPE: - RadiobuttonList
                 PAGE: - DolbyControl
                    Internal Mode  cmdID= 42485
                    Film Surround  value= 0
                    Film Stereo  value= 1
                    Music Surround  value= 2
                    Music Stereo  value= 3
                    Manual  value= 4  "
        ::= { iqmux33CmdEntry 42485 }


    iqmux33DolbyControlDolbyDEncoderCntrlBitstreamFormat OBJECT-TYPE
        SYNTAX            INTEGER {
                            val32bit(0),
                            val16bitChl1(1),
                            val16bitChl2(2)
                            }
        MAX-ACCESS        read-write
        STATUS            current
        DESCRIPTION
                "CMNT: - Dolby D encoder bit depth
                 TYPE: - RadiobuttonList
                 PAGE: - DolbyControl
                    Bitstream Format  cmdID= 42454
                    32 bit  value= 0
                    16 bit Chl1  value= 1
                    16 bit Chl2  value= 2  "
        ::= { iqmux33CmdEntry 42454 }


    iqmux33DolbyControlDolbyDEncoderCntrlMetadataSource OBJECT-TYPE
        SYNTAX            INTEGER {
                            valProgram1(0),
                            valProgram2(1),
                            valProgram3(2),
                            valProgram4(3),
                            valProgram5(4),
                            valProgram6(5),
                            valProgram7(6),
                            valProgram8(7),
                            valInternal(8)
                            }
        MAX-ACCESS        read-write
        STATUS            current
        DESCRIPTION
                "CMNT: - Dolby D encoder metadata sample rate converter
                 TYPE: - RadiobuttonList
                 PAGE: - DolbyControl
                    Metadata Source  cmdID= 42498
                    Program 1  value= 0
                    Program 2  value= 1
                    Program 3  value= 2
                    Program 4  value= 3
                    Program 5  value= 4
                    Program 6  value= 5
                    Program 7  value= 6
                    Program 8  value= 7
                    Internal  value= 8  "
        ::= { iqmux33CmdEntry 42498 }


    iqmux33DolbyControlDolbyDEncoderCntrlIntMetaDataRate OBJECT-TYPE
        SYNTAX            INTEGER {
                            valAuto384(0),
                            valAuto448(1),
                            val56kbps(2),
                            val64kbps(3),
                            val80kbps(4),
                            val96kbps(5),
                            val112kbps(6),
                            val128kbps(7),
                            val160kbps(8),
                            val192kbps(9),
                            val224kbps(10),
                            val256kbps(11),
                            val320kbps(12),
                            val384kbps(13),
                            val448kbps(14),
                            val512kbps(15),
                            val576kbps(16),
                            val640kbps(17)
                            }
        MAX-ACCESS        read-write
        STATUS            current
        DESCRIPTION
                "CMNT: - Dolby D encoder internal metadata rate
                 TYPE: - RadiobuttonList
                 PAGE: - DolbyControl
                    Int Meta Data Rate  cmdID= 42499
                    Auto 384  value= 0
                    Auto 448  value= 1
                    56 kbps  value= 2
                    64 kbps  value= 3
                    80 kbps  value= 4
                    96 kbps  value= 5
                    112 kbps  value= 6
                    128 kbps  value= 7
                    160 kbps  value= 8
                    192 kbps  value= 9
                    224 kbps  value= 10
                    256 kbps  value= 11
                    320 kbps  value= 12
                    384 kbps  value= 13
                    448 kbps  value= 14
                    512 kbps  value= 15
                    576 kbps  value= 16
                    640 kbps  value= 17  "
        ::= { iqmux33CmdEntry 42499 }


    iqmux33DolbyControlDolbyDEncoderCntrlExtMetaDataRate OBJECT-TYPE
        SYNTAX            INTEGER {
                            valAuto384(0),
                            valAuto448(1),
                            val56kbps(2),
                            val64kbps(3),
                            val80kbps(4),
                            val96kbps(5),
                            val112kbps(6),
                            val128kbps(7),
                            val160kbps(8),
                            val192kbps(9),
                            val224kbps(10),
                            val256kbps(11),
                            val320kbps(12),
                            val384kbps(13),
                            val448kbps(14),
                            val512kbps(15),
                            val576kbps(16),
                            val640kbps(17)
                            }
        MAX-ACCESS        read-write
        STATUS            current
        DESCRIPTION
                "CMNT: - Dolby D encoder external metadata rate
                 TYPE: - RadiobuttonList
                 PAGE: - DolbyControl
                    Ext Meta Data Rate  cmdID= 42500
                    Auto 384  value= 0
                    Auto 448  value= 1
                    56 kbps  value= 2
                    64 kbps  value= 3
                    80 kbps  value= 4
                    96 kbps  value= 5
                    112 kbps  value= 6
                    128 kbps  value= 7
                    160 kbps  value= 8
                    192 kbps  value= 9
                    224 kbps  value= 10
                    256 kbps  value= 11
                    320 kbps  value= 12
                    384 kbps  value= 13
                    448 kbps  value= 14
                    512 kbps  value= 15
                    576 kbps  value= 16
                    640 kbps  value= 17  "
        ::= { iqmux33CmdEntry 42500 }


    iqmux33DolbyControlDolbyDEncoderCntrlStreamNumber OBJECT-TYPE
        SYNTAX            INTEGER {
                            valStream0(0),
                            valStream1(1),
                            valStream2(2),
                            valStream3(3),
                            valStream4(4),
                            valStream5(5),
                            valStream6(6)
                            }
        MAX-ACCESS        read-write
        STATUS            current
        DESCRIPTION
                "CMNT: - Dolby D encoder stream number
                 TYPE: - RadiobuttonList
                 PAGE: - DolbyControl
                    Stream Number  cmdID= 42357
                    Stream 0  value= 0
                    Stream 1  value= 1
                    Stream 2  value= 2
                    Stream 3  value= 3
                    Stream 4  value= 4
                    Stream 5  value= 5
                    Stream 6  value= 6  "
        ::= { iqmux33CmdEntry 42357 }


    iqmux33DolbyControlDolbyMetaProgSelMetaProgramSelect OBJECT-TYPE
        SYNTAX            INTEGER {
                            valProgram1(0),
                            valProgram2(1),
                            valProgram3(2),
                            valProgram4(3),
                            valProgram5(4),
                            valProgram6(5),
                            valProgram7(6),
                            valProgram8(7)
                            }
        MAX-ACCESS        read-write
        STATUS            current
        DESCRIPTION
                "CMNT: - Dolby metadata program select
                 TYPE: - RadiobuttonList
                 PAGE: - DolbyControl
                    Meta Program Select  cmdID= 42413
                    Program 1  value= 0
                    Program 2  value= 1
                    Program 3  value= 2
                    Program 4  value= 3
                    Program 5  value= 4
                    Program 6  value= 5
                    Program 7  value= 6
                    Program 8  value= 7  "
        ::= { iqmux33CmdEntry 42413 }


    iqmux33DolbyStatusDolbyCommonStatusVideoSync OBJECT-TYPE
        SYNTAX            RollCallString
        MAX-ACCESS        read-only
        STATUS            current
        DESCRIPTION
                "CMNT: - Dolby video sync status
                 TYPE: - Display
                 PAGE: - DolbyStatus
                    Video Sync  cmdID= 42381  "
        ::= { iqmux33CmdEntry 42381 }


    iqmux33DolbyStatusDolbyCommonStatusFrameRate OBJECT-TYPE
        SYNTAX            RollCallString
        MAX-ACCESS        read-only
        STATUS            current
        DESCRIPTION
                "CMNT: - Dolby video frame rate
                 TYPE: - Display
                 PAGE: - DolbyStatus
                    Frame Rate  cmdID= 42412  "
        ::= { iqmux33CmdEntry 42412 }


    iqmux33DolbyStatusDolbyCommonStatusProgramConfig OBJECT-TYPE
        SYNTAX            RollCallString
        MAX-ACCESS        read-only
        STATUS            current
        DESCRIPTION
                "CMNT: - Dolby external metadata program configuration
                 TYPE: - Display
                 PAGE: - DolbyStatus
                    Program Config  cmdID= 42439  "
        ::= { iqmux33CmdEntry 42439 }


    iqmux33DolbyStatusDolbyCommonStatusFWVersion OBJECT-TYPE
        SYNTAX            RollCallString
        MAX-ACCESS        read-only
        STATUS            current
        DESCRIPTION
                "CMNT: - Dolby firmware version
                 TYPE: - Display
                 PAGE: - DolbyStatus
                    F/W Version  cmdID= 42493  "
        ::= { iqmux33CmdEntry 42493 }


    iqmux33DolbyStatusDolbyCommonStatusDeviceName OBJECT-TYPE
        SYNTAX            RollCallString
        MAX-ACCESS        read-only
        STATUS            current
        DESCRIPTION
                "CMNT: - Dolby device name
                 TYPE: - Display
                 PAGE: - DolbyStatus
                    Device Name  cmdID= 42495  "
        ::= { iqmux33CmdEntry 42495 }


    iqmux33DolbyCommonStatusChannelAssignmentDolbyA1 OBJECT-TYPE
        SYNTAX            RollCallString
        MAX-ACCESS        read-only
        STATUS            current
        DESCRIPTION
                "CMNT: - Dolby encoder A1 input channel assignment
                 TYPE: - Display
                 PAGE: - Dolby Common Status
                    Dolby A1  cmdID= 42548  "
        ::= { iqmux33CmdEntry 42548 }


    iqmux33DolbyCommonStatusChannelAssignmentDolbyA2 OBJECT-TYPE
        SYNTAX            RollCallString
        MAX-ACCESS        read-only
        STATUS            current
        DESCRIPTION
                "CMNT: - Dolby encoder A2 input channel assignment
                 TYPE: - Display
                 PAGE: - Dolby Common Status
                    Dolby A2  cmdID= 42549  "
        ::= { iqmux33CmdEntry 42549 }


    iqmux33DolbyCommonStatusChannelAssignmentDolbyB3 OBJECT-TYPE
        SYNTAX            RollCallString
        MAX-ACCESS        read-only
        STATUS            current
        DESCRIPTION
                "CMNT: - Dolby encoder B3 input channel assignment
                 TYPE: - Display
                 PAGE: - Dolby Common Status
                    Dolby B3  cmdID= 42550  "
        ::= { iqmux33CmdEntry 42550 }


    iqmux33DolbyCommonStatusChannelAssignmentDolbyB4 OBJECT-TYPE
        SYNTAX            RollCallString
        MAX-ACCESS        read-only
        STATUS            current
        DESCRIPTION
                "CMNT: - Dolby encoder B4 input channel assignment
                 TYPE: - Display
                 PAGE: - Dolby Common Status
                    Dolby B4  cmdID= 42551  "
        ::= { iqmux33CmdEntry 42551 }


    iqmux33DolbyCommonStatusChannelAssignmentDolbyC5 OBJECT-TYPE
        SYNTAX            RollCallString
        MAX-ACCESS        read-only
        STATUS            current
        DESCRIPTION
                "CMNT: - Dolby encoder C5 input channel assignment
                 TYPE: - Display
                 PAGE: - Dolby Common Status
                    Dolby C5  cmdID= 42552  "
        ::= { iqmux33CmdEntry 42552 }


    iqmux33DolbyCommonStatusChannelAssignmentDolbyC6 OBJECT-TYPE
        SYNTAX            RollCallString
        MAX-ACCESS        read-only
        STATUS            current
        DESCRIPTION
                "CMNT: - Dolby encoder C6 input channel assignment
                 TYPE: - Display
                 PAGE: - Dolby Common Status
                    Dolby C6  cmdID= 42553  "
        ::= { iqmux33CmdEntry 42553 }


    iqmux33DolbyCommonStatusChannelAssignmentDolbyD7 OBJECT-TYPE
        SYNTAX            RollCallString
        MAX-ACCESS        read-only
        STATUS            current
        DESCRIPTION
                "CMNT: - Dolby encoder D7 input channel assignment
                 TYPE: - Display
                 PAGE: - Dolby Common Status
                    Dolby D7  cmdID= 42554  "
        ::= { iqmux33CmdEntry 42554 }


    iqmux33DolbyCommonStatusChannelAssignmentDolbyD8 OBJECT-TYPE
        SYNTAX            RollCallString
        MAX-ACCESS        read-only
        STATUS            current
        DESCRIPTION
                "CMNT: - Dolby encoder D8 input channel assignment
                 TYPE: - Display
                 PAGE: - Dolby Common Status
                    Dolby D8  cmdID= 42555  "
        ::= { iqmux33CmdEntry 42555 }


    iqmux33DolbyCommonStatusChnlPairAssignmentDolby12 OBJECT-TYPE
        SYNTAX            RollCallString
        MAX-ACCESS        read-only
        STATUS            current
        DESCRIPTION
                "CMNT: - Dolby encoder A1/A2 output channel assignment
                 TYPE: - Display
                 PAGE: - Dolby Common Status
                    Dolby 1/2  cmdID= 42544  "
        ::= { iqmux33CmdEntry 42544 }


    iqmux33DolbyCommonStatusChnlPairAssignmentDolby34 OBJECT-TYPE
        SYNTAX            RollCallString
        MAX-ACCESS        read-only
        STATUS            current
        DESCRIPTION
                "CMNT: - Dolby encoder B3/B4 output channel assignment
                 TYPE: - Display
                 PAGE: - Dolby Common Status
                    Dolby 3/4  cmdID= 42545  "
        ::= { iqmux33CmdEntry 42545 }


    iqmux33DolbyCommonStatusChnlPairAssignmentDolby56 OBJECT-TYPE
        SYNTAX            RollCallString
        MAX-ACCESS        read-only
        STATUS            current
        DESCRIPTION
                "CMNT: - Dolby encoder C5/C6 output channel assignment
                 TYPE: - Display
                 PAGE: - Dolby Common Status
                    Dolby 5/6  cmdID= 42546  "
        ::= { iqmux33CmdEntry 42546 }


    iqmux33DolbyCommonStatusChnlPairAssignmentDolby78 OBJECT-TYPE
        SYNTAX            RollCallString
        MAX-ACCESS        read-only
        STATUS            current
        DESCRIPTION
                "CMNT: - Dolby encoder D7/D8 output channel assignment
                 TYPE: - Display
                 PAGE: - Dolby Common Status
                    Dolby 7/8  cmdID= 42547  "
        ::= { iqmux33CmdEntry 42547 }


    iqmux33DolbyStatusDolbyExtProgStatusP1Status OBJECT-TYPE
        SYNTAX            RollCallString
        MAX-ACCESS        read-only
        STATUS            current
        DESCRIPTION
                "CMNT: - Dolby external metadata program 1 status
                 TYPE: - Display
                 PAGE: - DolbyStatus
                    P1 Status  cmdID= 42441  "
        ::= { iqmux33CmdEntry 42441 }


    iqmux33DolbyStatusDolbyExtProgStatusP2Status OBJECT-TYPE
        SYNTAX            RollCallString
        MAX-ACCESS        read-only
        STATUS            current
        DESCRIPTION
                "CMNT: - Dolby external metadata program 2 status
                 TYPE: - Display
                 PAGE: - DolbyStatus
                    P2 Status  cmdID= 42442  "
        ::= { iqmux33CmdEntry 42442 }


    iqmux33DolbyStatusDolbyExtProgStatusP3Status OBJECT-TYPE
        SYNTAX            RollCallString
        MAX-ACCESS        read-only
        STATUS            current
        DESCRIPTION
                "CMNT: - Dolby external metadata program 3 status
                 TYPE: - Display
                 PAGE: - DolbyStatus
                    P3 Status  cmdID= 42443  "
        ::= { iqmux33CmdEntry 42443 }


    iqmux33DolbyStatusDolbyExtProgStatusP4Status OBJECT-TYPE
        SYNTAX            RollCallString
        MAX-ACCESS        read-only
        STATUS            current
        DESCRIPTION
                "CMNT: - Dolby external metadata program 4 status
                 TYPE: - Display
                 PAGE: - DolbyStatus
                    P4 Status  cmdID= 42444  "
        ::= { iqmux33CmdEntry 42444 }


    iqmux33DolbyStatusDolbyExtProgStatusP5Status OBJECT-TYPE
        SYNTAX            RollCallString
        MAX-ACCESS        read-only
        STATUS            current
        DESCRIPTION
                "CMNT: - Dolby external metadata program 5 status
                 TYPE: - Display
                 PAGE: - DolbyStatus
                    P5 Status  cmdID= 42445  "
        ::= { iqmux33CmdEntry 42445 }


    iqmux33DolbyStatusDolbyExtProgStatusP6Status OBJECT-TYPE
        SYNTAX            RollCallString
        MAX-ACCESS        read-only
        STATUS            current
        DESCRIPTION
                "CMNT: - Dolby external metadata program 6 status
                 TYPE: - Display
                 PAGE: - DolbyStatus
                    P6 Status  cmdID= 42446  "
        ::= { iqmux33CmdEntry 42446 }


    iqmux33DolbyStatusDolbyExtProgStatusP7Status OBJECT-TYPE
        SYNTAX            RollCallString
        MAX-ACCESS        read-only
        STATUS            current
        DESCRIPTION
                "CMNT: - Dolby external metadata program 7 status
                 TYPE: - Display
                 PAGE: - DolbyStatus
                    P7 Status  cmdID= 42447  "
        ::= { iqmux33CmdEntry 42447 }


    iqmux33DolbyStatusDolbyExtProgStatusP8Status OBJECT-TYPE
        SYNTAX            RollCallString
        MAX-ACCESS        read-only
        STATUS            current
        DESCRIPTION
                "CMNT: - Dolby external metadata program 8 status
                 TYPE: - Display
                 PAGE: - DolbyStatus
                    P8 Status  cmdID= 42448  "
        ::= { iqmux33CmdEntry 42448 }


    iqmux33DolbyStatusDolbyMetadataStatusProgramDescriptionL OBJECT-TYPE
        SYNTAX            RollCallString
        MAX-ACCESS        read-only
        STATUS            current
        DESCRIPTION
                "CMNT: - Dolby metadata AC-3 status text description (LH part)
                 TYPE: - Display
                 PAGE: - DolbyStatus
                    Program Description L  cmdID= 42508  "
        ::= { iqmux33CmdEntry 42508 }


    iqmux33DolbyStatusDolbyMetadataStatusProgramDescriptionR OBJECT-TYPE
        SYNTAX            RollCallString
        MAX-ACCESS        read-only
        STATUS            current
        DESCRIPTION
                "CMNT: - Dolby metadata AC-3 status text description (RH part)
                 TYPE: - Display
                 PAGE: - DolbyStatus
                    Program Description R  cmdID= 42509  "
        ::= { iqmux33CmdEntry 42509 }


    iqmux33DolbyStatusDolbyMetadataStatusDialogueNorm OBJECT-TYPE
        SYNTAX            RollCallString
        MAX-ACCESS        read-only
        STATUS            current
        DESCRIPTION
                "CMNT: - Dolby metadata AC-3 status dialogue normalisation
                 TYPE: - Display
                 PAGE: - DolbyStatus
                    Dialogue Norm  cmdID= 42422  "
        ::= { iqmux33CmdEntry 42422 }


    iqmux33DolbyStatusDolbyMetadataStatusChannelMode OBJECT-TYPE
        SYNTAX            RollCallString
        MAX-ACCESS        read-only
        STATUS            current
        DESCRIPTION
                "CMNT: - Dolby metadata AC-3 status channel (coding) mode
                 TYPE: - Display
                 PAGE: - DolbyStatus
                    Channel Mode  cmdID= 42415  "
        ::= { iqmux33CmdEntry 42415 }


    iqmux33DolbyStatusDolbyMetadataStatusLFE OBJECT-TYPE
        SYNTAX            RollCallString
        MAX-ACCESS        read-only
        STATUS            current
        DESCRIPTION
                "CMNT: - Dolby metadata AC-3 status low frequency effects channel
                 TYPE: - Display
                 PAGE: - DolbyStatus
                    LFE  cmdID= 42421  "
        ::= { iqmux33CmdEntry 42421 }


    iqmux33DolbyStatusDolbyMetadataStatusBitstreamMode OBJECT-TYPE
        SYNTAX            RollCallString
        MAX-ACCESS        read-only
        STATUS            current
        DESCRIPTION
                "CMNT: - Dolby metadata AC-3 status bitstream mode
                 TYPE: - Display
                 PAGE: - DolbyStatus
                    Bitstream Mode  cmdID= 42414  "
        ::= { iqmux33CmdEntry 42414 }


    iqmux33DolbyStatusDolbyMetadataStatusRFMode OBJECT-TYPE
        SYNTAX            RollCallString
        MAX-ACCESS        read-only
        STATUS            current
        DESCRIPTION
                "CMNT: - Dolby metadata AC-3 status RF mode
                 TYPE: - Display
                 PAGE: - DolbyStatus
                    RF Mode  cmdID= 42417  "
        ::= { iqmux33CmdEntry 42417 }


    iqmux33DolbyStatusDolbyMetadataStatusLineMode OBJECT-TYPE
        SYNTAX            RollCallString
        MAX-ACCESS        read-only
        STATUS            current
        DESCRIPTION
                "CMNT: - Dolby metadata AC-3 status line mode
                 TYPE: - Display
                 PAGE: - DolbyStatus
                    Line Mode  cmdID= 42416  "
        ::= { iqmux33CmdEntry 42416 }


    iqmux33DolbyStatusDolbyMetadataStatusCentreMixLevel OBJECT-TYPE
        SYNTAX            RollCallString
        MAX-ACCESS        read-only
        STATUS            current
        DESCRIPTION
                "CMNT: - Dolby metadata AC-3 status centre mix level
                 TYPE: - Display
                 PAGE: - DolbyStatus
                    Centre Mix Level  cmdID= 42418  "
        ::= { iqmux33CmdEntry 42418 }


    iqmux33DolbyStatusDolbyMetadataStatusSurroundMixLevel OBJECT-TYPE
        SYNTAX            RollCallString
        MAX-ACCESS        read-only
        STATUS            current
        DESCRIPTION
                "CMNT: - Dolby metadata AC-3 status surround mix level
                 TYPE: - Display
                 PAGE: - DolbyStatus
                    Surround Mix Level  cmdID= 42419  "
        ::= { iqmux33CmdEntry 42419 }


    iqmux33DolbyStatusDolbyMetadataStatusSurroundMode OBJECT-TYPE
        SYNTAX            RollCallString
        MAX-ACCESS        read-only
        STATUS            current
        DESCRIPTION
                "CMNT: - Dolby metadata AC-3 status surround mode
                 TYPE: - Display
                 PAGE: - DolbyStatus
                    Surround Mode  cmdID= 42420  "
        ::= { iqmux33CmdEntry 42420 }


    iqmux33DolbyStatusDolbyMetadataStatusCopyright OBJECT-TYPE
        SYNTAX            RollCallString
        MAX-ACCESS        read-only
        STATUS            current
        DESCRIPTION
                "CMNT: - Dolby metadata AC-3 status copyright
                 TYPE: - Display
                 PAGE: - DolbyStatus
                    Copyright  cmdID= 42438  "
        ::= { iqmux33CmdEntry 42438 }


    iqmux33DolbyMetadataStatusAudioProductionInfoAudioProdInfoExists OBJECT-TYPE
        SYNTAX            RollCallString
        MAX-ACCESS        read-only
        STATUS            current
        DESCRIPTION
                "CMNT: - Dolby metadata AC-3 status audio production information exists
                 TYPE: - Display
                 PAGE: - Dolby Metadata Status
                    Audio Prod Info Exists  cmdID= 42423  "
        ::= { iqmux33CmdEntry 42423 }


    iqmux33DolbyMetadataStatusAudioProductionInfoMixLevel OBJECT-TYPE
        SYNTAX            RollCallString
        MAX-ACCESS        read-only
        STATUS            current
        DESCRIPTION
                "CMNT: - Dolby metadata AC-3 status audio production mix level
                 TYPE: - Display
                 PAGE: - Dolby Metadata Status
                    Mix Level  cmdID= 42424  "
        ::= { iqmux33CmdEntry 42424 }


    iqmux33DolbyMetadataStatusAudioProductionInfoRoomType OBJECT-TYPE
        SYNTAX            RollCallString
        MAX-ACCESS        read-only
        STATUS            current
        DESCRIPTION
                "CMNT: - Dolby metadata AC-3 status audio production room type
                 TYPE: - Display
                 PAGE: - Dolby Metadata Status
                    Room Type  cmdID= 42425  "
        ::= { iqmux33CmdEntry 42425 }


    iqmux33DolbyStatusDolbyMetadataStatusExtendedBSI1Exists OBJECT-TYPE
        SYNTAX            RollCallString
        MAX-ACCESS        read-only
        STATUS            current
        DESCRIPTION
                "CMNT: - Dolby metadata AC-3 status BSI 1 exists
                 TYPE: - Display
                 PAGE: - DolbyStatus
                    Extended BSI1 Exists  cmdID= 42426  "
        ::= { iqmux33CmdEntry 42426 }


    iqmux33DolbyMetadataStatusExtendedBSI1StereoDownmixMode OBJECT-TYPE
        SYNTAX            RollCallString
        MAX-ACCESS        read-only
        STATUS            current
        DESCRIPTION
                "CMNT: - Dolby metadata AC-3 status BSI 1 preferred stereo downmix mode
                 TYPE: - Display
                 PAGE: - Dolby Metadata Status
                    Stereo Downmix Mode  cmdID= 42427  "
        ::= { iqmux33CmdEntry 42427 }


    iqmux33DolbyMetadataStatusExtendedBSI1LtRtCentreMixLevel OBJECT-TYPE
        SYNTAX            RollCallString
        MAX-ACCESS        read-only
        STATUS            current
        DESCRIPTION
                "CMNT: - Dolby metadata AC-3 status BSI 1 LtRt center mix level
                 TYPE: - Display
                 PAGE: - Dolby Metadata Status
                    Lt/Rt Centre Mix Level  cmdID= 42428  "
        ::= { iqmux33CmdEntry 42428 }


    iqmux33DolbyMetadataStatusExtendedBSI1LtRtSurrMixLevel OBJECT-TYPE
        SYNTAX            RollCallString
        MAX-ACCESS        read-only
        STATUS            current
        DESCRIPTION
                "CMNT: - Dolby metadata AC-3 status BSI 1 LtRt surround mix level
                 TYPE: - Display
                 PAGE: - Dolby Metadata Status
                    Lt/Rt Surr Mix Level  cmdID= 42429  "
        ::= { iqmux33CmdEntry 42429 }


    iqmux33DolbyMetadataStatusExtendedBSI1LoRoCentreMixLevel OBJECT-TYPE
        SYNTAX            RollCallString
        MAX-ACCESS        read-only
        STATUS            current
        DESCRIPTION
                "CMNT: - Dolby metadata AC-3 status BSI 1 LoRo center mix level
                 TYPE: - Display
                 PAGE: - Dolby Metadata Status
                    Lo/Ro Centre Mix Level  cmdID= 42430  "
        ::= { iqmux33CmdEntry 42430 }


    iqmux33DolbyMetadataStatusExtendedBSI1LoRoSurrMixLevel OBJECT-TYPE
        SYNTAX            RollCallString
        MAX-ACCESS        read-only
        STATUS            current
        DESCRIPTION
                "CMNT: - Dolby metadata AC-3 status BSI 1 LoRo surround mix level
                 TYPE: - Display
                 PAGE: - Dolby Metadata Status
                    Lo/Ro Surr Mix Level  cmdID= 42431  "
        ::= { iqmux33CmdEntry 42431 }


    iqmux33DolbyStatusDolbyMetadataStatusExtendedBSI2Exists OBJECT-TYPE
        SYNTAX            RollCallString
        MAX-ACCESS        read-only
        STATUS            current
        DESCRIPTION
                "CMNT: - Dolby metadata AC-3 status BSI 2 exists
                 TYPE: - Display
                 PAGE: - DolbyStatus
                    Extended BSI2 Exists  cmdID= 42432  "
        ::= { iqmux33CmdEntry 42432 }


    iqmux33DolbyMetadataStatusExtendedBSI2SurroundEXMode OBJECT-TYPE
        SYNTAX            RollCallString
        MAX-ACCESS        read-only
        STATUS            current
        DESCRIPTION
                "CMNT: - Dolby metadata AC-3 status BSI 2 surround EX mode
                 TYPE: - Display
                 PAGE: - Dolby Metadata Status
                    Surround EX Mode  cmdID= 42433  "
        ::= { iqmux33CmdEntry 42433 }


    iqmux33DolbyMetadataStatusExtendedBSI2LowpassFilter OBJECT-TYPE
        SYNTAX            RollCallString
        MAX-ACCESS        read-only
        STATUS            current
        DESCRIPTION
                "CMNT: - Dolby metadata AC-3 status BSI 2 lowpass filter
                 TYPE: - Display
                 PAGE: - Dolby Metadata Status
                    Lowpass Filter  cmdID= 42434  "
        ::= { iqmux33CmdEntry 42434 }


    iqmux33DolbyMetadataStatusExtendedBSI2LFEFilter OBJECT-TYPE
        SYNTAX            RollCallString
        MAX-ACCESS        read-only
        STATUS            current
        DESCRIPTION
                "CMNT: - Dolby metadata AC-3 status BSI 2 LFE filter
                 TYPE: - Display
                 PAGE: - Dolby Metadata Status
                    LFE Filter  cmdID= 42435  "
        ::= { iqmux33CmdEntry 42435 }


    iqmux33DolbyMetadataStatusExtendedBSI2SurrPhaseShiftFltr OBJECT-TYPE
        SYNTAX            RollCallString
        MAX-ACCESS        read-only
        STATUS            current
        DESCRIPTION
                "CMNT: - Dolby metadata AC-3 status BSI 2 surround 90deg phase shift filter
                 TYPE: - Display
                 PAGE: - Dolby Metadata Status
                    Surr Phase Shift Fltr  cmdID= 42436  "
        ::= { iqmux33CmdEntry 42436 }


    iqmux33DolbyMetadataStatusExtendedBSI2Surr3dBAtten OBJECT-TYPE
        SYNTAX            RollCallString
        MAX-ACCESS        read-only
        STATUS            current
        DESCRIPTION
                "CMNT: - Dolby metadata AC-3 status BSI 2 3dB surround channel attenuator
                 TYPE: - Display
                 PAGE: - Dolby Metadata Status
                    Surr 3dB Atten  cmdID= 42437  "
        ::= { iqmux33CmdEntry 42437 }


    iqmux33DolbyStatusDolbyEncoderStatusStatus OBJECT-TYPE
        SYNTAX            RollCallString
        MAX-ACCESS        read-only
        STATUS            current
        DESCRIPTION
                "CMNT: - Dolby encoder status
                 TYPE: - Display
                 PAGE: - DolbyStatus
                    Status  cmdID= 42491  "
        ::= { iqmux33CmdEntry 42491 }


    iqmux33DolbyStatusDolbyEncoderStatusBitstreamStatus OBJECT-TYPE
        SYNTAX            RollCallString
        MAX-ACCESS        read-only
        STATUS            current
        DESCRIPTION
                "CMNT: - Dolby encoder external metadata bitstream status
                 TYPE: - Display
                 PAGE: - DolbyStatus
                    Bitstream Status  cmdID= 42496  "
        ::= { iqmux33CmdEntry 42496 }


    iqmux33DolbyStatusDolbyEncoderStatusReversionStatus OBJECT-TYPE
        SYNTAX            RollCallString
        MAX-ACCESS        read-only
        STATUS            current
        DESCRIPTION
                "CMNT: - Dolby encoder external metadata reversion status
                 TYPE: - Display
                 PAGE: - DolbyStatus
                    Reversion Status  cmdID= 42497  "
        ::= { iqmux33CmdEntry 42497 }


    iqmux33DolbyStatusDolbyEncoderStatusHWVersion OBJECT-TYPE
        SYNTAX            RollCallString
        MAX-ACCESS        read-only
        STATUS            current
        DESCRIPTION
                "CMNT: - Dolby encoder hardware version
                 TYPE: - Display
                 PAGE: - DolbyStatus
                    H/W Version  cmdID= 42494  "
        ::= { iqmux33CmdEntry 42494 }


    iqmux33DolbyStatusDolbyEncoderStatusOPProgramConfig OBJECT-TYPE
        SYNTAX            RollCallString
        MAX-ACCESS        read-only
        STATUS            current
        DESCRIPTION
                "CMNT: - Dolby encoder output program configuration
                 TYPE: - Display
                 PAGE: - DolbyStatus
                    O/P Program Config  cmdID= 42392  "
        ::= { iqmux33CmdEntry 42392 }


    iqmux33RollCallMemoriesMemoriesABCRecallMemory OBJECT-TYPE
        SYNTAX            INTEGER {
                            valNoneSelected(0),
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - RollCall/Memories
                    Recall Memory  cmdID= 37100
                    None Selected  value= 0
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqmux33CmdEntry 37100 }


    iqmux33RollCallMemoriesMemoriesABCSelMemory OBJECT-TYPE
        SYNTAX            INTEGER {
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - RollCall/Memories
                    Sel Memory  cmdID= 37101
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqmux33CmdEntry 37101 }


    iqmux33RollCallMemoriesMemoriesABCSaveMemory OBJECT-TYPE
        SYNTAX            INTEGER { noAction(0),valSaveMemory(1) }
        MAX-ACCESS        read-write
        STATUS            current
        DESCRIPTION
                "CMNT: - 
                 TYPE: - Button
                 PAGE: - RollCall/Memories
                    Save Memory  cmdID= 37102
                    value= 1  "
        ::= { iqmux33CmdEntry 37102 }


    iqmux33RollCallMemoriesMemoriesABCClearMemory OBJECT-TYPE
        SYNTAX            INTEGER { noAction(0),valClearMemory(1) }
        MAX-ACCESS        read-write
        STATUS            current
        DESCRIPTION
                "CMNT: - Delete User Memory
                 TYPE: - Button
                 PAGE: - RollCall/Memories
                    Clear Memory  cmdID= 37105
                    value= 1  "
        ::= { iqmux33CmdEntry 37105 }


    iqmux33MemoriesABCMemoryNameChangeName OBJECT-TYPE
        SYNTAX            RollCallString
        MAX-ACCESS        read-write
        STATUS            current
        DESCRIPTION
                "CMNT: - 
                 TYPE: - Editstring
                 PAGE: - MemoriesABC
                    Change Name  cmdID= 37103
                    preset= Display Memory"
        ::= { iqmux33CmdEntry 37103 }


    iqmux33MemoriesABCMemoryNameLastUserMemory OBJECT-TYPE
        SYNTAX            RollCallString
        MAX-ACCESS        read-only
        STATUS            current
        DESCRIPTION
                "CMNT: - 
                 TYPE: - Display
                 PAGE: - MemoriesABC
                    Last User Memory  cmdID= 37104  "
        ::= { iqmux33CmdEntry 37104 }


    iqmux33RollCallMemoriesMemoriesABCMemoryName1 OBJECT-TYPE
        SYNTAX            RollCallString
        MAX-ACCESS        read-only
        STATUS            current
        DESCRIPTION
                "CMNT: - 
                 TYPE: - Display
                 PAGE: - RollCall/Memories
                    Memory Name1  cmdID= 37106  "
        ::= { iqmux33CmdEntry 37106 }


    iqmux33RollCallMemoriesMemoriesABCMemoryName2 OBJECT-TYPE
        SYNTAX            RollCallString
        MAX-ACCESS        read-only
        STATUS            current
        DESCRIPTION
                "CMNT: - 
                 TYPE: - Display
                 PAGE: - RollCall/Memories
                    Memory Name2  cmdID= 37107  "
        ::= { iqmux33CmdEntry 37107 }


    iqmux33RollCallMemoriesMemoriesABCMemoryName3 OBJECT-TYPE
        SYNTAX            RollCallString
        MAX-ACCESS        read-only
        STATUS            current
        DESCRIPTION
                "CMNT: - 
                 TYPE: - Display
                 PAGE: - RollCall/Memories
                    Memory Name3  cmdID= 37108  "
        ::= { iqmux33CmdEntry 37108 }


    iqmux33RollCallMemoriesMemoriesABCMemoryName4 OBJECT-TYPE
        SYNTAX            RollCallString
        MAX-ACCESS        read-only
        STATUS            current
        DESCRIPTION
                "CMNT: - 
                 TYPE: - Display
                 PAGE: - RollCall/Memories
                    Memory Name4  cmdID= 37109  "
        ::= { iqmux33CmdEntry 37109 }


    iqmux33RollCallMemoriesMemoriesABCMemoryName5 OBJECT-TYPE
        SYNTAX            RollCallString
        MAX-ACCESS        read-only
        STATUS            current
        DESCRIPTION
                "CMNT: - 
                 TYPE: - Display
                 PAGE: - RollCall/Memories
                    Memory Name5  cmdID= 37110  "
        ::= { iqmux33CmdEntry 37110 }


    iqmux33RollCallMemoriesMemoriesABCMemoryName6 OBJECT-TYPE
        SYNTAX            RollCallString
        MAX-ACCESS        read-only
        STATUS            current
        DESCRIPTION
                "CMNT: - 
                 TYPE: - Display
                 PAGE: - RollCall/Memories
                    Memory Name6  cmdID= 37111  "
        ::= { iqmux33CmdEntry 37111 }


    iqmux33RollCallMemoriesMemoriesABCMemoryName7 OBJECT-TYPE
        SYNTAX            RollCallString
        MAX-ACCESS        read-only
        STATUS            current
        DESCRIPTION
                "CMNT: - 
                 TYPE: - Display
                 PAGE: - RollCall/Memories
                    Memory Name7  cmdID= 37112  "
        ::= { iqmux33CmdEntry 37112 }


    iqmux33RollCallMemoriesMemoriesABCMemoryName8 OBJECT-TYPE
        SYNTAX            RollCallString
        MAX-ACCESS        read-only
        STATUS            current
        DESCRIPTION
                "CMNT: - 
                 TYPE: - Display
                 PAGE: - RollCall/Memories
                    Memory Name8  cmdID= 37113  "
        ::= { iqmux33CmdEntry 37113 }


    iqmux33RollCallMemoriesMemoriesABCMemoryName9 OBJECT-TYPE
        SYNTAX            RollCallString
        MAX-ACCESS        read-only
        STATUS            current
        DESCRIPTION
                "CMNT: - 
                 TYPE: - Display
                 PAGE: - RollCall/Memories
                    Memory Name9  cmdID= 37114  "
        ::= { iqmux33CmdEntry 37114 }


    iqmux33RollCallMemoriesMemoriesABCMemoryName10 OBJECT-TYPE
        SYNTAX            RollCallString
        MAX-ACCESS        read-only
        STATUS            current
        DESCRIPTION
                "CMNT: - 
                 TYPE: - Display
                 PAGE: - RollCall/Memories
                    Memory Name10  cmdID= 37115  "
        ::= { iqmux33CmdEntry 37115 }


    iqmux33RollCallMemoriesMemoriesABCMemoryName11 OBJECT-TYPE
        SYNTAX            RollCallString
        MAX-ACCESS        read-only
        STATUS            current
        DESCRIPTION
                "CMNT: - 
                 TYPE: - Display
                 PAGE: - RollCall/Memories
                    Memory Name11  cmdID= 37116  "
        ::= { iqmux33CmdEntry 37116 }


    iqmux33RollCallMemoriesMemoriesABCMemoryName12 OBJECT-TYPE
        SYNTAX            RollCallString
        MAX-ACCESS        read-only
        STATUS            current
        DESCRIPTION
                "CMNT: - 
                 TYPE: - Display
                 PAGE: - RollCall/Memories
                    Memory Name12  cmdID= 37117  "
        ::= { iqmux33CmdEntry 37117 }


    iqmux33RollCallMemoriesMemoriesABCMemoryName13 OBJECT-TYPE
        SYNTAX            RollCallString
        MAX-ACCESS        read-only
        STATUS            current
        DESCRIPTION
                "CMNT: - 
                 TYPE: - Display
                 PAGE: - RollCall/Memories
                    Memory Name13  cmdID= 37118  "
        ::= { iqmux33CmdEntry 37118 }


    iqmux33RollCallMemoriesMemoriesABCMemoryName14 OBJECT-TYPE
        SYNTAX            RollCallString
        MAX-ACCESS        read-only
        STATUS            current
        DESCRIPTION
                "CMNT: - 
                 TYPE: - Display
                 PAGE: - RollCall/Memories
                    Memory Name14  cmdID= 37119  "
        ::= { iqmux33CmdEntry 37119 }


    iqmux33RollCallMemoriesMemoriesABCMemoryName15 OBJECT-TYPE
        SYNTAX            RollCallString
        MAX-ACCESS        read-only
        STATUS            current
        DESCRIPTION
                "CMNT: - 
                 TYPE: - Display
                 PAGE: - RollCall/Memories
                    Memory Name15  cmdID= 37120  "
        ::= { iqmux33CmdEntry 37120 }


    iqmux33RollCallMemoriesMemoriesABCMemoryName16 OBJECT-TYPE
        SYNTAX            RollCallString
        MAX-ACCESS        read-only
        STATUS            current
        DESCRIPTION
                "CMNT: - 
                 TYPE: - Display
                 PAGE: - RollCall/Memories
                    Memory Name16  cmdID= 37121  "
        ::= { iqmux33CmdEntry 37121 }


    iqmux33Logging1AESInputAudLoggingLogAESInput1state OBJECT-TYPE
        SYNTAX            INTEGER { disable(0), enable(1)  }
        MAX-ACCESS        read-write
        STATUS            current
        DESCRIPTION
                "CMNT: - Enable/Disable logging for AES Input 1 state
                 TYPE: - Checkbox
                 PAGE: - Logging1
                    Log AES Input1 state  cmdID= 42016  "
        ::= { iqmux33CmdEntry 42016 }


    iqmux33Logging1AESInputAudLoggingAESInput1state OBJECT-TYPE
        SYNTAX            RollCallString
        MAX-ACCESS        read-only
        STATUS            current
        DESCRIPTION
                "CMNT: - Logging state for AES Input 1 state
                 TYPE: - Display
                 PAGE: - Logging1
                    AES Input1 state=  cmdID= 42216  "
        ::= { iqmux33CmdEntry 42216 }


    iqmux33Logging1AESInputAudLoggingLogAESInput2state OBJECT-TYPE
        SYNTAX            INTEGER { disable(0), enable(1)  }
        MAX-ACCESS        read-write
        STATUS            current
        DESCRIPTION
                "CMNT: - Enable/Disable logging for AES Input 2 state
                 TYPE: - Checkbox
                 PAGE: - Logging1
                    Log AES Input2 state  cmdID= 42017  "
        ::= { iqmux33CmdEntry 42017 }


    iqmux33Logging1AESInputAudLoggingAESInput2state OBJECT-TYPE
        SYNTAX            RollCallString
        MAX-ACCESS        read-only
        STATUS            current
        DESCRIPTION
                "CMNT: - Logging state for AES Input 2 state
                 TYPE: - Display
                 PAGE: - Logging1
                    AES Input2 state=  cmdID= 42217  "
        ::= { iqmux33CmdEntry 42217 }


    iqmux33Logging1AESInputAudLoggingLogAESInput3state OBJECT-TYPE
        SYNTAX            INTEGER { disable(0), enable(1)  }
        MAX-ACCESS        read-write
        STATUS            current
        DESCRIPTION
                "CMNT: - Enable/Disable logging for AES Input 3 state
                 TYPE: - Checkbox
                 PAGE: - Logging1
                    Log AES Input3 state  cmdID= 42018  "
        ::= { iqmux33CmdEntry 42018 }


    iqmux33Logging1AESInputAudLoggingAESInput3state OBJECT-TYPE
        SYNTAX            RollCallString
        MAX-ACCESS        read-only
        STATUS            current
        DESCRIPTION
                "CMNT: - Logging state for AES Input 3 state
                 TYPE: - Display
                 PAGE: - Logging1
                    AES Input3 state=  cmdID= 42218  "
        ::= { iqmux33CmdEntry 42218 }


    iqmux33Logging1AESInputAudLoggingLogAESInput4state OBJECT-TYPE
        SYNTAX            INTEGER { disable(0), enable(1)  }
        MAX-ACCESS        read-write
        STATUS            current
        DESCRIPTION
                "CMNT: - Enable/Disable logging for AES Input 4 state
                 TYPE: - Checkbox
                 PAGE: - Logging1
                    Log AES Input4 state  cmdID= 42019  "
        ::= { iqmux33CmdEntry 42019 }


    iqmux33Logging1AESInputAudLoggingAESInput4state OBJECT-TYPE
        SYNTAX            RollCallString
        MAX-ACCESS        read-only
        STATUS            current
        DESCRIPTION
                "CMNT: - Logging state for AES Input 4 state
                 TYPE: - Display
                 PAGE: - Logging1
                    AES Input4 state=  cmdID= 42219  "
        ::= { iqmux33CmdEntry 42219 }


    iqmux33Logging1AESInputAudLoggingLogAESInput5state OBJECT-TYPE
        SYNTAX            INTEGER { disable(0), enable(1)  }
        MAX-ACCESS        read-write
        STATUS            current
        DESCRIPTION
                "CMNT: - Enable/Disable logging for AES Input 5 state
                 TYPE: - Checkbox
                 PAGE: - Logging1
                    Log AES Input5 state  cmdID= 42020  "
        ::= { iqmux33CmdEntry 42020 }


    iqmux33Logging1AESInputAudLoggingAESInput5state OBJECT-TYPE
        SYNTAX            RollCallString
        MAX-ACCESS        read-only
        STATUS            current
        DESCRIPTION
                "CMNT: - Logging state for AES Input 5 state
                 TYPE: - Display
                 PAGE: - Logging1
                    AES Input5 state=  cmdID= 42220  "
        ::= { iqmux33CmdEntry 42220 }


    iqmux33Logging1AESInputAudLoggingLogAESInput6state OBJECT-TYPE
        SYNTAX            INTEGER { disable(0), enable(1)  }
        MAX-ACCESS        read-write
        STATUS            current
        DESCRIPTION
                "CMNT: - Enable/Disable logging for AES Input 6 state
                 TYPE: - Checkbox
                 PAGE: - Logging1
                    Log AES Input6 state  cmdID= 42021  "
        ::= { iqmux33CmdEntry 42021 }


    iqmux33Logging1AESInputAudLoggingAESInput6state OBJECT-TYPE
        SYNTAX            RollCallString
        MAX-ACCESS        read-only
        STATUS            current
        DESCRIPTION
                "CMNT: - Logging state for AES Input 6 state
                 TYPE: - Display
                 PAGE: - Logging1
                    AES Input6 state=  cmdID= 42221  "
        ::= { iqmux33CmdEntry 42221 }


    iqmux33Logging1AESInputAudLoggingLogAESInput7state OBJECT-TYPE
        SYNTAX            INTEGER { disable(0), enable(1)  }
        MAX-ACCESS        read-write
        STATUS            current
        DESCRIPTION
                "CMNT: - Enable/Disable logging for AES Input 7 state
                 TYPE: - Checkbox
                 PAGE: - Logging1
                    Log AES Input7 state  cmdID= 42022  "
        ::= { iqmux33CmdEntry 42022 }


    iqmux33Logging1AESInputAudLoggingAESInput7state OBJECT-TYPE
        SYNTAX            RollCallString
        MAX-ACCESS        read-only
        STATUS            current
        DESCRIPTION
                "CMNT: - Logging state for AES Input 7 state
                 TYPE: - Display
                 PAGE: - Logging1
                    AES Input7 state=  cmdID= 42222  "
        ::= { iqmux33CmdEntry 42222 }


    iqmux33Logging1AESInputAudLoggingLogAESInput8state OBJECT-TYPE
        SYNTAX            INTEGER { disable(0), enable(1)  }
        MAX-ACCESS        read-write
        STATUS            current
        DESCRIPTION
                "CMNT: - Enable/Disable logging for AES Input 8 state
                 TYPE: - Checkbox
                 PAGE: - Logging1
                    Log AES Input8 state  cmdID= 42023  "
        ::= { iqmux33CmdEntry 42023 }


    iqmux33Logging1AESInputAudLoggingAESInput8state OBJECT-TYPE
        SYNTAX            RollCallString
        MAX-ACCESS        read-only
        STATUS            current
        DESCRIPTION
                "CMNT: - Logging state for AES Input 8 state
                 TYPE: - Display
                 PAGE: - Logging1
                    AES Input8 state=  cmdID= 42223  "
        ::= { iqmux33CmdEntry 42223 }


    iqmux33Logging1OutEmbAudLoggingLogOutEmb11state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.11 state  cmdID= 42024  "
        ::= { iqmux33CmdEntry 42024 }


    iqmux33Logging1OutEmbAudLoggingOutEmb11state OBJECT-TYPE
        SYNTAX            RollCallString
        MAX-ACCESS        read-only
        STATUS            current
        DESCRIPTION
                "CMNT: - Logging state for Inp 1, Emb Pair 1 state
                 TYPE: - Display
                 PAGE: - Logging1
                    Out Emb.11 state=  cmdID= 42224  "
        ::= { iqmux33CmdEntry 42224 }


    iqmux33Logging1OutEmbAudLoggingLogOutEmb12state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.12 state  cmdID= 42025  "
        ::= { iqmux33CmdEntry 42025 }


    iqmux33Logging1OutEmbAudLoggingOutEmb12state OBJECT-TYPE
        SYNTAX            RollCallString
        MAX-ACCESS        read-only
        STATUS            current
        DESCRIPTION
                "CMNT: - Logging state for Inp 1, Emb Pair 1 state
                 TYPE: - Display
                 PAGE: - Logging1
                    Out Emb.12 state=  cmdID= 42225  "
        ::= { iqmux33CmdEntry 42225 }


    iqmux33Logging1OutEmbAudLoggingLogOutEmb21state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.21 state  cmdID= 42026  "
        ::= { iqmux33CmdEntry 42026 }


    iqmux33Logging1OutEmbAudLoggingOutEmb21state OBJECT-TYPE
        SYNTAX            RollCallString
        MAX-ACCESS        read-only
        STATUS            current
        DESCRIPTION
                "CMNT: - Logging state for Inp 1, Emb Pair 1 state
                 TYPE: - Display
                 PAGE: - Logging1
                    Out Emb.21 state=  cmdID= 42226  "
        ::= { iqmux33CmdEntry 42226 }


    iqmux33Logging1OutEmbAudLoggingLogOutEmb22state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.22 state  cmdID= 42027  "
        ::= { iqmux33CmdEntry 42027 }


    iqmux33Logging1OutEmbAudLoggingOutEmb22state OBJECT-TYPE
        SYNTAX            RollCallString
        MAX-ACCESS        read-only
        STATUS            current
        DESCRIPTION
                "CMNT: - Logging state for Inp 1, Emb Pair 1 state
                 TYPE: - Display
                 PAGE: - Logging1
                    Out Emb.22 state=  cmdID= 42227  "
        ::= { iqmux33CmdEntry 42227 }


    iqmux33Logging1OutEmbAudLoggingLogOutEmb31state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.31 state  cmdID= 42028  "
        ::= { iqmux33CmdEntry 42028 }


    iqmux33Logging1OutEmbAudLoggingOutEmb31state OBJECT-TYPE
        SYNTAX            RollCallString
        MAX-ACCESS        read-only
        STATUS            current
        DESCRIPTION
                "CMNT: - Logging state for Inp 1, Emb Pair 1 state
                 TYPE: - Display
                 PAGE: - Logging1
                    Out Emb.31 state=  cmdID= 42228  "
        ::= { iqmux33CmdEntry 42228 }


    iqmux33Logging1OutEmbAudLoggingLogOutEmb32state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.32 state  cmdID= 42029  "
        ::= { iqmux33CmdEntry 42029 }


    iqmux33Logging1OutEmbAudLoggingOutEmb32state OBJECT-TYPE
        SYNTAX            RollCallString
        MAX-ACCESS        read-only
        STATUS            current
        DESCRIPTION
                "CMNT: - Logging state for Inp 1, Emb Pair 1 state
                 TYPE: - Display
                 PAGE: - Logging1
                    Out Emb.32 state=  cmdID= 42229  "
        ::= { iqmux33CmdEntry 42229 }


    iqmux33Logging1OutEmbAudLoggingLogOutEmb41state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.41 state  cmdID= 42030  "
        ::= { iqmux33CmdEntry 42030 }


    iqmux33Logging1OutEmbAudLoggingOutEmb41state OBJECT-TYPE
        SYNTAX            RollCallString
        MAX-ACCESS        read-only
        STATUS            current
        DESCRIPTION
                "CMNT: - Logging state for Inp 1, Emb Pair 1 state
                 TYPE: - Display
                 PAGE: - Logging1
                    Out Emb.41 state=  cmdID= 42230  "
        ::= { iqmux33CmdEntry 42230 }


    iqmux33Logging1OutEmbAudLoggingLogOutEmb42state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.42 state  cmdID= 42031  "
        ::= { iqmux33CmdEntry 42031 }


    iqmux33Logging1OutEmbAudLoggingOutEmb42state OBJECT-TYPE
        SYNTAX            RollCallString
        MAX-ACCESS        read-only
        STATUS            current
        DESCRIPTION
                "CMNT: - Logging state for Inp 1, Emb Pair 1 state
                 TYPE: - Display
                 PAGE: - Logging1
                    Out Emb.42 state=  cmdID= 42231  "
        ::= { iqmux33CmdEntry 42231 }


    iqmux33Logging1OutEmbAudLoggingLogOutEmb51state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.51 state  cmdID= 42032  "
        ::= { iqmux33CmdEntry 42032 }


    iqmux33Logging1OutEmbAudLoggingOutEmb51state OBJECT-TYPE
        SYNTAX            RollCallString
        MAX-ACCESS        read-only
        STATUS            current
        DESCRIPTION
                "CMNT: - Logging state for Inp 1, Emb Pair 1 state
                 TYPE: - Display
                 PAGE: - Logging1
                    Out Emb.51 state=  cmdID= 42232  "
        ::= { iqmux33CmdEntry 42232 }


    iqmux33Logging1OutEmbAudLoggingLogOutEmb52state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.52 state  cmdID= 42033  "
        ::= { iqmux33CmdEntry 42033 }


    iqmux33Logging1OutEmbAudLoggingOutEmb52state OBJECT-TYPE
        SYNTAX            RollCallString
        MAX-ACCESS        read-only
        STATUS            current
        DESCRIPTION
                "CMNT: - Logging state for Inp 1, Emb Pair 1 state
                 TYPE: - Display
                 PAGE: - Logging1
                    Out Emb.52 state=  cmdID= 42233  "
        ::= { iqmux33CmdEntry 42233 }


    iqmux33Logging1OutEmbAudLoggingLogOutEmb61state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.61 state  cmdID= 42034  "
        ::= { iqmux33CmdEntry 42034 }


    iqmux33Logging1OutEmbAudLoggingOutEmb61state OBJECT-TYPE
        SYNTAX            RollCallString
        MAX-ACCESS        read-only
        STATUS            current
        DESCRIPTION
                "CMNT: - Logging state for Inp 1, Emb Pair 1 state
                 TYPE: - Display
                 PAGE: - Logging1
                    Out Emb.61 state=  cmdID= 42234  "
        ::= { iqmux33CmdEntry 42234 }


    iqmux33Logging1OutEmbAudLoggingLogOutEmb62state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.62 state  cmdID= 42035  "
        ::= { iqmux33CmdEntry 42035 }


    iqmux33Logging1OutEmbAudLoggingOutEmb62state OBJECT-TYPE
        SYNTAX            RollCallString
        MAX-ACCESS        read-only
        STATUS            current
        DESCRIPTION
                "CMNT: - Logging state for Inp 1, Emb Pair 1 state
                 TYPE: - Display
                 PAGE: - Logging1
                    Out Emb.62 state=  cmdID= 42235  "
        ::= { iqmux33CmdEntry 42235 }


    iqmux33Logging1OutEmbAudLoggingLogOutEmb71state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.71 state  cmdID= 42036  "
        ::= { iqmux33CmdEntry 42036 }


    iqmux33Logging1OutEmbAudLoggingOutEmb71state OBJECT-TYPE
        SYNTAX            RollCallString
        MAX-ACCESS        read-only
        STATUS            current
        DESCRIPTION
                "CMNT: - Logging state for Inp 1, Emb Pair 1 state
                 TYPE: - Display
                 PAGE: - Logging1
                    Out Emb.71 state=  cmdID= 42236  "
        ::= { iqmux33CmdEntry 42236 }


    iqmux33Logging1OutEmbAudLoggingLogOutEmb72state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.72 state  cmdID= 42037  "
        ::= { iqmux33CmdEntry 42037 }


    iqmux33Logging1OutEmbAudLoggingOutEmb72state OBJECT-TYPE
        SYNTAX            RollCallString
        MAX-ACCESS        read-only
        STATUS            current
        DESCRIPTION
                "CMNT: - Logging state for Inp 1, Emb Pair 1 state
                 TYPE: - Display
                 PAGE: - Logging1
                    Out Emb.72 state=  cmdID= 42237  "
        ::= { iqmux33CmdEntry 42237 }


    iqmux33Logging1OutEmbAudLoggingLogOutEmb81state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.81 state  cmdID= 42038  "
        ::= { iqmux33CmdEntry 42038 }


    iqmux33Logging1OutEmbAudLoggingOutEmb81state OBJECT-TYPE
        SYNTAX            RollCallString
        MAX-ACCESS        read-only
        STATUS            current
        DESCRIPTION
                "CMNT: - Logging state for Inp 1, Emb Pair 1 state
                 TYPE: - Display
                 PAGE: - Logging1
                    Out Emb.81 state=  cmdID= 42238  "
        ::= { iqmux33CmdEntry 42238 }


    iqmux33Logging1OutEmbAudLoggingLogOutEmb82state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.82 state  cmdID= 42039  "
        ::= { iqmux33CmdEntry 42039 }


    iqmux33Logging1OutEmbAudLoggingOutEmb82state OBJECT-TYPE
        SYNTAX            RollCallString
        MAX-ACCESS        read-only
        STATUS            current
        DESCRIPTION
                "CMNT: - Logging state for Inp 1, Emb Pair 1 state
                 TYPE: - Display
                 PAGE: - Logging1
                    Out Emb.82 state=  cmdID= 42239  "
        ::= { iqmux33CmdEntry 42239 }


    iqmux33Logging1DolbyDecoderLoggingLogBitstreamFormat OBJECT-TYPE
        SYNTAX            INTEGER { disable(0), enable(1)  }
        MAX-ACCESS        read-write
        STATUS            current
        DESCRIPTION
                "CMNT: - Enable/Disable logging for Dolby Decoder bitstream format
                 TYPE: - Checkbox
                 PAGE: - Logging1
                    Log Bitstream Format  cmdID= 42100  "
        ::= { iqmux33CmdEntry 42100 }


    iqmux33Logging1DolbyDecoderLoggingBitstreamFormat OBJECT-TYPE
        SYNTAX            RollCallString
        MAX-ACCESS        read-only
        STATUS            current
        DESCRIPTION
                "CMNT: - Logging state for Dolby Decoder bitstream format
                 TYPE: - Display
                 PAGE: - Logging1
                    Bitstream Format=  cmdID= 42300  "
        ::= { iqmux33CmdEntry 42300 }


    iqmux33Logging1DolbyDecoderLoggingLogBitstreamStatus OBJECT-TYPE
        SYNTAX            INTEGER { disable(0), enable(1)  }
        MAX-ACCESS        read-write
        STATUS            current
        DESCRIPTION
                "CMNT: - Enable/Disable logging for Dolby Decoder bitstream status
                 TYPE: - Checkbox
                 PAGE: - Logging1
                    Log Bitstream Status  cmdID= 42101  "
        ::= { iqmux33CmdEntry 42101 }


    iqmux33Logging1DolbyDecoderLoggingBitstreamStatus OBJECT-TYPE
        SYNTAX            RollCallString
        MAX-ACCESS        read-only
        STATUS            current
        DESCRIPTION
                "CMNT: - Logging state for Dolby Decoder bitstream status
                 TYPE: - Display
                 PAGE: - Logging1
                    Bitstream Status=  cmdID= 42301  "
        ::= { iqmux33CmdEntry 42301 }


    iqmux33Logging1DolbyDecoderLoggingLogDCRCErrors OBJECT-TYPE
        SYNTAX            INTEGER { disable(0), enable(1)  }
        MAX-ACCESS        read-write
        STATUS            current
        DESCRIPTION
                "CMNT: - Enable/Disable logging for Dolby DecoderD CRC error count
                 TYPE: - Checkbox
                 PAGE: - Logging1
                    Log D CRC Errors  cmdID= 42102  "
        ::= { iqmux33CmdEntry 42102 }


    iqmux33Logging1DolbyDecoderLoggingDCRCErrorCount OBJECT-TYPE
        SYNTAX            RollCallString
        MAX-ACCESS        read-only
        STATUS            current
        DESCRIPTION
                "CMNT: - Logging state for Dolby Decoder D CRC error count
                 TYPE: - Display
                 PAGE: - Logging1
                    D CRC Error Count=  cmdID= 42302  "
        ::= { iqmux33CmdEntry 42302 }


    iqmux33Logging1DolbyDecoderLoggingLogECRCErrors OBJECT-TYPE
        SYNTAX            INTEGER { disable(0), enable(1)  }
        MAX-ACCESS        read-write
        STATUS            current
        DESCRIPTION
                "CMNT: - Enable/Disable logging for Dolby Decoder E CRC error count
                 TYPE: - Checkbox
                 PAGE: - Logging1
                    Log E CRC Errors  cmdID= 42103  "
        ::= { iqmux33CmdEntry 42103 }


    iqmux33Logging1DolbyDecoderLoggingECRCErrorCount OBJECT-TYPE
        SYNTAX            RollCallString
        MAX-ACCESS        read-only
        STATUS            current
        DESCRIPTION
                "CMNT: - Logging state for Dolby Decoder E CRC error count
                 TYPE: - Display
                 PAGE: - Logging1
                    E CRC Error Count=  cmdID= 42303  "
        ::= { iqmux33CmdEntry 42303 }


    iqmux33Logging1DolbyEncoderLoggingLogEncoderStatus OBJECT-TYPE
        SYNTAX            INTEGER { disable(0), enable(1)  }
        MAX-ACCESS        read-write
        STATUS            current
        DESCRIPTION
                "CMNT: - Enable/Disable logging for Dolby Encoder status
                 TYPE: - Checkbox
                 PAGE: - Logging1
                    Log Encoder Status  cmdID= 42112  "
        ::= { iqmux33CmdEntry 42112 }


    iqmux33Logging1DolbyEncoderLoggingEncoderStatus OBJECT-TYPE
        SYNTAX            RollCallString
        MAX-ACCESS        read-only
        STATUS            current
        DESCRIPTION
                "CMNT: - Logging state for Dolby Encoder status
                 TYPE: - Display
                 PAGE: - Logging1
                    Encoder Status=  cmdID= 42312  "
        ::= { iqmux33CmdEntry 42312 }


    iqmux33Logging1DolbyEncoderLoggingLogBitstreamStatus OBJECT-TYPE
        SYNTAX            INTEGER { disable(0), enable(1)  }
        MAX-ACCESS        read-write
        STATUS            current
        DESCRIPTION
                "CMNT: - Enable/Disable logging for Dolby Encoder bitstream status
                 TYPE: - Checkbox
                 PAGE: - Logging1
                    Log Bitstream Status  cmdID= 42113  "
        ::= { iqmux33CmdEntry 42113 }


    iqmux33Logging1DolbyEncoderLoggingBitstreamStatus OBJECT-TYPE
        SYNTAX            RollCallString
        MAX-ACCESS        read-only
        STATUS            current
        DESCRIPTION
                "CMNT: - Logging state for Dolby Encoder bitstream status
                 TYPE: - Display
                 PAGE: - Logging1
                    Bitstream Status=  cmdID= 42313  "
        ::= { iqmux33CmdEntry 42313 }


    iqmux33Logging1DolbyEncoderLoggingLogReversionStatus OBJECT-TYPE
        SYNTAX            INTEGER { disable(0), enable(1)  }
        MAX-ACCESS        read-write
        STATUS            current
        DESCRIPTION
                "CMNT: - Enable/Disable logging for Dolby Encoder reversion status
                 TYPE: - Checkbox
                 PAGE: - Logging1
                    Log Reversion Status  cmdID= 42114  "
        ::= { iqmux33CmdEntry 42114 }


    iqmux33Logging1DolbyEncoderLoggingReversionStatus OBJECT-TYPE
        SYNTAX            RollCallString
        MAX-ACCESS        read-only
        STATUS            current
        DESCRIPTION
                "CMNT: - Logging state for Dolby Encoder reversion status
                 TYPE: - Display
                 PAGE: - Logging1
                    Reversion Status=  cmdID= 42314  "
        ::= { iqmux33CmdEntry 42314 }


    iqmux33Logging1DolbyLoggingLogVideoSync OBJECT-TYPE
        SYNTAX            INTEGER { disable(0), enable(1)  }
        MAX-ACCESS        read-write
        STATUS            current
        DESCRIPTION
                "CMNT: - Enable/Disable logging for Dolby video sync
                 TYPE: - Checkbox
                 PAGE: - Logging1
                    Log Video Sync  cmdID= 42104  "
        ::= { iqmux33CmdEntry 42104 }


    iqmux33Logging1DolbyLoggingVideoSync OBJECT-TYPE
        SYNTAX            RollCallString
        MAX-ACCESS        read-only
        STATUS            current
        DESCRIPTION
                "CMNT: - Logging state for Dolby video sync
                 TYPE: - Display
                 PAGE: - Logging1
                    Video Sync=  cmdID= 42304  "
        ::= { iqmux33CmdEntry 42304 }


    iqmux33Logging1DolbyLoggingLogFrameRate OBJECT-TYPE
        SYNTAX            INTEGER { disable(0), enable(1)  }
        MAX-ACCESS        read-write
        STATUS            current
        DESCRIPTION
                "CMNT: - Enable/Disable logging for Dolby frame rate
                 TYPE: - Checkbox
                 PAGE: - Logging1
                    Log Frame Rate  cmdID= 42105  "
        ::= { iqmux33CmdEntry 42105 }


    iqmux33Logging1DolbyLoggingFrameRate OBJECT-TYPE
        SYNTAX            RollCallString
        MAX-ACCESS        read-only
        STATUS            current
        DESCRIPTION
                "CMNT: - Logging state for Dolby frame rate
                 TYPE: - Display
                 PAGE: - Logging1
                    Frame Rate=  cmdID= 42305  "
        ::= { iqmux33CmdEntry 42305 }


    iqmux33Logging1DolbyLoggingLogProgramConfig OBJECT-TYPE
        SYNTAX            INTEGER { disable(0), enable(1)  }
        MAX-ACCESS        read-write
        STATUS            current
        DESCRIPTION
                "CMNT: - Enable/Disable logging for Dolby program config
                 TYPE: - Checkbox
                 PAGE: - Logging1
                    Log Program Config  cmdID= 42106  "
        ::= { iqmux33CmdEntry 42106 }


    iqmux33Logging1DolbyLoggingProgramConfig OBJECT-TYPE
        SYNTAX            RollCallString
        MAX-ACCESS        read-only
        STATUS            current
        DESCRIPTION
                "CMNT: - Logging state for Dolby program config
                 TYPE: - Display
                 PAGE: - Logging1
                    Program Config=  cmdID= 42306  "
        ::= { iqmux33CmdEntry 42306 }


    iqmux33Logging1DolbyMetadataLoggingLogSelectedProgram OBJECT-TYPE
        SYNTAX            INTEGER { disable(0), enable(1)  }
        MAX-ACCESS        read-write
        STATUS            current
        DESCRIPTION
                "CMNT: - Enable/Disable logging for Dolby selected program
                 TYPE: - Checkbox
                 PAGE: - Logging1
                    Log Selected Program  cmdID= 42107  "
        ::= { iqmux33CmdEntry 42107 }


    iqmux33Logging1DolbyMetadataLoggingSelectedProgram OBJECT-TYPE
        SYNTAX            RollCallString
        MAX-ACCESS        read-only
        STATUS            current
        DESCRIPTION
                "CMNT: - Logging state for Dolby selected program
                 TYPE: - Display
                 PAGE: - Logging1
                    Selected Program=  cmdID= 42307  "
        ::= { iqmux33CmdEntry 42307 }


    iqmux33Logging1DolbyMetadataLoggingLogProgramDescriptor OBJECT-TYPE
        SYNTAX            INTEGER { disable(0), enable(1)  }
        MAX-ACCESS        read-write
        STATUS            current
        DESCRIPTION
                "CMNT: - Enable/Disable logging for Dolby program descriptor
                 TYPE: - Checkbox
                 PAGE: - Logging1
                    Log Program Descriptor  cmdID= 42108  "
        ::= { iqmux33CmdEntry 42108 }


    iqmux33Logging1DolbyMetadataLoggingProgramDescriptor OBJECT-TYPE
        SYNTAX            RollCallString
        MAX-ACCESS        read-only
        STATUS            current
        DESCRIPTION
                "CMNT: - Logging state for Dolby program descriptor
                 TYPE: - Display
                 PAGE: - Logging1
                    Program Descriptor=  cmdID= 42308  "
        ::= { iqmux33CmdEntry 42308 }


    iqmux33Logging1DolbyMetadataLoggingProgramDescPt2 OBJECT-TYPE
        SYNTAX            RollCallString
        MAX-ACCESS        read-only
        STATUS            current
        DESCRIPTION
                "CMNT: - Used for displaying 2nd half of program descriptor on logging page
                 TYPE: - Display
                 PAGE: - Logging1
                    Program Desc Pt2  cmdID= 42400  "
        ::= { iqmux33CmdEntry 42400 }


    iqmux33Logging1DolbyMetadataLoggingLogChannelMode OBJECT-TYPE
        SYNTAX            INTEGER { disable(0), enable(1)  }
        MAX-ACCESS        read-write
        STATUS            current
        DESCRIPTION
                "CMNT: - Enable/Disable logging for Dolby channel mode
                 TYPE: - Checkbox
                 PAGE: - Logging1
                    Log Channel Mode  cmdID= 42109  "
        ::= { iqmux33CmdEntry 42109 }


    iqmux33Logging1DolbyMetadataLoggingChannelMode OBJECT-TYPE
        SYNTAX            RollCallString
        MAX-ACCESS        read-only
        STATUS            current
        DESCRIPTION
                "CMNT: - Logging state for Dolby channel mode
                 TYPE: - Display
                 PAGE: - Logging1
                    Channel Mode=  cmdID= 42309  "
        ::= { iqmux33CmdEntry 42309 }


    iqmux33Logging1DolbyMetadataLoggingLogLFEChannel OBJECT-TYPE
        SYNTAX            INTEGER { disable(0), enable(1)  }
        MAX-ACCESS        read-write
        STATUS            current
        DESCRIPTION
                "CMNT: - Enable/Disable logging for Dolby lfe channel
                 TYPE: - Checkbox
                 PAGE: - Logging1
                    Log LFE Channel  cmdID= 42110  "
        ::= { iqmux33CmdEntry 42110 }


    iqmux33Logging1DolbyMetadataLoggingLFEChannel OBJECT-TYPE
        SYNTAX            RollCallString
        MAX-ACCESS        read-only
        STATUS            current
        DESCRIPTION
                "CMNT: - Logging state for Dolby lfe channel
                 TYPE: - Display
                 PAGE: - Logging1
                    LFE Channel=  cmdID= 42310  "
        ::= { iqmux33CmdEntry 42310 }


    iqmux33Logging1DolbyMetadataLoggingLogDialogueNorm OBJECT-TYPE
        SYNTAX            INTEGER { disable(0), enable(1)  }
        MAX-ACCESS        read-write
        STATUS            current
        DESCRIPTION
                "CMNT: - Enable/Disable logging for Dolby dialogue norm
                 TYPE: - Checkbox
                 PAGE: - Logging1
                    Log Dialogue Norm  cmdID= 42111  "
        ::= { iqmux33CmdEntry 42111 }


    iqmux33Logging1DolbyMetadataLoggingDialogueNorm OBJECT-TYPE
        SYNTAX            RollCallString
        MAX-ACCESS        read-only
        STATUS            current
        DESCRIPTION
                "CMNT: - Logging state for Dolby dialogue norm
                 TYPE: - Display
                 PAGE: - Logging1
                    Dialogue Norm=  cmdID= 42311  "
        ::= { iqmux33CmdEntry 42311 }


    iqmux33Logging1AncillaryDataLoggingLogVIInp1 OBJECT-TYPE
        SYNTAX            INTEGER { disable(0), enable(1)  }
        MAX-ACCESS        read-write
        STATUS            current
        DESCRIPTION
                "CMNT: - Enable/Disable logging for ancillary data VI status
                 TYPE: - Checkbox
                 PAGE: - Logging1
                    Log VI Inp1  cmdID= 42120  "
        ::= { iqmux33CmdEntry 42120 }


    iqmux33Logging1AncillaryDataLoggingVIInp1 OBJECT-TYPE
        SYNTAX            RollCallString
        MAX-ACCESS        read-only
        STATUS            current
        DESCRIPTION
                "CMNT: - Logging state for VI ancillary data on input
                 TYPE: - Display
                 PAGE: - Logging1
                    VI Inp1=  cmdID= 42320  "
        ::= { iqmux33CmdEntry 42320 }


    iqmux33Logging1AncillaryDataLoggingLogWSSInp1 OBJECT-TYPE
        SYNTAX            INTEGER { disable(0), enable(1)  }
        MAX-ACCESS        read-write
        STATUS            current
        DESCRIPTION
                "CMNT: - Enable/Disable logging for ancillary data WSS status
                 TYPE: - Checkbox
                 PAGE: - Logging1
                    Log WSS Inp1  cmdID= 42121  "
        ::= { iqmux33CmdEntry 42121 }


    iqmux33Logging1AncillaryDataLoggingWSSInp1 OBJECT-TYPE
        SYNTAX            RollCallString
        MAX-ACCESS        read-only
        STATUS            current
        DESCRIPTION
                "CMNT: - Logging state for WSS ancillary data on input
                 TYPE: - Display
                 PAGE: - Logging1
                    WSS Inp1=  cmdID= 42321  "
        ::= { iqmux33CmdEntry 42321 }


    iqmux33Logging1AncillaryDataLoggingLogVITCInp1 OBJECT-TYPE
        SYNTAX            INTEGER { disable(0), enable(1)  }
        MAX-ACCESS        read-write
        STATUS            current
        DESCRIPTION
                "CMNT: - Enable/Disable logging for ancillary data VITC status
                 TYPE: - Checkbox
                 PAGE: - Logging1
                    Log VITC Inp1  cmdID= 42122  "
        ::= { iqmux33CmdEntry 42122 }


    iqmux33Logging1AncillaryDataLoggingVITCInp1 OBJECT-TYPE
        SYNTAX            RollCallString
        MAX-ACCESS        read-only
        STATUS            current
        DESCRIPTION
                "CMNT: - Logging state for VITC ancillary data on input
                 TYPE: - Display
                 PAGE: - Logging1
                    VITC Inp1=  cmdID= 42322  "
        ::= { iqmux33CmdEntry 42322 }


    iqmux33Logging1AncillaryDataLoggingLogWSTInp1 OBJECT-TYPE
        SYNTAX            INTEGER { disable(0), enable(1)  }
        MAX-ACCESS        read-write
        STATUS            current
        DESCRIPTION
                "CMNT: - Enable/Disable logging for ancillary data WST status
                 TYPE: - Checkbox
                 PAGE: - Logging1
                    Log WST Inp1  cmdID= 42123  "
        ::= { iqmux33CmdEntry 42123 }


    iqmux33Logging1AncillaryDataLoggingWSTInp1 OBJECT-TYPE
        SYNTAX            RollCallString
        MAX-ACCESS        read-only
        STATUS            current
        DESCRIPTION
                "CMNT: - Logging state for WST ancillary data on input
                 TYPE: - Display
                 PAGE: - Logging1
                    WST Inp1=  cmdID= 42323  "
        ::= { iqmux33CmdEntry 42323 }


    iqmux33Logging1AncillaryDataLoggingLogCC608Inp1 OBJECT-TYPE
        SYNTAX            INTEGER { disable(0), enable(1)  }
        MAX-ACCESS        read-write
        STATUS            current
        DESCRIPTION
                "CMNT: - Enable/Disable logging for ancillary data CC608 status
                 TYPE: - Checkbox
                 PAGE: - Logging1
                    Log CC608 Inp1  cmdID= 42124  "
        ::= { iqmux33CmdEntry 42124 }


    iqmux33Logging1AncillaryDataLoggingCC608Inp1 OBJECT-TYPE
        SYNTAX            RollCallString
        MAX-ACCESS        read-only
        STATUS            current
        DESCRIPTION
                "CMNT: - Logging state for CC608 ancillary data on input
                 TYPE: - Display
                 PAGE: - Logging1
                    CC608 Inp1=  cmdID= 42324  "
        ::= { iqmux33CmdEntry 42324 }


    iqmux33Logging1AncillaryDataLoggingLogATCInp1 OBJECT-TYPE
        SYNTAX            INTEGER { disable(0), enable(1)  }
        MAX-ACCESS        read-write
        STATUS            current
        DESCRIPTION
                "CMNT: - Enable/Disable logging for ancillary data ATC status
                 TYPE: - Checkbox
                 PAGE: - Logging1
                    Log ATC Inp1  cmdID= 42126  "
        ::= { iqmux33CmdEntry 42126 }


    iqmux33Logging1AncillaryDataLoggingATCInp1 OBJECT-TYPE
        SYNTAX            RollCallString
        MAX-ACCESS        read-only
        STATUS            current
        DESCRIPTION
                "CMNT: - Logging state for ATC/VITC ancillary data on input
                 TYPE: - Display
                 PAGE: - Logging1
                    ATC Inp1=  cmdID= 42326  "
        ::= { iqmux33CmdEntry 42326 }


    iqmux33Logging1AncillaryDataLoggingLogCC708Inp1 OBJECT-TYPE
        SYNTAX            INTEGER { disable(0), enable(1)  }
        MAX-ACCESS        read-write
        STATUS            current
        DESCRIPTION
                "CMNT: - Enable/Disable logging for ancillary data CC708 status
                 TYPE: - Checkbox
                 PAGE: - Logging1
                    Log CC708 Inp1  cmdID= 42127  "
        ::= { iqmux33CmdEntry 42127 }


    iqmux33Logging1AncillaryDataLoggingCC708Inp1 OBJECT-TYPE
        SYNTAX            RollCallString
        MAX-ACCESS        read-only
        STATUS            current
        DESCRIPTION
                "CMNT: - Logging state for CC708/OP47 ancillary data on input
                 TYPE: - Display
                 PAGE: - Logging1
                    CC708 Inp1=  cmdID= 42327  "
        ::= { iqmux33CmdEntry 42327 }


    iqmux33Logging1AncillaryDataLoggingLogVIInp2 OBJECT-TYPE
        SYNTAX            INTEGER { disable(0), enable(1)  }
        MAX-ACCESS        read-write
        STATUS            current
        DESCRIPTION
                "CMNT: - Enable/Disable logging for ancillary data VI status
                 TYPE: - Checkbox
                 PAGE: - Logging1
                    Log VI Inp2  cmdID= 42180  "
        ::= { iqmux33CmdEntry 42180 }


    iqmux33Logging1AncillaryDataLoggingVIInp2 OBJECT-TYPE
        SYNTAX            RollCallString
        MAX-ACCESS        read-only
        STATUS            current
        DESCRIPTION
                "CMNT: - Logging state for VI ancillary data on input
                 TYPE: - Display
                 PAGE: - Logging1
                    VI Inp2=  cmdID= 42290  "
        ::= { iqmux33CmdEntry 42290 }


    iqmux33Logging1AncillaryDataLoggingLogWSSInp2 OBJECT-TYPE
        SYNTAX            INTEGER { disable(0), enable(1)  }
        MAX-ACCESS        read-write
        STATUS            current
        DESCRIPTION
                "CMNT: - Enable/Disable logging for ancillary data WSS status
                 TYPE: - Checkbox
                 PAGE: - Logging1
                    Log WSS Inp2  cmdID= 42181  "
        ::= { iqmux33CmdEntry 42181 }


    iqmux33Logging1AncillaryDataLoggingWSSInp2 OBJECT-TYPE
        SYNTAX            RollCallString
        MAX-ACCESS        read-only
        STATUS            current
        DESCRIPTION
                "CMNT: - Logging state for WSS ancillary data on input
                 TYPE: - Display
                 PAGE: - Logging1
                    WSS Inp2=  cmdID= 42291  "
        ::= { iqmux33CmdEntry 42291 }


    iqmux33Logging1AncillaryDataLoggingLogVITCInp2 OBJECT-TYPE
        SYNTAX            INTEGER { disable(0), enable(1)  }
        MAX-ACCESS        read-write
        STATUS            current
        DESCRIPTION
                "CMNT: - Enable/Disable logging for ancillary data VITC status
                 TYPE: - Checkbox
                 PAGE: - Logging1
                    Log VITC Inp2  cmdID= 42182  "
        ::= { iqmux33CmdEntry 42182 }


    iqmux33Logging1AncillaryDataLoggingVITCInp2 OBJECT-TYPE
        SYNTAX            RollCallString
        MAX-ACCESS        read-only
        STATUS            current
        DESCRIPTION
                "CMNT: - Logging state for VITC ancillary data on input
                 TYPE: - Display
                 PAGE: - Logging1
                    VITC Inp2=  cmdID= 42292  "
        ::= { iqmux33CmdEntry 42292 }


    iqmux33Logging1AncillaryDataLoggingLogWSTInp2 OBJECT-TYPE
        SYNTAX            INTEGER { disable(0), enable(1)  }
        MAX-ACCESS        read-write
        STATUS            current
        DESCRIPTION
                "CMNT: - Enable/Disable logging for ancillary data WST status
                 TYPE: - Checkbox
                 PAGE: - Logging1
                    Log WST Inp2  cmdID= 42183  "
        ::= { iqmux33CmdEntry 42183 }


    iqmux33Logging1AncillaryDataLoggingWSTInp2 OBJECT-TYPE
        SYNTAX            RollCallString
        MAX-ACCESS        read-only
        STATUS            current
        DESCRIPTION
                "CMNT: - Logging state for WST ancillary data on input
                 TYPE: - Display
                 PAGE: - Logging1
                    WST Inp2=  cmdID= 42293  "
        ::= { iqmux33CmdEntry 42293 }


    iqmux33Logging1AncillaryDataLoggingLogCC608Inp2 OBJECT-TYPE
        SYNTAX            INTEGER { disable(0), enable(1)  }
        MAX-ACCESS        read-write
        STATUS            current
        DESCRIPTION
                "CMNT: - Enable/Disable logging for ancillary data CC608 status
                 TYPE: - Checkbox
                 PAGE: - Logging1
                    Log CC608 Inp2  cmdID= 42184  "
        ::= { iqmux33CmdEntry 42184 }


    iqmux33Logging1AncillaryDataLoggingCC608Inp2 OBJECT-TYPE
        SYNTAX            RollCallString
        MAX-ACCESS        read-only
        STATUS            current
        DESCRIPTION
                "CMNT: - Logging state for CC608 ancillary data on input
                 TYPE: - Display
                 PAGE: - Logging1
                    CC608 Inp2=  cmdID= 42294  "
        ::= { iqmux33CmdEntry 42294 }


    iqmux33Logging1AncillaryDataLoggingLogATCInp2 OBJECT-TYPE
        SYNTAX            INTEGER { disable(0), enable(1)  }
        MAX-ACCESS        read-write
        STATUS            current
        DESCRIPTION
                "CMNT: - Enable/Disable logging for ancillary data ATC status
                 TYPE: - Checkbox
                 PAGE: - Logging1
                    Log ATC Inp2  cmdID= 42186  "
        ::= { iqmux33CmdEntry 42186 }


    iqmux33Logging1AncillaryDataLoggingATCInp2 OBJECT-TYPE
        SYNTAX            RollCallString
        MAX-ACCESS        read-only
        STATUS            current
        DESCRIPTION
                "CMNT: - Logging state for ATC/VITC ancillary data on input
                 TYPE: - Display
                 PAGE: - Logging1
                    ATC Inp2=  cmdID= 42296  "
        ::= { iqmux33CmdEntry 42296 }


    iqmux33Logging1AncillaryDataLoggingLogCC708Inp2 OBJECT-TYPE
        SYNTAX            INTEGER { disable(0), enable(1)  }
        MAX-ACCESS        read-write
        STATUS            current
        DESCRIPTION
                "CMNT: - Enable/Disable logging for ancillary data CC708 status
                 TYPE: - Checkbox
                 PAGE: - Logging1
                    Log CC708 Inp2  cmdID= 42187  "
        ::= { iqmux33CmdEntry 42187 }


    iqmux33Logging1AncillaryDataLoggingCC708Inp2 OBJECT-TYPE
        SYNTAX            RollCallString
        MAX-ACCESS        read-only
        STATUS            current
        DESCRIPTION
                "CMNT: - Logging state for CC708/OP47 ancillary data on input
                 TYPE: - Display
                 PAGE: - Logging1
                    CC708 Inp2=  cmdID= 42297  "
        ::= { iqmux33CmdEntry 42297 }


    iqmux33Logging2VideoRefLogInp1Type OBJECT-TYPE
        SYNTAX            INTEGER { disable(0), enable(1)  }
        MAX-ACCESS        read-write
        STATUS            current
        DESCRIPTION
                "CMNT: - Enable/Disable logging for Inp 1, Type
                 TYPE: - Checkbox
                 PAGE: - Logging2
                    Log Inp1 Type  cmdID= 42060  "
        ::= { iqmux33CmdEntry 42060 }


    iqmux33Logging2VideoRefInp1Type OBJECT-TYPE
        SYNTAX            RollCallString
        MAX-ACCESS        read-only
        STATUS            current
        DESCRIPTION
                "CMNT: - Logging state for Inp 1 Type
                 TYPE: - Display
                 PAGE: - Logging2
                    Inp1 Type=  cmdID= 42260  "
        ::= { iqmux33CmdEntry 42260 }


    iqmux33Logging2VideoRefLogInp1State OBJECT-TYPE
        SYNTAX            INTEGER { disable(0), enable(1)  }
        MAX-ACCESS        read-write
        STATUS            current
        DESCRIPTION
                "CMNT: - Enable/Disable logging for Inp 1, State
                 TYPE: - Checkbox
                 PAGE: - Logging2
                    Log Inp1 State  cmdID= 42063  "
        ::= { iqmux33CmdEntry 42063 }


    iqmux33Logging2VideoRefInp1State OBJECT-TYPE
        SYNTAX            RollCallString
        MAX-ACCESS        read-only
        STATUS            current
        DESCRIPTION
                "CMNT: - Logging state for Inp 1 State
                 TYPE: - Display
                 PAGE: - Logging2
                    Inp1 State=  cmdID= 42263  "
        ::= { iqmux33CmdEntry 42263 }


    iqmux33Logging2VideoRefLogInp1Std OBJECT-TYPE
        SYNTAX            INTEGER { disable(0), enable(1)  }
        MAX-ACCESS        read-write
        STATUS            current
        DESCRIPTION
                "CMNT: - Enable/Disable logging for Inp 1, Standard
                 TYPE: - Checkbox
                 PAGE: - Logging2
                    Log Inp1 Std  cmdID= 42066  "
        ::= { iqmux33CmdEntry 42066 }


    iqmux33Logging2VideoRefInp1Std OBJECT-TYPE
        SYNTAX            RollCallString
        MAX-ACCESS        read-only
        STATUS            current
        DESCRIPTION
                "CMNT: - Logging state for Inp 1 Standard
                 TYPE: - Display
                 PAGE: - Logging2
                    Inp1 Std=  cmdID= 42266  "
        ::= { iqmux33CmdEntry 42266 }


    iqmux33Logging2VideoRefLogInp1SDIErrs OBJECT-TYPE
        SYNTAX            INTEGER { disable(0), enable(1)  }
        MAX-ACCESS        read-write
        STATUS            current
        DESCRIPTION
                "CMNT: - Enable/Disable logging for Inp 1, Sdi Errs
                 TYPE: - Checkbox
                 PAGE: - Logging2
                    Log Inp1 SDIErrs  cmdID= 42069  "
        ::= { iqmux33CmdEntry 42069 }


    iqmux33Logging2VideoRefInp1SDIErrs OBJECT-TYPE
        SYNTAX            RollCallString
        MAX-ACCESS        read-only
        STATUS            current
        DESCRIPTION
                "CMNT: - Logging state for Inp 1 Sdi Errs
                 TYPE: - Display
                 PAGE: - Logging2
                    Inp1 SDIErrs=  cmdID= 42269  "
        ::= { iqmux33CmdEntry 42269 }


    iqmux33Logging2VideoRefLogInp1SDIErrSec OBJECT-TYPE
        SYNTAX            INTEGER { disable(0), enable(1)  }
        MAX-ACCESS        read-write
        STATUS            current
        DESCRIPTION
                "CMNT: - Enable/Disable logging for Inp 1, Sdi Errs
                 TYPE: - Checkbox
                 PAGE: - Logging2
                    Log Inp1 SDIErrSec  cmdID= 42071  "
        ::= { iqmux33CmdEntry 42071 }


    iqmux33Logging2VideoRefInp1SDIErrSec OBJECT-TYPE
        SYNTAX            RollCallString
        MAX-ACCESS        read-only
        STATUS            current
        DESCRIPTION
                "CMNT: - Logging state for Inp 1 Sdi Errs
                 TYPE: - Display
                 PAGE: - Logging2
                    Inp1 SDIErrSec=  cmdID= 42271  "
        ::= { iqmux33CmdEntry 42271 }


    iqmux33Logging2VideoRefLogInp1ANCerrs OBJECT-TYPE
        SYNTAX            INTEGER { disable(0), enable(1)  }
        MAX-ACCESS        read-write
        STATUS            current
        DESCRIPTION
                "CMNT: - Enable/Disable logging for Inp 1, Sdi Anc Errs
                 TYPE: - Checkbox
                 PAGE: - Logging2
                    Log Inp1 ANCerrs  cmdID= 42073  "
        ::= { iqmux33CmdEntry 42073 }


    iqmux33Logging2VideoRefInp1ANCerrs OBJECT-TYPE
        SYNTAX            RollCallString
        MAX-ACCESS        read-only
        STATUS            current
        DESCRIPTION
                "CMNT: - Logging state for Inp 1 Sdi Anc Errs
                 TYPE: - Display
                 PAGE: - Logging2
                    Inp1 ANCerrs=  cmdID= 42273  "
        ::= { iqmux33CmdEntry 42273 }


    iqmux33Logging2VideoRefLogInp1ANCerrSec OBJECT-TYPE
        SYNTAX            INTEGER { disable(0), enable(1)  }
        MAX-ACCESS        read-write
        STATUS            current
        DESCRIPTION
                "CMNT: - Enable/Disable logging for Inp 1, Sdi Anc Errs
                 TYPE: - Checkbox
                 PAGE: - Logging2
                    Log Inp1 ANCerrSec  cmdID= 42075  "
        ::= { iqmux33CmdEntry 42075 }


    iqmux33Logging2VideoRefInp1ANCerrSec OBJECT-TYPE
        SYNTAX            RollCallString
        MAX-ACCESS        read-only
        STATUS            current
        DESCRIPTION
                "CMNT: - Logging state for Inp 1 Sdi Anc Errs
                 TYPE: - Display
                 PAGE: - Logging2
                    Inp1 ANCerrSec=  cmdID= 42275  "
        ::= { iqmux33CmdEntry 42275 }


    iqmux33Logging2VideoRefLogOutp1Type OBJECT-TYPE
        SYNTAX            INTEGER { disable(0), enable(1)  }
        MAX-ACCESS        read-write
        STATUS            current
        DESCRIPTION
                "CMNT: - Enable/Disable logging for Out 1, Type
                 TYPE: - Checkbox
                 PAGE: - Logging2
                    Log Outp1 Type  cmdID= 42077  "
        ::= { iqmux33CmdEntry 42077 }


    iqmux33Logging2VideoRefOutp1Type OBJECT-TYPE
        SYNTAX            RollCallString
        MAX-ACCESS        read-only
        STATUS            current
        DESCRIPTION
                "CMNT: - Logging state for Out 1 Type
                 TYPE: - Display
                 PAGE: - Logging2
                    Outp1 Type=  cmdID= 42277  "
        ::= { iqmux33CmdEntry 42277 }


    iqmux33Logging2VideoRefLogOutp1State OBJECT-TYPE
        SYNTAX            INTEGER { disable(0), enable(1)  }
        MAX-ACCESS        read-write
        STATUS            current
        DESCRIPTION
                "CMNT: - Enable/Disable logging for Out 1, State
                 TYPE: - Checkbox
                 PAGE: - Logging2
                    Log Outp1 State  cmdID= 42078  "
        ::= { iqmux33CmdEntry 42078 }


    iqmux33Logging2VideoRefOutp1State OBJECT-TYPE
        SYNTAX            RollCallString
        MAX-ACCESS        read-only
        STATUS            current
        DESCRIPTION
                "CMNT: - Logging state for Out 1 State
                 TYPE: - Display
                 PAGE: - Logging2
                    Outp1 State=  cmdID= 42278  "
        ::= { iqmux33CmdEntry 42278 }


    iqmux33Logging2VideoRefLogOutp1Std OBJECT-TYPE
        SYNTAX            INTEGER { disable(0), enable(1)  }
        MAX-ACCESS        read-write
        STATUS            current
        DESCRIPTION
                "CMNT: - Enable/Disable logging for Out 1, Standard
                 TYPE: - Checkbox
                 PAGE: - Logging2
                    Log Outp1 Std  cmdID= 42079  "
        ::= { iqmux33CmdEntry 42079 }


    iqmux33Logging2VideoRefOutp1Std OBJECT-TYPE
        SYNTAX            RollCallString
        MAX-ACCESS        read-only
        STATUS            current
        DESCRIPTION
                "CMNT: - Logging state for Out 1 Standard
                 TYPE: - Display
                 PAGE: - Logging2
                    Outp1 Std=  cmdID= 42279  "
        ::= { iqmux33CmdEntry 42279 }


    iqmux33Logging2VideoRefLogOutp1Capt OBJECT-TYPE
        SYNTAX            INTEGER { disable(0), enable(1)  }
        MAX-ACCESS        read-write
        STATUS            current
        DESCRIPTION
                "CMNT: - Enable/Disable logging for Out 1 CAPTION 
                 TYPE: - Checkbox
                 PAGE: - Logging2
                    Log Outp1 Capt  cmdID= 42081  "
        ::= { iqmux33CmdEntry 42081 }


    iqmux33Logging2VideoRefOutp1Capt OBJECT-TYPE
        SYNTAX            RollCallString
        MAX-ACCESS        read-only
        STATUS            current
        DESCRIPTION
                "CMNT: - Logging state for Out 1 CAPTION
                 TYPE: - Display
                 PAGE: - Logging2
                    Outp1 Capt=  cmdID= 42281  "
        ::= { iqmux33CmdEntry 42281 }


    iqmux33Logging2VideoRefLogRefType OBJECT-TYPE
        SYNTAX            INTEGER { disable(0), enable(1)  }
        MAX-ACCESS        read-write
        STATUS            current
        DESCRIPTION
                "CMNT: - Enable/Disable logging for REFERENCE 1, Type
                 TYPE: - Checkbox
                 PAGE: - Logging2
                    Log Ref Type  cmdID= 42083  "
        ::= { iqmux33CmdEntry 42083 }


    iqmux33Logging2VideoRefRefType OBJECT-TYPE
        SYNTAX            RollCallString
        MAX-ACCESS        read-only
        STATUS            current
        DESCRIPTION
                "CMNT: - Logging state for REFERENCE 1 Type
                 TYPE: - Display
                 PAGE: - Logging2
                    Ref Type=  cmdID= 42283  "
        ::= { iqmux33CmdEntry 42283 }


    iqmux33Logging2VideoRefLogRefState OBJECT-TYPE
        SYNTAX            INTEGER { disable(0), enable(1)  }
        MAX-ACCESS        read-write
        STATUS            current
        DESCRIPTION
                "CMNT: - Enable/Disable logging for REFERENCE 1 STATE
                 TYPE: - Checkbox
                 PAGE: - Logging2
                    Log Ref State  cmdID= 42084  "
        ::= { iqmux33CmdEntry 42084 }


    iqmux33Logging2VideoRefRefState OBJECT-TYPE
        SYNTAX            RollCallString
        MAX-ACCESS        read-only
        STATUS            current
        DESCRIPTION
                "CMNT: - Logging state for REFERENCE 1 STATE
                 TYPE: - Display
                 PAGE: - Logging2
                    Ref State=  cmdID= 42284  "
        ::= { iqmux33CmdEntry 42284 }


    iqmux33Logging2VideoRefLogRefStd OBJECT-TYPE
        SYNTAX            INTEGER { disable(0), enable(1)  }
        MAX-ACCESS        read-write
        STATUS            current
        DESCRIPTION
                "CMNT: - Enable/Disable logging for REFERENCE 1 STANDARD
                 TYPE: - Checkbox
                 PAGE: - Logging2
                    Log Ref Std  cmdID= 42085  "
        ::= { iqmux33CmdEntry 42085 }


    iqmux33Logging2VideoRefRefStd OBJECT-TYPE
        SYNTAX            RollCallString
        MAX-ACCESS        read-only
        STATUS            current
        DESCRIPTION
                "CMNT: - Logging state for REFERENCE 1 STANDARD
                 TYPE: - Display
                 PAGE: - Logging2
                    Ref Std=  cmdID= 42285  "
        ::= { iqmux33CmdEntry 42285 }


    iqmux33Logging2VideoRefLogGenlockState OBJECT-TYPE
        SYNTAX            INTEGER { disable(0), enable(1)  }
        MAX-ACCESS        read-write
        STATUS            current
        DESCRIPTION
                "CMNT: - Enable/Disable logging for GENLOCK 1, State
                 TYPE: - Checkbox
                 PAGE: - Logging2
                    Log Genlock State  cmdID= 42082  "
        ::= { iqmux33CmdEntry 42082 }


    iqmux33Logging2VideoRefGenlocState OBJECT-TYPE
        SYNTAX            RollCallString
        MAX-ACCESS        read-only
        STATUS            current
        DESCRIPTION
                "CMNT: - Logging state for GENLOCK 1 State
                 TYPE: - Display
                 PAGE: - Logging2
                    Genloc State=  cmdID= 42282  "
        ::= { iqmux33CmdEntry 42282 }


    iqmux33Logging2VideoRefLogInp1Ident OBJECT-TYPE
        SYNTAX            INTEGER { disable(0), enable(1)  }
        MAX-ACCESS        read-write
        STATUS            current
        DESCRIPTION
                "CMNT: - Enable/Disable logging for Inp 1, Ident
                 TYPE: - Checkbox
                 PAGE: - Logging2
                    Log Inp1 Ident  cmdID= 42130  "
        ::= { iqmux33CmdEntry 42130 }


    iqmux33Logging2VideoRefInp1Ident OBJECT-TYPE
        SYNTAX            RollCallString
        MAX-ACCESS        read-only
        STATUS            current
        DESCRIPTION
                "CMNT: - Logging state for Inp 1 Ident
                 TYPE: - Display
                 PAGE: - Logging2
                    Inp1 Ident=  cmdID= 42330  "
        ::= { iqmux33CmdEntry 42330 }


    iqmux33Logging2VideoRefLogInp1Name OBJECT-TYPE
        SYNTAX            INTEGER { disable(0), enable(1)  }
        MAX-ACCESS        read-write
        STATUS            current
        DESCRIPTION
                "CMNT: - Enable/Disable logging for Inp 1, Name
                 TYPE: - Checkbox
                 PAGE: - Logging2
                    Log Inp1 Name  cmdID= 42133  "
        ::= { iqmux33CmdEntry 42133 }


    iqmux33Logging2VideoRefInp1Name OBJECT-TYPE
        SYNTAX            RollCallString
        MAX-ACCESS        read-only
        STATUS            current
        DESCRIPTION
                "CMNT: - Logging state for Inp 1 Name
                 TYPE: - Display
                 PAGE: - Logging2
                    Inp1 Name=  cmdID= 42333  "
        ::= { iqmux33CmdEntry 42333 }


    iqmux33Logging2InEmbAudLoggingInpEmb1state OBJECT-TYPE
        SYNTAX            RollCallString
        MAX-ACCESS        read-only
        STATUS            current
        DESCRIPTION
                "CMNT: - Logging state for Inp 1, Emb Pair 1 state
                 TYPE: - Display
                 PAGE: - Logging2
                    Inp Emb.1 state=  cmdID= 42200  "
        ::= { iqmux33CmdEntry 42200 }


    iqmux33Logging2InEmbAudLoggingInpEmb2state OBJECT-TYPE
        SYNTAX            RollCallString
        MAX-ACCESS        read-only
        STATUS            current
        DESCRIPTION
                "CMNT: - Logging state for Inp 1, Emb Pair 2 state
                 TYPE: - Display
                 PAGE: - Logging2
                    Inp Emb.2 state=  cmdID= 42201  "
        ::= { iqmux33CmdEntry 42201 }


    iqmux33Logging2InEmbAudLoggingInpEmb3state OBJECT-TYPE
        SYNTAX            RollCallString
        MAX-ACCESS        read-only
        STATUS            current
        DESCRIPTION
                "CMNT: - Logging state for Inp 1, Emb Pair 3 state
                 TYPE: - Display
                 PAGE: - Logging2
                    Inp Emb.3 state=  cmdID= 42202  "
        ::= { iqmux33CmdEntry 42202 }


    iqmux33Logging2InEmbAudLoggingInpEmb4state OBJECT-TYPE
        SYNTAX            RollCallString
        MAX-ACCESS        read-only
        STATUS            current
        DESCRIPTION
                "CMNT: - Logging state for Inp 1, Emb Pair 4 state
                 TYPE: - Display
                 PAGE: - Logging2
                    Inp Emb.4 state=  cmdID= 42203  "
        ::= { iqmux33CmdEntry 42203 }


    iqmux33Logging2InEmbAudLoggingInpEmb5state OBJECT-TYPE
        SYNTAX            RollCallString
        MAX-ACCESS        read-only
        STATUS            current
        DESCRIPTION
                "CMNT: - Logging state for Inp 1, Emb Pair 5 state
                 TYPE: - Display
                 PAGE: - Logging2
                    Inp Emb.5 state=  cmdID= 42204  "
        ::= { iqmux33CmdEntry 42204 }


    iqmux33Logging2InEmbAudLoggingInpEmb6state OBJECT-TYPE
        SYNTAX            RollCallString
        MAX-ACCESS        read-only
        STATUS            current
        DESCRIPTION
                "CMNT: - Logging state for Inp 1, Emb Pair 6 state
                 TYPE: - Display
                 PAGE: - Logging2
                    Inp Emb.6 state=  cmdID= 42205  "
        ::= { iqmux33CmdEntry 42205 }


    iqmux33Logging2InEmbAudLoggingInpEmb7state OBJECT-TYPE
        SYNTAX            RollCallString
        MAX-ACCESS        read-only
        STATUS            current
        DESCRIPTION
                "CMNT: - Logging state for Inp 1, Emb Pair 7 state
                 TYPE: - Display
                 PAGE: - Logging2
                    Inp Emb.7 state=  cmdID= 42206  "
        ::= { iqmux33CmdEntry 42206 }


    iqmux33Logging2InEmbAudLoggingInpEmb8state OBJECT-TYPE
        SYNTAX            RollCallString
        MAX-ACCESS        read-only
        STATUS            current
        DESCRIPTION
                "CMNT: - Logging state for Inp 1, Emb Pair 8 state
                 TYPE: - Display
                 PAGE: - Logging2
                    Inp Emb.8 state=  cmdID= 42207  "
        ::= { iqmux33CmdEntry 42207 }


    iqmux33Logging2In1EmbAudLoggingLogInp1Emb1state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging2
                    Log Inp1 Emb.1 state  cmdID= 42139  "
        ::= { iqmux33CmdEntry 42139 }


    iqmux33Logging2In1EmbAudLoggingInp1Emb1state OBJECT-TYPE
        SYNTAX            RollCallString
        MAX-ACCESS        read-only
        STATUS            current
        DESCRIPTION
                "CMNT: - Logging state for Inp 1, Emb Pair 1 state
                 TYPE: - Display
                 PAGE: - Logging2
                    Inp1 Emb.1 state=  cmdID= 42339  "
        ::= { iqmux33CmdEntry 42339 }


    iqmux33Logging2In1EmbAudLoggingLogInp1Emb2state OBJECT-TYPE
        SYNTAX            INTEGER { disable(0), enable(1)  }
        MAX-ACCESS        read-write
        STATUS            current
        DESCRIPTION
                "CMNT: - Enable/Disable logging for Inp 1, Emb Pair 2 state
                 TYPE: - Checkbox
                 PAGE: - Logging2
                    Log Inp1 Emb.2 state  cmdID= 42140  "
        ::= { iqmux33CmdEntry 42140 }


    iqmux33Logging2In1EmbAudLoggingInp1Emb2state OBJECT-TYPE
        SYNTAX            RollCallString
        MAX-ACCESS        read-only
        STATUS            current
        DESCRIPTION
                "CMNT: - Logging state for Inp 1, Emb Pair 2 state
                 TYPE: - Display
                 PAGE: - Logging2
                    Inp1 Emb.2 state=  cmdID= 42340  "
        ::= { iqmux33CmdEntry 42340 }


    iqmux33Logging2In1EmbAudLoggingLogInp1Emb3state OBJECT-TYPE
        SYNTAX            INTEGER { disable(0), enable(1)  }
        MAX-ACCESS        read-write
        STATUS            current
        DESCRIPTION
                "CMNT: - Enable/Disable logging for Inp 1, Emb Pair 3 state
                 TYPE: - Checkbox
                 PAGE: - Logging2
                    Log Inp1 Emb.3 state  cmdID= 42141  "
        ::= { iqmux33CmdEntry 42141 }


    iqmux33Logging2In1EmbAudLoggingInp1Emb3state OBJECT-TYPE
        SYNTAX            RollCallString
        MAX-ACCESS        read-only
        STATUS            current
        DESCRIPTION
                "CMNT: - Logging state for Inp 1, Emb Pair 3 state
                 TYPE: - Display
                 PAGE: - Logging2
                    Inp1 Emb.3 state=  cmdID= 42341  "
        ::= { iqmux33CmdEntry 42341 }


    iqmux33Logging2In1EmbAudLoggingLogInp1Emb4state OBJECT-TYPE
        SYNTAX            INTEGER { disable(0), enable(1)  }
        MAX-ACCESS        read-write
        STATUS            current
        DESCRIPTION
                "CMNT: - Enable/Disable logging for Inp 1, Emb Pair 4 state
                 TYPE: - Checkbox
                 PAGE: - Logging2
                    Log Inp1 Emb.4 state  cmdID= 42142  "
        ::= { iqmux33CmdEntry 42142 }


    iqmux33Logging2In1EmbAudLoggingInp1Emb4state OBJECT-TYPE
        SYNTAX            RollCallString
        MAX-ACCESS        read-only
        STATUS            current
        DESCRIPTION
                "CMNT: - Logging state for Inp 1, Emb Pair 4 state
                 TYPE: - Display
                 PAGE: - Logging2
                    Inp1 Emb.4 state=  cmdID= 42342  "
        ::= { iqmux33CmdEntry 42342 }


    iqmux33Logging2In1EmbAudLoggingLogInp1Emb5state OBJECT-TYPE
        SYNTAX            INTEGER { disable(0), enable(1)  }
        MAX-ACCESS        read-write
        STATUS            current
        DESCRIPTION
                "CMNT: - Enable/Disable logging for Inp 1, Emb Pair 5 state
                 TYPE: - Checkbox
                 PAGE: - Logging2
                    Log Inp1 Emb.5 state  cmdID= 42143  "
        ::= { iqmux33CmdEntry 42143 }


    iqmux33Logging2In1EmbAudLoggingInp1Emb5state OBJECT-TYPE
        SYNTAX            RollCallString
        MAX-ACCESS        read-only
        STATUS            current
        DESCRIPTION
                "CMNT: - Logging state for Inp 1, Emb Pair 5 state
                 TYPE: - Display
                 PAGE: - Logging2
                    Inp1 Emb.5 state=  cmdID= 42343  "
        ::= { iqmux33CmdEntry 42343 }


    iqmux33Logging2In1EmbAudLoggingLogInp1Emb6state OBJECT-TYPE
        SYNTAX            INTEGER { disable(0), enable(1)  }
        MAX-ACCESS        read-write
        STATUS            current
        DESCRIPTION
                "CMNT: - Enable/Disable logging for Inp 1, Emb Pair 6 state
                 TYPE: - Checkbox
                 PAGE: - Logging2
                    Log Inp1 Emb.6 state  cmdID= 42144  "
        ::= { iqmux33CmdEntry 42144 }


    iqmux33Logging2In1EmbAudLoggingInp1Emb6state OBJECT-TYPE
        SYNTAX            RollCallString
        MAX-ACCESS        read-only
        STATUS            current
        DESCRIPTION
                "CMNT: - Logging state for Inp 1, Emb Pair 6 state
                 TYPE: - Display
                 PAGE: - Logging2
                    Inp1 Emb.6 state=  cmdID= 42344  "
        ::= { iqmux33CmdEntry 42344 }


    iqmux33Logging2In1EmbAudLoggingLogInp1Emb7state OBJECT-TYPE
        SYNTAX            INTEGER { disable(0), enable(1)  }
        MAX-ACCESS        read-write
        STATUS            current
        DESCRIPTION
                "CMNT: - Enable/Disable logging for Inp 1, Emb Pair 7 state
                 TYPE: - Checkbox
                 PAGE: - Logging2
                    Log Inp1 Emb.7 state  cmdID= 42145  "
        ::= { iqmux33CmdEntry 42145 }


    iqmux33Logging2In1EmbAudLoggingInp1Emb7state OBJECT-TYPE
        SYNTAX            RollCallString
        MAX-ACCESS        read-only
        STATUS            current
        DESCRIPTION
                "CMNT: - Logging state for Inp 1, Emb Pair 7 state
                 TYPE: - Display
                 PAGE: - Logging2
                    Inp1 Emb.7 state=  cmdID= 42345  "
        ::= { iqmux33CmdEntry 42345 }


    iqmux33Logging2In1EmbAudLoggingLogInp1Emb8state OBJECT-TYPE
        SYNTAX            INTEGER { disable(0), enable(1)  }
        MAX-ACCESS        read-write
        STATUS            current
        DESCRIPTION
                "CMNT: - Enable/Disable logging for Inp 1, Emb Pair 8 state
                 TYPE: - Checkbox
                 PAGE: - Logging2
                    Log Inp1 Emb.8 state  cmdID= 42146  "
        ::= { iqmux33CmdEntry 42146 }


    iqmux33Logging2In1EmbAudLoggingInp1Emb8state OBJECT-TYPE
        SYNTAX            RollCallString
        MAX-ACCESS        read-only
        STATUS            current
        DESCRIPTION
                "CMNT: - Logging state for Inp 1, Emb Pair 8 state
                 TYPE: - Display
                 PAGE: - Logging2
                    Inp1 Emb.8 state=  cmdID= 42346  "
        ::= { iqmux33CmdEntry 42346 }


    iqmux33Logging2DolbyEAlignLogOutEmb1dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.1 dolby  cmdID= 42160  "
        ::= { iqmux33CmdEntry 42160 }


    iqmux33Logging2DolbyEAlignOutEmb1Dolby OBJECT-TYPE
        SYNTAX            RollCallString
        MAX-ACCESS        read-only
        STATUS            current
        DESCRIPTION
                "CMNT: - Logging state for Outp 1, Emb Dolby
                 TYPE: - Display
                 PAGE: - Logging2
                    Out Emb.1 Dolby=  cmdID= 42360  "
        ::= { iqmux33CmdEntry 42360 }


    iqmux33Logging2DolbyEAlignLogOutEmb2dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.2 dolby  cmdID= 42161  "
        ::= { iqmux33CmdEntry 42161 }


    iqmux33Logging2DolbyEAlignOutEmb2Dolby OBJECT-TYPE
        SYNTAX            RollCallString
        MAX-ACCESS        read-only
        STATUS            current
        DESCRIPTION
                "CMNT: - Logging state for Outp 1, Emb Dolby
                 TYPE: - Display
                 PAGE: - Logging2
                    Out Emb.2 Dolby=  cmdID= 42361  "
        ::= { iqmux33CmdEntry 42361 }


    iqmux33Logging2DolbyEAlignLogOutEmb3dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.3 dolby  cmdID= 42162  "
        ::= { iqmux33CmdEntry 42162 }


    iqmux33Logging2DolbyEAlignOutEmb3Dolby OBJECT-TYPE
        SYNTAX            RollCallString
        MAX-ACCESS        read-only
        STATUS            current
        DESCRIPTION
                "CMNT: - Logging state for Outp 1, Emb Dolby
                 TYPE: - Display
                 PAGE: - Logging2
                    Out Emb.3 Dolby=  cmdID= 42362  "
        ::= { iqmux33CmdEntry 42362 }


    iqmux33Logging2DolbyEAlignLogOutEmb4dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.4 dolby  cmdID= 42163  "
        ::= { iqmux33CmdEntry 42163 }


    iqmux33Logging2DolbyEAlignOutEmb4Dolby OBJECT-TYPE
        SYNTAX            RollCallString
        MAX-ACCESS        read-only
        STATUS            current
        DESCRIPTION
                "CMNT: - Logging state for Outp 1, Emb Dolby
                 TYPE: - Display
                 PAGE: - Logging2
                    Out Emb.4 Dolby=  cmdID= 42363  "
        ::= { iqmux33CmdEntry 42363 }


    iqmux33Logging2DolbyEAlignLogOutEmb5dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.5 dolby  cmdID= 42164  "
        ::= { iqmux33CmdEntry 42164 }


    iqmux33Logging2DolbyEAlignOutEmb5Dolby OBJECT-TYPE
        SYNTAX            RollCallString
        MAX-ACCESS        read-only
        STATUS            current
        DESCRIPTION
                "CMNT: - Logging state for Outp 1, Emb Dolby
                 TYPE: - Display
                 PAGE: - Logging2
                    Out Emb.5 Dolby=  cmdID= 42364  "
        ::= { iqmux33CmdEntry 42364 }


    iqmux33Logging2DolbyEAlignLogOutEmb6dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.6 dolby  cmdID= 42165  "
        ::= { iqmux33CmdEntry 42165 }


    iqmux33Logging2DolbyEAlignOutEmb6Dolby OBJECT-TYPE
        SYNTAX            RollCallString
        MAX-ACCESS        read-only
        STATUS            current
        DESCRIPTION
                "CMNT: - Logging state for Outp 1, Emb Dolby
                 TYPE: - Display
                 PAGE: - Logging2
                    Out Emb.6 Dolby=  cmdID= 42365  "
        ::= { iqmux33CmdEntry 42365 }


    iqmux33Logging2DolbyEAlignLogOutEmb7dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.7 dolby  cmdID= 42166  "
        ::= { iqmux33CmdEntry 42166 }


    iqmux33Logging2DolbyEAlignOutEmb7Dolby OBJECT-TYPE
        SYNTAX            RollCallString
        MAX-ACCESS        read-only
        STATUS            current
        DESCRIPTION
                "CMNT: - Logging state for Outp 1, Emb Dolby
                 TYPE: - Display
                 PAGE: - Logging2
                    Out Emb.7 Dolby=  cmdID= 42366  "
        ::= { iqmux33CmdEntry 42366 }


    iqmux33Logging2DolbyEAlignLogOutEmb8dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.8 dolby  cmdID= 42167  "
        ::= { iqmux33CmdEntry 42167 }


    iqmux33Logging2DolbyEAlignOutEmb8Dolby OBJECT-TYPE
        SYNTAX            RollCallString
        MAX-ACCESS        read-only
        STATUS            current
        DESCRIPTION
                "CMNT: - Logging state for Outp 1, Emb Dolby
                 TYPE: - Display
                 PAGE: - Logging2
                    Out Emb.8 Dolby=  cmdID= 42367  "
        ::= { iqmux33CmdEntry 42367 }


    iqmux33Logging2MiscLoggingLogSerialNo OBJECT-TYPE
        SYNTAX            INTEGER { disable(0), enable(1)  }
        MAX-ACCESS        read-write
        STATUS            current
        DESCRIPTION
                "CMNT: - Enable/Disable logging for Serial No.
                 TYPE: - Checkbox
                 PAGE: - Logging2
                    Log Serial No.  cmdID= 35015  "
        ::= { iqmux33CmdEntry 35015 }


    iqmux33Logging2MiscLoggingSerialNo OBJECT-TYPE
        SYNTAX            RollCallString
        MAX-ACCESS        read-only
        STATUS            current
        DESCRIPTION
                "CMNT: - Logging state for Serial No.
                 TYPE: - Display
                 PAGE: - Logging2
                    Serial No.=  cmdID= 36015  "
        ::= { iqmux33CmdEntry 36015 }


    iqmux33Logging2MiscLoggingLogOSVersion OBJECT-TYPE
        SYNTAX            INTEGER { disable(0), enable(1)  }
        MAX-ACCESS        read-write
        STATUS            current
        DESCRIPTION
                "CMNT: - Enable/Disable logging for OS Version
                 TYPE: - Checkbox
                 PAGE: - Logging2
                    Log OS Version  cmdID= 35993  "
        ::= { iqmux33CmdEntry 35993 }


    iqmux33Logging2MiscLoggingOSVersion OBJECT-TYPE
        SYNTAX            RollCallString
        MAX-ACCESS        read-only
        STATUS            current
        DESCRIPTION
                "CMNT: - Logging state for OS Version
                 TYPE: - Display
                 PAGE: - Logging2
                    OS Version=  cmdID= 36993  "
        ::= { iqmux33CmdEntry 36993 }


    iqmux33Logging2MiscLoggingLogBuildNo OBJECT-TYPE
        SYNTAX            INTEGER { disable(0), enable(1)  }
        MAX-ACCESS        read-write
        STATUS            current
        DESCRIPTION
                "CMNT: - Enable/Disable logging for Build No.
                 TYPE: - Checkbox
                 PAGE: - Logging2
                    Log Build No.  cmdID= 35990  "
        ::= { iqmux33CmdEntry 35990 }


    iqmux33Logging2MiscLoggingBuildNo OBJECT-TYPE
        SYNTAX            RollCallString
        MAX-ACCESS        read-only
        STATUS            current
        DESCRIPTION
                "CMNT: - Logging state for Build No.
                 TYPE: - Display
                 PAGE: - Logging2
                    Build No.=  cmdID= 36990  "
        ::= { iqmux33CmdEntry 36990 }


    iqmux33Logging2MiscLoggingLogHardwareVer OBJECT-TYPE
        SYNTAX            INTEGER { disable(0), enable(1)  }
        MAX-ACCESS        read-write
        STATUS            current
        DESCRIPTION
                "CMNT: - Enable/Disable logging for Hardware Ver.
                 TYPE: - Checkbox
                 PAGE: - Logging2
                    Log Hardware Ver.  cmdID= 35992  "
        ::= { iqmux33CmdEntry 35992 }


    iqmux33Logging2MiscLoggingHardwareVer OBJECT-TYPE
        SYNTAX            RollCallString
        MAX-ACCESS        read-only
        STATUS            current
        DESCRIPTION
                "CMNT: - Logging state for Hardware Ver.
                 TYPE: - Display
                 PAGE: - Logging2
                    Hardware Ver.=  cmdID= 36992  "
        ::= { iqmux33CmdEntry 36992 }


    iqmux33Logging2MiscLoggingLogFirmwareVer OBJECT-TYPE
        SYNTAX            INTEGER { disable(0), enable(1)  }
        MAX-ACCESS        read-write
        STATUS            current
        DESCRIPTION
                "CMNT: - Enable/Disable logging for Firmware Ver.
                 TYPE: - Checkbox
                 PAGE: - Logging2
                    Log Firmware Ver.  cmdID= 35991  "
        ::= { iqmux33CmdEntry 35991 }


    iqmux33Logging2MiscLoggingFirmwareVer OBJECT-TYPE
        SYNTAX            RollCallString
        MAX-ACCESS        read-only
        STATUS            current
        DESCRIPTION
                "CMNT: - Logging state for Firmware Ver.
                 TYPE: - Display
                 PAGE: - Logging2
                    Firmware Ver.=  cmdID= 36991  "
        ::= { iqmux33CmdEntry 36991 }


    iqmux33Logging2MiscLoggingLogUpTime OBJECT-TYPE
        SYNTAX            INTEGER { disable(0), enable(1)  }
        MAX-ACCESS        read-write
        STATUS            current
        DESCRIPTION
                "CMNT: - Enable/Disable logging for Up Time
                 TYPE: - Checkbox
                 PAGE: - Logging2
                    Log Up Time  cmdID= 35994  "
        ::= { iqmux33CmdEntry 35994 }


    iqmux33Logging2MiscLoggingUpTime OBJECT-TYPE
        SYNTAX            RollCallString
        MAX-ACCESS        read-only
        STATUS            current
        DESCRIPTION
                "CMNT: - Logging state for Up Time
                 TYPE: - Display
                 PAGE: - Logging2
                    Up Time=  cmdID= 36994  "
        ::= { iqmux33CmdEntry 36994 }


    iqmux33Logging2MiscLoggingLogLicensedOpt OBJECT-TYPE
        SYNTAX            INTEGER { disable(0), enable(1)  }
        MAX-ACCESS        read-write
        STATUS            current
        DESCRIPTION
                "CMNT: - Enable/Disable logging for Display Licensed Options
                 TYPE: - Checkbox
                 PAGE: - Logging2
                    Log Licensed Opt.  cmdID= 35995  "
        ::= { iqmux33CmdEntry 35995 }


    iqmux33Logging2MiscLoggingLicensedOptions OBJECT-TYPE
        SYNTAX            RollCallString
        MAX-ACCESS        read-only
        STATUS            current
        DESCRIPTION
                "CMNT: - Logging Licened Options
                 TYPE: - Display
                 PAGE: - Logging2
                    Licensed Options   cmdID= 36995  "
        ::= { iqmux33CmdEntry 36995 }


    iqmux33Logging2MiscLoggingLogLicensedOpt2 OBJECT-TYPE
        SYNTAX            INTEGER { disable(0), enable(1)  }
        MAX-ACCESS        read-write
        STATUS            current
        DESCRIPTION
                "CMNT: - Enable/Disable logging for Display Licensed Options
                 TYPE: - Checkbox
                 PAGE: - Logging2
                    Log Licensed Opt2.  cmdID= 35996  "
        ::= { iqmux33CmdEntry 35996 }


    iqmux33Logging2MiscLoggingLicensedOptions2 OBJECT-TYPE
        SYNTAX            RollCallString
        MAX-ACCESS        read-only
        STATUS            current
        DESCRIPTION
                "CMNT: - Logging Licened Options
                 TYPE: - Display
                 PAGE: - Logging2
                    Licensed Options 2  cmdID= 36996  "
        ::= { iqmux33CmdEntry 36996 }


    iqmux33Logging2MiscLoggingLogTemp1State OBJECT-TYPE
        SYNTAX            INTEGER { disable(0), enable(1)  }
        MAX-ACCESS        read-write
        STATUS            current
        DESCRIPTION
                "CMNT: - Enable/Disable logging for TEMP 1 STATE
                 TYPE: - Checkbox
                 PAGE: - Logging2
                    Log Temp1State  cmdID= 42137  "
        ::= { iqmux33CmdEntry 42137 }


    iqmux33Logging2MiscLoggingTemp1State OBJECT-TYPE
        SYNTAX            RollCallString
        MAX-ACCESS        read-only
        STATUS            current
        DESCRIPTION
                "CMNT: - Logging state for TEMP_1_STATE
                 TYPE: - Display
                 PAGE: - Logging2
                    Temp1State=  cmdID= 42337  "
        ::= { iqmux33CmdEntry 42337 }


    iqmux33Logging2MiscLoggingLogTemp1Name OBJECT-TYPE
        SYNTAX            INTEGER { disable(0), enable(1)  }
        MAX-ACCESS        read-write
        STATUS            current
        DESCRIPTION
                "CMNT: - Enable/Disable logging for TEMP 1 NAME
                 TYPE: - Checkbox
                 PAGE: - Logging2
                    Log Temp1Name  cmdID= 42138  "
        ::= { iqmux33CmdEntry 42138 }


    iqmux33Logging2MiscLoggingTemp1Name OBJECT-TYPE
        SYNTAX            RollCallString
        MAX-ACCESS        read-only
        STATUS            current
        DESCRIPTION
                "CMNT: - Logging state for TEMP_1_NAME
                 TYPE: - Display
                 PAGE: - Logging2
                    Temp1Name=  cmdID= 42338  "
        ::= { iqmux33CmdEntry 42338 }


    iqmux33Logging2MiscLoggingLogRearId OBJECT-TYPE
        SYNTAX            INTEGER { disable(0), enable(1)  }
        MAX-ACCESS        read-write
        STATUS            current
        DESCRIPTION
                "CMNT: - Enable/Disable logging for Display Rear Id
                 TYPE: - Checkbox
                 PAGE: - Logging2
                    Log RearId  cmdID= 35997  "
        ::= { iqmux33CmdEntry 35997 }


    iqmux33Logging2MiscLoggingRearID OBJECT-TYPE
        SYNTAX            RollCallString
        MAX-ACCESS        read-only
        STATUS            current
        DESCRIPTION
                "CMNT: - Logging Rear ID
                 TYPE: - Display
                 PAGE: - Logging2
                    RearID=  cmdID= 36997  "
        ::= { iqmux33CmdEntry 36997 }


    iqmux33Logging2MiscLoggingLogSlotWidth OBJECT-TYPE
        SYNTAX            INTEGER { disable(0), enable(1)  }
        MAX-ACCESS        read-write
        STATUS            current
        DESCRIPTION
                "CMNT: - Enable/Disable logging for Display Slot Width
                 TYPE: - Checkbox
                 PAGE: - Logging2
                    Log Slot Width  cmdID= 35998  "
        ::= { iqmux33CmdEntry 35998 }


    iqmux33Logging2MiscLoggingSlotWidth OBJECT-TYPE
        SYNTAX            RollCallString
        MAX-ACCESS        read-only
        STATUS            current
        DESCRIPTION
                "CMNT: - Logging Slot width
                 TYPE: - Display
                 PAGE: - Logging2
                    SlotWidth=  cmdID= 36998  "
        ::= { iqmux33CmdEntry 36998 }


    iqmux33Logging2MiscLoggingLogSlotStart OBJECT-TYPE
        SYNTAX            INTEGER { disable(0), enable(1)  }
        MAX-ACCESS        read-write
        STATUS            current
        DESCRIPTION
                "CMNT: - Enable/Disable logging for Display Slot Start
                 TYPE: - Checkbox
                 PAGE: - Logging2
                    Log Slot Start  cmdID= 35999  "
        ::= { iqmux33CmdEntry 35999 }


    iqmux33Logging2MiscLoggingSlotStart OBJECT-TYPE
        SYNTAX            RollCallString
        MAX-ACCESS        read-only
        STATUS            current
        DESCRIPTION
                "CMNT: - Logging Slot start
                 TYPE: - Display
                 PAGE: - Logging2
                    SlotStart=  cmdID= 36999  "
        ::= { iqmux33CmdEntry 36999 }


    iqmux33Logging2MiscLoggingLogRearStatus OBJECT-TYPE
        SYNTAX            INTEGER { disable(0), enable(1)  }
        MAX-ACCESS        read-write
        STATUS            current
        DESCRIPTION
                "CMNT: - Enable/Disable logging for Display Rear Status
                 TYPE: - Checkbox
                 PAGE: - Logging2
                    Log RearStatus  cmdID= 36000  "
        ::= { iqmux33CmdEntry 36000 }


    iqmux33Logging2MiscLoggingRearSTATUS OBJECT-TYPE
        SYNTAX            RollCallString
        MAX-ACCESS        read-only
        STATUS            current
        DESCRIPTION
                "CMNT: - Logging Rear Status
                 TYPE: - Display
                 PAGE: - Logging2
                    RearSTATUS=  cmdID= 37000  "
        ::= { iqmux33CmdEntry 37000 }


    iqmux33RollCallMemoriesRollTrackDisableAll OBJECT-TYPE
        SYNTAX            INTEGER { disable(0), enable(1)  }
        MAX-ACCESS        read-write
        STATUS            current
        DESCRIPTION
                "CMNT: - Disable all rolltrack outputs
                 TYPE: - Checkbox
                 PAGE: - RollCall/Memories
                    Disable All  cmdID= 36104  "
        ::= { iqmux33CmdEntry 36104 }


    iqmux33RollCallMemoriesRollTrackIndex OBJECT-TYPE
        SYNTAX            INTEGER
        MAX-ACCESS        read-write
        STATUS            current
        DESCRIPTION
                "CMNT: - Select rolltrack to edit
                 TYPE: - BarGraph
                 PAGE: - RollCall/Memories
                    Index  cmdID= 36100
                    min= 1  max= 32  step= 1  format= %0.0f  div_scale= 1  preset= 1
                    Min = 1  Max = 32  Step = 1  Preset = 1  "
        ::= { iqmux33CmdEntry 36100 }


    iqmux33RollCallMemoriesRollTrackSource OBJECT-TYPE
        SYNTAX            INTEGER {
                            valUnused(-1),
                            valVideoDelay(0),
                            valInputPresent(2),
                            valInput1Present(3),
                            valInput2Present(4),
                            valAnalogPresent(5),
                            valInputLoss(6),
                            valInput1Loss(7),
                            valInput2Loss(8),
                            valAnalogLoss(9),
                            valInput1Select(10),
                            valInput2Select(11),
                            valAnalogSelect(12),
                            valInput108059p(13),
                            valInput108050p(14),
                            valInput108029i(15),
                            valInput108025i(16),
                            valInput72059p(17),
                            valInput72050p(18),
                            valInput52529i(19),
                            valInput62525i(20),
                            valOutputBlackOn(21),
                            valOutputBlackOff(22),
                            valOutputFreeze(23),
                            valOutputUnFreeze(24),
                            valOutputPatternOn(25),
                            valOutputPatternOff(26),
                            valOutputCaptionOn(27),
                            valOutputCaptionOff(28),
                            valReferenceOK(29),
                            valReferenceLoss(30),
                            valAES1PCM(31),
                            valAES1Data(32),
                            valAES1DolbyE(33),
                            valAES1Loss(34),
                            valAES2PCM(35),
                            valAES2Data(36),
                            valAES2DolbyE(37),
                            valAES2Loss(38),
                            valAES3PCM(39),
                            valAES3Data(40),
                            valAES3DolbyE(41),
                            valAES3Loss(42),
                            valAES4PCM(43),
                            valAES4Data(44),
                            valAES4DolbyE(45),
                            valAES4Loss(46),
                            valAES5PCM(47),
                            valAES5Data(48),
                            valAES5DolbyE(49),
                            valAES5Loss(50),
                            valAES6PCM(51),
                            valAES6Data(52),
                            valAES6DolbyE(53),
                            valAES6Loss(54),
                            valAES7PCM(55),
                            valAES7Data(56),
                            valAES7DolbyE(57),
                            valAES7Loss(58),
                            valAES8PCM(59),
                            valAES8Data(60),
                            valAES8DolbyE(61),
                            valAES8Loss(62),
                            valDisemb1PCM(63),
                            valDisemb1Data(64),
                            valDisemb1DolbyE(65),
                            valDisemb1Loss(66),
                            valDisemb2PCM(67),
                            valDisemb2Data(68),
                            valDisemb2DolbyE(69),
                            valDisemb2Loss(70),
                            valDisemb3PCM(71),
                            valDisemb3Data(72),
                            valDisemb3DolbyE(73),
                            valDisemb3Loss(74),
                            valDisemb4PCM(75),
                            valDisemb4Data(76),
                            valDisemb4DolbyE(77),
                            valDisemb4Loss(78),
                            valDisemb5PCM(79),
                            valDisemb5Data(80),
                            valDisemb5DolbyE(81),
                            valDisemb5Loss(82),
                            valDisemb6PCM(83),
                            valDisemb6Data(84),
                            valDisemb6DolbyE(85),
                            valDisemb6Loss(86),
                            valDisemb7PCM(87),
                            valDisemb7Data(88),
                            valDisemb7DolbyE(89),
                            valDisemb7Loss(90),
                            valDisemb8PCM(91),
                            valDisemb8Data(92),
                            valDisemb8DolbyE(93),
                            valDisemb8Loss(94),
                            valDecoderIPDolbyD(95),
                            valDecoderIPDolbyE(96),
                            valDecoderIPPCM(97),
                            valDecoderIPNoErr(98),
                            valDecoderIPError(99),
                            valExtMetaAbsent(100),
                            valExtMetaInvalid(101),
                            valExtMetaNoAC3(102),
                            valExtMetaNoBSI(103),
                            valExtMetaValid(104),
                            valVideoSyncOK(105),
                            valVideoSyncLoss(106),
                            valEncoderActive(107),
                            valEncoderStopped(108),
                            valEncoderPassthru(109)
                            }
        MAX-ACCESS        read-write
        STATUS            current
        DESCRIPTION
                "CMNT: - Source for Rolltrack
                 TYPE: - RadiobuttonList
                 PAGE: - RollCall/Memories
                    Source  cmdID= 36101
                    Unused  value= -1
                    Video Delay  value= 0
                    Input Present  value= 2
                    Input 1 Present  value= 3
                    Input 2 Present  value= 4
                    Analog Present  value= 5
                    Input Loss  value= 6
                    Input 1 Loss  value= 7
                    Input 2 Loss  value= 8
                    Analog Loss  value= 9
                    Input 1 Select  value= 10
                    Input 2 Select  value= 11
                    Analog Select  value= 12
                    Input 1080/59p  value= 13
                    Input 1080/50p  value= 14
                    Input 1080/29i  value= 15
                    Input 1080/25i  value= 16
                    Input 720/59p  value= 17
                    Input 720/50p  value= 18
                    Input 525/29i  value= 19
                    Input 625/25i  value= 20
                    Output Black On  value= 21
                    Output Black Off  value= 22
                    Output Freeze  value= 23
                    Output UnFreeze  value= 24
                    Output Pattern On  value= 25
                    Output Pattern Off  value= 26
                    Output Caption On  value= 27
                    Output Caption Off  value= 28
                    Reference OK  value= 29
                    Reference Loss  value= 30
                    AES 1 PCM  value= 31
                    AES 1 Data  value= 32
                    AES 1 DolbyE  value= 33
                    AES 1 Loss  value= 34
                    AES 2 PCM  value= 35
                    AES 2 Data  value= 36
                    AES 2 DolbyE  value= 37
                    AES 2 Loss  value= 38
                    AES 3 PCM  value= 39
                    AES 3 Data  value= 40
                    AES 3 DolbyE  value= 41
                    AES 3 Loss  value= 42
                    AES 4 PCM  value= 43
                    AES 4 Data  value= 44
                    AES 4 DolbyE  value= 45
                    AES 4 Loss  value= 46
                    AES 5 PCM  value= 47
                    AES 5 Data  value= 48
                    AES 5 DolbyE  value= 49
                    AES 5 Loss  value= 50
                    AES 6 PCM  value= 51
                    AES 6 Data  value= 52
                    AES 6 DolbyE  value= 53
                    AES 6 Loss  value= 54
                    AES 7 PCM  value= 55
                    AES 7 Data  value= 56
                    AES 7 DolbyE  value= 57
                    AES 7 Loss  value= 58
                    AES 8 PCM  value= 59
                    AES 8 Data  value= 60
                    AES 8 DolbyE  value= 61
                    AES 8 Loss  value= 62
                    Disemb 1 PCM  value= 63
                    Disemb 1 Data  value= 64
                    Disemb 1 DolbyE  value= 65
                    Disemb 1 Loss  value= 66
                    Disemb 2 PCM  value= 67
                    Disemb 2 Data  value= 68
                    Disemb 2 DolbyE  value= 69
                    Disemb 2 Loss  value= 70
                    Disemb 3 PCM  value= 71
                    Disemb 3 Data  value= 72
                    Disemb 3 DolbyE  value= 73
                    Disemb 3 Loss  value= 74
                    Disemb 4 PCM  value= 75
                    Disemb 4 Data  value= 76
                    Disemb 4 DolbyE  value= 77
                    Disemb 4 Loss  value= 78
                    Disemb 5 PCM  value= 79
                    Disemb 5 Data  value= 80
                    Disemb 5 DolbyE  value= 81
                    Disemb 5 Loss  value= 82
                    Disemb 6 PCM  value= 83
                    Disemb 6 Data  value= 84
                    Disemb 6 DolbyE  value= 85
                    Disemb 6 Loss  value= 86
                    Disemb 7 PCM  value= 87
                    Disemb 7 Data  value= 88
                    Disemb 7 DolbyE  value= 89
                    Disemb 7 Loss  value= 90
                    Disemb 8 PCM  value= 91
                    Disemb 8 Data  value= 92
                    Disemb 8 DolbyE  value= 93
                    Disemb 8 Loss  value= 94
                    Decoder I/P Dolby D  value= 95
                    Decoder I/P Dolby E  value= 96
                    Decoder I/P PCM  value= 97
                    Decoder I/P No Err  value= 98
                    Decoder I/P Error  value= 99
                    Ext Meta Absent  value= 100
                    Ext Meta Invalid  value= 101
                    Ext Meta No AC3  value= 102
                    Ext Meta No BSI  value= 103
                    Ext Meta Valid  value= 104
                    Video Sync OK  value= 105
                    Video Sync Loss  value= 106
                    Encoder Active  value= 107
                    Encoder Stopped  value= 108
                    Encoder Passthru  value= 109  "
        ::= { iqmux33CmdEntry 36101 }


    iqmux33RollCallMemoriesRollTrackAddress OBJECT-TYPE
        SYNTAX            RollCallString
        MAX-ACCESS        read-write
        STATUS            current
        DESCRIPTION
                "CMNT: - Unit address for Rolltrack message
                 TYPE: - Editstring
                 PAGE: - RollCall/Memories
                    Address  cmdID= 36102
                    preset= 0000:00:00*0"
        ::= { iqmux33CmdEntry 36102 }


    iqmux33RollCallMemoriesRollTrackCommand OBJECT-TYPE
        SYNTAX            RollCallString
        MAX-ACCESS        read-write
        STATUS            current
        DESCRIPTION
                "CMNT: - Command to send for Rolltrack message
                 TYPE: - Editstring
                 PAGE: - RollCall/Memories
                    Command  cmdID= 36103
                    preset= 000:000\0"
        ::= { iqmux33CmdEntry 36103 }


    iqmux33RollCallMemoriesRollTrackStatus OBJECT-TYPE
        SYNTAX            RollCallString
        MAX-ACCESS        read-only
        STATUS            current
        DESCRIPTION
                "CMNT: - Rolltrack status
                 TYPE: - Display
                 PAGE: - RollCall/Memories
                    Status  cmdID= 36105  "
        ::= { iqmux33CmdEntry 36105 }


    iqmux33RollCallMemoriesRollTrackSending OBJECT-TYPE
        SYNTAX            RollCallString
        MAX-ACCESS        read-only
        STATUS            current
        DESCRIPTION
                "CMNT: - Rolltrack sending status: true/false
                 TYPE: - Display
                 PAGE: - RollCall/Memories
                    Sending  cmdID= 36106  "
        ::= { iqmux33CmdEntry 36106 }


    iqmux33RollCallMemoriesHideGpio OBJECT-TYPE
        SYNTAX            INTEGER
        MAX-ACCESS        read-write
        STATUS            current
        DESCRIPTION
                "CMNT: - 
                 TYPE: - Number
                 PAGE: - RollCall/Memories
                    HideGpio  cmdID= 54
                    min= 0  max= 1  step= 1  format= %d  div_scale= 1  preset= 0
                    Min = 0  Max = 0  Step = 0  Preset = 0  "
        ::= { iqmux33CmdEntry 54 }


    iqmux33RollCallMemoriesHideInpAES14 OBJECT-TYPE
        SYNTAX            INTEGER
        MAX-ACCESS        read-write
        STATUS            current
        DESCRIPTION
                "CMNT: - 
                 TYPE: - Number
                 PAGE: - RollCall/Memories
                    HideInpAES1_4  cmdID= 56
                    min= 0  max= 1  step= 1  format= %d  div_scale= 1  preset= 0
                    Min = 0  Max = 0  Step = 0  Preset = 0  "
        ::= { iqmux33CmdEntry 56 }


    iqmux33RollCallMemoriesHideInpAES18 OBJECT-TYPE
        SYNTAX            INTEGER
        MAX-ACCESS        read-write
        STATUS            current
        DESCRIPTION
                "CMNT: - 
                 TYPE: - Number
                 PAGE: - RollCall/Memories
                    HideInpAES1_8  cmdID= 57
                    min= 0  max= 1  step= 1  format= %d  div_scale= 1  preset= 0
                    Min = 0  Max = 0  Step = 0  Preset = 0  "
        ::= { iqmux33CmdEntry 57 }


    iqmux33RollCallMemoriesHideInpLogAES14 OBJECT-TYPE
        SYNTAX            INTEGER
        MAX-ACCESS        read-write
        STATUS            current
        DESCRIPTION
                "CMNT: - 
                 TYPE: - Number
                 PAGE: - RollCall/Memories
                    HideInpLogAES1_4  cmdID= 55
                    min= 0  max= 1  step= 1  format= %d  div_scale= 1  preset= 0
                    Min = 0  Max = 0  Step = 0  Preset = 0  "
        ::= { iqmux33CmdEntry 55 }


    iqmux33RollCallMemoriesHideInpLogAES18 OBJECT-TYPE
        SYNTAX            INTEGER
        MAX-ACCESS        read-write
        STATUS            current
        DESCRIPTION
                "CMNT: - 
                 TYPE: - Number
                 PAGE: - RollCall/Memories
                    HideInpLogAES1_8  cmdID= 61
                    min= 0  max= 1  step= 1  format= %d  div_scale= 1  preset= 0
                    Min = 0  Max = 0  Step = 0  Preset = 0  "
        ::= { iqmux33CmdEntry 61 }


    iqmux33RollCallMemoriesHideOutAES14 OBJECT-TYPE
        SYNTAX            INTEGER
        MAX-ACCESS        read-write
        STATUS            current
        DESCRIPTION
                "CMNT: - 
                 TYPE: - Number
                 PAGE: - RollCall/Memories
                    HideOutAES1_4  cmdID= 58
                    min= 0  max= 1  step= 1  format= %d  div_scale= 1  preset= 0
                    Min = 0  Max = 0  Step = 0  Preset = 0  "
        ::= { iqmux33CmdEntry 58 }


    iqmux33RollCallMemoriesHideOutAES18 OBJECT-TYPE
        SYNTAX            INTEGER
        MAX-ACCESS        read-write
        STATUS            current
        DESCRIPTION
                "CMNT: - 
                 TYPE: - Number
                 PAGE: - RollCall/Memories
                    HideOutAES1_8  cmdID= 59
                    min= 0  max= 1  step= 1  format= %d  div_scale= 1  preset= 0
                    Min = 0  Max = 0  Step = 0  Preset = 0  "
        ::= { iqmux33CmdEntry 59 }


    iqmux33RollCallMemoriesHideOutLogAES14 OBJECT-TYPE
        SYNTAX            INTEGER
        MAX-ACCESS        read-write
        STATUS            current
        DESCRIPTION
                "CMNT: - 
                 TYPE: - Number
                 PAGE: - RollCall/Memories
                    HideOutLogAES1_4  cmdID= 60
                    min= 0  max= 1  step= 1  format= %d  div_scale= 1  preset= 0
                    Min = 0  Max = 0  Step = 0  Preset = 0  "
        ::= { iqmux33CmdEntry 60 }


    iqmux33RollCallMemoriesHideOutLogAES18 OBJECT-TYPE
        SYNTAX            INTEGER
        MAX-ACCESS        read-write
        STATUS            current
        DESCRIPTION
                "CMNT: - 
                 TYPE: - Number
                 PAGE: - RollCall/Memories
                    HideOutLogAES1_8  cmdID= 62
                    min= 0  max= 1  step= 1  format= %d  div_scale= 1  preset= 0
                    Min = 0  Max = 0  Step = 0  Preset = 0  "
        ::= { iqmux33CmdEntry 62 }


    iqmux33GPIOGPI1GPIO1Mode OBJECT-TYPE
        SYNTAX            INTEGER {
                            valUnused(0),
                            valInputGPI1(1),
                            valOutputGPO1(2)
                            }
        MAX-ACCESS        read-write
        STATUS            current
        DESCRIPTION
                "CMNT: - GPIO-1 Input/Output
                 TYPE: - RadiobuttonList
                 PAGE: - GPIO
                    GPI/O 1 Mode  cmdID= 36120
                    Unused  value= 0
                    Input (GPI1)  value= 1
                    Output (GPO1)  value= 2  "
        ::= { iqmux33CmdEntry 36120 }


    iqmux33GPIOGPI1GPI1IPHighSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Input High action
                 TYPE: - RadiobuttonList
                 PAGE: - GPIO
                    GPI 1 I/P High Select  cmdID= 36121
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqmux33CmdEntry 36121 }


    iqmux33GPIOGPI1GPI1IPLowSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Input Low action
                 TYPE: - RadiobuttonList
                 PAGE: - GPIO
                    GPI 1 I/P Low Select  cmdID= 36125
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqmux33CmdEntry 36125 }


    iqmux33GPIOGPI1GPO1OPSelect OBJECT-TYPE
        SYNTAX            INTEGER {
                            valUnused(-1),
                            valInputOK(0),
                            valInput1OK(50),
                            valInput2OK(51),
                            valAnalogInputOK(52),
                            valInput1Selected(53),
                            valInput2Selected(54),
                            valAnalogIPSelected(55),
                            valBlack(56),
                            valFreeze(57),
                            valPattern(58),
                            valNoUserMemSeld(99),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valNoDispMemSeld(60),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Output action
                 TYPE: - RadiobuttonList
                 PAGE: - GPIO
                    GPO 1 O/P Select  cmdID= 36122
                    Unused  value= -1
                    Input OK  value= 0
                    Input 1 OK  value= 50
                    Input 2 OK  value= 51
                    Analog Input OK  value= 52
                    Input 1 Selected  value= 53
                    Input 2 Selected  value= 54
                    Analog I/P Selected  value= 55
                    Black  value= 56
                    Freeze  value= 57
                    Pattern  value= 58
                    No User Mem Sel'd  value= 99
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    No Disp Mem Sel'd  value= 60
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqmux33CmdEntry 36122 }


    iqmux33GPIOGPI1InvertGPIO1 OBJECT-TYPE
        SYNTAX            INTEGER { disable(0), enable(1)  }
        MAX-ACCESS        read-write
        STATUS            current
        DESCRIPTION
                "CMNT: - GPI-1 Port Invert
                 TYPE: - Checkbox
                 PAGE: - GPIO
                    Invert GPIO 1  cmdID= 36123  "
        ::= { iqmux33CmdEntry 36123 }


    iqmux33GPIOGPI1Status OBJECT-TYPE
        SYNTAX            RollCallString
        MAX-ACCESS        read-only
        STATUS            current
        DESCRIPTION
                "CMNT: - GPIO-1 Status
                 TYPE: - Display
                 PAGE: - GPIO
                    Status  cmdID= 36134  "
        ::= { iqmux33CmdEntry 36134 }


    iqmux33GPIOGPI2GPIO2Mode OBJECT-TYPE
        SYNTAX            INTEGER {
                            valUnused(0),
                            valInputGPI2(1),
                            valOutputGPO2(2)
                            }
        MAX-ACCESS        read-write
        STATUS            current
        DESCRIPTION
                "CMNT: - GPIO-2 Input/Output
                 TYPE: - RadiobuttonList
                 PAGE: - GPIO
                    GPI/O 2 Mode  cmdID= 36130
                    Unused  value= 0
                    Input (GPI2)  value= 1
                    Output (GPO2)  value= 2  "
        ::= { iqmux33CmdEntry 36130 }


    iqmux33GPIOGPI2GPI2IPHighSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Input High action
                 TYPE: - RadiobuttonList
                 PAGE: - GPIO
                    GPI 2 I/P High Select  cmdID= 36131
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqmux33CmdEntry 36131 }


    iqmux33GPIOGPI2GPI2IPLowSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Input Low action
                 TYPE: - RadiobuttonList
                 PAGE: - GPIO
                    GPI 2 I/P Low Select  cmdID= 36137
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqmux33CmdEntry 36137 }


    iqmux33GPIOGPI2GPO2OPSelect OBJECT-TYPE
        SYNTAX            INTEGER {
                            valUnused(-1),
                            valInputOK(0),
                            valInput1OK(50),
                            valInput2OK(51),
                            valAnalogInputOK(52),
                            valInput1Selected(53),
                            valInput2Selected(54),
                            valAnalogIPSelected(55),
                            valBlack(56),
                            valFreeze(57),
                            valPattern(58),
                            valNoUserMemSeld(99),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valNoDispMemSeld(60),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Output action
                 TYPE: - RadiobuttonList
                 PAGE: - GPIO
                    GPO 2 O/P Select  cmdID= 36132
                    Unused  value= -1
                    Input OK  value= 0
                    Input 1 OK  value= 50
                    Input 2 OK  value= 51
                    Analog Input OK  value= 52
                    Input 1 Selected  value= 53
                    Input 2 Selected  value= 54
                    Analog I/P Selected  value= 55
                    Black  value= 56
                    Freeze  value= 57
                    Pattern  value= 58
                    No User Mem Sel'd  value= 99
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    No Disp Mem Sel'd  value= 60
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqmux33CmdEntry 36132 }


    iqmux33GPIOGPI2InvertGPIO2 OBJECT-TYPE
        SYNTAX            INTEGER { disable(0), enable(1)  }
        MAX-ACCESS        read-write
        STATUS            current
        DESCRIPTION
                "CMNT: - GPI-2 Port Invert
                 TYPE: - Checkbox
                 PAGE: - GPIO
                    Invert GPIO 2  cmdID= 36133  "
        ::= { iqmux33CmdEntry 36133 }


    iqmux33GPIOGPI2Status OBJECT-TYPE
        SYNTAX            RollCallString
        MAX-ACCESS        read-only
        STATUS            current
        DESCRIPTION
                "CMNT: - GPIO-2 Status
                 TYPE: - Display
                 PAGE: - GPIO
                    Status  cmdID= 36135  "
        ::= { iqmux33CmdEntry 36135 }


    iqmux33SetupDisplay OBJECT-TYPE
        SYNTAX            INTEGER {
                            valVideoStatus(0),
                            valAudioStatus(1),
                            valDolbyStatus(2),
                            valRefStatus(3),
                            valLedStatus(4),
                            valAncStatus(5),
                            valAfdStatus(6)
                            }
        MAX-ACCESS        read-write
        STATUS            current
        DESCRIPTION
                "CMNT: - Select Info display to show
                 TYPE: - RadiobuttonList
                 PAGE: - Setup
                    Display  cmdID= 32773
                    VideoStatus  value= 0
                    AudioStatus  value= 1
                    DolbyStatus  value= 2
                    RefStatus  value= 3
                    LedStatus  value= 4
                    AncStatus  value= 5
                    AfdStatus  value= 6  "
        ::= { iqmux33CmdEntry 32773 }


    iqmux33SetupProduct OBJECT-TYPE
        SYNTAX            RollCallString
        MAX-ACCESS        read-only
        STATUS            current
        DESCRIPTION
                "CMNT: - 
                 TYPE: - Display
                 PAGE: - Setup
                    Product  cmdID= 32771  "
        ::= { iqmux33CmdEntry 32771 }


    iqmux33SetupRelease OBJECT-TYPE
        SYNTAX            RollCallString
        MAX-ACCESS        read-only
        STATUS            current
        DESCRIPTION
                "CMNT: - Unit version number
                 TYPE: - Display
                 PAGE: - Setup
                    Release  cmdID= 2  "
        ::= { iqmux33CmdEntry 2 }


    iqmux33SetupBuild OBJECT-TYPE
        SYNTAX            RollCallString
        MAX-ACCESS        read-only
        STATUS            current
        DESCRIPTION
                "CMNT: - Unit build number
                 TYPE: - Display
                 PAGE: - Setup
                    Build  cmdID= 5  "
        ::= { iqmux33CmdEntry 5 }


    iqmux33SetupKOS OBJECT-TYPE
        SYNTAX            RollCallString
        MAX-ACCESS        read-only
        STATUS            current
        DESCRIPTION
                "CMNT: - 
                 TYPE: - Display
                 PAGE: - Setup
                    KOS  cmdID= 32772  "
        ::= { iqmux33CmdEntry 32772 }


    iqmux33SetupSerialNo OBJECT-TYPE
        SYNTAX            RollCallString
        MAX-ACCESS        read-only
        STATUS            current
        DESCRIPTION
                "CMNT: - Unit serial number
                 TYPE: - Display
                 PAGE: - Setup
                    Serial No.  cmdID= 1  "
        ::= { iqmux33CmdEntry 1 }


    iqmux33SetupFactoryDefault OBJECT-TYPE
        SYNTAX            INTEGER { noAction(0),valFactoryDefault(1) }
        MAX-ACCESS        read-write
        STATUS            current
        DESCRIPTION
                "CMNT: - Recall factory defaults
                 TYPE: - Button
                 PAGE: - Setup
                    Factory Default  cmdID= 37002
                    value= 1  "
        ::= { iqmux33CmdEntry 37002 }


    iqmux33SetupRestart OBJECT-TYPE
        SYNTAX            INTEGER { noAction(0),valRestart(1) }
        MAX-ACCESS        read-write
        STATUS            current
        DESCRIPTION
                "CMNT: - Restart unit
                 TYPE: - Button
                 PAGE: - Setup
                    Restart  cmdID= 4
                    value= 1  "
        ::= { iqmux33CmdEntry 4 }


    iqmux33SetupDefaultSettings OBJECT-TYPE
        SYNTAX            INTEGER { noAction(0),valDefaultSettings(1) }
        MAX-ACCESS        read-write
        STATUS            current
        DESCRIPTION
                "CMNT: - Recall factory defaults-KeepMemories
                 TYPE: - Button
                 PAGE: - Setup
                    Default Settings  cmdID= 37001
                    value= 1  "
        ::= { iqmux33CmdEntry 37001 }


    iqmux33SetupSerialNumber OBJECT-TYPE
        SYNTAX            RollCallString
        MAX-ACCESS        read-write
        STATUS            current
        DESCRIPTION
                "CMNT: - Edit serial number (On Factory Test Only)
                 TYPE: - Editstring
                 PAGE: - Setup
                    Serial Number  cmdID= 32774
                    preset= unknown"
        ::= { iqmux33CmdEntry 32774 }


    iqmux33SetupBoardID OBJECT-TYPE
        SYNTAX            INTEGER {
                            valIQUPC00(539),
                            valIQUPC01(540),
                            valIQDNC00(541),
                            valIQDNC01(549),
                            valIQDCC00(542),
                            valIQUDC10(543),
                            valIQUDC11(544),
                            valIQUCC00(548),
                            valIQUAV10(545),
                            valIQMUX33(546),
                            valIQDMX33(547),
                            valIQSYN33(551)
                            }
        MAX-ACCESS        read-write
        STATUS            current
        DESCRIPTION
                "CMNT: - Edit product type (On Factory Test Only)
                 TYPE: - RadiobuttonList
                 PAGE: - Setup
                    BoardID  cmdID= 32776
                    IQUPC00  value= 539
                    IQUPC01  value= 540
                    IQDNC00  value= 541
                    IQDNC01  value= 549
                    IQDCC00  value= 542
                    IQUDC10  value= 543
                    IQUDC11  value= 544
                    IQUCC00  value= 548
                    IQUAV10  value= 545
                    IQMUX33  value= 546
                    IQDMX33  value= 547
                    IQSYN33  value= 551  "
        ::= { iqmux33CmdEntry 32776 }


    iqmux33SetupSaveID OBJECT-TYPE
        SYNTAX            INTEGER { noAction(0),valSaveID(1) }
        MAX-ACCESS        read-write
        STATUS            current
        DESCRIPTION
                "CMNT: - Save serial number/board type (On Factory Test Only)
                 TYPE: - Button
                 PAGE: - Setup
                    Save ID  cmdID= 32775
                    value= 1  "
        ::= { iqmux33CmdEntry 32775 }


    iqmux33SetupFpgaBoardType OBJECT-TYPE
        SYNTAX            RollCallString
        MAX-ACCESS        read-only
        STATUS            current
        DESCRIPTION
                "CMNT: - FPGA board type
                 TYPE: - Display
                 PAGE: - Setup
                    Board Type  cmdID= 33152  "
        ::= { iqmux33CmdEntry 33152 }


    iqmux33SetupFpgaSerialNo OBJECT-TYPE
        SYNTAX            RollCallString
        MAX-ACCESS        read-only
        STATUS            current
        DESCRIPTION
                "CMNT: - FPGA serial number
                 TYPE: - Display
                 PAGE: - Setup
                    Fpga SerialNo  cmdID= 33156  "
        ::= { iqmux33CmdEntry 33156 }


    iqmux33SetupFpgaSoftVer OBJECT-TYPE
        SYNTAX            RollCallString
        MAX-ACCESS        read-only
        STATUS            current
        DESCRIPTION
                "CMNT: - FPGA version number
                 TYPE: - Display
                 PAGE: - Setup
                    Soft Ver  cmdID= 33150  "
        ::= { iqmux33CmdEntry 33150 }


    iqmux33SetupFpgaVer OBJECT-TYPE
        SYNTAX            RollCallString
        MAX-ACCESS        read-only
        STATUS            current
        DESCRIPTION
                "CMNT: - FPGA firmware version number
                 TYPE: - Display
                 PAGE: - Setup
                    Fpga Ver  cmdID= 33157  "
        ::= { iqmux33CmdEntry 33157 }


    iqmux33SetupFpgaTIVer OBJECT-TYPE
        SYNTAX            RollCallString
        MAX-ACCESS        read-only
        STATUS            current
        DESCRIPTION
                "CMNT: - FPGA TI version number
                 TYPE: - Display
                 PAGE: - Setup
                    TI Ver  cmdID= 33160  "
        ::= { iqmux33CmdEntry 33160 }


    iqmux33SetupFpgaDolbyModId OBJECT-TYPE
        SYNTAX            RollCallString
        MAX-ACCESS        read-only
        STATUS            current
        DESCRIPTION
                "CMNT: - FPGA Dolby Module Type
                 TYPE: - Display
                 PAGE: - Setup
                    Dolby Mod Id  cmdID= 33162  "
        ::= { iqmux33CmdEntry 33162 }


    iqmux33SetupFpgaProtVer OBJECT-TYPE
        SYNTAX            RollCallString
        MAX-ACCESS        read-only
        STATUS            current
        DESCRIPTION
                "CMNT: - FPGA protocol version
                 TYPE: - Display
                 PAGE: - Setup
                    Prot Ver  cmdID= 33151  "
        ::= { iqmux33CmdEntry 33151 }


    iqmux33SetupFpgaProgCRC OBJECT-TYPE
        SYNTAX            RollCallString
        MAX-ACCESS        read-only
        STATUS            current
        DESCRIPTION
                "CMNT: - FPGA code CRC
                 TYPE: - Display
                 PAGE: - Setup
                    Prog CRC  cmdID= 33155  "
        ::= { iqmux33CmdEntry 33155 }


    iqmux33SetupFpgaUptime OBJECT-TYPE
        SYNTAX            RollCallString
        MAX-ACCESS        read-only
        STATUS            current
        DESCRIPTION
                "CMNT: - FPGA Uptime
                 TYPE: - Display
                 PAGE: - Setup
                    Uptime  cmdID= 33163  "
        ::= { iqmux33CmdEntry 33163 }


    iqmux33SetupFpgaENGVXPVer OBJECT-TYPE
        SYNTAX            RollCallString
        MAX-ACCESS        read-only
        STATUS            current
        DESCRIPTION
                "CMNT: - FPGA VXP version number
                 TYPE: - Display
                 PAGE: - Setup
                    VXP Ver  cmdID= 33158  "
        ::= { iqmux33CmdEntry 33158 }


    iqmux33SetupFpgaENGSharcVer OBJECT-TYPE
        SYNTAX            RollCallString
        MAX-ACCESS        read-only
        STATUS            current
        DESCRIPTION
                "CMNT: - FPGA Sharc version number
                 TYPE: - Display
                 PAGE: - Setup
                    Sharc Ver  cmdID= 33159  "
        ::= { iqmux33CmdEntry 33159 }


    iqmux33SetupFpgaENGAlteraVer OBJECT-TYPE
        SYNTAX            RollCallString
        MAX-ACCESS        read-only
        STATUS            current
        DESCRIPTION
                "CMNT: - FPGA Altera version number
                 TYPE: - Display
                 PAGE: - Setup
                    Altera Ver  cmdID= 33161  "
        ::= { iqmux33CmdEntry 33161 }


    iqmux33SetupFpgaENGVCCint OBJECT-TYPE
        SYNTAX            RollCallString
        MAX-ACCESS        read-only
        STATUS            current
        DESCRIPTION
                "CMNT: - FPGA Internal Voltage
                 TYPE: - Display
                 PAGE: - Setup
                    VCCint  cmdID= 33164  "
        ::= { iqmux33CmdEntry 33164 }


    iqmux33SetupFpgaENGVCCaux OBJECT-TYPE
        SYNTAX            RollCallString
        MAX-ACCESS        read-only
        STATUS            current
        DESCRIPTION
                "CMNT: - FPGA Aux Voltage
                 TYPE: - Display
                 PAGE: - Setup
                    VCCaux  cmdID= 33165  "
        ::= { iqmux33CmdEntry 33165 }


    iqmux33SetupOptionsOption1 OBJECT-TYPE
        SYNTAX            RollCallString
        MAX-ACCESS        read-only
        STATUS            current
        DESCRIPTION
                "CMNT: - Upmix option
                 TYPE: - Display
                 PAGE: - Setup
                    Option1  cmdID= 33166  "
        ::= { iqmux33CmdEntry 33166 }


    iqmux33SetupOptionsOption2 OBJECT-TYPE
        SYNTAX            RollCallString
        MAX-ACCESS        read-only
        STATUS            current
        DESCRIPTION
                "CMNT: - Dolby Decode option
                 TYPE: - Display
                 PAGE: - Setup
                    Option2  cmdID= 33167  "
        ::= { iqmux33CmdEntry 33167 }


    iqmux33SetupOptionsOption3 OBJECT-TYPE
        SYNTAX            RollCallString
        MAX-ACCESS        read-only
        STATUS            current
        DESCRIPTION
                "CMNT: - Dolby Encode D option
                 TYPE: - Display
                 PAGE: - Setup
                    Option3  cmdID= 33168  "
        ::= { iqmux33CmdEntry 33168 }


    iqmux33SetupOptionsOption4 OBJECT-TYPE
        SYNTAX            RollCallString
        MAX-ACCESS        read-only
        STATUS            current
        DESCRIPTION
                "CMNT: - Dolby Encode E option
                 TYPE: - Display
                 PAGE: - Setup
                    Option4  cmdID= 33169  "
        ::= { iqmux33CmdEntry 33169 }


    iqmux33SetupOptionsOption5 OBJECT-TYPE
        SYNTAX            RollCallString
        MAX-ACCESS        read-only
        STATUS            current
        DESCRIPTION
                "CMNT: - Color corrector option
                 TYPE: - Display
                 PAGE: - Setup
                    Option5  cmdID= 33170  "
        ::= { iqmux33CmdEntry 33170 }


    iqmux33SetupOptionsOption6 OBJECT-TYPE
        SYNTAX            RollCallString
        MAX-ACCESS        read-only
        STATUS            current
        DESCRIPTION
                "CMNT: - Loudness 5.1 option
                 TYPE: - Display
                 PAGE: - Setup
                    Option6  cmdID= 33171  "
        ::= { iqmux33CmdEntry 33171 }


    iqmux33SetupOptionsOption7 OBJECT-TYPE
        SYNTAX            RollCallString
        MAX-ACCESS        read-only
        STATUS            current
        DESCRIPTION
                "CMNT: - Loudness 1x2.0 option
                 TYPE: - Display
                 PAGE: - Setup
                    Option7  cmdID= 33172  "
        ::= { iqmux33CmdEntry 33172 }


    iqmux33SetupOptionsOption8 OBJECT-TYPE
        SYNTAX            RollCallString
        MAX-ACCESS        read-only
        STATUS            current
        DESCRIPTION
                "CMNT: - Loudness 2x2.0 option
                 TYPE: - Display
                 PAGE: - Setup
                    Option8  cmdID= 33173  "
        ::= { iqmux33CmdEntry 33173 }


    iqmux33SetupOptionsOption9 OBJECT-TYPE
        SYNTAX            RollCallString
        MAX-ACCESS        read-only
        STATUS            current
        DESCRIPTION
                "CMNT: - 24 HOUR options
                 TYPE: - Display
                 PAGE: - Setup
                    Option9  cmdID= 33174  "
        ::= { iqmux33CmdEntry 33174 }


    iqmux33SetupOptionsMask OBJECT-TYPE
        SYNTAX            INTEGER
        MAX-ACCESS        read-write
        STATUS            current
        DESCRIPTION
                "CMNT: - Bit mask of current licence options
                 TYPE: - Number
                 PAGE: - Setup
                    OptionsMask  cmdID= 36147
                    min= 0  max= 65535  step= 1  format= %d  div_scale= 1  preset= 0
                    Min = 0  Max = 0  Step = 0  Preset = 0  "
        ::= { iqmux33CmdEntry 36147 }


    iqmux33SetupDemoNonDemoRestart OBJECT-TYPE
        SYNTAX            INTEGER { noAction(0),valNonDemoRestart(1) }
        MAX-ACCESS        read-write
        STATUS            current
        DESCRIPTION
                "CMNT: - hard restart, removes demo options
                 TYPE: - Button
                 PAGE: - Setup
                    NonDemoRestart  cmdID= 43092
                    value= 1  "
        ::= { iqmux33CmdEntry 43092 }


    iqmux33SetupDemoPeriod OBJECT-TYPE
        SYNTAX            INTEGER
        MAX-ACCESS        read-write
        STATUS            current
        DESCRIPTION
                "CMNT: - Factory configured total demo period,
                 TYPE: - Number
                 PAGE: - Setup
                    DemoPeriod  cmdID= 65
                    min= 0  max= 720  step= 1  format= %0.0f Hours  div_scale= 1  preset= 0
                    Min = 0 Hours  Max = 720 Hours  Step = 1 Hours  Preset = 0 Hours  "
        ::= { iqmux33CmdEntry 65 }


    iqmux33SetupDemoRestartMode OBJECT-TYPE
        SYNTAX            INTEGER { disable(0), enable(1)  }
        MAX-ACCESS        read-write
        STATUS            current
        DESCRIPTION
                "CMNT: - Restart mode demo/non-demo
                 TYPE: - Checkbox
                 PAGE: - Setup
                    RestartMode  cmdID= 43093  "
        ::= { iqmux33CmdEntry 43093 }


    iqmux33SetupDemoRemainingDemo OBJECT-TYPE
        SYNTAX            INTEGER
        MAX-ACCESS        read-write
        STATUS            current
        DESCRIPTION
                "CMNT: - demo remaining period,
                 TYPE: - Number
                 PAGE: - Setup
                    RemainingDemo  cmdID= 43091
                    min= 0  max= 50000  step= 1  format= %d  div_scale= 1  preset= 0
                    Min = 0  Max = 0  Step = 0  Preset = 0  "
        ::= { iqmux33CmdEntry 43091 }


    iqmux33SetupDemoRemaining24h OBJECT-TYPE
        SYNTAX            INTEGER
        MAX-ACCESS        read-write
        STATUS            current
        DESCRIPTION
                "CMNT: - demo remaining period before next restart
                 TYPE: - Number
                 PAGE: - Setup
                    Remaining24h  cmdID= 43094
                    min= 0  max= 1440  step= 1  format= %d  div_scale= 1  preset= 0
                    Min = 0  Max = 0  Step = 0  Preset = 0  "
        ::= { iqmux33CmdEntry 43094 }


    iqmux33SetupDemoStatus OBJECT-TYPE
        SYNTAX            INTEGER
        MAX-ACCESS        read-write
        STATUS            current
        DESCRIPTION
                "CMNT: - Factory configured total demo period Status
                 TYPE: - Number
                 PAGE: - Setup
                    DemoStatus  cmdID= 43101
                    min= 0  max= 1  step= 1  format= %0.0f  div_scale= 1  preset= 0
                    Min = 0  Max = 1  Step = 1  Preset = 0  "
        ::= { iqmux33CmdEntry 43101 }


    iqmux33SetupRestartHard OBJECT-TYPE
        SYNTAX            INTEGER { noAction(0),valRestartHard(1) }
        MAX-ACCESS        read-write
        STATUS            current
        DESCRIPTION
                "CMNT: - Restart unit
                 TYPE: - Button
                 PAGE: - Setup
                    Restart Hard  cmdID= 36138
                    value= 1  "
        ::= { iqmux33CmdEntry 36138 }


    iqmux33SetupInput1Name OBJECT-TYPE
        SYNTAX            RollCallString
        MAX-ACCESS        read-write
        STATUS            current
        DESCRIPTION
                "CMNT: - 
                 TYPE: - Editstring
                 PAGE: - Setup
                    Input 1 Name  cmdID= 9000
                    preset= INPUT 1 SERIAL IN"
        ::= { iqmux33CmdEntry 9000 }


    iqmux33SetupInput2Name OBJECT-TYPE
        SYNTAX            RollCallString
        MAX-ACCESS        read-write
        STATUS            current
        DESCRIPTION
                "CMNT: - 
                 TYPE: - Editstring
                 PAGE: - Setup
                    Input 2 Name  cmdID= 9001
                    preset= INPUT 2 SERIAL IN"
        ::= { iqmux33CmdEntry 9001 }


    iqmux33SetupInput3Name OBJECT-TYPE
        SYNTAX            RollCallString
        MAX-ACCESS        read-write
        STATUS            current
        DESCRIPTION
                "CMNT: - 
                 TYPE: - Editstring
                 PAGE: - Setup
                    Input 3 Name  cmdID= 9002
                    preset= INPUT 3 ANALOG IN"
        ::= { iqmux33CmdEntry 9002 }


    iqmux33SetupCalibrationVideoOut8 OBJECT-TYPE
        SYNTAX            INTEGER
        MAX-ACCESS        read-write
        STATUS            current
        DESCRIPTION
                "CMNT: - Analog cal video out 8
                 TYPE: - Number
                 PAGE: - Setup
                    VideoOut8  cmdID= 43097
                    min= -128  max= 127  step= 1  format= %0.0f  div_scale= 1  preset= 0
                    Min = -128  Max = 127  Step = 1  Preset = 0  "
        ::= { iqmux33CmdEntry 43097 }


    iqmux33SetupCalibrationVideoOut10 OBJECT-TYPE
        SYNTAX            INTEGER
        MAX-ACCESS        read-write
        STATUS            current
        DESCRIPTION
                "CMNT: - Analog cal video out 10
                 TYPE: - Number
                 PAGE: - Setup
                    VideoOut10  cmdID= 43099
                    min= -128  max= 127  step= 1  format= %0.0f  div_scale= 1  preset= 0
                    Min = -128  Max = 127  Step = 1  Preset = 0  "
        ::= { iqmux33CmdEntry 43099 }


    iqmux33SetupCalibrationVideoOut11 OBJECT-TYPE
        SYNTAX            INTEGER
        MAX-ACCESS        read-write
        STATUS            current
        DESCRIPTION
                "CMNT: - Analog cal video out 11
                 TYPE: - Number
                 PAGE: - Setup
                    VideoOut11  cmdID= 43100
                    min= -128  max= 127  step= 1  format= %0.0f  div_scale= 1  preset= 0
                    Min = -128  Max = 127  Step = 1  Preset = 0  "
        ::= { iqmux33CmdEntry 43100 }


    iqmux33SetupCalibrationAudio0 OBJECT-TYPE
        SYNTAX            INTEGER
        MAX-ACCESS        read-write
        STATUS            current
        DESCRIPTION
                "CMNT: - Analog cal audio 0
                 TYPE: - Number
                 PAGE: - Setup
                    Audio0  cmdID= 43080
                    min= -128  max= 127  step= 1  format= %0.2f  div_scale= 100  preset= 0
                    Min = -1.28  Max = 1.27  Step = 0.01  Preset = 0.00  "
        ::= { iqmux33CmdEntry 43080 }


    iqmux33SetupCalibrationAudio1 OBJECT-TYPE
        SYNTAX            INTEGER
        MAX-ACCESS        read-write
        STATUS            current
        DESCRIPTION
                "CMNT: - Analog cal audio 1
                 TYPE: - Number
                 PAGE: - Setup
                    Audio1  cmdID= 43081
                    min= -128  max= 127  step= 1  format= %0.2f  div_scale= 100  preset= 0
                    Min = -1.28  Max = 1.27  Step = 0.01  Preset = 0.00  "
        ::= { iqmux33CmdEntry 43081 }


    iqmux33SetupCalibrationAudio2 OBJECT-TYPE
        SYNTAX            INTEGER
        MAX-ACCESS        read-write
        STATUS            current
        DESCRIPTION
                "CMNT: - Analog cal audio 2
                 TYPE: - Number
                 PAGE: - Setup
                    Audio2  cmdID= 43082
                    min= -128  max= 127  step= 1  format= %0.2f  div_scale= 100  preset= 0
                    Min = -1.28  Max = 1.27  Step = 0.01  Preset = 0.00  "
        ::= { iqmux33CmdEntry 43082 }


    iqmux33SetupCalibrationAudio3 OBJECT-TYPE
        SYNTAX            INTEGER
        MAX-ACCESS        read-write
        STATUS            current
        DESCRIPTION
                "CMNT: - Analog cal audio 3
                 TYPE: - Number
                 PAGE: - Setup
                    Audio3  cmdID= 43083
                    min= -128  max= 127  step= 1  format= %0.2f  div_scale= 100  preset= 0
                    Min = -1.28  Max = 1.27  Step = 0.01  Preset = 0.00  "
        ::= { iqmux33CmdEntry 43083 }


    iqmux33SetupCalibrationCalibrateTake OBJECT-TYPE
        SYNTAX            INTEGER { noAction(0),valCalibrateTake(1) }
        MAX-ACCESS        read-write
        STATUS            current
        DESCRIPTION
                "CMNT: - Analog take
                 TYPE: - Button
                 PAGE: - Setup
                    CalibrateTake  cmdID= 43088
                    value= 1  "
        ::= { iqmux33CmdEntry 43088 }


    iqmux33SetupCalibrationCalibratePreset OBJECT-TYPE
        SYNTAX            INTEGER { noAction(0),valCalibratePreset(1) }
        MAX-ACCESS        read-write
        STATUS            current
        DESCRIPTION
                "CMNT: - Analog preset
                 TYPE: - Button
                 PAGE: - Setup
                    CalibratePreset  cmdID= 43089
                    value= 1  "
        ::= { iqmux33CmdEntry 43089 }


    iqmux33SetupCalibrationCalibrateDefault OBJECT-TYPE
        SYNTAX            INTEGER { noAction(0),valCalibrateDefault(1) }
        MAX-ACCESS        read-write
        STATUS            current
        DESCRIPTION
                "CMNT: - Analog SET defaults
                 TYPE: - Button
                 PAGE: - Setup
                    CalibrateDefault  cmdID= 43102
                    value= 1  "
        ::= { iqmux33CmdEntry 43102 }


    iqmux33SetupCalibrationCalibrateFactory OBJECT-TYPE
        SYNTAX            INTEGER { noAction(0),valCalibrateFactory(1) }
        MAX-ACCESS        read-write
        STATUS            current
        DESCRIPTION
                "CMNT: - Analog SET FACTORY
                 TYPE: - Button
                 PAGE: - Setup
                    CalibrateFactory  cmdID= 43103
                    value= 1  "
        ::= { iqmux33CmdEntry 43103 }


    iqmux33SetupCalibrationCalUnlock OBJECT-TYPE
        SYNTAX            RollCallString
        MAX-ACCESS        read-write
        STATUS            current
        DESCRIPTION
                "CMNT: - Analog SET Unlock
                 TYPE: - Editstring
                 PAGE: - Setup
                    CalUnlock  cmdID= 43104
                    preset= UnlockString"
        ::= { iqmux33CmdEntry 43104 }


    iqmux33LKFS1SourceLSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43200
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqmux33CmdEntry 43200 }


    iqmux33LKFS1SourceRSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43201
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqmux33CmdEntry 43201 }


    iqmux33LKFS1SourceLSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43202
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqmux33CmdEntry 43202 }


    iqmux33LKFS1SourceRSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43203
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqmux33CmdEntry 43203 }


    iqmux33LKFS1SourceCSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43204
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqmux33CmdEntry 43204 }


    iqmux33LKFS1ResetSession OBJECT-TYPE
        SYNTAX            INTEGER { noAction(0),valResetSession(1) }
        MAX-ACCESS        read-write
        STATUS            current
        DESCRIPTION
                "CMNT: - lkfs Process 1 sess reset
                 TYPE: - Button
                 PAGE: - LKFS1
                    ResetSession  cmdID= 43211
                    value= 1  "
        ::= { iqmux33CmdEntry 43211 }


    iqmux33LKFS1SessLevel OBJECT-TYPE
        SYNTAX            RollCallString
        MAX-ACCESS        read-only
        STATUS            current
        DESCRIPTION
                "CMNT: - lkfs Process 1 Sess LEVEL
                 TYPE: - Display
                 PAGE: - LKFS1
                    SessLevel  cmdID= 43217  "
        ::= { iqmux33CmdEntry 43217 }


    iqmux33LKFS1SessTime OBJECT-TYPE
        SYNTAX            RollCallString
        MAX-ACCESS        read-only
        STATUS            current
        DESCRIPTION
                "CMNT: - lkfs Process 1 Session Period
                 TYPE: - Display
                 PAGE: - LKFS1
                    SessTime  cmdID= 43225  "
        ::= { iqmux33CmdEntry 43225 }


    iqmux33LKFS1currrate OBJECT-TYPE
        SYNTAX            INTEGER
        MAX-ACCESS        read-write
        STATUS            current
        DESCRIPTION
                "CMNT: - lkfs Process 1 update rate
                 TYPE: - Number
                 PAGE: - LKFS1
                    curr rate  cmdID= 43213
                    min= 1  max= 63  step= 1  format= %0.0f  div_scale= 1  preset= 2
                    Min = 1  Max = 63  Step = 1  Preset = 2  "
        ::= { iqmux33CmdEntry 43213 }


    iqmux33LKFS1CurrLevelTime OBJECT-TYPE
        SYNTAX            RollCallString
        MAX-ACCESS        read-only
        STATUS            current
        DESCRIPTION
                "CMNT: - lkfs Process 1 LEVEL Update Timeout
                 TYPE: - Display
                 PAGE: - LKFS1
                    CurrLevelTime  cmdID= 43221  "
        ::= { iqmux33CmdEntry 43221 }


    iqmux33LKFS1CurrLevel OBJECT-TYPE
        SYNTAX            RollCallString
        MAX-ACCESS        read-only
        STATUS            current
        DESCRIPTION
                "CMNT: - lkfs Process 1 CUR LEVEL
                 TYPE: - Display
                 PAGE: - LKFS1
                    CurrLevel  cmdID= 43215  "
        ::= { iqmux33CmdEntry 43215 }


    iqmux33LKFS1CurrLevel2 OBJECT-TYPE
        SYNTAX            RollCallString
        MAX-ACCESS        read-only
        STATUS            current
        DESCRIPTION
                "CMNT: - lkfs Process 1 CUR LEVEL
                 TYPE: - Display
                 PAGE: - LKFS1
                    CurrLevel2  cmdID= 43226  "
        ::= { iqmux33CmdEntry 43226 }


    iqmux33LKFS1RollMapUpd OBJECT-TYPE
        SYNTAX            RollCallString
        MAX-ACCESS        read-only
        STATUS            current
        DESCRIPTION
                "CMNT: - Audio Loudness updates to rollmap
                 TYPE: - Display
                 PAGE: - LKFS1
                    RollMapUpd  cmdID= 38277  "
        ::= { iqmux33CmdEntry 38277 }


    iqmux33LKFS1UpdateRate OBJECT-TYPE
        SYNTAX            INTEGER {
                            valOn(1),
                            valOff(0)
                            }
        MAX-ACCESS        read-write
        STATUS            current
        DESCRIPTION
                "CMNT: - lkfs Process 1 LEVEL Update
                 TYPE: - RadiobuttonList
                 PAGE: - LKFS1
                    Update Rate  cmdID= 43219
                    On  value= 1
                    Off  value= 0  "
        ::= { iqmux33CmdEntry 43219 }


    iqmux33LKFS2SourceLSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43206
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqmux33CmdEntry 43206 }


    iqmux33LKFS2SourceRSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43207
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqmux33CmdEntry 43207 }


    iqmux33LKFS2SourceLSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43208
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqmux33CmdEntry 43208 }


    iqmux33LKFS2SourceRSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43209
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqmux33CmdEntry 43209 }


    iqmux33LKFS2SourceCSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43210
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqmux33CmdEntry 43210 }


    iqmux33LKFS2SessLevel OBJECT-TYPE
        SYNTAX            RollCallString
        MAX-ACCESS        read-only
        STATUS            current
        DESCRIPTION
                "CMNT: - lkfs Process 2 Sess LEVEL
                 TYPE: - Display
                 PAGE: - LKFS2
                    SessLevel  cmdID= 43218  "
        ::= { iqmux33CmdEntry 43218 }


    iqmux33LKFS2CurrLevel OBJECT-TYPE
        SYNTAX            RollCallString
        MAX-ACCESS        read-only
        STATUS            current
        DESCRIPTION
                "CMNT: - lkfs Process 2 CUR LEVEL
                 TYPE: - Display
                 PAGE: - LKFS2
                    CurrLevel  cmdID= 43216  "
        ::= { iqmux33CmdEntry 43216 }


    iqmux33LKFS2CurrLevel2 OBJECT-TYPE
        SYNTAX            RollCallString
        MAX-ACCESS        read-only
        STATUS            current
        DESCRIPTION
                "CMNT: - lkfs Process 2 CUR LEVEL
                 TYPE: - Display
                 PAGE: - LKFS2
                    CurrLevel2  cmdID= 43227  "
        ::= { iqmux33CmdEntry 43227 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: S40512345
-- Comments		: Serial number of unit
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 100:10:35:00
-- Comments		: Uptime in days/hours/mins
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
--
-- Value(s)		: 103
-- Comments		: ID of rear interface
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: V115 Release
-- Comments		: Operating system version
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
--
-- Value(s)		: 7
-- Comments		: First Slot position of rear
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
--
-- Value(s)		: 2
--				: 3
-- Comments		: Number of slots rear uses
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
--
-- Value(s)		: OK
--				: WARN:Type Mismatch
-- Comments		: Status of rear
--
---------------------------------------------------------------------------------------------------
-- Header		: TEMP_1_NAME
--
-- MIB ref		: swCardEventLogSlotXX       .11.84.69.77.80.95.49.95.78.65.77.69
-- absolute OID	: 1.3.6.1.4.1.7995.2.6.1.1.XX.11.84.69.77.80.95.49.95.78.65.77.69
--
-- Value(s)		: Temperature FPGA
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 0004304563
-- Comments		: Software Build Number
--
---------------------------------------------------------------------------------------------------
-- Header		: INPUT_1_NAME
--
-- MIB ref		: swCardEventLogSlotXX       .12.73.78.80.85.84.95.49.95.78.65.77.69
-- absolute OID	: 1.3.6.1.4.1.7995.2.6.1.1.XX.12.73.78.80.85.84.95.49.95.78.65.77.69
--
-- Value(s)		: INPUT 1 SERIAL IN
-- Comments		:
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD/SD/3G SDI
--				: HD/SD SDI
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: TEMP_1_STATE
--
-- MIB ref		: swCardEventLogSlotXX       .12.84.69.77.80.95.49.95.83.84.65.84.69
-- absolute OID	: 1.3.6.1.4.1.7995.2.6.1.1.XX.12.84.69.77.80.95.49.95.83.84.65.84.69
--
-- Value(s)		: OK
--				: Unknown
--				: WARN_High
--				: FAIL:Fan
-- Comments		:
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
--
-- Value(s)		: SER IN 1
-- Comments		: Text on Rear
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: OK
--				: WARN:Mismatch
--				: FAIL:Lost
-- Comments		:
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
--
-- Value(s)		: HD/SD SDI
--				: HD/SD/3G SDI
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
--
-- Value(s)		: OK
--				: WARN:Black
--				: WARN:Freeze
--				: WARN:Pattern
--				: WARN:Input
--				: WARN:Reclocked
--				: WARN:Disabled
-- Comments		:
--
---------------------------------------------------------------------------------------------------
-- Header		: GENLOCK_1_STATE
--
-- MIB ref		: swCardEventLogSlotXX       .15.71.69.78.76.79.67.75.95.49.95.83.84.65.84.69
-- absolute OID	: 1.3.6.1.4.1.7995.2.6.1.1.XX.15.71.69.78.76.79.67.75.95.49.95.83.84.65.84.69
--
-- Value(s)		: WARN:Freerun
--				: OK:Reference
--				: OK:Input
-- Comments		: Internal genlock state
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: 520505115
-- Comments		: Fpga version number
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: RGMPP1C
-- Comments		:
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
--
-- Value(s)		: OK
--				: WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: LOST
--				: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
--
-- Value(s)		: FAIL:Bad File
--				: WARN:NONE
--				: FAIL:No File
--				: SDHD
--				: SDHD:3G
-- Comments		:
--
---------------------------------------------------------------------------------------------------
-- Header		: OUTPUT_1_CAPTION
--
-- MIB ref		: swCardEventLogSlotXX       .16.79.85.84.80.85.84.95.49.95.67.65.80.84.73.79.78
-- absolute OID	: 1.3.6.1.4.1.7995.2.6.1.1.XX.16.79.85.84.80.85.84.95.49.95.67.65.80.84.73.79.78
--
-- Value(s)		: OK:Off
--				: WARN:On[CaptionText]
-- Comments		:
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
--
-- Value(s)		: OK:Tri-Level
--				: OK:Bi-Level
--				: WARN:Unknown
-- Comments		:
--
---------------------------------------------------------------------------------------------------
-- Header		: AES_INPUT_1_STATE
--
-- MIB ref		: swCardEventLogSlotXX       .17.65.69.83.95.73.78.80.85.84.95.49.95.83.84.65.84.69
-- absolute OID	: 1.3.6.1.4.1.7995.2.6.1.1.XX.17.65.69.83.95.73.78.80.85.84.95.49.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_2_STATE
--
-- MIB ref		: swCardEventLogSlotXX       .17.65.69.83.95.73.78.80.85.84.95.50.95.83.84.65.84.69
-- absolute OID	: 1.3.6.1.4.1.7995.2.6.1.1.XX.17.65.69.83.95.73.78.80.85.84.95.50.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_3_STATE
--
-- MIB ref		: swCardEventLogSlotXX       .17.65.69.83.95.73.78.80.85.84.95.51.95.83.84.65.84.69
-- absolute OID	: 1.3.6.1.4.1.7995.2.6.1.1.XX.17.65.69.83.95.73.78.80.85.84.95.51.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_4_STATE
--
-- MIB ref		: swCardEventLogSlotXX       .17.65.69.83.95.73.78.80.85.84.95.52.95.83.84.65.84.69
-- absolute OID	: 1.3.6.1.4.1.7995.2.6.1.1.XX.17.65.69.83.95.73.78.80.85.84.95.52.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_5_STATE
--
-- MIB ref		: swCardEventLogSlotXX       .17.65.69.83.95.73.78.80.85.84.95.53.95.83.84.65.84.69
-- absolute OID	: 1.3.6.1.4.1.7995.2.6.1.1.XX.17.65.69.83.95.73.78.80.85.84.95.53.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_6_STATE
--
-- MIB ref		: swCardEventLogSlotXX       .17.65.69.83.95.73.78.80.85.84.95.54.95.83.84.65.84.69
-- absolute OID	: 1.3.6.1.4.1.7995.2.6.1.1.XX.17.65.69.83.95.73.78.80.85.84.95.54.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_7_STATE
--
-- MIB ref		: swCardEventLogSlotXX       .17.65.69.83.95.73.78.80.85.84.95.55.95.83.84.65.84.69
-- absolute OID	: 1.3.6.1.4.1.7995.2.6.1.1.XX.17.65.69.83.95.73.78.80.85.84.95.55.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: AES_INPUT_8_STATE
--
-- MIB ref		: swCardEventLogSlotXX       .17.65.69.83.95.73.78.80.85.84.95.56.95.83.84.65.84.69
-- absolute OID	: 1.3.6.1.4.1.7995.2.6.1.1.XX.17.65.69.83.95.73.78.80.85.84.95.56.95.83.84.65.84.69
--
-- Value(s)		: OK:PCM
--				: OK:Data
--				: OK:DolbyE
--				: WARN:Unknown
--				: FAIL:Lost
--				: FAIL:Input Lost
--				: WARN:Output
--				: WARN:Input
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
--
-- Value(s)		: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
--
-- Value(s)		: OK
--				: WARN:Mismatch
--				: FAIL:Lost
-- Comments		: External ref state
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
--
-- Value(s)		: 0
--				: 1
--				: 2
-- Comments		: Number of error seconds
--
---------------------------------------------------------------------------------------------------
-- Header		: LICENSED_OPTIONS_2
--
-- MIB ref		: swCardEventLogSlotXX       .18.76.73.67.69.78.83.69.68.95.79.80.84.73.79.78.83.95.50
-- absolute OID	: 1.3.6.1.4.1.7995.2.6.1.1.XX.18.76.73.67.69.78.83.69.68.95.79.80.84.73.79.78.83.95.50
--
-- Value(s)		: FAIL:No File
--				: FAIL:Bad SerialNum
--				: WARN:Type??
--				: FAIL:Type Unknown
--				: WARN:Type Mismatch
--				: WARN:Bad File
--				: FAIL:Invalid
--				: OK:0 Options(s)
--				: OK:1 Options(s)
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
--
-- Value(s)		: OK
--				: WARN
-- Comments		:
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
--
-- Value(s)		: LOST
--				: 525/29i
--				: 625/25i
--				: 720/50p
--				: 720/59p
--				: 1080/25i
--				: 1080/29i
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
--
-- Value(s)		: 0
--				: 1
--				: 2
-- Comments		: Number of error seconds
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
--
-- Value(s)		: OK:PCM
--				: OK:Data
--				: OK:DolbyE
--				: WARN:Unknown
--				: FAIL:Lost
--				: FAIL:Input Lost
-- Comments		:
--
---------------------------------------------------------------------------------------------------
-- Header		: OUTPUT_1_EMBED_AUDIO_1_1_STATE
--
-- MIB ref		: swCardEventLogSlotXX       .30.79.85.84.80.85.84.95.49.95.69.77.66.69.68.95.65.85.68.73.79.95.49.95.49.95.83.84.65.84.69
-- absolute OID	: 1.3.6.1.4.1.7995.2.6.1.1.XX.30.79.85.84.80.85.84.95.49.95.69.77.66.69.68.95.65.85.68.73.79.95.49.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_1_2_STATE
--
-- MIB ref		: swCardEventLogSlotXX       .30.79.85.84.80.85.84.95.49.95.69.77.66.69.68.95.65.85.68.73.79.95.49.95.50.95.83.84.65.84.69
-- absolute OID	: 1.3.6.1.4.1.7995.2.6.1.1.XX.30.79.85.84.80.85.84.95.49.95.69.77.66.69.68.95.65.85.68.73.79.95.49.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_2_1_STATE
--
-- MIB ref		: swCardEventLogSlotXX       .30.79.85.84.80.85.84.95.49.95.69.77.66.69.68.95.65.85.68.73.79.95.50.95.49.95.83.84.65.84.69
-- absolute OID	: 1.3.6.1.4.1.7995.2.6.1.1.XX.30.79.85.84.80.85.84.95.49.95.69.77.66.69.68.95.65.85.68.73.79.95.50.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_2_2_STATE
--
-- MIB ref		: swCardEventLogSlotXX       .30.79.85.84.80.85.84.95.49.95.69.77.66.69.68.95.65.85.68.73.79.95.50.95.50.95.83.84.65.84.69
-- absolute OID	: 1.3.6.1.4.1.7995.2.6.1.1.XX.30.79.85.84.80.85.84.95.49.95.69.77.66.69.68.95.65.85.68.73.79.95.50.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_3_1_STATE
--
-- MIB ref		: swCardEventLogSlotXX       .30.79.85.84.80.85.84.95.49.95.69.77.66.69.68.95.65.85.68.73.79.95.51.95.49.95.83.84.65.84.69
-- absolute OID	: 1.3.6.1.4.1.7995.2.6.1.1.XX.30.79.85.84.80.85.84.95.49.95.69.77.66.69.68.95.65.85.68.73.79.95.51.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_3_2_STATE
--
-- MIB ref		: swCardEventLogSlotXX       .30.79.85.84.80.85.84.95.49.95.69.77.66.69.68.95.65.85.68.73.79.95.51.95.50.95.83.84.65.84.69
-- absolute OID	: 1.3.6.1.4.1.7995.2.6.1.1.XX.30.79.85.84.80.85.84.95.49.95.69.77.66.69.68.95.65.85.68.73.79.95.51.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_4_1_STATE
--
-- MIB ref		: swCardEventLogSlotXX       .30.79.85.84.80.85.84.95.49.95.69.77.66.69.68.95.65.85.68.73.79.95.52.95.49.95.83.84.65.84.69
-- absolute OID	: 1.3.6.1.4.1.7995.2.6.1.1.XX.30.79.85.84.80.85.84.95.49.95.69.77.66.69.68.95.65.85.68.73.79.95.52.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_4_2_STATE
--
-- MIB ref		: swCardEventLogSlotXX       .30.79.85.84.80.85.84.95.49.95.69.77.66.69.68.95.65.85.68.73.79.95.52.95.50.95.83.84.65.84.69
-- absolute OID	: 1.3.6.1.4.1.7995.2.6.1.1.XX.30.79.85.84.80.85.84.95.49.95.69.77.66.69.68.95.65.85.68.73.79.95.52.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_5_1_STATE
--
-- MIB ref		: swCardEventLogSlotXX       .30.79.85.84.80.85.84.95.49.95.69.77.66.69.68.95.65.85.68.73.79.95.53.95.49.95.83.84.65.84.69
-- absolute OID	: 1.3.6.1.4.1.7995.2.6.1.1.XX.30.79.85.84.80.85.84.95.49.95.69.77.66.69.68.95.65.85.68.73.79.95.53.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_5_2_STATE
--
-- MIB ref		: swCardEventLogSlotXX       .30.79.85.84.80.85.84.95.49.95.69.77.66.69.68.95.65.85.68.73.79.95.53.95.50.95.83.84.65.84.69
-- absolute OID	: 1.3.6.1.4.1.7995.2.6.1.1.XX.30.79.85.84.80.85.84.95.49.95.69.77.66.69.68.95.65.85.68.73.79.95.53.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_6_1_STATE
--
-- MIB ref		: swCardEventLogSlotXX       .30.79.85.84.80.85.84.95.49.95.69.77.66.69.68.95.65.85.68.73.79.95.54.95.49.95.83.84.65.84.69
-- absolute OID	: 1.3.6.1.4.1.7995.2.6.1.1.XX.30.79.85.84.80.85.84.95.49.95.69.77.66.69.68.95.65.85.68.73.79.95.54.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_6_2_STATE
--
-- MIB ref		: swCardEventLogSlotXX       .30.79.85.84.80.85.84.95.49.95.69.77.66.69.68.95.65.85.68.73.79.95.54.95.50.95.83.84.65.84.69
-- absolute OID	: 1.3.6.1.4.1.7995.2.6.1.1.XX.30.79.85.84.80.85.84.95.49.95.69.77.66.69.68.95.65.85.68.73.79.95.54.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_7_1_STATE
--
-- MIB ref		: swCardEventLogSlotXX       .30.79.85.84.80.85.84.95.49.95.69.77.66.69.68.95.65.85.68.73.79.95.55.95.49.95.83.84.65.84.69
-- absolute OID	: 1.3.6.1.4.1.7995.2.6.1.1.XX.30.79.85.84.80.85.84.95.49.95.69.77.66.69.68.95.65.85.68.73.79.95.55.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_7_2_STATE
--
-- MIB ref		: swCardEventLogSlotXX       .30.79.85.84.80.85.84.95.49.95.69.77.66.69.68.95.65.85.68.73.79.95.55.95.50.95.83.84.65.84.69
-- absolute OID	: 1.3.6.1.4.1.7995.2.6.1.1.XX.30.79.85.84.80.85.84.95.49.95.69.77.66.69.68.95.65.85.68.73.79.95.55.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_8_1_STATE
--
-- MIB ref		: swCardEventLogSlotXX       .30.79.85.84.80.85.84.95.49.95.69.77.66.69.68.95.65.85.68.73.79.95.56.95.49.95.83.84.65.84.69
-- absolute OID	: 1.3.6.1.4.1.7995.2.6.1.1.XX.30.79.85.84.80.85.84.95.49.95.69.77.66.69.68.95.65.85.68.73.79.95.56.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_8_2_STATE
--
-- MIB ref		: swCardEventLogSlotXX       .30.79.85.84.80.85.84.95.49.95.69.77.66.69.68.95.65.85.68.73.79.95.56.95.50.95.83.84.65.84.69
-- absolute OID	: 1.3.6.1.4.1.7995.2.6.1.1.XX.30.79.85.84.80.85.84.95.49.95.69.77.66.69.68.95.65.85.68.73.79.95.56.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
--
-- Value(s)		: NONE
--				: OK
--				: WARN:Early
--				: WARN:Late
--				: FAIL:Early
--				: FAIL:Late
-- Comments		:
--
---------------------------------------------------------------------------------------------------
