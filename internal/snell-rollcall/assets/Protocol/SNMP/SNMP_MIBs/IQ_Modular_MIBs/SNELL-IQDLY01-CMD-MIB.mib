-- ************************************************************************************
-- Snell&Wilcox Card:IQDLY01
--        Module Id#:379
--       Command Set:5
--          Filename:SNELL-IQDLY01-CMD-MIB.mib
--            Author:Jonathan Riches
--              Date:08/06/2005
--              Time:10:14
--
-- Copyright (c) 2005 Snell & Wilcox Ltd
-- All rights reserved.
--
-- ************************************************************************************

SNELL-IQDLY01-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDLY01,
    moduleIQDLY01MIB
        FROM SNELL-WILCOX-PRODUCT-REG;

 moduleIQDLY01CmdMi MODULE-IDENTITY
    LAST-UPDATED "0506081014Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDLY01MIB 1 }




--********************************************************************************
--*
--*  Snell Wilcox Card:
--*  command set:
--*  list commands/menus:
--*
--******************************************************************************
	iqdly01CmdTable OBJECT-TYPE
		SYNTAX			SEQUENCE OF Iqdly01CmdEntry
		MAX-ACCESS		not-accessible
		STATUS			current
		DESCRIPTION
				"Note the instance of this table is relected in the command set Version"
		::= { moduleIQDLY01 1 }

	iqdly01CmdEntry OBJECT-TYPE
		SYNTAX		Iqdly01CmdEntry
		MAX-ACCESS		not-accessible
		STATUS			current
		DESCRIPTION
				"Entry in command table."
		INDEX	{ iqdly01SlotIndex }
		::= { iqdly01CmdTable 1 }

	Iqdly01CmdEntry ::=
		SEQUENCE {
			iqdly01SlotIndex
				Unsigned32,
			iqdly01AudioAESOutputAES1Source
				INTEGER,
			iqdly01AudioAESOutputAES2Source
				INTEGER,
			iqdly01AudioAESOutputAES3Source
				INTEGER,
			iqdly01AudioAESOutputAES4Source
				INTEGER,
			iqdly01AudioProcAmpStereo1
				INTEGER,
			iqdly01ProcAmpAES1LGainAES1L
				INTEGER,
			iqdly01ProcAmpAES1LInvert
				INTEGER,
			iqdly01ProcAmpAES1LMute
				INTEGER,
			iqdly01ProcAmpAES1RGainAES1R
				INTEGER,
			iqdly01ProcAmpAES1RInvert
				INTEGER,
			iqdly01ProcAmpAES1RMute
				INTEGER,
			iqdly01AudioProcAmpStereo2
				INTEGER,
			iqdly01ProcAmpAES2LGainAES2L
				INTEGER,
			iqdly01ProcAmpAES2LInvert
				INTEGER,
			iqdly01ProcAmpAES2LMute
				INTEGER,
			iqdly01ProcAmpAES2RGainAES2R
				INTEGER,
			iqdly01ProcAmpAES2RInvert
				INTEGER,
			iqdly01ProcAmpAES2RMute
				INTEGER,
			iqdly01AudioProcAmpStereo3
				INTEGER,
			iqdly01ProcAmpAES3LGainAES3L
				INTEGER,
			iqdly01ProcAmpAES3LInvert
				INTEGER,
			iqdly01ProcAmpAES3LMute
				INTEGER,
			iqdly01ProcAmpAES3RGainAES3R
				INTEGER,
			iqdly01ProcAmpAES3RInvert
				INTEGER,
			iqdly01ProcAmpAES3RMute
				INTEGER,
			iqdly01AudioProcAmpStereo4
				INTEGER,
			iqdly01ProcAmpAES4LGainAES4L
				INTEGER,
			iqdly01ProcAmpAES4LInvert
				INTEGER,
			iqdly01ProcAmpAES4LMute
				INTEGER,
			iqdly01ProcAmpAES4RGainAES4R
				INTEGER,
			iqdly01ProcAmpAES4RInvert
				INTEGER,
			iqdly01ProcAmpAES4RMute
				INTEGER,
			iqdly01Mixer1Mix1Source1
				INTEGER,
			iqdly01MixMixer1Gain1
				INTEGER,
			iqdly01Mixer1Mix1Source2
				INTEGER,
			iqdly01MixMixer1Gain2
				INTEGER,
			iqdly01Mixer1Mix1Source3
				INTEGER,
			iqdly01MixMixer1Gain3
				INTEGER,
			iqdly01Mixer1Mix1Source4
				INTEGER,
			iqdly01MixMixer1Gain4
				INTEGER,
			iqdly01Mixer2Mix2Source1
				INTEGER,
			iqdly01MixMixer2Gain1
				INTEGER,
			iqdly01Mixer2Mix2Source2
				INTEGER,
			iqdly01MixMixer2Gain2
				INTEGER,
			iqdly01Mixer2Mix2Source3
				INTEGER,
			iqdly01MixMixer2Gain3
				INTEGER,
			iqdly01Mixer2Mix2Source4
				INTEGER,
			iqdly01MixMixer2Gain4
				INTEGER,
			iqdly01Mixer3Mix3Source1
				INTEGER,
			iqdly01MixMixer3Gain1
				INTEGER,
			iqdly01Mixer3Mix3Source2
				INTEGER,
			iqdly01MixMixer3Gain2
				INTEGER,
			iqdly01Mixer3Mix3Source3
				INTEGER,
			iqdly01MixMixer3Gain3
				INTEGER,
			iqdly01Mixer3Mix3Source4
				INTEGER,
			iqdly01MixMixer3Gain4
				INTEGER,
			iqdly01Mixer4Mix4Source1
				INTEGER,
			iqdly01MixMixer4Gain1
				INTEGER,
			iqdly01Mixer4Mix4Source2
				INTEGER,
			iqdly01MixMixer4Gain2
				INTEGER,
			iqdly01Mixer4Mix4Source3
				INTEGER,
			iqdly01MixMixer4Gain3
				INTEGER,
			iqdly01Mixer4Mix4Source4
				INTEGER,
			iqdly01MixMixer4Gain4
				INTEGER,
			iqdly01BusSourceBusALSource
				INTEGER,
			iqdly01BusSourceBusARSource
				INTEGER,
			iqdly01BusSourceBusBLSource
				INTEGER,
			iqdly01BusSourceBusBRSource
				INTEGER,
			iqdly01BusSourceBusCLSource
				INTEGER,
			iqdly01BusSourceBusCRSource
				INTEGER,
			iqdly01BusSourceBusDLSource
				INTEGER,
			iqdly01BusSourceBusDRSource
				INTEGER,
			iqdly01BusesBusProcAmpStereoA
				INTEGER,
			iqdly01BusProcAmpBusALGainBusAL
				INTEGER,
			iqdly01BusProcAmpBusALInvert
				INTEGER,
			iqdly01BusProcAmpBusALMute
				INTEGER,
			iqdly01BusProcAmpBusARGainBusAR
				INTEGER,
			iqdly01BusProcAmpBusARInvert
				INTEGER,
			iqdly01BusProcAmpBusARMute
				INTEGER,
			iqdly01BusesBusProcAmpStereoB
				INTEGER,
			iqdly01BusProcAmpBusBLGainBusBL
				INTEGER,
			iqdly01BusProcAmpBusBLInvert
				INTEGER,
			iqdly01BusProcAmpBusBLMute
				INTEGER,
			iqdly01BusProcAmpBusBRGainBusBR
				INTEGER,
			iqdly01BusProcAmpBusBRInvert
				INTEGER,
			iqdly01BusProcAmpBusBRMute
				INTEGER,
			iqdly01BusesBusProcAmpStereoC
				INTEGER,
			iqdly01BusProcAmpBusCLGainBusCL
				INTEGER,
			iqdly01BusProcAmpBusCLInvert
				INTEGER,
			iqdly01BusProcAmpBusCLMute
				INTEGER,
			iqdly01BusProcAmpBusCRGainBusCR
				INTEGER,
			iqdly01BusProcAmpBusCRInvert
				INTEGER,
			iqdly01BusProcAmpBusCRMute
				INTEGER,
			iqdly01BusesBusProcAmpStereoD
				INTEGER,
			iqdly01BusProcAmpBusDLGainBusDL
				INTEGER,
			iqdly01BusProcAmpBusDLInvert
				INTEGER,
			iqdly01BusProcAmpBusDLMute
				INTEGER,
			iqdly01BusProcAmpBusDRGainBusDR
				INTEGER,
			iqdly01BusProcAmpBusDRInvert
				INTEGER,
			iqdly01BusProcAmpBusDRMute
				INTEGER,
			iqdly01AudioDelayAESInput1Delay
				INTEGER,
			iqdly01AudioDelayAESInput2Delay
				INTEGER,
			iqdly01AudioDelayAESInput3Delay
				INTEGER,
			iqdly01AudioDelayAESInput4Delay
				INTEGER,
			iqdly01DelayDelaySelectManual
				INTEGER,
			iqdly01DelayDelaySelectRolltrack14
				INTEGER,
			iqdly01DelayDelaySelectRolltrack15
				INTEGER,
			iqdly01DelayDelaySelectRolltrack16
				INTEGER,
			iqdly01DelayDelaySelectRolltrack17
				INTEGER,
			iqdly01DelayDelaySelectGPIDelaySelect
				INTEGER,
			iqdly01DelayDelayStatus
				INTEGER,
			iqdly01DelayDelayStatusRolltrack14
				RollCallString,
			iqdly01DelayDelayStatusRolltrack15
				RollCallString,
			iqdly01DelayDelayStatusRolltrack16
				RollCallString,
			iqdly01DelayDelayStatusRolltrack17
				RollCallString,
			iqdly01DelayDelayStatusGPIDelayDisplay
				RollCallString,
			iqdly01DelayDelayStatusTotalDelayDisplay
				RollCallString,
			iqdly01AudioMonitorSilenceLevel
				INTEGER,
			iqdly01AudioMonitorLowLevel
				INTEGER,
			iqdly01AudioMonitorHighLevel
				INTEGER,
			iqdly01AudioMonitorOverloadLevel
				INTEGER,
			iqdly01AudioMonitorWarningTimer
				INTEGER,
			iqdly01Genlock
				INTEGER,
			iqdly01GenlockFreerunFreq
				INTEGER,
			iqdly01UserMemMemory1Save1
				INTEGER,
			iqdly01UserMemMemory1Recall1
				INTEGER,
			iqdly01UserMemMemory1Clear1
				INTEGER,
			iqdly01UserMemMemory1Name1
				RollCallString,
			iqdly01UserMemMemory2Save2
				INTEGER,
			iqdly01UserMemMemory2Recall2
				INTEGER,
			iqdly01UserMemMemory2Clear2
				INTEGER,
			iqdly01UserMemMemory2Name2
				RollCallString,
			iqdly01UserMemMemory3Save3
				INTEGER,
			iqdly01UserMemMemory3Recall3
				INTEGER,
			iqdly01UserMemMemory3Clear3
				INTEGER,
			iqdly01UserMemMemory3Name3
				RollCallString,
			iqdly01UserMemMemory4Save4
				INTEGER,
			iqdly01UserMemMemory4Recall4
				INTEGER,
			iqdly01UserMemMemory4Clear4
				INTEGER,
			iqdly01UserMemMemory4Name4
				RollCallString,
			iqdly01UserMemMemory5Save5
				INTEGER,
			iqdly01UserMemMemory5Recall5
				INTEGER,
			iqdly01UserMemMemory5Clear5
				INTEGER,
			iqdly01UserMemMemory5Name5
				RollCallString,
			iqdly01UserMemMemory6Save6
				INTEGER,
			iqdly01UserMemMemory6Recall6
				INTEGER,
			iqdly01UserMemMemory6Clear6
				INTEGER,
			iqdly01UserMemMemory6Name6
				RollCallString,
			iqdly01UserMemMemory7Save7
				INTEGER,
			iqdly01UserMemMemory7Recall7
				INTEGER,
			iqdly01UserMemMemory7Clear7
				INTEGER,
			iqdly01UserMemMemory7Name7
				RollCallString,
			iqdly01UserMemMemory8Save8
				INTEGER,
			iqdly01UserMemMemory8Recall8
				INTEGER,
			iqdly01UserMemMemory8Clear8
				INTEGER,
			iqdly01UserMemMemory8Name8
				RollCallString,
			iqdly01SetupAudioToneIdentEnable
				INTEGER,
			iqdly01SetupAudioToneFrequency
				INTEGER,
			iqdly01SetupAudioToneFrequencyR
				INTEGER,
			iqdly01SetupAudioToneHeadRoom
				INTEGER,
			iqdly01SetupSlewRate
				INTEGER,
			iqdly01SetupChannelStatus
				RollCallString,
			iqdly01GPIIOGPIInputDisableInputs
				INTEGER,
			iqdly01GPIIOGPIInputInputTimerEnable
				INTEGER,
			iqdly01GPIIOGPIInputTimerActiveHigh
				INTEGER,
			iqdly01GPIIOGPIInputInputSelection
				INTEGER,
			iqdly01GPIIOGPIInputGPIInStatus
				RollCallString,
			iqdly01GPIIOGPIOutputOutActiveHigh
				INTEGER,
			iqdly01GPIIOGPIOutputOutputSelection
				INTEGER,
			iqdly01GPIIOGPIOutputGPIOutStatus
				RollCallString,
			iqdly01GPIIOGPIInputOutputGPIO1
				INTEGER,
			iqdly01SetupGPIIOInputSelection
				INTEGER,
			iqdly01SetupGPIIOOutputSelection
				INTEGER,
			iqdly01SetupRollTrackRollTrackIndex
				INTEGER,
			iqdly01SetupRollTrackRollTrackSource
				INTEGER,
			iqdly01SetupRollTrackRollTrackDisable
				INTEGER,
			iqdly01SetupRollTrackRollTrackAddress
				RollCallString,
			iqdly01SetupRollTrackRollTrackCommand
				RollCallString,
			iqdly01SetupRollTrackRollTrackSending
				RollCallString,
			iqdly01SetupRollTrackRollTrackStatus
				RollCallString,
			iqdly01SetupRollTrackRollTrack_Index
				INTEGER,
			iqdly01SetupRollTrackRollTrack_Source
				INTEGER,
			iqdly01SetupRollTrackRollTrack_Address
				RollCallString,
			iqdly01SetupRollTrackRollTrack_Command
				RollCallString,
			iqdly01SetupLoggingReference
				INTEGER,
			iqdly01SetupLoggingRollTrack
				INTEGER,
			iqdly01SetupLoggingAES1
				INTEGER,
			iqdly01SetupLoggingAES2
				INTEGER,
			iqdly01SetupLoggingAES3
				INTEGER,
			iqdly01SetupLoggingAES4
				INTEGER,
			iqdly01SetupLoggingBusAL
				INTEGER,
			iqdly01SetupLoggingBusAR
				INTEGER,
			iqdly01SetupLoggingBusBL
				INTEGER,
			iqdly01SetupLoggingBusBR
				INTEGER,
			iqdly01SetupLoggingBusCL
				INTEGER,
			iqdly01SetupLoggingBusCR
				INTEGER,
			iqdly01SetupLoggingBusDL
				INTEGER,
			iqdly01SetupLoggingBusDR
				INTEGER,
			iqdly01SetupLoggingFault
				INTEGER,
			iqdly01SetupLoggingStatusEXTREF
				RollCallString,
			iqdly01SetupLoggingStatusROLLTRACK
				RollCallString,
			iqdly01SetupLoggingStatusAES1
				RollCallString,
			iqdly01SetupLoggingStatusAES2
				RollCallString,
			iqdly01SetupLoggingStatusAES3
				RollCallString,
			iqdly01SetupLoggingStatusAES4
				RollCallString,
			iqdly01SetupLoggingStatusBUSAL
				RollCallString,
			iqdly01SetupLoggingStatusBUSAR
				RollCallString,
			iqdly01SetupLoggingStatusBUSBL
				RollCallString,
			iqdly01SetupLoggingStatusBUSBR
				RollCallString,
			iqdly01SetupLoggingStatusBUSCL
				RollCallString,
			iqdly01SetupLoggingStatusBUSCR
				RollCallString,
			iqdly01SetupLoggingStatusBUSDL
				RollCallString,
			iqdly01SetupLoggingStatusBUSDR
				RollCallString,
			iqdly01SetupLoggingStatusFAULT
				RollCallString,
			iqdly01SetupUnitSoftwareVersion
				RollCallString,
			iqdly01SetupUnitSerialNo
				RollCallString,
			iqdly01SetupUnitPresetUnit
				INTEGER,
			iqdly01SetupUnitRestart
				INTEGER,
			iqdly01SetupUnitBuildNo
				RollCallString
		}

	iqdly01SlotIndex OBJECT-TYPE
		SYNTAX		Unsigned32
		MAX-ACCESS		not-accessible
		STATUS			current
		DESCRIPTION
				"The unique Index value for each slot.  Its value
					ranges between 1 and the value of slotNumber."
		::= { iqdly01CmdEntry 0 }


	iqdly01AudioAESOutputAES1Source OBJECT-TYPE
		SYNTAX		INTEGER {
							val_BUS_A(0),
							val_BUS_B(1),
							val_BUS_C(2),
							val_BUS_D(3),
							val_AES_1_Direct(4),
							val_AES_2_Direct(5),
							val_AES_3_Direct(6),
							val_AES_4_Direct(7),
							val_Test_tone(8),
							val_Silence(9)
							}
		MAX-ACCESS		read-write
		STATUS			current
		DESCRIPTION
				"TYPE: - RadiobuttonList
				 PAGE: - Audio- AES Output
					AES 1 Source  cmdID= 2951 
					BUS A  value= 0  
					BUS B  value= 1  
					BUS C  value= 2  
					BUS D  value= 3  
					AES 1 Direct  value= 4  
					AES 2 Direct  value= 5  
					AES 3 Direct  value= 6  
					AES 4 Direct  value= 7  
					Test tone  value= 8  
					Silence  value= 9  "
		::= { iqdly01CmdEntry 2951 }


	iqdly01AudioAESOutputAES2Source OBJECT-TYPE
		SYNTAX		INTEGER {
							val_BUS_A(0),
							val_BUS_B(1),
							val_BUS_C(2),
							val_BUS_D(3),
							val_AES_1_Direct(4),
							val_AES_2_Direct(5),
							val_AES_3_Direct(6),
							val_AES_4_Direct(7),
							val_Test_tone(8),
							val_Silence(9)
							}
		MAX-ACCESS		read-write
		STATUS			current
		DESCRIPTION
				"TYPE: - RadiobuttonList
				 PAGE: - Audio- AES Output
					AES 2 Source  cmdID= 2952 
					BUS A  value= 0  
					BUS B  value= 1  
					BUS C  value= 2  
					BUS D  value= 3  
					AES 1 Direct  value= 4  
					AES 2 Direct  value= 5  
					AES 3 Direct  value= 6  
					AES 4 Direct  value= 7  
					Test tone  value= 8  
					Silence  value= 9  "
		::= { iqdly01CmdEntry 2952 }


	iqdly01AudioAESOutputAES3Source OBJECT-TYPE
		SYNTAX		INTEGER {
							val_BUS_A(0),
							val_BUS_B(1),
							val_BUS_C(2),
							val_BUS_D(3),
							val_AES_1_Direct(4),
							val_AES_2_Direct(5),
							val_AES_3_Direct(6),
							val_AES_4_Direct(7),
							val_Test_tone(8),
							val_Silence(9)
							}
		MAX-ACCESS		read-write
		STATUS			current
		DESCRIPTION
				"TYPE: - RadiobuttonList
				 PAGE: - Audio- AES Output
					AES 3 Source  cmdID= 2953 
					BUS A  value= 0  
					BUS B  value= 1  
					BUS C  value= 2  
					BUS D  value= 3  
					AES 1 Direct  value= 4  
					AES 2 Direct  value= 5  
					AES 3 Direct  value= 6  
					AES 4 Direct  value= 7  
					Test tone  value= 8  
					Silence  value= 9  "
		::= { iqdly01CmdEntry 2953 }


	iqdly01AudioAESOutputAES4Source OBJECT-TYPE
		SYNTAX		INTEGER {
							val_BUS_A(0),
							val_BUS_B(1),
							val_BUS_C(2),
							val_BUS_D(3),
							val_AES_1_Direct(4),
							val_AES_2_Direct(5),
							val_AES_3_Direct(6),
							val_AES_4_Direct(7),
							val_Test_tone(8),
							val_Silence(9)
							}
		MAX-ACCESS		read-write
		STATUS			current
		DESCRIPTION
				"TYPE: - RadiobuttonList
				 PAGE: - Audio- AES Output
					AES 4 Source  cmdID= 2954 
					BUS A  value= 0  
					BUS B  value= 1  
					BUS C  value= 2  
					BUS D  value= 3  
					AES 1 Direct  value= 4  
					AES 2 Direct  value= 5  
					AES 3 Direct  value= 6  
					AES 4 Direct  value= 7  
					Test tone  value= 8  
					Silence  value= 9  "
		::= { iqdly01CmdEntry 2954 }


	iqdly01AudioProcAmpStereo1 OBJECT-TYPE
		SYNTAX		INTEGER { disable(0), enable(1) }
		MAX-ACCESS		read-write
		STATUS			current
		DESCRIPTION
				"TYPE: - Checkbox
				 PAGE: - Audio- ProcAmp
					Stereo 1  cmdID= 3324 "
		::= { iqdly01CmdEntry 3324 }


	iqdly01ProcAmpAES1LGainAES1L OBJECT-TYPE
		SYNTAX		INTEGER
		MAX-ACCESS		read-write
		STATUS			current
		DESCRIPTION
				"TYPE: - Number
				 PAGE: - Audio- ProcAmp
					Gain AES 1L  cmdID= 3088  min= -180  max= 180  step= 1  format= %0.1fdB  div_scale= 10 
					Min = -18.0dB  Max = 18.0dB  Step = 0.1dB "
		::= { iqdly01CmdEntry 3088 }


	iqdly01ProcAmpAES1LInvert OBJECT-TYPE
		SYNTAX		INTEGER { disable(0), enable(1) }
		MAX-ACCESS		read-write
		STATUS			current
		DESCRIPTION
				"TYPE: - Checkbox
				 PAGE: - Audio- ProcAmp
					Invert  cmdID= 3168 "
		::= { iqdly01CmdEntry 3168 }


	iqdly01ProcAmpAES1LMute OBJECT-TYPE
		SYNTAX		INTEGER { disable(0), enable(1) }
		MAX-ACCESS		read-write
		STATUS			current
		DESCRIPTION
				"TYPE: - Checkbox
				 PAGE: - Audio- ProcAmp
					Mute  cmdID= 3248 "
		::= { iqdly01CmdEntry 3248 }


	iqdly01ProcAmpAES1RGainAES1R OBJECT-TYPE
		SYNTAX		INTEGER
		MAX-ACCESS		read-write
		STATUS			current
		DESCRIPTION
				"TYPE: - Number
				 PAGE: - Audio- ProcAmp
					Gain AES 1R  cmdID= 3089  min= -180  max= 180  step= 1  format= %0.1fdB  div_scale= 10 
					Min = -18.0dB  Max = 18.0dB  Step = 0.1dB "
		::= { iqdly01CmdEntry 3089 }


	iqdly01ProcAmpAES1RInvert OBJECT-TYPE
		SYNTAX		INTEGER { disable(0), enable(1) }
		MAX-ACCESS		read-write
		STATUS			current
		DESCRIPTION
				"TYPE: - Checkbox
				 PAGE: - Audio- ProcAmp
					Invert  cmdID= 3169 "
		::= { iqdly01CmdEntry 3169 }


	iqdly01ProcAmpAES1RMute OBJECT-TYPE
		SYNTAX		INTEGER { disable(0), enable(1) }
		MAX-ACCESS		read-write
		STATUS			current
		DESCRIPTION
				"TYPE: - Checkbox
				 PAGE: - Audio- ProcAmp
					Mute  cmdID= 3249 "
		::= { iqdly01CmdEntry 3249 }


	iqdly01AudioProcAmpStereo2 OBJECT-TYPE
		SYNTAX		INTEGER { disable(0), enable(1) }
		MAX-ACCESS		read-write
		STATUS			current
		DESCRIPTION
				"TYPE: - Checkbox
				 PAGE: - Audio- ProcAmp
					Stereo 2  cmdID= 3325 "
		::= { iqdly01CmdEntry 3325 }


	iqdly01ProcAmpAES2LGainAES2L OBJECT-TYPE
		SYNTAX		INTEGER
		MAX-ACCESS		read-write
		STATUS			current
		DESCRIPTION
				"TYPE: - Number
				 PAGE: - Audio- ProcAmp
					Gain AES 2L  cmdID= 3090  min= -180  max= 180  step= 1  format= %0.1fdB  div_scale= 10 
					Min = -18.0dB  Max = 18.0dB  Step = 0.1dB "
		::= { iqdly01CmdEntry 3090 }


	iqdly01ProcAmpAES2LInvert OBJECT-TYPE
		SYNTAX		INTEGER { disable(0), enable(1) }
		MAX-ACCESS		read-write
		STATUS			current
		DESCRIPTION
				"TYPE: - Checkbox
				 PAGE: - Audio- ProcAmp
					Invert  cmdID= 3170 "
		::= { iqdly01CmdEntry 3170 }


	iqdly01ProcAmpAES2LMute OBJECT-TYPE
		SYNTAX		INTEGER { disable(0), enable(1) }
		MAX-ACCESS		read-write
		STATUS			current
		DESCRIPTION
				"TYPE: - Checkbox
				 PAGE: - Audio- ProcAmp
					Mute  cmdID= 3250 "
		::= { iqdly01CmdEntry 3250 }


	iqdly01ProcAmpAES2RGainAES2R OBJECT-TYPE
		SYNTAX		INTEGER
		MAX-ACCESS		read-write
		STATUS			current
		DESCRIPTION
				"TYPE: - Number
				 PAGE: - Audio- ProcAmp
					Gain AES 2R  cmdID= 3091  min= -180  max= 180  step= 1  format= %0.1fdB  div_scale= 10 
					Min = -18.0dB  Max = 18.0dB  Step = 0.1dB "
		::= { iqdly01CmdEntry 3091 }


	iqdly01ProcAmpAES2RInvert OBJECT-TYPE
		SYNTAX		INTEGER { disable(0), enable(1) }
		MAX-ACCESS		read-write
		STATUS			current
		DESCRIPTION
				"TYPE: - Checkbox
				 PAGE: - Audio- ProcAmp
					Invert  cmdID= 3171 "
		::= { iqdly01CmdEntry 3171 }


	iqdly01ProcAmpAES2RMute OBJECT-TYPE
		SYNTAX		INTEGER { disable(0), enable(1) }
		MAX-ACCESS		read-write
		STATUS			current
		DESCRIPTION
				"TYPE: - Checkbox
				 PAGE: - Audio- ProcAmp
					Mute  cmdID= 3251 "
		::= { iqdly01CmdEntry 3251 }


	iqdly01AudioProcAmpStereo3 OBJECT-TYPE
		SYNTAX		INTEGER { disable(0), enable(1) }
		MAX-ACCESS		read-write
		STATUS			current
		DESCRIPTION
				"TYPE: - Checkbox
				 PAGE: - Audio- ProcAmp
					Stereo 3  cmdID= 3326 "
		::= { iqdly01CmdEntry 3326 }


	iqdly01ProcAmpAES3LGainAES3L OBJECT-TYPE
		SYNTAX		INTEGER
		MAX-ACCESS		read-write
		STATUS			current
		DESCRIPTION
				"TYPE: - Number
				 PAGE: - Audio- ProcAmp
					Gain AES 3L  cmdID= 3092  min= -180  max= 180  step= 1  format= %0.1fdB  div_scale= 10 
					Min = -18.0dB  Max = 18.0dB  Step = 0.1dB "
		::= { iqdly01CmdEntry 3092 }


	iqdly01ProcAmpAES3LInvert OBJECT-TYPE
		SYNTAX		INTEGER { disable(0), enable(1) }
		MAX-ACCESS		read-write
		STATUS			current
		DESCRIPTION
				"TYPE: - Checkbox
				 PAGE: - Audio- ProcAmp
					Invert  cmdID= 3172 "
		::= { iqdly01CmdEntry 3172 }


	iqdly01ProcAmpAES3LMute OBJECT-TYPE
		SYNTAX		INTEGER { disable(0), enable(1) }
		MAX-ACCESS		read-write
		STATUS			current
		DESCRIPTION
				"TYPE: - Checkbox
				 PAGE: - Audio- ProcAmp
					Mute  cmdID= 3252 "
		::= { iqdly01CmdEntry 3252 }


	iqdly01ProcAmpAES3RGainAES3R OBJECT-TYPE
		SYNTAX		INTEGER
		MAX-ACCESS		read-write
		STATUS			current
		DESCRIPTION
				"TYPE: - Number
				 PAGE: - Audio- ProcAmp
					Gain AES 3R  cmdID= 3093  min= -180  max= 180  step= 1  format= %0.1fdB  div_scale= 10 
					Min = -18.0dB  Max = 18.0dB  Step = 0.1dB "
		::= { iqdly01CmdEntry 3093 }


	iqdly01ProcAmpAES3RInvert OBJECT-TYPE
		SYNTAX		INTEGER { disable(0), enable(1) }
		MAX-ACCESS		read-write
		STATUS			current
		DESCRIPTION
				"TYPE: - Checkbox
				 PAGE: - Audio- ProcAmp
					Invert  cmdID= 3173 "
		::= { iqdly01CmdEntry 3173 }


	iqdly01ProcAmpAES3RMute OBJECT-TYPE
		SYNTAX		INTEGER { disable(0), enable(1) }
		MAX-ACCESS		read-write
		STATUS			current
		DESCRIPTION
				"TYPE: - Checkbox
				 PAGE: - Audio- ProcAmp
					Mute  cmdID= 3253 "
		::= { iqdly01CmdEntry 3253 }


	iqdly01AudioProcAmpStereo4 OBJECT-TYPE
		SYNTAX		INTEGER { disable(0), enable(1) }
		MAX-ACCESS		read-write
		STATUS			current
		DESCRIPTION
				"TYPE: - Checkbox
				 PAGE: - Audio- ProcAmp
					Stereo 4  cmdID= 3327 "
		::= { iqdly01CmdEntry 3327 }


	iqdly01ProcAmpAES4LGainAES4L OBJECT-TYPE
		SYNTAX		INTEGER
		MAX-ACCESS		read-write
		STATUS			current
		DESCRIPTION
				"TYPE: - Number
				 PAGE: - Audio- ProcAmp
					Gain AES 4L  cmdID= 3094  min= -180  max= 180  step= 1  format= %0.1fdB  div_scale= 10 
					Min = -18.0dB  Max = 18.0dB  Step = 0.1dB "
		::= { iqdly01CmdEntry 3094 }


	iqdly01ProcAmpAES4LInvert OBJECT-TYPE
		SYNTAX		INTEGER { disable(0), enable(1) }
		MAX-ACCESS		read-write
		STATUS			current
		DESCRIPTION
				"TYPE: - Checkbox
				 PAGE: - Audio- ProcAmp
					Invert  cmdID= 3174 "
		::= { iqdly01CmdEntry 3174 }


	iqdly01ProcAmpAES4LMute OBJECT-TYPE
		SYNTAX		INTEGER { disable(0), enable(1) }
		MAX-ACCESS		read-write
		STATUS			current
		DESCRIPTION
				"TYPE: - Checkbox
				 PAGE: - Audio- ProcAmp
					Mute  cmdID= 3254 "
		::= { iqdly01CmdEntry 3254 }


	iqdly01ProcAmpAES4RGainAES4R OBJECT-TYPE
		SYNTAX		INTEGER
		MAX-ACCESS		read-write
		STATUS			current
		DESCRIPTION
				"TYPE: - Number
				 PAGE: - Audio- ProcAmp
					Gain AES 4R  cmdID= 3095  min= -180  max= 180  step= 1  format= %0.1fdB  div_scale= 10 
					Min = -18.0dB  Max = 18.0dB  Step = 0.1dB "
		::= { iqdly01CmdEntry 3095 }


	iqdly01ProcAmpAES4RInvert OBJECT-TYPE
		SYNTAX		INTEGER { disable(0), enable(1) }
		MAX-ACCESS		read-write
		STATUS			current
		DESCRIPTION
				"TYPE: - Checkbox
				 PAGE: - Audio- ProcAmp
					Invert  cmdID= 3175 "
		::= { iqdly01CmdEntry 3175 }


	iqdly01ProcAmpAES4RMute OBJECT-TYPE
		SYNTAX		INTEGER { disable(0), enable(1) }
		MAX-ACCESS		read-write
		STATUS			current
		DESCRIPTION
				"TYPE: - Checkbox
				 PAGE: - Audio- ProcAmp
					Mute  cmdID= 3255 "
		::= { iqdly01CmdEntry 3255 }


	iqdly01Mixer1Mix1Source1 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 1- Mix1 Source1
					Mix1 Source1  cmdID= 3440 
					AES 1L  value= 0  
					AES 1R  value= 1  
					AES 2L  value= 2  
					AES 2R  value= 3  
					AES 3L  value= 4  
					AES 3R  value= 5  
					AES 4L  value= 6  
					AES 4R  value= 7  "
		::= { iqdly01CmdEntry 3440 }


	iqdly01MixMixer1Gain1 OBJECT-TYPE
		SYNTAX		INTEGER
		MAX-ACCESS		read-write
		STATUS			current
		DESCRIPTION
				"TYPE: - Number
				 PAGE: - Audio- Mix- Mixer 1
					Gain1  cmdID= 3360  min= -71  max= 0  step= 1  format= %0.0fdB  div_scale= 1 
					Min = -71dB  Max = 0dB  Step = 1dB "
		::= { iqdly01CmdEntry 3360 }


	iqdly01Mixer1Mix1Source2 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 1- Mix1 Source2
					Mix1 Source2  cmdID= 3441 
					AES 1L  value= 0  
					AES 1R  value= 1  
					AES 2L  value= 2  
					AES 2R  value= 3  
					AES 3L  value= 4  
					AES 3R  value= 5  
					AES 4L  value= 6  
					AES 4R  value= 7  "
		::= { iqdly01CmdEntry 3441 }


	iqdly01MixMixer1Gain2 OBJECT-TYPE
		SYNTAX		INTEGER
		MAX-ACCESS		read-write
		STATUS			current
		DESCRIPTION
				"TYPE: - Number
				 PAGE: - Audio- Mix- Mixer 1
					Gain2  cmdID= 3361  min= -71  max= 0  step= 1  format= %0.0fdB  div_scale= 1 
					Min = -71dB  Max = 0dB  Step = 1dB "
		::= { iqdly01CmdEntry 3361 }


	iqdly01Mixer1Mix1Source3 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 1- Mix1 Source3
					Mix1 Source3  cmdID= 3442 
					AES 1L  value= 0  
					AES 1R  value= 1  
					AES 2L  value= 2  
					AES 2R  value= 3  
					AES 3L  value= 4  
					AES 3R  value= 5  
					AES 4L  value= 6  
					AES 4R  value= 7  "
		::= { iqdly01CmdEntry 3442 }


	iqdly01MixMixer1Gain3 OBJECT-TYPE
		SYNTAX		INTEGER
		MAX-ACCESS		read-write
		STATUS			current
		DESCRIPTION
				"TYPE: - Number
				 PAGE: - Audio- Mix- Mixer 1
					Gain3  cmdID= 3362  min= -71  max= 0  step= 1  format= %0.0fdB  div_scale= 1 
					Min = -71dB  Max = 0dB  Step = 1dB "
		::= { iqdly01CmdEntry 3362 }


	iqdly01Mixer1Mix1Source4 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 1- Mix1 Source4
					Mix1 Source4  cmdID= 3443 
					AES 1L  value= 0  
					AES 1R  value= 1  
					AES 2L  value= 2  
					AES 2R  value= 3  
					AES 3L  value= 4  
					AES 3R  value= 5  
					AES 4L  value= 6  
					AES 4R  value= 7  "
		::= { iqdly01CmdEntry 3443 }


	iqdly01MixMixer1Gain4 OBJECT-TYPE
		SYNTAX		INTEGER
		MAX-ACCESS		read-write
		STATUS			current
		DESCRIPTION
				"TYPE: - Number
				 PAGE: - Audio- Mix- Mixer 1
					Gain4  cmdID= 3363  min= -71  max= 0  step= 1  format= %0.0fdB  div_scale= 1 
					Min = -71dB  Max = 0dB  Step = 1dB "
		::= { iqdly01CmdEntry 3363 }


	iqdly01Mixer2Mix2Source1 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 2- Mix2 Source1
					Mix2 Source1  cmdID= 3444 
					AES 1L  value= 0  
					AES 1R  value= 1  
					AES 2L  value= 2  
					AES 2R  value= 3  
					AES 3L  value= 4  
					AES 3R  value= 5  
					AES 4L  value= 6  
					AES 4R  value= 7  "
		::= { iqdly01CmdEntry 3444 }


	iqdly01MixMixer2Gain1 OBJECT-TYPE
		SYNTAX		INTEGER
		MAX-ACCESS		read-write
		STATUS			current
		DESCRIPTION
				"TYPE: - Number
				 PAGE: - Audio- Mix- Mixer 2
					Gain1  cmdID= 3364  min= -71  max= 0  step= 1  format= %0.0fdB  div_scale= 1 
					Min = -71dB  Max = 0dB  Step = 1dB "
		::= { iqdly01CmdEntry 3364 }


	iqdly01Mixer2Mix2Source2 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 2- Mix2 Source2
					Mix2 Source2  cmdID= 3445 
					AES 1L  value= 0  
					AES 1R  value= 1  
					AES 2L  value= 2  
					AES 2R  value= 3  
					AES 3L  value= 4  
					AES 3R  value= 5  
					AES 4L  value= 6  
					AES 4R  value= 7  "
		::= { iqdly01CmdEntry 3445 }


	iqdly01MixMixer2Gain2 OBJECT-TYPE
		SYNTAX		INTEGER
		MAX-ACCESS		read-write
		STATUS			current
		DESCRIPTION
				"TYPE: - Number
				 PAGE: - Audio- Mix- Mixer 2
					Gain2  cmdID= 3365  min= -71  max= 0  step= 1  format= %0.0fdB  div_scale= 1 
					Min = -71dB  Max = 0dB  Step = 1dB "
		::= { iqdly01CmdEntry 3365 }


	iqdly01Mixer2Mix2Source3 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 2- Mix2 Source3
					Mix2 Source3  cmdID= 3446 
					AES 1L  value= 0  
					AES 1R  value= 1  
					AES 2L  value= 2  
					AES 2R  value= 3  
					AES 3L  value= 4  
					AES 3R  value= 5  
					AES 4L  value= 6  
					AES 4R  value= 7  "
		::= { iqdly01CmdEntry 3446 }


	iqdly01MixMixer2Gain3 OBJECT-TYPE
		SYNTAX		INTEGER
		MAX-ACCESS		read-write
		STATUS			current
		DESCRIPTION
				"TYPE: - Number
				 PAGE: - Audio- Mix- Mixer 2
					Gain3  cmdID= 3366  min= -71  max= 0  step= 1  format= %0.0fdB  div_scale= 1 
					Min = -71dB  Max = 0dB  Step = 1dB "
		::= { iqdly01CmdEntry 3366 }


	iqdly01Mixer2Mix2Source4 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 2- Mix2 Source4
					Mix2 Source4  cmdID= 3447 
					AES 1L  value= 0  
					AES 1R  value= 1  
					AES 2L  value= 2  
					AES 2R  value= 3  
					AES 3L  value= 4  
					AES 3R  value= 5  
					AES 4L  value= 6  
					AES 4R  value= 7  "
		::= { iqdly01CmdEntry 3447 }


	iqdly01MixMixer2Gain4 OBJECT-TYPE
		SYNTAX		INTEGER
		MAX-ACCESS		read-write
		STATUS			current
		DESCRIPTION
				"TYPE: - Number
				 PAGE: - Audio- Mix- Mixer 2
					Gain4  cmdID= 3367  min= -71  max= 0  step= 1  format= %0.0fdB  div_scale= 1 
					Min = -71dB  Max = 0dB  Step = 1dB "
		::= { iqdly01CmdEntry 3367 }


	iqdly01Mixer3Mix3Source1 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 3- Mix3 Source1
					Mix3 Source1  cmdID= 3448 
					AES 1L  value= 0  
					AES 1R  value= 1  
					AES 2L  value= 2  
					AES 2R  value= 3  
					AES 3L  value= 4  
					AES 3R  value= 5  
					AES 4L  value= 6  
					AES 4R  value= 7  "
		::= { iqdly01CmdEntry 3448 }


	iqdly01MixMixer3Gain1 OBJECT-TYPE
		SYNTAX		INTEGER
		MAX-ACCESS		read-write
		STATUS			current
		DESCRIPTION
				"TYPE: - Number
				 PAGE: - Audio- Mix- Mixer 3
					Gain1  cmdID= 3368  min= -71  max= 0  step= 1  format= %0.0fdB  div_scale= 1 
					Min = -71dB  Max = 0dB  Step = 1dB "
		::= { iqdly01CmdEntry 3368 }


	iqdly01Mixer3Mix3Source2 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 3- Mix3 Source2
					Mix3 Source2  cmdID= 3449 
					AES 1L  value= 0  
					AES 1R  value= 1  
					AES 2L  value= 2  
					AES 2R  value= 3  
					AES 3L  value= 4  
					AES 3R  value= 5  
					AES 4L  value= 6  
					AES 4R  value= 7  "
		::= { iqdly01CmdEntry 3449 }


	iqdly01MixMixer3Gain2 OBJECT-TYPE
		SYNTAX		INTEGER
		MAX-ACCESS		read-write
		STATUS			current
		DESCRIPTION
				"TYPE: - Number
				 PAGE: - Audio- Mix- Mixer 3
					Gain2  cmdID= 3369  min= -71  max= 0  step= 1  format= %0.0fdB  div_scale= 1 
					Min = -71dB  Max = 0dB  Step = 1dB "
		::= { iqdly01CmdEntry 3369 }


	iqdly01Mixer3Mix3Source3 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 3- Mix3 Source3
					Mix3 Source3  cmdID= 3450 
					AES 1L  value= 0  
					AES 1R  value= 1  
					AES 2L  value= 2  
					AES 2R  value= 3  
					AES 3L  value= 4  
					AES 3R  value= 5  
					AES 4L  value= 6  
					AES 4R  value= 7  "
		::= { iqdly01CmdEntry 3450 }


	iqdly01MixMixer3Gain3 OBJECT-TYPE
		SYNTAX		INTEGER
		MAX-ACCESS		read-write
		STATUS			current
		DESCRIPTION
				"TYPE: - Number
				 PAGE: - Audio- Mix- Mixer 3
					Gain3  cmdID= 3370  min= -71  max= 0  step= 1  format= %0.0fdB  div_scale= 1 
					Min = -71dB  Max = 0dB  Step = 1dB "
		::= { iqdly01CmdEntry 3370 }


	iqdly01Mixer3Mix3Source4 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 3- Mix3 Source4
					Mix3 Source4  cmdID= 3451 
					AES 1L  value= 0  
					AES 1R  value= 1  
					AES 2L  value= 2  
					AES 2R  value= 3  
					AES 3L  value= 4  
					AES 3R  value= 5  
					AES 4L  value= 6  
					AES 4R  value= 7  "
		::= { iqdly01CmdEntry 3451 }


	iqdly01MixMixer3Gain4 OBJECT-TYPE
		SYNTAX		INTEGER
		MAX-ACCESS		read-write
		STATUS			current
		DESCRIPTION
				"TYPE: - Number
				 PAGE: - Audio- Mix- Mixer 3
					Gain4  cmdID= 3371  min= -71  max= 0  step= 1  format= %0.0fdB  div_scale= 1 
					Min = -71dB  Max = 0dB  Step = 1dB "
		::= { iqdly01CmdEntry 3371 }


	iqdly01Mixer4Mix4Source1 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 4- Mix4 Source1
					Mix4 Source1  cmdID= 3452 
					AES 1L  value= 0  
					AES 1R  value= 1  
					AES 2L  value= 2  
					AES 2R  value= 3  
					AES 3L  value= 4  
					AES 3R  value= 5  
					AES 4L  value= 6  
					AES 4R  value= 7  "
		::= { iqdly01CmdEntry 3452 }


	iqdly01MixMixer4Gain1 OBJECT-TYPE
		SYNTAX		INTEGER
		MAX-ACCESS		read-write
		STATUS			current
		DESCRIPTION
				"TYPE: - Number
				 PAGE: - Audio- Mix- Mixer 4
					Gain1  cmdID= 3372  min= -71  max= 0  step= 1  format= %0.0fdB  div_scale= 1 
					Min = -71dB  Max = 0dB  Step = 1dB "
		::= { iqdly01CmdEntry 3372 }


	iqdly01Mixer4Mix4Source2 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 4- Mix4 Source2
					Mix4 Source2  cmdID= 3453 
					AES 1L  value= 0  
					AES 1R  value= 1  
					AES 2L  value= 2  
					AES 2R  value= 3  
					AES 3L  value= 4  
					AES 3R  value= 5  
					AES 4L  value= 6  
					AES 4R  value= 7  "
		::= { iqdly01CmdEntry 3453 }


	iqdly01MixMixer4Gain2 OBJECT-TYPE
		SYNTAX		INTEGER
		MAX-ACCESS		read-write
		STATUS			current
		DESCRIPTION
				"TYPE: - Number
				 PAGE: - Audio- Mix- Mixer 4
					Gain2  cmdID= 3373  min= -71  max= 0  step= 1  format= %0.0fdB  div_scale= 1 
					Min = -71dB  Max = 0dB  Step = 1dB "
		::= { iqdly01CmdEntry 3373 }


	iqdly01Mixer4Mix4Source3 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 4- Mix4 Source3
					Mix4 Source3  cmdID= 3454 
					AES 1L  value= 0  
					AES 1R  value= 1  
					AES 2L  value= 2  
					AES 2R  value= 3  
					AES 3L  value= 4  
					AES 3R  value= 5  
					AES 4L  value= 6  
					AES 4R  value= 7  "
		::= { iqdly01CmdEntry 3454 }


	iqdly01MixMixer4Gain3 OBJECT-TYPE
		SYNTAX		INTEGER
		MAX-ACCESS		read-write
		STATUS			current
		DESCRIPTION
				"TYPE: - Number
				 PAGE: - Audio- Mix- Mixer 4
					Gain3  cmdID= 3374  min= -71  max= 0  step= 1  format= %0.0fdB  div_scale= 1 
					Min = -71dB  Max = 0dB  Step = 1dB "
		::= { iqdly01CmdEntry 3374 }


	iqdly01Mixer4Mix4Source4 OBJECT-TYPE
		SYNTAX		INTEGER {
							val_AES_1L(0),
							val_AES_1R(1),
							val_AES_2L(2),
							val_AES_2R(3),
							val_AES_3L(4),
							val_AES_3R(5),
							val_AES_4L(6),
							val_AES_4R(7)
							}
		MAX-ACCESS		read-write
		STATUS			current
		DESCRIPTION
				"TYPE: - RadiobuttonList
				 PAGE: - Audio- Mix- Mixer 4- Mix4 Source4
					Mix4 Source4  cmdID= 3455 
					AES 1L  value= 0  
					AES 1R  value= 1  
					AES 2L  value= 2  
					AES 2R  value= 3  
					AES 3L  value= 4  
					AES 3R  value= 5  
					AES 4L  value= 6  
					AES 4R  value= 7  "
		::= { iqdly01CmdEntry 3455 }


	iqdly01MixMixer4Gain4 OBJECT-TYPE
		SYNTAX		INTEGER
		MAX-ACCESS		read-write
		STATUS			current
		DESCRIPTION
				"TYPE: - Number
				 PAGE: - Audio- Mix- Mixer 4
					Gain4  cmdID= 3375  min= -71  max= 0  step= 1  format= %0.0fdB  div_scale= 1 
					Min = -71dB  Max = 0dB  Step = 1dB "
		::= { iqdly01CmdEntry 3375 }


	iqdly01BusSourceBusALSource OBJECT-TYPE
		SYNTAX		INTEGER {
							val_AES_1L(0),
							val_AES_1R(1),
							val_AES_2L(2),
							val_AES_2R(3),
							val_AES_3L(4),
							val_AES_3R(5),
							val_AES_4L(6),
							val_AES_4R(7),
							val_MIX_1(8),
							val_MIX_2(9),
							val_MIX_3(10),
							val_MIX_4(11)
							}
		MAX-ACCESS		read-write
		STATUS			current
		DESCRIPTION
				"TYPE: - RadiobuttonList
				 PAGE: - Audio- Buses- Bus Source- BusAL Source
					BusAL Source  cmdID= 3520 
					AES 1L  value= 0  
					AES 1R  value= 1  
					AES 2L  value= 2  
					AES 2R  value= 3  
					AES 3L  value= 4  
					AES 3R  value= 5  
					AES 4L  value= 6  
					AES 4R  value= 7  
					MIX 1  value= 8  
					MIX 2  value= 9  
					MIX 3  value= 10  
					MIX 4  value= 11  "
		::= { iqdly01CmdEntry 3520 }


	iqdly01BusSourceBusARSource OBJECT-TYPE
		SYNTAX		INTEGER {
							val_AES_1L(0),
							val_AES_1R(1),
							val_AES_2L(2),
							val_AES_2R(3),
							val_AES_3L(4),
							val_AES_3R(5),
							val_AES_4L(6),
							val_AES_4R(7),
							val_MIX_1(8),
							val_MIX_2(9),
							val_MIX_3(10),
							val_MIX_4(11)
							}
		MAX-ACCESS		read-write
		STATUS			current
		DESCRIPTION
				"TYPE: - RadiobuttonList
				 PAGE: - Audio- Buses- Bus Source- BusAR Source
					BusAR Source  cmdID= 3521 
					AES 1L  value= 0  
					AES 1R  value= 1  
					AES 2L  value= 2  
					AES 2R  value= 3  
					AES 3L  value= 4  
					AES 3R  value= 5  
					AES 4L  value= 6  
					AES 4R  value= 7  
					MIX 1  value= 8  
					MIX 2  value= 9  
					MIX 3  value= 10  
					MIX 4  value= 11  "
		::= { iqdly01CmdEntry 3521 }


	iqdly01BusSourceBusBLSource OBJECT-TYPE
		SYNTAX		INTEGER {
							val_AES_1L(0),
							val_AES_1R(1),
							val_AES_2L(2),
							val_AES_2R(3),
							val_AES_3L(4),
							val_AES_3R(5),
							val_AES_4L(6),
							val_AES_4R(7),
							val_MIX_1(8),
							val_MIX_2(9),
							val_MIX_3(10),
							val_MIX_4(11)
							}
		MAX-ACCESS		read-write
		STATUS			current
		DESCRIPTION
				"TYPE: - RadiobuttonList
				 PAGE: - Audio- Buses- Bus Source- BusBL Source
					BusBL Source  cmdID= 3522 
					AES 1L  value= 0  
					AES 1R  value= 1  
					AES 2L  value= 2  
					AES 2R  value= 3  
					AES 3L  value= 4  
					AES 3R  value= 5  
					AES 4L  value= 6  
					AES 4R  value= 7  
					MIX 1  value= 8  
					MIX 2  value= 9  
					MIX 3  value= 10  
					MIX 4  value= 11  "
		::= { iqdly01CmdEntry 3522 }


	iqdly01BusSourceBusBRSource OBJECT-TYPE
		SYNTAX		INTEGER {
							val_AES_1L(0),
							val_AES_1R(1),
							val_AES_2L(2),
							val_AES_2R(3),
							val_AES_3L(4),
							val_AES_3R(5),
							val_AES_4L(6),
							val_AES_4R(7),
							val_MIX_1(8),
							val_MIX_2(9),
							val_MIX_3(10),
							val_MIX_4(11)
							}
		MAX-ACCESS		read-write
		STATUS			current
		DESCRIPTION
				"TYPE: - RadiobuttonList
				 PAGE: - Audio- Buses- Bus Source- BusBR Source
					BusBR Source  cmdID= 3523 
					AES 1L  value= 0  
					AES 1R  value= 1  
					AES 2L  value= 2  
					AES 2R  value= 3  
					AES 3L  value= 4  
					AES 3R  value= 5  
					AES 4L  value= 6  
					AES 4R  value= 7  
					MIX 1  value= 8  
					MIX 2  value= 9  
					MIX 3  value= 10  
					MIX 4  value= 11  "
		::= { iqdly01CmdEntry 3523 }


	iqdly01BusSourceBusCLSource OBJECT-TYPE
		SYNTAX		INTEGER {
							val_AES_1L(0),
							val_AES_1R(1),
							val_AES_2L(2),
							val_AES_2R(3),
							val_AES_3L(4),
							val_AES_3R(5),
							val_AES_4L(6),
							val_AES_4R(7),
							val_MIX_1(8),
							val_MIX_2(9),
							val_MIX_3(10),
							val_MIX_4(11)
							}
		MAX-ACCESS		read-write
		STATUS			current
		DESCRIPTION
				"TYPE: - RadiobuttonList
				 PAGE: - Audio- Buses- Bus Source- BusCL Source
					BusCL Source  cmdID= 3524 
					AES 1L  value= 0  
					AES 1R  value= 1  
					AES 2L  value= 2  
					AES 2R  value= 3  
					AES 3L  value= 4  
					AES 3R  value= 5  
					AES 4L  value= 6  
					AES 4R  value= 7  
					MIX 1  value= 8  
					MIX 2  value= 9  
					MIX 3  value= 10  
					MIX 4  value= 11  "
		::= { iqdly01CmdEntry 3524 }


	iqdly01BusSourceBusCRSource OBJECT-TYPE
		SYNTAX		INTEGER {
							val_AES_1L(0),
							val_AES_1R(1),
							val_AES_2L(2),
							val_AES_2R(3),
							val_AES_3L(4),
							val_AES_3R(5),
							val_AES_4L(6),
							val_AES_4R(7),
							val_MIX_1(8),
							val_MIX_2(9),
							val_MIX_3(10),
							val_MIX_4(11)
							}
		MAX-ACCESS		read-write
		STATUS			current
		DESCRIPTION
				"TYPE: - RadiobuttonList
				 PAGE: - Audio- Buses- Bus Source- BusCR Source
					BusCR Source  cmdID= 3525 
					AES 1L  value= 0  
					AES 1R  value= 1  
					AES 2L  value= 2  
					AES 2R  value= 3  
					AES 3L  value= 4  
					AES 3R  value= 5  
					AES 4L  value= 6  
					AES 4R  value= 7  
					MIX 1  value= 8  
					MIX 2  value= 9  
					MIX 3  value= 10  
					MIX 4  value= 11  "
		::= { iqdly01CmdEntry 3525 }


	iqdly01BusSourceBusDLSource OBJECT-TYPE
		SYNTAX		INTEGER {
							val_AES_1L(0),
							val_AES_1R(1),
							val_AES_2L(2),
							val_AES_2R(3),
							val_AES_3L(4),
							val_AES_3R(5),
							val_AES_4L(6),
							val_AES_4R(7),
							val_MIX_1(8),
							val_MIX_2(9),
							val_MIX_3(10),
							val_MIX_4(11)
							}
		MAX-ACCESS		read-write
		STATUS			current
		DESCRIPTION
				"TYPE: - RadiobuttonList
				 PAGE: - Audio- Buses- Bus Source- BusDL Source
					BusDL Source  cmdID= 3526 
					AES 1L  value= 0  
					AES 1R  value= 1  
					AES 2L  value= 2  
					AES 2R  value= 3  
					AES 3L  value= 4  
					AES 3R  value= 5  
					AES 4L  value= 6  
					AES 4R  value= 7  
					MIX 1  value= 8  
					MIX 2  value= 9  
					MIX 3  value= 10  
					MIX 4  value= 11  "
		::= { iqdly01CmdEntry 3526 }


	iqdly01BusSourceBusDRSource OBJECT-TYPE
		SYNTAX		INTEGER {
							val_AES_1L(0),
							val_AES_1R(1),
							val_AES_2L(2),
							val_AES_2R(3),
							val_AES_3L(4),
							val_AES_3R(5),
							val_AES_4L(6),
							val_AES_4R(7),
							val_MIX_1(8),
							val_MIX_2(9),
							val_MIX_3(10),
							val_MIX_4(11)
							}
		MAX-ACCESS		read-write
		STATUS			current
		DESCRIPTION
				"TYPE: - RadiobuttonList
				 PAGE: - Audio- Buses- Bus Source- BusDR Source
					BusDR Source  cmdID= 3527 
					AES 1L  value= 0  
					AES 1R  value= 1  
					AES 2L  value= 2  
					AES 2R  value= 3  
					AES 3L  value= 4  
					AES 3R  value= 5  
					AES 4L  value= 6  
					AES 4R  value= 7  
					MIX 1  value= 8  
					MIX 2  value= 9  
					MIX 3  value= 10  
					MIX 4  value= 11  "
		::= { iqdly01CmdEntry 3527 }


	iqdly01BusesBusProcAmpStereoA OBJECT-TYPE
		SYNTAX		INTEGER { disable(0), enable(1) }
		MAX-ACCESS		read-write
		STATUS			current
		DESCRIPTION
				"TYPE: - Checkbox
				 PAGE: - Audio- Buses
					Stereo A  cmdID= 3320 "
		::= { iqdly01CmdEntry 3320 }


	iqdly01BusProcAmpBusALGainBusAL OBJECT-TYPE
		SYNTAX		INTEGER
		MAX-ACCESS		read-write
		STATUS			current
		DESCRIPTION
				"TYPE: - Number
				 PAGE: - Audio- Buses
					Gain Bus AL  cmdID= 3080  min= -180  max= 180  step= 1  format= %0.1fdB  div_scale= 10 
					Min = -18.0dB  Max = 18.0dB  Step = 0.1dB "
		::= { iqdly01CmdEntry 3080 }


	iqdly01BusProcAmpBusALInvert OBJECT-TYPE
		SYNTAX		INTEGER { disable(0), enable(1) }
		MAX-ACCESS		read-write
		STATUS			current
		DESCRIPTION
				"TYPE: - Checkbox
				 PAGE: - Audio- Buses
					Invert  cmdID= 3160 "
		::= { iqdly01CmdEntry 3160 }


	iqdly01BusProcAmpBusALMute OBJECT-TYPE
		SYNTAX		INTEGER { disable(0), enable(1) }
		MAX-ACCESS		read-write
		STATUS			current
		DESCRIPTION
				"TYPE: - Checkbox
				 PAGE: - Audio- Buses
					Mute  cmdID= 3240 "
		::= { iqdly01CmdEntry 3240 }


	iqdly01BusProcAmpBusARGainBusAR OBJECT-TYPE
		SYNTAX		INTEGER
		MAX-ACCESS		read-write
		STATUS			current
		DESCRIPTION
				"TYPE: - Number
				 PAGE: - Audio- Buses
					Gain Bus AR  cmdID= 3081  min= -180  max= 180  step= 1  format= %0.1fdB  div_scale= 10 
					Min = -18.0dB  Max = 18.0dB  Step = 0.1dB "
		::= { iqdly01CmdEntry 3081 }


	iqdly01BusProcAmpBusARInvert OBJECT-TYPE
		SYNTAX		INTEGER { disable(0), enable(1) }
		MAX-ACCESS		read-write
		STATUS			current
		DESCRIPTION
				"TYPE: - Checkbox
				 PAGE: - Audio- Buses
					Invert  cmdID= 3161 "
		::= { iqdly01CmdEntry 3161 }


	iqdly01BusProcAmpBusARMute OBJECT-TYPE
		SYNTAX		INTEGER { disable(0), enable(1) }
		MAX-ACCESS		read-write
		STATUS			current
		DESCRIPTION
				"TYPE: - Checkbox
				 PAGE: - Audio- Buses
					Mute  cmdID= 3241 "
		::= { iqdly01CmdEntry 3241 }


	iqdly01BusesBusProcAmpStereoB OBJECT-TYPE
		SYNTAX		INTEGER { disable(0), enable(1) }
		MAX-ACCESS		read-write
		STATUS			current
		DESCRIPTION
				"TYPE: - Checkbox
				 PAGE: - Audio- Buses
					Stereo B  cmdID= 3321 "
		::= { iqdly01CmdEntry 3321 }


	iqdly01BusProcAmpBusBLGainBusBL OBJECT-TYPE
		SYNTAX		INTEGER
		MAX-ACCESS		read-write
		STATUS			current
		DESCRIPTION
				"TYPE: - Number
				 PAGE: - Audio- Buses
					Gain Bus BL  cmdID= 3082  min= -180  max= 180  step= 1  format= %0.1fdB  div_scale= 10 
					Min = -18.0dB  Max = 18.0dB  Step = 0.1dB "
		::= { iqdly01CmdEntry 3082 }


	iqdly01BusProcAmpBusBLInvert OBJECT-TYPE
		SYNTAX		INTEGER { disable(0), enable(1) }
		MAX-ACCESS		read-write
		STATUS			current
		DESCRIPTION
				"TYPE: - Checkbox
				 PAGE: - Audio- Buses
					Invert  cmdID= 3162 "
		::= { iqdly01CmdEntry 3162 }


	iqdly01BusProcAmpBusBLMute OBJECT-TYPE
		SYNTAX		INTEGER { disable(0), enable(1) }
		MAX-ACCESS		read-write
		STATUS			current
		DESCRIPTION
				"TYPE: - Checkbox
				 PAGE: - Audio- Buses
					Mute  cmdID= 3242 "
		::= { iqdly01CmdEntry 3242 }


	iqdly01BusProcAmpBusBRGainBusBR OBJECT-TYPE
		SYNTAX		INTEGER
		MAX-ACCESS		read-write
		STATUS			current
		DESCRIPTION
				"TYPE: - Number
				 PAGE: - Audio- Buses
					Gain Bus BR  cmdID= 3083  min= -180  max= 180  step= 1  format= %0.1fdB  div_scale= 10 
					Min = -18.0dB  Max = 18.0dB  Step = 0.1dB "
		::= { iqdly01CmdEntry 3083 }


	iqdly01BusProcAmpBusBRInvert OBJECT-TYPE
		SYNTAX		INTEGER { disable(0), enable(1) }
		MAX-ACCESS		read-write
		STATUS			current
		DESCRIPTION
				"TYPE: - Checkbox
				 PAGE: - Audio- Buses
					Invert  cmdID= 3163 "
		::= { iqdly01CmdEntry 3163 }


	iqdly01BusProcAmpBusBRMute OBJECT-TYPE
		SYNTAX		INTEGER { disable(0), enable(1) }
		MAX-ACCESS		read-write
		STATUS			current
		DESCRIPTION
				"TYPE: - Checkbox
				 PAGE: - Audio- Buses
					Mute  cmdID= 3243 "
		::= { iqdly01CmdEntry 3243 }


	iqdly01BusesBusProcAmpStereoC OBJECT-TYPE
		SYNTAX		INTEGER { disable(0), enable(1) }
		MAX-ACCESS		read-write
		STATUS			current
		DESCRIPTION
				"TYPE: - Checkbox
				 PAGE: - Audio- Buses
					Stereo C  cmdID= 3322 "
		::= { iqdly01CmdEntry 3322 }


	iqdly01BusProcAmpBusCLGainBusCL OBJECT-TYPE
		SYNTAX		INTEGER
		MAX-ACCESS		read-write
		STATUS			current
		DESCRIPTION
				"TYPE: - Number
				 PAGE: - Audio- Buses
					Gain Bus CL  cmdID= 3084  min= -180  max= 180  step= 1  format= %0.1fdB  div_scale= 10 
					Min = -18.0dB  Max = 18.0dB  Step = 0.1dB "
		::= { iqdly01CmdEntry 3084 }


	iqdly01BusProcAmpBusCLInvert OBJECT-TYPE
		SYNTAX		INTEGER { disable(0), enable(1) }
		MAX-ACCESS		read-write
		STATUS			current
		DESCRIPTION
				"TYPE: - Checkbox
				 PAGE: - Audio- Buses
					Invert  cmdID= 3164 "
		::= { iqdly01CmdEntry 3164 }


	iqdly01BusProcAmpBusCLMute OBJECT-TYPE
		SYNTAX		INTEGER { disable(0), enable(1) }
		MAX-ACCESS		read-write
		STATUS			current
		DESCRIPTION
				"TYPE: - Checkbox
				 PAGE: - Audio- Buses
					Mute  cmdID= 3244 "
		::= { iqdly01CmdEntry 3244 }


	iqdly01BusProcAmpBusCRGainBusCR OBJECT-TYPE
		SYNTAX		INTEGER
		MAX-ACCESS		read-write
		STATUS			current
		DESCRIPTION
				"TYPE: - Number
				 PAGE: - Audio- Buses
					Gain Bus CR  cmdID= 3085  min= -180  max= 180  step= 1  format= %0.1fdB  div_scale= 10 
					Min = -18.0dB  Max = 18.0dB  Step = 0.1dB "
		::= { iqdly01CmdEntry 3085 }


	iqdly01BusProcAmpBusCRInvert OBJECT-TYPE
		SYNTAX		INTEGER { disable(0), enable(1) }
		MAX-ACCESS		read-write
		STATUS			current
		DESCRIPTION
				"TYPE: - Checkbox
				 PAGE: - Audio- Buses
					Invert  cmdID= 3165 "
		::= { iqdly01CmdEntry 3165 }


	iqdly01BusProcAmpBusCRMute OBJECT-TYPE
		SYNTAX		INTEGER { disable(0), enable(1) }
		MAX-ACCESS		read-write
		STATUS			current
		DESCRIPTION
				"TYPE: - Checkbox
				 PAGE: - Audio- Buses
					Mute  cmdID= 3245 "
		::= { iqdly01CmdEntry 3245 }


	iqdly01BusesBusProcAmpStereoD OBJECT-TYPE
		SYNTAX		INTEGER { disable(0), enable(1) }
		MAX-ACCESS		read-write
		STATUS			current
		DESCRIPTION
				"TYPE: - Checkbox
				 PAGE: - Audio- Buses
					Stereo D  cmdID= 3323 "
		::= { iqdly01CmdEntry 3323 }


	iqdly01BusProcAmpBusDLGainBusDL OBJECT-TYPE
		SYNTAX		INTEGER
		MAX-ACCESS		read-write
		STATUS			current
		DESCRIPTION
				"TYPE: - Number
				 PAGE: - Audio- Buses
					Gain Bus DL  cmdID= 3086  min= -180  max= 180  step= 1  format= %0.1fdB  div_scale= 10 
					Min = -18.0dB  Max = 18.0dB  Step = 0.1dB "
		::= { iqdly01CmdEntry 3086 }


	iqdly01BusProcAmpBusDLInvert OBJECT-TYPE
		SYNTAX		INTEGER { disable(0), enable(1) }
		MAX-ACCESS		read-write
		STATUS			current
		DESCRIPTION
				"TYPE: - Checkbox
				 PAGE: - Audio- Buses
					Invert  cmdID= 3166 "
		::= { iqdly01CmdEntry 3166 }


	iqdly01BusProcAmpBusDLMute OBJECT-TYPE
		SYNTAX		INTEGER { disable(0), enable(1) }
		MAX-ACCESS		read-write
		STATUS			current
		DESCRIPTION
				"TYPE: - Checkbox
				 PAGE: - Audio- Buses
					Mute  cmdID= 3246 "
		::= { iqdly01CmdEntry 3246 }


	iqdly01BusProcAmpBusDRGainBusDR OBJECT-TYPE
		SYNTAX		INTEGER
		MAX-ACCESS		read-write
		STATUS			current
		DESCRIPTION
				"TYPE: - Number
				 PAGE: - Audio- Buses
					Gain Bus DR  cmdID= 3087  min= -180  max= 180  step= 1  format= %0.1fdB  div_scale= 10 
					Min = -18.0dB  Max = 18.0dB  Step = 0.1dB "
		::= { iqdly01CmdEntry 3087 }


	iqdly01BusProcAmpBusDRInvert OBJECT-TYPE
		SYNTAX		INTEGER { disable(0), enable(1) }
		MAX-ACCESS		read-write
		STATUS			current
		DESCRIPTION
				"TYPE: - Checkbox
				 PAGE: - Audio- Buses
					Invert  cmdID= 3167 "
		::= { iqdly01CmdEntry 3167 }


	iqdly01BusProcAmpBusDRMute OBJECT-TYPE
		SYNTAX		INTEGER { disable(0), enable(1) }
		MAX-ACCESS		read-write
		STATUS			current
		DESCRIPTION
				"TYPE: - Checkbox
				 PAGE: - Audio- Buses
					Mute  cmdID= 3247 "
		::= { iqdly01CmdEntry 3247 }


	iqdly01AudioDelayAESInput1Delay OBJECT-TYPE
		SYNTAX		INTEGER
		MAX-ACCESS		read-write
		STATUS			current
		DESCRIPTION
				"TYPE: - Number
				 PAGE: - Audio- Delay
					AES Input 1 Delay  cmdID= 2928  min= 0  max= 1500  step= 1  format= %0.0f ms  div_scale= 1 
					Min = 0 ms  Max = 1500 ms  Step = 1 ms "
		::= { iqdly01CmdEntry 2928 }


	iqdly01AudioDelayAESInput2Delay OBJECT-TYPE
		SYNTAX		INTEGER
		MAX-ACCESS		read-write
		STATUS			current
		DESCRIPTION
				"TYPE: - Number
				 PAGE: - Audio- Delay
					AES Input 2 Delay  cmdID= 2929  min= 0  max= 1500  step= 1  format= %0.0f ms  div_scale= 1 
					Min = 0 ms  Max = 1500 ms  Step = 1 ms "
		::= { iqdly01CmdEntry 2929 }


	iqdly01AudioDelayAESInput3Delay OBJECT-TYPE
		SYNTAX		INTEGER
		MAX-ACCESS		read-write
		STATUS			current
		DESCRIPTION
				"TYPE: - Number
				 PAGE: - Audio- Delay
					AES Input 3 Delay  cmdID= 2930  min= 0  max= 1500  step= 1  format= %0.0f ms  div_scale= 1 
					Min = 0 ms  Max = 1500 ms  Step = 1 ms "
		::= { iqdly01CmdEntry 2930 }


	iqdly01AudioDelayAESInput4Delay OBJECT-TYPE
		SYNTAX		INTEGER
		MAX-ACCESS		read-write
		STATUS			current
		DESCRIPTION
				"TYPE: - Number
				 PAGE: - Audio- Delay
					AES Input 4 Delay  cmdID= 2931  min= 0  max= 1500  step= 1  format= %0.0f ms  div_scale= 1 
					Min = 0 ms  Max = 1500 ms  Step = 1 ms "
		::= { iqdly01CmdEntry 2931 }


	iqdly01DelayDelaySelectManual OBJECT-TYPE
		SYNTAX		INTEGER { disable(0), enable(1) }
		MAX-ACCESS		read-write
		STATUS			current
		DESCRIPTION
				"TYPE: - Checkbox
				 PAGE: - Audio- Delay
					Manual  cmdID= 2568 "
		::= { iqdly01CmdEntry 2568 }


	iqdly01DelayDelaySelectRolltrack14 OBJECT-TYPE
		SYNTAX		INTEGER { disable(0), enable(1) }
		MAX-ACCESS		read-write
		STATUS			current
		DESCRIPTION
				"TYPE: - Checkbox
				 PAGE: - Audio- Delay
					Rolltrack 14  cmdID= 2569 "
		::= { iqdly01CmdEntry 2569 }


	iqdly01DelayDelaySelectRolltrack15 OBJECT-TYPE
		SYNTAX		INTEGER { disable(0), enable(1) }
		MAX-ACCESS		read-write
		STATUS			current
		DESCRIPTION
				"TYPE: - Checkbox
				 PAGE: - Audio- Delay
					Rolltrack 15  cmdID= 2570 "
		::= { iqdly01CmdEntry 2570 }


	iqdly01DelayDelaySelectRolltrack16 OBJECT-TYPE
		SYNTAX		INTEGER { disable(0), enable(1) }
		MAX-ACCESS		read-write
		STATUS			current
		DESCRIPTION
				"TYPE: - Checkbox
				 PAGE: - Audio- Delay
					Rolltrack 16  cmdID= 2571 "
		::= { iqdly01CmdEntry 2571 }


	iqdly01DelayDelaySelectRolltrack17 OBJECT-TYPE
		SYNTAX		INTEGER { disable(0), enable(1) }
		MAX-ACCESS		read-write
		STATUS			current
		DESCRIPTION
				"TYPE: - Checkbox
				 PAGE: - Audio- Delay
					Rolltrack 17  cmdID= 2572 "
		::= { iqdly01CmdEntry 2572 }


	iqdly01DelayDelaySelectGPIDelaySelect OBJECT-TYPE
		SYNTAX		INTEGER { disable(0), enable(1) }
		MAX-ACCESS		read-write
		STATUS			current
		DESCRIPTION
				"TYPE: - Checkbox
				 PAGE: - Audio- Delay
					GPI Delay Select  cmdID= 3051 "
		::= { iqdly01CmdEntry 3051 }


	iqdly01DelayDelayStatus OBJECT-TYPE
		SYNTAX		INTEGER
		MAX-ACCESS		read-write
		STATUS			current
		DESCRIPTION
				"TYPE: - Number
				 PAGE: - Audio- Delay
					Manual Delay  cmdID= 2573  min= -40  max= 1500  step= 1  format= %3.0f ms  div_scale= 1 
					Manual  cmdID= 2573  format=   
					Min = -40 ms  Max = 1500 ms  Step =   1 ms "
		::= { iqdly01CmdEntry 2573 }


	iqdly01DelayDelayStatusRolltrack14 OBJECT-TYPE
		SYNTAX		RollCallString
		MAX-ACCESS		read-only
		STATUS			current
		DESCRIPTION
				"TYPE: - Display
				 PAGE: - Audio- Delay
					Rolltrack 14  cmdID= 14  format=   "
		::= { iqdly01CmdEntry 14 }


	iqdly01DelayDelayStatusRolltrack15 OBJECT-TYPE
		SYNTAX		RollCallString
		MAX-ACCESS		read-only
		STATUS			current
		DESCRIPTION
				"TYPE: - Display
				 PAGE: - Audio- Delay
					Rolltrack 15  cmdID= 15  format=   "
		::= { iqdly01CmdEntry 15 }


	iqdly01DelayDelayStatusRolltrack16 OBJECT-TYPE
		SYNTAX		RollCallString
		MAX-ACCESS		read-only
		STATUS			current
		DESCRIPTION
				"TYPE: - Display
				 PAGE: - Audio- Delay
					Rolltrack 16  cmdID= 16  format=   "
		::= { iqdly01CmdEntry 16 }


	iqdly01DelayDelayStatusRolltrack17 OBJECT-TYPE
		SYNTAX		RollCallString
		MAX-ACCESS		read-only
		STATUS			current
		DESCRIPTION
				"TYPE: - Display
				 PAGE: - Audio- Delay
					Rolltrack 17  cmdID= 17  format=   "
		::= { iqdly01CmdEntry 17 }


	iqdly01DelayDelayStatusGPIDelayDisplay OBJECT-TYPE
		SYNTAX		RollCallString
		MAX-ACCESS		read-only
		STATUS			current
		DESCRIPTION
				"TYPE: - Display
				 PAGE: - Audio- Delay
					GPI Delay Display  cmdID= 3052  format=   "
		::= { iqdly01CmdEntry 3052 }


	iqdly01DelayDelayStatusTotalDelayDisplay OBJECT-TYPE
		SYNTAX		RollCallString
		MAX-ACCESS		read-only
		STATUS			current
		DESCRIPTION
				"TYPE: - Display
				 PAGE: - Audio- Delay
					Total Delay Display  cmdID= 2979  format=   "
		::= { iqdly01CmdEntry 2979 }


	iqdly01AudioMonitorSilenceLevel OBJECT-TYPE
		SYNTAX		INTEGER
		MAX-ACCESS		read-write
		STATUS			current
		DESCRIPTION
				"TYPE: - Number
				 PAGE: - Audio- Monitor
					Silence Level  cmdID= 3056  min= -96  max= 0  step= 1  format= %1.1f dB  div_scale= 1 
					Min = -96.0 dB  Max = 0.0 dB  Step = 1.0 dB "
		::= { iqdly01CmdEntry 3056 }


	iqdly01AudioMonitorLowLevel OBJECT-TYPE
		SYNTAX		INTEGER
		MAX-ACCESS		read-write
		STATUS			current
		DESCRIPTION
				"TYPE: - Number
				 PAGE: - Audio- Monitor
					Low Level  cmdID= 2517  min= -96  max= 0  step= 1  format= %1.1f dB  div_scale= 1 
					Min = -96.0 dB  Max = 0.0 dB  Step = 1.0 dB "
		::= { iqdly01CmdEntry 2517 }


	iqdly01AudioMonitorHighLevel OBJECT-TYPE
		SYNTAX		INTEGER
		MAX-ACCESS		read-write
		STATUS			current
		DESCRIPTION
				"TYPE: - Number
				 PAGE: - Audio- Monitor
					High Level  cmdID= 3057  min= -96  max= 0  step= 1  format= %1.1f dB  div_scale= 1 
					Min = -96.0 dB  Max = 0.0 dB  Step = 1.0 dB "
		::= { iqdly01CmdEntry 3057 }


	iqdly01AudioMonitorOverloadLevel OBJECT-TYPE
		SYNTAX		INTEGER
		MAX-ACCESS		read-write
		STATUS			current
		DESCRIPTION
				"TYPE: - Number
				 PAGE: - Audio- Monitor
					Overload Level  cmdID= 3058  min= -96  max= 0  step= 1  format= %1.1f dB  div_scale= 1 
					Min = -96.0 dB  Max = 0.0 dB  Step = 1.0 dB "
		::= { iqdly01CmdEntry 3058 }


	iqdly01AudioMonitorWarningTimer OBJECT-TYPE
		SYNTAX		INTEGER
		MAX-ACCESS		read-write
		STATUS			current
		DESCRIPTION
				"TYPE: - Number
				 PAGE: - Audio- Monitor
					Warning Timer  cmdID= 2518  min= 1  max= 20  step= 1  format= %1.0f sec  div_scale= 1 
					Min = 1 sec  Max = 20 sec  Step = 1 sec "
		::= { iqdly01CmdEntry 2518 }


	iqdly01Genlock OBJECT-TYPE
		SYNTAX		INTEGER {
							val_Lock_to_Reference(0),
							val_Lock_to_Input(1),
							val_Free_Run(2)
							}
		MAX-ACCESS		read-write
		STATUS			current
		DESCRIPTION
				"TYPE: - Button
				 PAGE: - Genlock
					Lock to Reference  cmdID= 1049  value= 0  
					Lock to Input  cmdID= 1049  value= 1  
					Free Run  cmdID= 1049  value= 2  "
		::= { iqdly01CmdEntry 1049 }


	iqdly01GenlockFreerunFreq OBJECT-TYPE
		SYNTAX		INTEGER
		MAX-ACCESS		read-write
		STATUS			current
		DESCRIPTION
				"TYPE: - Number
				 PAGE: - Genlock
					Freerun Freq  cmdID= 2449  min= -60  max= 60  step= 1  format=   %.0f  div_scale= 1 
					Min =   -60  Max =   60  Step =   1 "
		::= { iqdly01CmdEntry 2449 }


	iqdly01UserMemMemory1Save1 OBJECT-TYPE
		SYNTAX		INTEGER { noAction(0),val_Save_1(1) }
		MAX-ACCESS		read-write
		STATUS			current
		DESCRIPTION
				"TYPE: - Button
				 PAGE: - User Mem
					Save 1  cmdID= 1600  value= 1  "
		::= { iqdly01CmdEntry 1600 }


	iqdly01UserMemMemory1Recall1 OBJECT-TYPE
		SYNTAX		INTEGER { noAction(0),val_Recall_1(1) }
		MAX-ACCESS		read-write
		STATUS			current
		DESCRIPTION
				"TYPE: - Button
				 PAGE: - User Mem
					Recall 1  cmdID= 1601  value= 1  "
		::= { iqdly01CmdEntry 1601 }


	iqdly01UserMemMemory1Clear1 OBJECT-TYPE
		SYNTAX		INTEGER { noAction(0),val_Clear_1(1) }
		MAX-ACCESS		read-write
		STATUS			current
		DESCRIPTION
				"TYPE: - Button
				 PAGE: - User Mem
					Clear 1  cmdID= 1602  value= 1  "
		::= { iqdly01CmdEntry 1602 }


	iqdly01UserMemMemory1Name1 OBJECT-TYPE
		SYNTAX		RollCallString
		MAX-ACCESS		read-write
		STATUS			current
		DESCRIPTION
				"TYPE: - Editstring
				 PAGE: - User Mem
					Name 1  cmdID= 1603  "
		::= { iqdly01CmdEntry 1603 }


	iqdly01UserMemMemory2Save2 OBJECT-TYPE
		SYNTAX		INTEGER { noAction(0),val_Save_2(1) }
		MAX-ACCESS		read-write
		STATUS			current
		DESCRIPTION
				"TYPE: - Button
				 PAGE: - User Mem
					Save 2  cmdID= 1604  value= 1  "
		::= { iqdly01CmdEntry 1604 }


	iqdly01UserMemMemory2Recall2 OBJECT-TYPE
		SYNTAX		INTEGER { noAction(0),val_Recall_2(1) }
		MAX-ACCESS		read-write
		STATUS			current
		DESCRIPTION
				"TYPE: - Button
				 PAGE: - User Mem
					Recall 2  cmdID= 1605  value= 1  "
		::= { iqdly01CmdEntry 1605 }


	iqdly01UserMemMemory2Clear2 OBJECT-TYPE
		SYNTAX		INTEGER { noAction(0),val_Clear_2(1) }
		MAX-ACCESS		read-write
		STATUS			current
		DESCRIPTION
				"TYPE: - Button
				 PAGE: - User Mem
					Clear 2  cmdID= 1606  value= 1  "
		::= { iqdly01CmdEntry 1606 }


	iqdly01UserMemMemory2Name2 OBJECT-TYPE
		SYNTAX		RollCallString
		MAX-ACCESS		read-write
		STATUS			current
		DESCRIPTION
				"TYPE: - Editstring
				 PAGE: - User Mem
					Name 2  cmdID= 1607  "
		::= { iqdly01CmdEntry 1607 }


	iqdly01UserMemMemory3Save3 OBJECT-TYPE
		SYNTAX		INTEGER { noAction(0),val_Save_3(1) }
		MAX-ACCESS		read-write
		STATUS			current
		DESCRIPTION
				"TYPE: - Button
				 PAGE: - User Mem
					Save 3  cmdID= 1608  value= 1  "
		::= { iqdly01CmdEntry 1608 }


	iqdly01UserMemMemory3Recall3 OBJECT-TYPE
		SYNTAX		INTEGER { noAction(0),val_Recall_3(1) }
		MAX-ACCESS		read-write
		STATUS			current
		DESCRIPTION
				"TYPE: - Button
				 PAGE: - User Mem
					Recall 3  cmdID= 1609  value= 1  "
		::= { iqdly01CmdEntry 1609 }


	iqdly01UserMemMemory3Clear3 OBJECT-TYPE
		SYNTAX		INTEGER { noAction(0),val_Clear_3(1) }
		MAX-ACCESS		read-write
		STATUS			current
		DESCRIPTION
				"TYPE: - Button
				 PAGE: - User Mem
					Clear 3  cmdID= 1610  value= 1  "
		::= { iqdly01CmdEntry 1610 }


	iqdly01UserMemMemory3Name3 OBJECT-TYPE
		SYNTAX		RollCallString
		MAX-ACCESS		read-write
		STATUS			current
		DESCRIPTION
				"TYPE: - Editstring
				 PAGE: - User Mem
					Name 3  cmdID= 1611  "
		::= { iqdly01CmdEntry 1611 }


	iqdly01UserMemMemory4Save4 OBJECT-TYPE
		SYNTAX		INTEGER { noAction(0),val_Save_4(1) }
		MAX-ACCESS		read-write
		STATUS			current
		DESCRIPTION
				"TYPE: - Button
				 PAGE: - User Mem
					Save 4  cmdID= 1612  value= 1  "
		::= { iqdly01CmdEntry 1612 }


	iqdly01UserMemMemory4Recall4 OBJECT-TYPE
		SYNTAX		INTEGER { noAction(0),val_Recall_4(1) }
		MAX-ACCESS		read-write
		STATUS			current
		DESCRIPTION
				"TYPE: - Button
				 PAGE: - User Mem
					Recall 4  cmdID= 1613  value= 1  "
		::= { iqdly01CmdEntry 1613 }


	iqdly01UserMemMemory4Clear4 OBJECT-TYPE
		SYNTAX		INTEGER { noAction(0),val_Clear_4(1) }
		MAX-ACCESS		read-write
		STATUS			current
		DESCRIPTION
				"TYPE: - Button
				 PAGE: - User Mem
					Clear 4  cmdID= 1614  value= 1  "
		::= { iqdly01CmdEntry 1614 }


	iqdly01UserMemMemory4Name4 OBJECT-TYPE
		SYNTAX		RollCallString
		MAX-ACCESS		read-write
		STATUS			current
		DESCRIPTION
				"TYPE: - Editstring
				 PAGE: - User Mem
					Name 4  cmdID= 1615  "
		::= { iqdly01CmdEntry 1615 }


	iqdly01UserMemMemory5Save5 OBJECT-TYPE
		SYNTAX		INTEGER { noAction(0),val_Save_5(1) }
		MAX-ACCESS		read-write
		STATUS			current
		DESCRIPTION
				"TYPE: - Button
				 PAGE: - User Mem
					Save 5  cmdID= 1616  value= 1  "
		::= { iqdly01CmdEntry 1616 }


	iqdly01UserMemMemory5Recall5 OBJECT-TYPE
		SYNTAX		INTEGER { noAction(0),val_Recall_5(1) }
		MAX-ACCESS		read-write
		STATUS			current
		DESCRIPTION
				"TYPE: - Button
				 PAGE: - User Mem
					Recall 5  cmdID= 1617  value= 1  "
		::= { iqdly01CmdEntry 1617 }


	iqdly01UserMemMemory5Clear5 OBJECT-TYPE
		SYNTAX		INTEGER { noAction(0),val_Clear_5(1) }
		MAX-ACCESS		read-write
		STATUS			current
		DESCRIPTION
				"TYPE: - Button
				 PAGE: - User Mem
					Clear 5  cmdID= 1618  value= 1  "
		::= { iqdly01CmdEntry 1618 }


	iqdly01UserMemMemory5Name5 OBJECT-TYPE
		SYNTAX		RollCallString
		MAX-ACCESS		read-write
		STATUS			current
		DESCRIPTION
				"TYPE: - Editstring
				 PAGE: - User Mem
					Name 5  cmdID= 1619  "
		::= { iqdly01CmdEntry 1619 }


	iqdly01UserMemMemory6Save6 OBJECT-TYPE
		SYNTAX		INTEGER { noAction(0),val_Save_6(1) }
		MAX-ACCESS		read-write
		STATUS			current
		DESCRIPTION
				"TYPE: - Button
				 PAGE: - User Mem
					Save 6  cmdID= 1620  value= 1  "
		::= { iqdly01CmdEntry 1620 }


	iqdly01UserMemMemory6Recall6 OBJECT-TYPE
		SYNTAX		INTEGER { noAction(0),val_Recall_6(1) }
		MAX-ACCESS		read-write
		STATUS			current
		DESCRIPTION
				"TYPE: - Button
				 PAGE: - User Mem
					Recall 6  cmdID= 1621  value= 1  "
		::= { iqdly01CmdEntry 1621 }


	iqdly01UserMemMemory6Clear6 OBJECT-TYPE
		SYNTAX		INTEGER { noAction(0),val_Clear_6(1) }
		MAX-ACCESS		read-write
		STATUS			current
		DESCRIPTION
				"TYPE: - Button
				 PAGE: - User Mem
					Clear 6  cmdID= 1622  value= 1  "
		::= { iqdly01CmdEntry 1622 }


	iqdly01UserMemMemory6Name6 OBJECT-TYPE
		SYNTAX		RollCallString
		MAX-ACCESS		read-write
		STATUS			current
		DESCRIPTION
				"TYPE: - Editstring
				 PAGE: - User Mem
					Name 6  cmdID= 1623  "
		::= { iqdly01CmdEntry 1623 }


	iqdly01UserMemMemory7Save7 OBJECT-TYPE
		SYNTAX		INTEGER { noAction(0),val_Save_7(1) }
		MAX-ACCESS		read-write
		STATUS			current
		DESCRIPTION
				"TYPE: - Button
				 PAGE: - User Mem
					Save 7  cmdID= 1624  value= 1  "
		::= { iqdly01CmdEntry 1624 }


	iqdly01UserMemMemory7Recall7 OBJECT-TYPE
		SYNTAX		INTEGER { noAction(0),val_Recall_7(1) }
		MAX-ACCESS		read-write
		STATUS			current
		DESCRIPTION
				"TYPE: - Button
				 PAGE: - User Mem
					Recall 7  cmdID= 1625  value= 1  "
		::= { iqdly01CmdEntry 1625 }


	iqdly01UserMemMemory7Clear7 OBJECT-TYPE
		SYNTAX		INTEGER { noAction(0),val_Clear_7(1) }
		MAX-ACCESS		read-write
		STATUS			current
		DESCRIPTION
				"TYPE: - Button
				 PAGE: - User Mem
					Clear 7  cmdID= 1626  value= 1  "
		::= { iqdly01CmdEntry 1626 }


	iqdly01UserMemMemory7Name7 OBJECT-TYPE
		SYNTAX		RollCallString
		MAX-ACCESS		read-write
		STATUS			current
		DESCRIPTION
				"TYPE: - Editstring
				 PAGE: - User Mem
					Name 7  cmdID= 1627  "
		::= { iqdly01CmdEntry 1627 }


	iqdly01UserMemMemory8Save8 OBJECT-TYPE
		SYNTAX		INTEGER { noAction(0),val_Save_8(1) }
		MAX-ACCESS		read-write
		STATUS			current
		DESCRIPTION
				"TYPE: - Button
				 PAGE: - User Mem
					Save 8  cmdID= 1628  value= 1  "
		::= { iqdly01CmdEntry 1628 }


	iqdly01UserMemMemory8Recall8 OBJECT-TYPE
		SYNTAX		INTEGER { noAction(0),val_Recall_8(1) }
		MAX-ACCESS		read-write
		STATUS			current
		DESCRIPTION
				"TYPE: - Button
				 PAGE: - User Mem
					Recall 8  cmdID= 1629  value= 1  "
		::= { iqdly01CmdEntry 1629 }


	iqdly01UserMemMemory8Clear8 OBJECT-TYPE
		SYNTAX		INTEGER { noAction(0),val_Clear_8(1) }
		MAX-ACCESS		read-write
		STATUS			current
		DESCRIPTION
				"TYPE: - Button
				 PAGE: - User Mem
					Clear 8  cmdID= 1630  value= 1  "
		::= { iqdly01CmdEntry 1630 }


	iqdly01UserMemMemory8Name8 OBJECT-TYPE
		SYNTAX		RollCallString
		MAX-ACCESS		read-write
		STATUS			current
		DESCRIPTION
				"TYPE: - Editstring
				 PAGE: - User Mem
					Name 8  cmdID= 1631  "
		::= { iqdly01CmdEntry 1631 }


	iqdly01SetupAudioToneIdentEnable OBJECT-TYPE
		SYNTAX		INTEGER { disable(0), enable(1) }
		MAX-ACCESS		read-write
		STATUS			current
		DESCRIPTION
				"TYPE: - Checkbox
				 PAGE: - Setup- Audio Tone
					Ident Enable  cmdID= 2489 "
		::= { iqdly01CmdEntry 2489 }


	iqdly01SetupAudioToneFrequency OBJECT-TYPE
		SYNTAX		INTEGER
		MAX-ACCESS		read-write
		STATUS			current
		DESCRIPTION
				"TYPE: - Number
				 PAGE: - Setup- Audio Tone
					Frequency  cmdID= 2487  min= 100  max= 15000  step= 100  format= %.1f Hz  div_scale= 1 
					Min = 100.0 Hz  Max = 15000.0 Hz  Step = 100.0 Hz "
		::= { iqdly01CmdEntry 2487 }


	iqdly01SetupAudioToneFrequencyR OBJECT-TYPE
		SYNTAX		INTEGER
		MAX-ACCESS		read-write
		STATUS			current
		DESCRIPTION
				"TYPE: - Number
				 PAGE: - Setup- Audio Tone
					Frequency R  cmdID= 2488  min= 100  max= 15000  step= 100  format= %.1f Hz  div_scale= 1 
					Min = 100.0 Hz  Max = 15000.0 Hz  Step = 100.0 Hz "
		::= { iqdly01CmdEntry 2488 }


	iqdly01SetupAudioToneHeadRoom OBJECT-TYPE
		SYNTAX		INTEGER
		MAX-ACCESS		read-write
		STATUS			current
		DESCRIPTION
				"TYPE: - Number
				 PAGE: - Setup- Audio Tone
					HeadRoom  cmdID= 3055  min= 4  max= 24  step= 1  format= %.1f dB  div_scale= 1 
					Min = 4.0 dB  Max = 24.0 dB  Step = 1.0 dB "
		::= { iqdly01CmdEntry 3055 }


	iqdly01SetupSlewRate OBJECT-TYPE
		SYNTAX		INTEGER {
							val_Instant(0),
							val_Fast(1),
							val_Medium(2),
							val_Slow(3),
							val_Slowest(4)
							}
		MAX-ACCESS		read-write
		STATUS			current
		DESCRIPTION
				"TYPE: - RadiobuttonList
				 PAGE: - Setup
					Slew Rate  cmdID= 2972 
					Instant  value= 0  
					Fast  value= 1  
					Medium  value= 2  
					Slow  value= 3  
					Slowest  value= 4  "
		::= { iqdly01CmdEntry 2972 }


	iqdly01SetupChannelStatus OBJECT-TYPE
		SYNTAX		RollCallString
		MAX-ACCESS		read-write
		STATUS			current
		DESCRIPTION
				"TYPE: - Editstring
				 PAGE: - Setup
					Channel Status  cmdID= 3060  "
		::= { iqdly01CmdEntry 3060 }


	iqdly01GPIIOGPIInputDisableInputs OBJECT-TYPE
		SYNTAX		INTEGER { disable(0), enable(1) }
		MAX-ACCESS		read-write
		STATUS			current
		DESCRIPTION
				"TYPE: - Checkbox
				 PAGE: - Setup- GPI I/O
					Disable Inputs  cmdID= 2605 "
		::= { iqdly01CmdEntry 2605 }


	iqdly01GPIIOGPIInputInputTimerEnable OBJECT-TYPE
		SYNTAX		INTEGER { disable(0), enable(1) }
		MAX-ACCESS		read-write
		STATUS			current
		DESCRIPTION
				"TYPE: - Checkbox
				 PAGE: - Setup- GPI I/O
					InputTimer Enable  cmdID= 3053 "
		::= { iqdly01CmdEntry 3053 }


	iqdly01GPIIOGPIInputTimerActiveHigh OBJECT-TYPE
		SYNTAX		INTEGER { disable(0), enable(1) }
		MAX-ACCESS		read-write
		STATUS			current
		DESCRIPTION
				"TYPE: - Checkbox
				 PAGE: - Setup- GPI I/O
					TimerActive High  cmdID= 3054 "
		::= { iqdly01CmdEntry 3054 }


	iqdly01GPIIOGPIInputInputSelection OBJECT-TYPE
		SYNTAX		INTEGER
		MAX-ACCESS		read-write
		STATUS			current
		DESCRIPTION
				"TYPE: - Number
				 PAGE: - Setup- GPI I/O
					Input Selection  cmdID= 2011  min= -1  max= 11  step= 1  format= %.0f  div_scale= 1 
					Min = -1  Max = 11  Step = 1 "
		::= { iqdly01CmdEntry 2011 }


	iqdly01GPIIOGPIInputGPIInStatus OBJECT-TYPE
		SYNTAX		RollCallString
		MAX-ACCESS		read-only
		STATUS			current
		DESCRIPTION
				"TYPE: - Display
				 PAGE: - Setup- GPI I/O
					GPI In Status  cmdID= 2048  format=   "
		::= { iqdly01CmdEntry 2048 }


	iqdly01GPIIOGPIOutputOutActiveHigh OBJECT-TYPE
		SYNTAX		INTEGER { disable(0), enable(1) }
		MAX-ACCESS		read-write
		STATUS			current
		DESCRIPTION
				"TYPE: - Checkbox
				 PAGE: - Setup- GPI I/O
					Out Active High  cmdID= 3540 "
		::= { iqdly01CmdEntry 3540 }


	iqdly01GPIIOGPIOutputOutputSelection OBJECT-TYPE
		SYNTAX		INTEGER
		MAX-ACCESS		read-write
		STATUS			current
		DESCRIPTION
				"TYPE: - Number
				 PAGE: - Setup- GPI I/O
					Output Selection  cmdID= 2013  min= -1  max= 4  step= 1  format= %.0f  div_scale= 1 
					Min = -1  Max = 4  Step = 1 "
		::= { iqdly01CmdEntry 2013 }


	iqdly01GPIIOGPIOutputGPIOutStatus OBJECT-TYPE
		SYNTAX		RollCallString
		MAX-ACCESS		read-only
		STATUS			current
		DESCRIPTION
				"TYPE: - Display
				 PAGE: - Setup- GPI I/O
					GPI Out Status  cmdID= 2049  format=   "
		::= { iqdly01CmdEntry 2049 }


	iqdly01GPIIOGPIInputOutputGPIO1 OBJECT-TYPE
		SYNTAX		INTEGER { disable(0), enable(1) }
		MAX-ACCESS		read-write
		STATUS			current
		DESCRIPTION
				"TYPE: - Checkbox
				 PAGE: - Setup- GPI I/O
					GPI/O 1  cmdID= 2014 "
		::= { iqdly01CmdEntry 2014 }


	iqdly01SetupGPIIOInputSelection OBJECT-TYPE
		SYNTAX		INTEGER
		MAX-ACCESS		read-write
		STATUS			current
		DESCRIPTION
				"TYPE: - Number
				 PAGE: - Setup- GPI I/O
					Input Selection  cmdID= 2875  min= -1  max= 11  step= 1  format= %.0f  div_scale= 1 
					Min = -1  Max = 11  Step = 1 "
		::= { iqdly01CmdEntry 2875 }


	iqdly01SetupGPIIOOutputSelection OBJECT-TYPE
		SYNTAX		INTEGER
		MAX-ACCESS		read-write
		STATUS			current
		DESCRIPTION
				"TYPE: - Number
				 PAGE: - Setup- GPI I/O
					Output Selection  cmdID= 2877  min= -1  max= 4  step= 1  format= %.0f  div_scale= 1 
					Min = -1  Max = 4  Step = 1 "
		::= { iqdly01CmdEntry 2877 }


	iqdly01SetupRollTrackRollTrackIndex OBJECT-TYPE
		SYNTAX		INTEGER
		MAX-ACCESS		read-write
		STATUS			current
		DESCRIPTION
				"TYPE: - Number
				 PAGE: - Setup- RollTrack
					RollTrack Index  cmdID= 1495  min= 0  max= 49  step= 1  format= %.0f  div_scale= 1 
					Min = 0  Max = 49  Step = 1 "
		::= { iqdly01CmdEntry 1495 }


	iqdly01SetupRollTrackRollTrackSource OBJECT-TYPE
		SYNTAX		INTEGER
		MAX-ACCESS		read-write
		STATUS			current
		DESCRIPTION
				"TYPE: - Number
				 PAGE: - Setup- RollTrack
					RollTrack Source  cmdID= 1496  min= -1  max= 14  step= 1  format= %.0f  div_scale= 1 
					Min = -1  Max = 14  Step = 1 "
		::= { iqdly01CmdEntry 1496 }


	iqdly01SetupRollTrackRollTrackDisable OBJECT-TYPE
		SYNTAX		INTEGER { disable(0), enable(1) }
		MAX-ACCESS		read-write
		STATUS			current
		DESCRIPTION
				"TYPE: - Checkbox
				 PAGE: - Setup- RollTrack
					RollTrack Disable  cmdID= 1513 "
		::= { iqdly01CmdEntry 1513 }


	iqdly01SetupRollTrackRollTrackAddress OBJECT-TYPE
		SYNTAX		RollCallString
		MAX-ACCESS		read-write
		STATUS			current
		DESCRIPTION
				"TYPE: - Editstring
				 PAGE: - Setup- RollTrack
					RollTrack Address  cmdID= 1497  "
		::= { iqdly01CmdEntry 1497 }


	iqdly01SetupRollTrackRollTrackCommand OBJECT-TYPE
		SYNTAX		RollCallString
		MAX-ACCESS		read-write
		STATUS			current
		DESCRIPTION
				"TYPE: - Editstring
				 PAGE: - Setup- RollTrack
					RollTrack Command  cmdID= 1498  "
		::= { iqdly01CmdEntry 1498 }


	iqdly01SetupRollTrackRollTrackSending OBJECT-TYPE
		SYNTAX		RollCallString
		MAX-ACCESS		read-only
		STATUS			current
		DESCRIPTION
				"TYPE: - Display
				 PAGE: - Setup- RollTrack
					RollTrack Sending  cmdID= 1514  format=   "
		::= { iqdly01CmdEntry 1514 }


	iqdly01SetupRollTrackRollTrackStatus OBJECT-TYPE
		SYNTAX		RollCallString
		MAX-ACCESS		read-only
		STATUS			current
		DESCRIPTION
				"TYPE: - Display
				 PAGE: - Setup- RollTrack
					RollTrack Status  cmdID= 1511  format=   "
		::= { iqdly01CmdEntry 1511 }


	iqdly01SetupRollTrackRollTrack_Index OBJECT-TYPE
		SYNTAX		INTEGER
		MAX-ACCESS		read-write
		STATUS			current
		DESCRIPTION
				"TYPE: - Number
				 PAGE: - Setup- RollTrack
					RollTrack Index  cmdID= 2870  min= 0  max= 49  step= 1  format= %.0f  div_scale= 1 
					Min = 0  Max = 49  Step = 1 "
		::= { iqdly01CmdEntry 2870 }


	iqdly01SetupRollTrackRollTrack_Source OBJECT-TYPE
		SYNTAX		INTEGER
		MAX-ACCESS		read-write
		STATUS			current
		DESCRIPTION
				"TYPE: - Number
				 PAGE: - Setup- RollTrack
					RollTrack Source  cmdID= 2871  min= -1  max= 14  step= 1  format= %.0f  div_scale= 1 
					Min = -1  Max = 14  Step = 1 "
		::= { iqdly01CmdEntry 2871 }


	iqdly01SetupRollTrackRollTrack_Address OBJECT-TYPE
		SYNTAX		RollCallString
		MAX-ACCESS		read-write
		STATUS			current
		DESCRIPTION
				"TYPE: - Editstring
				 PAGE: - Setup- RollTrack
					RollTrack Address  cmdID= 2872  "
		::= { iqdly01CmdEntry 2872 }


	iqdly01SetupRollTrackRollTrack_Command OBJECT-TYPE
		SYNTAX		RollCallString
		MAX-ACCESS		read-write
		STATUS			current
		DESCRIPTION
				"TYPE: - Editstring
				 PAGE: - Setup- RollTrack
					RollTrack Command  cmdID= 2873  "
		::= { iqdly01CmdEntry 2873 }


	iqdly01SetupLoggingReference OBJECT-TYPE
		SYNTAX		INTEGER { disable(0), enable(1) }
		MAX-ACCESS		read-write
		STATUS			current
		DESCRIPTION
				"TYPE: - Checkbox
				 PAGE: - Setup- Logging
					Reference  cmdID= 1062 "
		::= { iqdly01CmdEntry 1062 }


	iqdly01SetupLoggingRollTrack OBJECT-TYPE
		SYNTAX		INTEGER { disable(0), enable(1) }
		MAX-ACCESS		read-write
		STATUS			current
		DESCRIPTION
				"TYPE: - Checkbox
				 PAGE: - Setup- Logging
					RollTrack  cmdID= 1106 "
		::= { iqdly01CmdEntry 1106 }


	iqdly01SetupLoggingAES1 OBJECT-TYPE
		SYNTAX		INTEGER { disable(0), enable(1) }
		MAX-ACCESS		read-write
		STATUS			current
		DESCRIPTION
				"TYPE: - Checkbox
				 PAGE: - Setup- Logging
					AES 1  cmdID= 1108 "
		::= { iqdly01CmdEntry 1108 }


	iqdly01SetupLoggingAES2 OBJECT-TYPE
		SYNTAX		INTEGER { disable(0), enable(1) }
		MAX-ACCESS		read-write
		STATUS			current
		DESCRIPTION
				"TYPE: - Checkbox
				 PAGE: - Setup- Logging
					AES 2  cmdID= 1109 "
		::= { iqdly01CmdEntry 1109 }


	iqdly01SetupLoggingAES3 OBJECT-TYPE
		SYNTAX		INTEGER { disable(0), enable(1) }
		MAX-ACCESS		read-write
		STATUS			current
		DESCRIPTION
				"TYPE: - Checkbox
				 PAGE: - Setup- Logging
					AES 3  cmdID= 1110 "
		::= { iqdly01CmdEntry 1110 }


	iqdly01SetupLoggingAES4 OBJECT-TYPE
		SYNTAX		INTEGER { disable(0), enable(1) }
		MAX-ACCESS		read-write
		STATUS			current
		DESCRIPTION
				"TYPE: - Checkbox
				 PAGE: - Setup- Logging
					AES 4  cmdID= 1111 "
		::= { iqdly01CmdEntry 1111 }


	iqdly01SetupLoggingBusAL OBJECT-TYPE
		SYNTAX		INTEGER { disable(0), enable(1) }
		MAX-ACCESS		read-write
		STATUS			current
		DESCRIPTION
				"TYPE: - Checkbox
				 PAGE: - Setup- Logging
					Bus AL  cmdID= 1112 "
		::= { iqdly01CmdEntry 1112 }


	iqdly01SetupLoggingBusAR OBJECT-TYPE
		SYNTAX		INTEGER { disable(0), enable(1) }
		MAX-ACCESS		read-write
		STATUS			current
		DESCRIPTION
				"TYPE: - Checkbox
				 PAGE: - Setup- Logging
					Bus AR  cmdID= 1113 "
		::= { iqdly01CmdEntry 1113 }


	iqdly01SetupLoggingBusBL OBJECT-TYPE
		SYNTAX		INTEGER { disable(0), enable(1) }
		MAX-ACCESS		read-write
		STATUS			current
		DESCRIPTION
				"TYPE: - Checkbox
				 PAGE: - Setup- Logging
					Bus BL  cmdID= 1114 "
		::= { iqdly01CmdEntry 1114 }


	iqdly01SetupLoggingBusBR OBJECT-TYPE
		SYNTAX		INTEGER { disable(0), enable(1) }
		MAX-ACCESS		read-write
		STATUS			current
		DESCRIPTION
				"TYPE: - Checkbox
				 PAGE: - Setup- Logging
					Bus BR  cmdID= 1115 "
		::= { iqdly01CmdEntry 1115 }


	iqdly01SetupLoggingBusCL OBJECT-TYPE
		SYNTAX		INTEGER { disable(0), enable(1) }
		MAX-ACCESS		read-write
		STATUS			current
		DESCRIPTION
				"TYPE: - Checkbox
				 PAGE: - Setup- Logging
					Bus CL  cmdID= 1116 "
		::= { iqdly01CmdEntry 1116 }


	iqdly01SetupLoggingBusCR OBJECT-TYPE
		SYNTAX		INTEGER { disable(0), enable(1) }
		MAX-ACCESS		read-write
		STATUS			current
		DESCRIPTION
				"TYPE: - Checkbox
				 PAGE: - Setup- Logging
					Bus CR  cmdID= 1117 "
		::= { iqdly01CmdEntry 1117 }


	iqdly01SetupLoggingBusDL OBJECT-TYPE
		SYNTAX		INTEGER { disable(0), enable(1) }
		MAX-ACCESS		read-write
		STATUS			current
		DESCRIPTION
				"TYPE: - Checkbox
				 PAGE: - Setup- Logging
					Bus DL  cmdID= 1118 "
		::= { iqdly01CmdEntry 1118 }


	iqdly01SetupLoggingBusDR OBJECT-TYPE
		SYNTAX		INTEGER { disable(0), enable(1) }
		MAX-ACCESS		read-write
		STATUS			current
		DESCRIPTION
				"TYPE: - Checkbox
				 PAGE: - Setup- Logging
					Bus DR  cmdID= 1119 "
		::= { iqdly01CmdEntry 1119 }


	iqdly01SetupLoggingFault OBJECT-TYPE
		SYNTAX		INTEGER { disable(0), enable(1) }
		MAX-ACCESS		read-write
		STATUS			current
		DESCRIPTION
				"TYPE: - Checkbox
				 PAGE: - Setup- Logging
					Fault  cmdID= 1069 "
		::= { iqdly01CmdEntry 1069 }


	iqdly01SetupLoggingStatusEXTREF OBJECT-TYPE
		SYNTAX		RollCallString
		MAX-ACCESS		read-only
		STATUS			current
		DESCRIPTION
				"TYPE: - Display
				 PAGE: - Setup- Logging Status
					EXTREF=  cmdID= 2986  format=   "
		::= { iqdly01CmdEntry 2986 }


	iqdly01SetupLoggingStatusROLLTRACK OBJECT-TYPE
		SYNTAX		RollCallString
		MAX-ACCESS		read-only
		STATUS			current
		DESCRIPTION
				"TYPE: - Display
				 PAGE: - Setup- Logging Status
					ROLLTRACK=  cmdID= 2989  format=   "
		::= { iqdly01CmdEntry 2989 }


	iqdly01SetupLoggingStatusAES1 OBJECT-TYPE
		SYNTAX		RollCallString
		MAX-ACCESS		read-only
		STATUS			current
		DESCRIPTION
				"TYPE: - Display
				 PAGE: - Setup- Logging Status
					AES1=  cmdID= 2994  format=   "
		::= { iqdly01CmdEntry 2994 }


	iqdly01SetupLoggingStatusAES2 OBJECT-TYPE
		SYNTAX		RollCallString
		MAX-ACCESS		read-only
		STATUS			current
		DESCRIPTION
				"TYPE: - Display
				 PAGE: - Setup- Logging Status
					AES2=  cmdID= 2995  format=   "
		::= { iqdly01CmdEntry 2995 }


	iqdly01SetupLoggingStatusAES3 OBJECT-TYPE
		SYNTAX		RollCallString
		MAX-ACCESS		read-only
		STATUS			current
		DESCRIPTION
				"TYPE: - Display
				 PAGE: - Setup- Logging Status
					AES3=  cmdID= 2996  format=   "
		::= { iqdly01CmdEntry 2996 }


	iqdly01SetupLoggingStatusAES4 OBJECT-TYPE
		SYNTAX		RollCallString
		MAX-ACCESS		read-only
		STATUS			current
		DESCRIPTION
				"TYPE: - Display
				 PAGE: - Setup- Logging Status
					AES4=  cmdID= 2997  format=   "
		::= { iqdly01CmdEntry 2997 }


	iqdly01SetupLoggingStatusBUSAL OBJECT-TYPE
		SYNTAX		RollCallString
		MAX-ACCESS		read-only
		STATUS			current
		DESCRIPTION
				"TYPE: - Display
				 PAGE: - Setup- Logging Status
					BUSAL=  cmdID= 2998  format=   "
		::= { iqdly01CmdEntry 2998 }


	iqdly01SetupLoggingStatusBUSAR OBJECT-TYPE
		SYNTAX		RollCallString
		MAX-ACCESS		read-only
		STATUS			current
		DESCRIPTION
				"TYPE: - Display
				 PAGE: - Setup- Logging Status
					BUSAR=  cmdID= 2999  format=   "
		::= { iqdly01CmdEntry 2999 }


	iqdly01SetupLoggingStatusBUSBL OBJECT-TYPE
		SYNTAX		RollCallString
		MAX-ACCESS		read-only
		STATUS			current
		DESCRIPTION
				"TYPE: - Display
				 PAGE: - Setup- Logging Status
					BUSBL=  cmdID= 3000  format=   "
		::= { iqdly01CmdEntry 3000 }


	iqdly01SetupLoggingStatusBUSBR OBJECT-TYPE
		SYNTAX		RollCallString
		MAX-ACCESS		read-only
		STATUS			current
		DESCRIPTION
				"TYPE: - Display
				 PAGE: - Setup- Logging Status
					BUSBR=  cmdID= 3001  format=   "
		::= { iqdly01CmdEntry 3001 }


	iqdly01SetupLoggingStatusBUSCL OBJECT-TYPE
		SYNTAX		RollCallString
		MAX-ACCESS		read-only
		STATUS			current
		DESCRIPTION
				"TYPE: - Display
				 PAGE: - Setup- Logging Status
					BUSCL=  cmdID= 3002  format=   "
		::= { iqdly01CmdEntry 3002 }


	iqdly01SetupLoggingStatusBUSCR OBJECT-TYPE
		SYNTAX		RollCallString
		MAX-ACCESS		read-only
		STATUS			current
		DESCRIPTION
				"TYPE: - Display
				 PAGE: - Setup- Logging Status
					BUSCR=  cmdID= 3003  format=   "
		::= { iqdly01CmdEntry 3003 }


	iqdly01SetupLoggingStatusBUSDL OBJECT-TYPE
		SYNTAX		RollCallString
		MAX-ACCESS		read-only
		STATUS			current
		DESCRIPTION
				"TYPE: - Display
				 PAGE: - Setup- Logging Status
					BUSDL=  cmdID= 3004  format=   "
		::= { iqdly01CmdEntry 3004 }


	iqdly01SetupLoggingStatusBUSDR OBJECT-TYPE
		SYNTAX		RollCallString
		MAX-ACCESS		read-only
		STATUS			current
		DESCRIPTION
				"TYPE: - Display
				 PAGE: - Setup- Logging Status
					BUSDR=  cmdID= 3005  format=   "
		::= { iqdly01CmdEntry 3005 }


	iqdly01SetupLoggingStatusFAULT OBJECT-TYPE
		SYNTAX		RollCallString
		MAX-ACCESS		read-only
		STATUS			current
		DESCRIPTION
				"TYPE: - Display
				 PAGE: - Setup- Logging Status
					FAULT=  cmdID= 2990  format=   "
		::= { iqdly01CmdEntry 2990 }


	iqdly01SetupUnitSoftwareVersion OBJECT-TYPE
		SYNTAX		RollCallString
		MAX-ACCESS		read-only
		STATUS			current
		DESCRIPTION
				"TYPE: - Display
				 PAGE: - Setup- Unit
					Software Version  cmdID= 2  format=   "
		::= { iqdly01CmdEntry 2 }


	iqdly01SetupUnitSerialNo OBJECT-TYPE
		SYNTAX		RollCallString
		MAX-ACCESS		read-only
		STATUS			current
		DESCRIPTION
				"TYPE: - Display
				 PAGE: - Setup- Unit
					Serial No  cmdID= 1  format=   "
		::= { iqdly01CmdEntry 1 }


	iqdly01SetupUnitPresetUnit OBJECT-TYPE
		SYNTAX		INTEGER { noAction(0),val_Preset_Unit(1) }
		MAX-ACCESS		read-write
		STATUS			current
		DESCRIPTION
				"TYPE: - Button
				 PAGE: - Setup- Unit
					Preset Unit  cmdID= 3  value= 1  "
		::= { iqdly01CmdEntry 3 }


	iqdly01SetupUnitRestart OBJECT-TYPE
		SYNTAX		INTEGER { noAction(0),val_Restart(1) }
		MAX-ACCESS		read-write
		STATUS			current
		DESCRIPTION
				"TYPE: - Button
				 PAGE: - Setup- Unit
					Restart  cmdID= 4  value= 1  "
		::= { iqdly01CmdEntry 4 }


	iqdly01SetupUnitBuildNo OBJECT-TYPE
		SYNTAX		RollCallString
		MAX-ACCESS		read-only
		STATUS			current
		DESCRIPTION
				"TYPE: - Display
				 PAGE: - Setup- Unit
					Build No  cmdID= 5  format=   "
		::= { iqdly01CmdEntry 5 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: xxxxxxxxxxxxxxxxxxx
--				: 
-- Comments		: Serial Number   Runtime string  
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: AES_1
--
-- MIB ref		: swCardEventLogSlotXX       .5.65.69.83.95.49
-- absolute OID	: 1.3.6.1.4.1.7995.2.6.1.1.XX.5.65.69.83.95.49
-- Vary			: YES
--
-- Value(s)		: NONPCM            Non-PCM signal present on AES input 1
--				: OK                Valid signal present on AES input 1
--              : LOST              Signal not present at AES input 1
-- Comments		: 
--
---------------------------------------------------------------------------------------------------
-- Header		: AES_2
--
-- MIB ref		: swCardEventLogSlotXX       .5.65.69.83.95.50
-- absolute OID	: 1.3.6.1.4.1.7995.2.6.1.1.XX.5.65.69.83.95.50
-- Vary			: YES
--
-- Value(s)		: NONPCM            Non-PCM signal present on AES input 2
--				: OK                Valid signal present on AES input 2
--              : LOST              Signal not present at AES input 2
-- Comments		: 
--
---------------------------------------------------------------------------------------------------
-- Header		: AES_3
--
-- MIB ref		: swCardEventLogSlotXX       .5.65.69.83.95.51
-- absolute OID	: 1.3.6.1.4.1.7995.2.6.1.1.XX.5.65.69.83.95.51
-- Vary			: YES
--
-- Value(s)		: NONPCM            Non-PCM signal present on AES input 3
--				: OK                Valid signal present on AES input 3
--              : LOST              Signal not present at AES input 3
-- Comments		: 
--
---------------------------------------------------------------------------------------------------
-- Header		: AES_4
--
-- MIB ref		: swCardEventLogSlotXX       .5.65.69.83.95.52
-- absolute OID	: 1.3.6.1.4.1.7995.2.6.1.1.XX.5.65.69.83.95.52
-- Vary			: YES
--
-- Value(s)		: NONPCM            Non-PCM signal present on AES input 4
--				: OK                Valid signal present on AES input 4
--              : LOST              Signal not present at AES input 4
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: NONE              No Internal errors detected
--				: FAIL              Internal error detected
--              : FAIL.FPGA_LOAD    Fpga load failure detected
-- Comments		: 
--
---------------------------------------------------------------------------------------------------
-- Header		: BUS_AL
--
-- MIB ref		: swCardEventLogSlotXX       .6.66.85.83.95.65.76
-- absolute OID	: 1.3.6.1.4.1.7995.2.6.1.1.XX.6.66.85.83.95.65.76
-- Vary			: YES
--
-- Value(s)		: OK                Router BUS A Left channel has valid signal selected            
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_AR
--
-- MIB ref		: swCardEventLogSlotXX       .6.66.85.83.95.65.82
-- absolute OID	: 1.3.6.1.4.1.7995.2.6.1.1.XX.6.66.85.83.95.65.82
-- Vary			: YES
--
-- Value(s)		: OK                Router BUS A Right channel has valid signal selected
--              : WARNING           Router BUS A Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_BL
--
-- MIB ref		: swCardEventLogSlotXX       .6.66.85.83.95.66.76
-- absolute OID	: 1.3.6.1.4.1.7995.2.6.1.1.XX.6.66.85.83.95.66.76
-- Vary			: YES
--
-- Value(s)		: OK                Router BUS B Left channel has valid signal selected            
--              : WARNING           Router BUS B Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_BR
--
-- MIB ref		: swCardEventLogSlotXX       .6.66.85.83.95.66.82
-- absolute OID	: 1.3.6.1.4.1.7995.2.6.1.1.XX.6.66.85.83.95.66.82
-- Vary			: YES
--
-- Value(s)		: OK                Router BUS B Right channel has valid signal selected
--              : WARNING           Router BUS B Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_CL
--
-- MIB ref		: swCardEventLogSlotXX       .6.66.85.83.95.67.76
-- absolute OID	: 1.3.6.1.4.1.7995.2.6.1.1.XX.6.66.85.83.95.67.76
-- Vary			: YES
--
-- Value(s)		: OK                Router BUS C Left channel has valid signal selected            
--              : WARNING           Router BUS C Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_CR
--
-- MIB ref		: swCardEventLogSlotXX       .6.66.85.83.95.67.82
-- absolute OID	: 1.3.6.1.4.1.7995.2.6.1.1.XX.6.66.85.83.95.67.82
-- Vary			: YES
--
-- Value(s)		: OK                Router BUS C Right channel has valid signal selected
--              : WARNING           Router BUS C Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_DL
--
-- MIB ref		: swCardEventLogSlotXX       .6.66.85.83.95.68.76
-- absolute OID	: 1.3.6.1.4.1.7995.2.6.1.1.XX.6.66.85.83.95.68.76
-- Vary			: YES
--
-- Value(s)		: OK                Router BUS D Left channel has valid signal selected            
--              : WARNING           Router BUS D Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_DR
--
-- MIB ref		: swCardEventLogSlotXX       .6.66.85.83.95.68.82
-- absolute OID	: 1.3.6.1.4.1.7995.2.6.1.1.XX.6.66.85.83.95.68.82
-- Vary			: YES
--
-- Value(s)		: OK                Router BUS D Right channel has valid signal selected
--              : WARNING           Router BUS D Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: NONE              No reference signal present                
--				: 525               Valid 525 reference signal                 
--              : ERROR             Reference/Output standard mismatch         
--              : WARNING           Reference signal available but not selected
--              : 625               Valid 625 reference signal                 
-- Comments		: 
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: OK                RollTrack message sent and received OK
--				: FAIL              RollTrack message not acknowledged    
-- Comments		: 
--
---------------------------------------------------------------------------------------------------
