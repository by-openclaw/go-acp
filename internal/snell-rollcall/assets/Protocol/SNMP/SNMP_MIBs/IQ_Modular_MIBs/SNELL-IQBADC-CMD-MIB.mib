-- ************************************************************************************
-- Snell&Wilcox Card:IQBADC
--        Module Id#:51
--       Command Set:7
--          Filename:SNELL-IQBADC-CMD-MIB.mib
--            Author:Jonathan Riches
--              Date:30/06/2005
--              Time:13:11
-- Last Modification:Logging comments added
--   Version Control:CVS $Id: SNELL-IQBADC-CMD-MIB.mib 224 2006-12-20 13:57:33Z nikolaoskatsampekis $
-- Copyright (c) 2006 Snell & Wilcox Ltd
-- All rights reserved.
--
-- ************************************************************************************

SNELL-IQBADC-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQBADC,
    moduleIQBADCMIB
        FROM SNELL-WILCOX-PRODUCT-REG;

 moduleIQBADCCmdMi MODULE-IDENTITY
    LAST-UPDATED "0506301311Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQBADCMIB 1 }




--********************************************************************************
--*
--*  Snell Wilcox Card:
--*  command set:
--*  list commands/menus:
--*
--******************************************************************************
	iqbadcCmdTable OBJECT-TYPE
		SYNTAX			SEQUENCE OF IqbadcCmdEntry
		MAX-ACCESS		not-accessible
		STATUS			current
		DESCRIPTION
				"Note the instance of this table is relected in the command set Version"
		::= { moduleIQBADC 1 }

	iqbadcCmdEntry OBJECT-TYPE
		SYNTAX		IqbadcCmdEntry
		MAX-ACCESS		not-accessible
		STATUS			current
		DESCRIPTION
				"Entry in command table."
		INDEX	{ iqbadcSlotIndex }
		::= { iqbadcCmdTable 1 }

	IqbadcCmdEntry ::=
		SEQUENCE {
			iqbadcSlotIndex
				Unsigned32,
			iqbadcDelayManualDelayTime
				INTEGER,
			iqbadcDelayManualDelay
				INTEGER,
			iqbadcDelayRollTrack
				INTEGER,
			iqbadcDelayExternalDelay
				INTEGER,
			iqbadcLockMode
				INTEGER,
			iqbadcAttenuator
				INTEGER,
			iqbadcMute
				INTEGER,
			iqbadcSampleRate
				INTEGER,
			iqbadcSetupExtDelayPolarity
				INTEGER,
			iqbadcSetupPresetUnit
				INTEGER,
			iqbadcSetupLoggingOverflow
				INTEGER,
			iqbadcSetupLoggingRefLoss
				INTEGER,
			iqbadcSetupSoftwareVersion
				RollCallString,
			iqbadcSetupSerialNo
				RollCallString,
			iqbadcExtDelay1
				INTEGER,
			iqbadcExtDelay2
				INTEGER,
			iqbadcExtDelay3
				INTEGER,
			iqbadcExtDelay4
				INTEGER,
			iqbadcExtDelay5
				INTEGER
		}

	iqbadcSlotIndex OBJECT-TYPE
		SYNTAX		Unsigned32
		MAX-ACCESS		not-accessible
		STATUS			current
		DESCRIPTION
				"The unique Index value for each slot.  Its value
					ranges between 1 and the value of slotNumber."
		::= { iqbadcCmdEntry 0 }


	iqbadcDelayManualDelayTime OBJECT-TYPE
		SYNTAX		INTEGER
		MAX-ACCESS		read-write
		STATUS			current
		DESCRIPTION
				"TYPE: - Number
					Manual_Delay_Time  cmdID= 7  min= -1800  max= 1800  step= 1  format= %.0f ms  div_scale= 1 
					Min = -1800 ms  Max = 1800 ms  Step = 1 ms "
		::= { iqbadcCmdEntry 7 }


	iqbadcDelayManualDelay OBJECT-TYPE
		SYNTAX		INTEGER { disable(0), enable(1) }
		MAX-ACCESS		read-write
		STATUS			current
		DESCRIPTION
				"TYPE: - Checkbox
					Manual_Delay  cmdID= 22 "
		::= { iqbadcCmdEntry 22 }


	iqbadcDelayRollTrack OBJECT-TYPE
		SYNTAX		INTEGER { disable(0), enable(1) }
		MAX-ACCESS		read-write
		STATUS			current
		DESCRIPTION
				"TYPE: - Checkbox
					RollTrack  cmdID= 21 "
		::= { iqbadcCmdEntry 21 }


	iqbadcDelayExternalDelay OBJECT-TYPE
		SYNTAX		INTEGER { disable(0), enable(1) }
		MAX-ACCESS		read-write
		STATUS			current
		DESCRIPTION
				"TYPE: - Checkbox
					External_Delay  cmdID= 8 "
		::= { iqbadcCmdEntry 8 }


	iqbadcLockMode OBJECT-TYPE
		SYNTAX		INTEGER {
							val_External_Video(0),
							val_AES_Reference(1),
							val_Internal(2)
							}
		MAX-ACCESS		read-write
		STATUS			current
		DESCRIPTION
				"TYPE: - RadiobuttonList
					LockMode  cmdID= 4 
					External_Video  value= 0  
					AES_Reference  value= 1  
					Internal  value= 2  "
		::= { iqbadcCmdEntry 4 }


	iqbadcAttenuator OBJECT-TYPE
		SYNTAX		INTEGER {
							val_18dBu(18),
							val_21dBu(21),
							val_24dBu(24)
							}
		MAX-ACCESS		read-write
		STATUS			current
		DESCRIPTION
				"TYPE: - RadiobuttonList
					Attenuator  cmdID= 5 
					18dBu  value= 18  
					21dBu  value= 21  
					24dBu  value= 24  "
		::= { iqbadcCmdEntry 5 }


	iqbadcMute OBJECT-TYPE
		SYNTAX		INTEGER { disable(0), enable(1) }
		MAX-ACCESS		read-write
		STATUS			current
		DESCRIPTION
				"TYPE: - Checkbox
					Mute  cmdID= 6 "
		::= { iqbadcCmdEntry 6 }


	iqbadcSampleRate OBJECT-TYPE
		SYNTAX		INTEGER {
							val_48KHz(48),
							val_44_1KHz(44),
							val_32KHz(32)
							}
		MAX-ACCESS		read-write
		STATUS			current
		DESCRIPTION
				"TYPE: - RadiobuttonList
					Sample_Rate  cmdID= 9 
					48KHz  value= 48  
					44.1KHz  value= 44  
					32KHz  value= 32  "
		::= { iqbadcCmdEntry 9 }


	iqbadcSetupExtDelayPolarity OBJECT-TYPE
		SYNTAX		INTEGER {
							val_Positive(1),
							val_Negative(0)
							}
		MAX-ACCESS		read-write
		STATUS			current
		DESCRIPTION
				"TYPE: - RadiobuttonList
					Ext_Delay_Polarity  cmdID= 20 
					Positive  value= 1  
					Negative  value= 0  "
		::= { iqbadcCmdEntry 20 }


	iqbadcSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqbadcCmdEntry 3 }


	iqbadcSetupLoggingOverflow OBJECT-TYPE
		SYNTAX		INTEGER { disable(0), enable(1) }
		MAX-ACCESS		read-write
		STATUS			current
		DESCRIPTION
				"TYPE: - Checkbox
					Overflow  cmdID= 11 "
		::= { iqbadcCmdEntry 11 }


	iqbadcSetupLoggingRefLoss OBJECT-TYPE
		SYNTAX		INTEGER { disable(0), enable(1) }
		MAX-ACCESS		read-write
		STATUS			current
		DESCRIPTION
				"TYPE: - Checkbox
					Ref_Loss  cmdID= 12 "
		::= { iqbadcCmdEntry 12 }


	iqbadcSetupSoftwareVersion OBJECT-TYPE
		SYNTAX		RollCallString
		MAX-ACCESS		read-only
		STATUS			current
		DESCRIPTION
				"TYPE: - Display
					Software_Version  cmdID= 2  format=   "
		::= { iqbadcCmdEntry 2 }


	iqbadcSetupSerialNo OBJECT-TYPE
		SYNTAX		RollCallString
		MAX-ACCESS		read-only
		STATUS			current
		DESCRIPTION
				"TYPE: - Display
					Serial_No  cmdID= 1  format=   "
		::= { iqbadcCmdEntry 1 }


	iqbadcExtDelay1 OBJECT-TYPE
		SYNTAX		INTEGER
		MAX-ACCESS		read-write
		STATUS			current
		DESCRIPTION
				"TYPE: - Number
					Ext_Delay_1  cmdID= 14  min= 0  max= 1600  step= 1  format= %1.0f ms  div_scale= 1 
					Min = 0 ms  Max = 1600 ms  Step = 1 ms "
		::= { iqbadcCmdEntry 14 }


	iqbadcExtDelay2 OBJECT-TYPE
		SYNTAX		INTEGER
		MAX-ACCESS		read-write
		STATUS			current
		DESCRIPTION
				"TYPE: - Number
					Ext_Delay_2  cmdID= 15  min= 0  max= 1600  step= 1  format= %1.0f ms  div_scale= 1 
					Min = 0 ms  Max = 1600 ms  Step = 1 ms "
		::= { iqbadcCmdEntry 15 }


	iqbadcExtDelay3 OBJECT-TYPE
		SYNTAX		INTEGER
		MAX-ACCESS		read-write
		STATUS			current
		DESCRIPTION
				"TYPE: - Number
					Ext_Delay_3  cmdID= 16  min= 0  max= 1600  step= 1  format= %1.0f ms  div_scale= 1 
					Min = 0 ms  Max = 1600 ms  Step = 1 ms "
		::= { iqbadcCmdEntry 16 }


	iqbadcExtDelay4 OBJECT-TYPE
		SYNTAX		INTEGER
		MAX-ACCESS		read-write
		STATUS			current
		DESCRIPTION
				"TYPE: - Number
					Ext_Delay_4  cmdID= 17  min= 0  max= 1600  step= 1  format= %1.0f ms  div_scale= 1 
					Min = 0 ms  Max = 1600 ms  Step = 1 ms "
		::= { iqbadcCmdEntry 17 }


	iqbadcExtDelay5 OBJECT-TYPE
		SYNTAX		INTEGER
		MAX-ACCESS		read-write
		STATUS			current
		DESCRIPTION
				"TYPE: - Number
					Ext_Delay_5  cmdID= 18  min= 0  max= 1600  step= 1  format= %1.0f ms  div_scale= 1 
					Min = 0 ms  Max = 1600 ms  Step = 1 ms "
		::= { iqbadcCmdEntry 18 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		:             
--				: 
-- Comments		: This log field shows the unique S&W serial number for this
--				: board instance.
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: This log field shows whether the IQ frame gateway card
--				: can communicate with this module.
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: This log field shows that the module is in Local Mode.
--				: When a device boots up in Local Mode, all settings will be
--				: set to the values indicated by card edge switches, (ignoring
--				: any previous values set through RollCall), and any parameters
--				: not accessible from the card edge will be restored to their
--				: factory defaults.
--				: Generally Local mode is not suitable in a networked
--				: environment, and Remote Mode should be used instead.
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
-- Comments		: This log field shows the detected state of the SDI input signal.
--				: LOST indicates no input detected. 
--				: ERROR indicates that the detected input is not valid.
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: LOST
--				: 625
--				: 525
--				: OK
--				: N/A
-- Comments		: This log field shows the status of the reference.
--				: OK indicates that the card is locked to the selected input.
--				: N/A indicates no valid reference signal available.
--				: LOST indicates that the reference signal has been Lost.
--				: 625 indicates that the reference signal detected is 625.
--				: 525 indicates that the reference signal detected is 525.
--
--
---------------------------------------------------------------------------------------------------
-- Header		: CH-LEFT
--
-- MIB ref		: swCardEventLogSlotXX       .7.67.72.45.76.69.70.84
-- absolute OID	: 1.3.6.1.4.1.7995.2.6.1.1.XX.7.67.72.45.76.69.70.84
-- Vary			: YES
--
-- Value(s)		: OK
--				: OVERFLOW
--				: LOST
-- Comments		: This log field shows the detected audio state of the Left Channel input.
--				: LOST indicates no input detected at this Channel. 
--				: OVERFLOW indicates that a bit overflow is detected on the Left channel.
--
---------------------------------------------------------------------------------------------------
-- Header		: CH-RIGHT
--
-- MIB ref		: swCardEventLogSlotXX       .8.67.72.45.82.73.71.72.84
-- absolute OID	: 1.3.6.1.4.1.7995.2.6.1.1.XX.8.67.72.45.82.73.71.72.84
-- Vary			: YES
--
-- Value(s)		: OK
--				: OVERFLOW
--				: LOST
-- Comments		: This log field shows the detected audio state of the Right Channel input.
--				: LOST indicates no input detected at this Channel. 
--				: OVERFLOW indicates that a bit overflow is detected on the Right channel.
--
---------------------------------------------------------------------------------------------------
