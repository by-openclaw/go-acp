-- ************************************************************************************
--        Snell Card:IQUDC12
--        Module Id#:643
--       Command Set:17
--          Filename:SNELL-IQUDC12-CMD-MIB.mib
--            Author:N Hewer
--              Date:13/11/2014
--              Time:15:20
--
-- Copyright (c) 2010 Snell Ltd
-- All rights reserved.
--
-- ************************************************************************************

SNELL-IQUDC12-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQUDC12,
    moduleIQUDC12MIB
        FROM SNELL-WILCOX-PRODUCT-REG;

 moduleIQUDC12CmdMi MODULE-IDENTITY
    LAST-UPDATED "1411131520Z"
    ORGANIZATION "Snell Ltd"
    CONTACT-INFO
        "Primary Author:N Hewer

         postal:    Southleigh Park House
                    Eastleigh Road
                    Havant, Hants
                    PO9 2PE
         phone:     +44 (0)23 92489000
         email:     snmp.support@snellgroup.com"
    DESCRIPTION
        "This file defines the Snell card, command set  translations."
    ::= { moduleIQUDC12MIB 1 }




--********************************************************************************
--*
--*  Snell Card:
--*  command set:
--*  list commands/menus:
--*
--******************************************************************************
	iqudc12CmdTable OBJECT-TYPE
		SYNTAX			SEQUENCE OF Iqudc12CmdEntry
		MAX-ACCESS		not-accessible
		STATUS			current
		DESCRIPTION
				"Note the instance of this table is relected in the command set Version"
		::= { moduleIQUDC12 1 }

	iqudc12CmdEntry OBJECT-TYPE
		SYNTAX		Iqudc12CmdEntry
		MAX-ACCESS		not-accessible
		STATUS			current
		DESCRIPTION
				"Entry in command table."
		INDEX	{ iqudc12SlotIndex }
		::= { iqudc12CmdTable 1 }

	Iqudc12CmdEntry ::=
		SEQUENCE {
			iqudc12SlotIndex
				Unsigned32,
			iqudc12Video1VideoInputInput1Std
				RollCallString,
			iqudc12Video1VideoInputInput2Std
				RollCallString,
			iqudc12Video1VideoInputInputAnalogStd
				RollCallString,
			iqudc12Video1VideoInputIPSelect
				INTEGER,
			iqudc12VideoInputValidStandards108050p
				INTEGER,
			iqudc12VideoInputValidStandards108059p
				INTEGER,
			iqudc12VideoInputValidStandards108025i
				INTEGER,
			iqudc12VideoInputValidStandards108029i
				INTEGER,
			iqudc12VideoInputValidStandards72050p
				INTEGER,
			iqudc12VideoInputValidStandards72059p
				INTEGER,
			iqudc12VideoInputValidStandards62525i
				INTEGER,
			iqudc12VideoInputValidStandards52529i
				INTEGER,
			iqudc12VideoInputValidStandards108023psf
				INTEGER,
			iqudc12VideoInputValidStandards108025psf
				INTEGER,
			iqudc12VideoInputValidStandards108025p
				INTEGER,
			iqudc12VideoInputValidStandards108029p
				INTEGER,
			iqudc12VideoInputErrorsErrorReset
				INTEGER,
			iqudc12VideoInputErrorsResetSec
				RollCallString,
			iqudc12VideoInputErrorsCRCErrs1
				RollCallString,
			iqudc12VideoInputErrorsANCErrs1
				RollCallString,
			iqudc12VideoInputErrorsCRCErrs2
				RollCallString,
			iqudc12VideoInputErrorsANCErrs2
				RollCallString,
			iqudc12VideoInputErrorsCRCErrSec1
				RollCallString,
			iqudc12VideoInputErrorsANCErrSec1
				RollCallString,
			iqudc12VideoInputErrorsCRCErrSec2
				RollCallString,
			iqudc12VideoInputErrorsANCErrSec2
				RollCallString,
			iqudc12Video1VideoInputSDAnlgEncode
				INTEGER,
			iqudc12Video1VideoInputAnlgType
				INTEGER,
			iqudc12Video1VideoInputPedComposDec
				INTEGER,
			iqudc12Video1VideoInputYCDelay
				INTEGER,
			iqudc12Video1BackupBackupEnable
				INTEGER,
			iqudc12Video1BackupORInput1State
				RollCallString,
			iqudc12Video1BackupORInput2State
				RollCallString,
			iqudc12Video1BackupRevertDelay
				INTEGER,
			iqudc12Video1BackupPriority
				INTEGER,
			iqudc12Video1BackupQualifyInvStd
				INTEGER,
			iqudc12Video1BackupQualifyCRCErr
				INTEGER,
			iqudc12Video1BackupQualifyANCErr
				INTEGER,
			iqudc12Video1BackupQualifyAudioFail
				INTEGER,
			iqudc12BackupInput1SelStatInp1OK
				RollCallString,
			iqudc12BackupInput1SelStatInp2FAIL
				RollCallString,
			iqudc12BackupInput1SelStatInp2Err
				RollCallString,
			iqudc12BackupInput1SelStatAUDFail2
				RollCallString,
			iqudc12BackupInput1SelStatStd2
				RollCallString,
			iqudc12BackupInput1SelStatGPI1
				RollCallString,
			iqudc12BackupInput1SelStatGPI2
				RollCallString,
			iqudc12BackupInput1SelEnblInp1OK
				INTEGER,
			iqudc12BackupInput1SelEnblInp2FAIL
				INTEGER,
			iqudc12BackupInput1SelEnblInp2Err
				INTEGER,
			iqudc12BackupInput1SelEnblGPI1
				INTEGER,
			iqudc12BackupInput1SelEnblGPI2
				INTEGER,
			iqudc12BackupInput1SelEnblStdInp2
				INTEGER,
			iqudc12BackupInput1SelDlyInp1OK
				INTEGER,
			iqudc12BackupInput1SelDlyInp2FAIL
				INTEGER,
			iqudc12BackupInput1SelDlyInp2Err
				INTEGER,
			iqudc12BackupInput1SelDlyGPI1
				INTEGER,
			iqudc12BackupInput1SelDlyGPI2
				INTEGER,
			iqudc12BackupInput1SelDlyAud2FAIL
				INTEGER,
			iqudc12BackupInput1SelDlyStd2
				INTEGER,
			iqudc12BackupInput1SelGPI1State
				INTEGER,
			iqudc12BackupInput1SelGPI2State
				INTEGER,
			iqudc12BackupInput1SelInp12AudFailG1C39149
				INTEGER,
			iqudc12BackupInput1SelInp12AudFailG1C39150
				INTEGER,
			iqudc12BackupInput1SelInp12AudFailG2C39151
				INTEGER,
			iqudc12BackupInput1SelInp12AudFailG2C39152
				INTEGER,
			iqudc12BackupInput1SelInp12AudFailG3C39153
				INTEGER,
			iqudc12BackupInput1SelInp12AudFailG3C39154
				INTEGER,
			iqudc12BackupInput1SelInp12AudFailG4C39155
				INTEGER,
			iqudc12BackupInput1SelInp12AudFailG4C39156
				INTEGER,
			iqudc12BackupInput1SelInp12AudFailLoc
				INTEGER,
			iqudc12BackupInput1SelSelAll
				INTEGER,
			iqudc12BackupInput1SelSelNone
				INTEGER,
			iqudc12BackupInput2SelStatInp2OK
				RollCallString,
			iqudc12BackupInput2SelStatInp1FAIL
				RollCallString,
			iqudc12BackupInput2SelStatInp1Err
				RollCallString,
			iqudc12BackupInput2SelStatAUDFail1
				RollCallString,
			iqudc12BackupInput2SelStatStd1
				RollCallString,
			iqudc12BackupInput2SelStatGPI1
				RollCallString,
			iqudc12BackupInput2SelStatGPI2
				RollCallString,
			iqudc12BackupInput2SelEnblInp2OK
				INTEGER,
			iqudc12BackupInput2SelEnblInp1FAIL
				INTEGER,
			iqudc12BackupInput2SelEnblInp1Err
				INTEGER,
			iqudc12BackupInput2SelEnblGPI1
				INTEGER,
			iqudc12BackupInput2SelEnblGPI2
				INTEGER,
			iqudc12BackupInput2SelEnblAudInp1Err
				INTEGER,
			iqudc12BackupInput2SelEnblStdInp1
				INTEGER,
			iqudc12BackupInput2SelInp21AudFailG1C39163
				INTEGER,
			iqudc12BackupInput2SelInp21AudFailG1C39164
				INTEGER,
			iqudc12BackupInput2SelInp21AudFailG2C39165
				INTEGER,
			iqudc12BackupInput2SelInp21AudFailG2C39166
				INTEGER,
			iqudc12BackupInput2SelInp21AudFailG3C39167
				INTEGER,
			iqudc12BackupInput2SelInp21AudFailG3C39168
				INTEGER,
			iqudc12BackupInput2SelInp21AudFailG4C39169
				INTEGER,
			iqudc12BackupInput2SelInp21AudFailG4C39170
				INTEGER,
			iqudc12BackupInput2SelDlyInp2OK
				INTEGER,
			iqudc12BackupInput2SelDlyInp1FAIL
				INTEGER,
			iqudc12BackupInput2SelDlyInp1Err
				INTEGER,
			iqudc12BackupInput2SelDlyGPI1
				INTEGER,
			iqudc12BackupInput2SelDlyGPI2
				INTEGER,
			iqudc12BackupInput2SelDlyAud1FAIL
				INTEGER,
			iqudc12BackupInput2SelDlyStd1
				INTEGER,
			iqudc12BackupInput2SelGPI1State
				INTEGER,
			iqudc12BackupInput2SelGPI2State
				INTEGER,
			iqudc12BackupInput2SelInp21AudFailLoc
				INTEGER,
			iqudc12BackupInput2SelSelAll
				INTEGER,
			iqudc12BackupInput2SelSelNone
				INTEGER,
			iqudc12Video2VideoOutputConversionStandard
				INTEGER,
			iqudc12Video2VideoOutputOutputAType
				INTEGER,
			iqudc12Video2VideoOutputOutputBType
				INTEGER,
			iqudc12Video2VideoOutputOutput1Std
				RollCallString,
			iqudc12VideoOutputVideoProcMasterGain
				INTEGER,
			iqudc12VideoOutputVideoProcYGain
				INTEGER,
			iqudc12VideoOutputVideoProcCGain
				INTEGER,
			iqudc12VideoOutputVideoProcBlackLevel
				INTEGER,
			iqudc12VideoOutputVideoProcHueLevel
				INTEGER,
			iqudc12VideoOutputVideoProcActiveSig
				INTEGER,
			iqudc12Video2VideoOutputDefaultOutput
				INTEGER,
			iqudc12Video2VideoOutputOutputMode
				INTEGER,
			iqudc12Video2VideoOutputPatternType
				INTEGER,
			iqudc12Video2VideoOutputSDAnlgEncode
				INTEGER,
			iqudc12Video2VideoOutputPedComposEnc
				INTEGER,
			iqudc12Video2VideoOutputAnlgType
				INTEGER,
			iqudc12VideoOutputUserCaptionsEnable
				INTEGER,
			iqudc12VideoOutputUserCaptionsEnableAlt
				INTEGER,
			iqudc12VideoOutputUserCaptionsText
				RollCallString,
			iqudc12VideoOutputUserCaptionsTextAlt
				RollCallString,
			iqudc12VideoOutputUserCaptionsXPos
				INTEGER,
			iqudc12VideoOutputUserCaptionsYPos
				INTEGER,
			iqudc12VideoOutputUserCaptionsXSize
				INTEGER,
			iqudc12VideoOutputUserCaptionsYSize
				INTEGER,
			iqudc12Video2VideoOutputOutStdnonConv
				INTEGER,
			iqudc12Video2VideoOutputFollowStdnonConv
				INTEGER,
			iqudc12Video2VideoOutputLastRefStd
				INTEGER,
			iqudc12Video2VideoOutputLastFrameRate
				INTEGER,
			iqudc12PictureAdvancedHEnhanceEnable
				INTEGER,
			iqudc12PictureAdvancedHEnhanceFrequencyBand
				INTEGER,
			iqudc12PictureAdvancedHEnhancePreset
				INTEGER,
			iqudc12PictureAdvancedHEnhanceGain
				INTEGER,
			iqudc12PictureAdvancedHEnhanceNoiseRejection
				INTEGER,
			iqudc12PictureRGBLegaliserRange
				INTEGER,
			iqudc12PictureLumaClipperEnable
				INTEGER,
			iqudc12PictureLumaClipperWhitemax
				INTEGER,
			iqudc12PictureLumaClipperBlackmin
				INTEGER,
			iqudc12PictureOutputPictureColorimetry
				INTEGER,
			iqudc12PictureEnhanceNoiseThreshold
				INTEGER,
			iqudc12PictureEnhanceSharpnessThreshold
				INTEGER,
			iqudc12PictureEnhanceSharpnessAmplitude
				INTEGER,
			iqudc12PictureOutputPictureFilmCadence
				RollCallString,
			iqudc12PictureOutputColorCorrectGreenOffset
				INTEGER,
			iqudc12PictureOutputColorCorrectBlueOffset
				INTEGER,
			iqudc12PictureOutputColorCorrectRedOffset
				INTEGER,
			iqudc12PictureOutputColorCorrectGangOffset
				INTEGER,
			iqudc12PictureOutputColorCorrectGreenGain
				INTEGER,
			iqudc12PictureOutputColorCorrectBlueGain
				INTEGER,
			iqudc12PictureOutputColorCorrectRedGain
				INTEGER,
			iqudc12PictureOutputColorCorrectGangGain
				INTEGER,
			iqudc12PictureOutputColorCorrectGreenGamma
				INTEGER,
			iqudc12PictureOutputColorCorrectBlueGamma
				INTEGER,
			iqudc12PictureOutputColorCorrectRedGamma
				INTEGER,
			iqudc12PictureOutputColorCorrectGangGamma
				INTEGER,
			iqudc12PictureOutputOutputBorderLeft
				INTEGER,
			iqudc12PictureOutputOutputBorderRight
				INTEGER,
			iqudc12PictureOutputOutputBorderTop
				INTEGER,
			iqudc12PictureOutputOutputBorderBottom
				INTEGER,
			iqudc12PictureOutputOutputBorderRed
				INTEGER,
			iqudc12PictureOutputOutputBorderGreen
				INTEGER,
			iqudc12PictureOutputOutputBorderBlue
				INTEGER,
			iqudc12PictureOutputSharpnessHcoeffSharp
				INTEGER,
			iqudc12PictureOutputSharpnessVcoeffSharp
				INTEGER,
			iqudc12MenuARCCtrlRecallDisplayMemo
				INTEGER,
			iqudc12MenuARCCtrlSelDisplayMemory
				INTEGER,
			iqudc12MenuARCCtrlSaveset
				INTEGER,
			iqudc12MenuARCCtrlSaveDispMemory
				INTEGER,
			iqudc12ARCCtrlDispMemoryNameChangeName
				RollCallString,
			iqudc12ARCCtrlARCSize
				INTEGER,
			iqudc12ARCCtrlARCAspect
				INTEGER,
			iqudc12ARCCtrlARCTilt
				INTEGER,
			iqudc12ARCCtrlARCPan
				INTEGER,
			iqudc12ARCCtrlInputCropLeft
				INTEGER,
			iqudc12ARCCtrlInputCropRight
				INTEGER,
			iqudc12ARCCtrlInputCropTop
				INTEGER,
			iqudc12ARCCtrlInputCropBottom
				INTEGER,
			iqudc12MenuARCCtrlSelStdPreset
				INTEGER,
			iqudc12MenuARCCtrlRecallStdPreset
				INTEGER,
			iqudc12MenuARCCtrlDefaultALLMemory
				INTEGER,
			iqudc12MenuARCCtrlLastDisplayMemory
				RollCallString,
			iqudc12MenuARCCtrl43AFDMapping2
				INTEGER,
			iqudc12MenuARCCtrl43AFDMapping3
				INTEGER,
			iqudc12MenuARCCtrl43AFDMapping4
				INTEGER,
			iqudc12MenuARCCtrl43AFDMapping8
				INTEGER,
			iqudc12MenuARCCtrl43AFDMapping9
				INTEGER,
			iqudc12MenuARCCtrl43AFDMapping10
				INTEGER,
			iqudc12MenuARCCtrl43AFDMapping11
				INTEGER,
			iqudc12MenuARCCtrl43AFDMapping12
				INTEGER,
			iqudc12MenuARCCtrl43AFDMapping13
				INTEGER,
			iqudc12MenuARCCtrl43AFDMapping14
				INTEGER,
			iqudc12MenuARCCtrl43AFDMapping15
				INTEGER,
			iqudc12MenuARCCtrl43AFDMapping16
				INTEGER,
			iqudc12MenuARCCtrl169AFDMapping2
				INTEGER,
			iqudc12MenuARCCtrl169AFDMapping3
				INTEGER,
			iqudc12MenuARCCtrl169AFDMapping4
				INTEGER,
			iqudc12MenuARCCtrl169AFDMapping8
				INTEGER,
			iqudc12MenuARCCtrl169AFDMapping9
				INTEGER,
			iqudc12MenuARCCtrl169AFDMapping10
				INTEGER,
			iqudc12MenuARCCtrl169AFDMapping11
				INTEGER,
			iqudc12MenuARCCtrl169AFDMapping12
				INTEGER,
			iqudc12MenuARCCtrl169AFDMapping13
				INTEGER,
			iqudc12MenuARCCtrl169AFDMapping14
				INTEGER,
			iqudc12MenuARCCtrl169AFDMapping15
				INTEGER,
			iqudc12MenuARCCtrl169AFDMapping16
				INTEGER,
			iqudc12MenuARCCtrlNoSignalMapping
				INTEGER,
			iqudc12MenuARCCtrlForceMapping1
				INTEGER,
			iqudc12MenuARCCtrlForceMapping2
				INTEGER,
			iqudc12MenuARCCtrlForceMapping3
				INTEGER,
			iqudc12MenuARCCtrlForceMapping4
				INTEGER,
			iqudc12MenuARCCtrl43ARCMapping2
				INTEGER,
			iqudc12MenuARCCtrl43ARCMapping3
				INTEGER,
			iqudc12MenuARCCtrl43ARCMapping4
				INTEGER,
			iqudc12MenuARCCtrl43ARCMapping8
				INTEGER,
			iqudc12MenuARCCtrl43ARCMapping9
				INTEGER,
			iqudc12MenuARCCtrl43ARCMapping10
				INTEGER,
			iqudc12MenuARCCtrl43ARCMapping11
				INTEGER,
			iqudc12MenuARCCtrl43ARCMapping12
				INTEGER,
			iqudc12MenuARCCtrl43ARCMapping13
				INTEGER,
			iqudc12MenuARCCtrl43ARCMapping14
				INTEGER,
			iqudc12MenuARCCtrl43ARCMapping15
				INTEGER,
			iqudc12MenuARCCtrl43ARCMapping16
				INTEGER,
			iqudc12MenuARCCtrl169ARCMapping2
				INTEGER,
			iqudc12MenuARCCtrl169ARCMapping3
				INTEGER,
			iqudc12MenuARCCtrl169ARCMapping4
				INTEGER,
			iqudc12MenuARCCtrl169ARCMapping8
				INTEGER,
			iqudc12MenuARCCtrl169ARCMapping9
				INTEGER,
			iqudc12MenuARCCtrl169ARCMapping139067
				INTEGER,
			iqudc12MenuARCCtrl169ARCMapping139068
				INTEGER,
			iqudc12MenuARCCtrl169ARCMapping139069
				INTEGER,
			iqudc12MenuARCCtrl169ARCMapping139070
				INTEGER,
			iqudc12MenuARCCtrl169ARCMapping139071
				INTEGER,
			iqudc12MenuARCCtrl169ARCMapping139072
				INTEGER,
			iqudc12MenuARCCtrl169ARCMapping16
				INTEGER,
			iqudc12MenuARCCtrlNoSignalARCMappi
				INTEGER,
			iqudc12MenuARCCtrlForceARCMapping1
				INTEGER,
			iqudc12MenuARCCtrlForceARCMapping2
				INTEGER,
			iqudc12MenuARCCtrlForceARCMapping3
				INTEGER,
			iqudc12MenuARCCtrlForceARCMapping4
				INTEGER,
			iqudc12MenuARCCtrlForceIndex
				INTEGER,
			iqudc12GenlockBlankingGenlockStandard
				INTEGER,
			iqudc12GenlockBlankingGenlockDelayMode
				INTEGER,
			iqudc12GenlockSetDelayDelayFrames
				INTEGER,
			iqudc12GenlockSetDelayVerticalPhase
				INTEGER,
			iqudc12GenlockSetDelayHorizontalPhase
				INTEGER,
			iqudc12GenlockSetDelayVerticalDelay
				INTEGER,
			iqudc12GenlockSetDelayHorizontalDelay
				INTEGER,
			iqudc12GenlockBlankingGenlockRefLogHide
				RollCallString,
			iqudc12GenlockDolbyELineStandard
				INTEGER,
			iqudc12GenlockDolbyELineAutoLineNo
				INTEGER,
			iqudc12DolbyELineUserDolbyELinePair1
				INTEGER,
			iqudc12DolbyELineUserDolbyELinePair2
				INTEGER,
			iqudc12DolbyELineUserDolbyELinePair3
				INTEGER,
			iqudc12DolbyELineUserDolbyELinePair4
				INTEGER,
			iqudc12DolbyELineUserDolbyELinePair5
				INTEGER,
			iqudc12DolbyELineUserDolbyELinePair6
				INTEGER,
			iqudc12DolbyELineUserDolbyELinePair7
				INTEGER,
			iqudc12DolbyELineUserDolbyELinePair8
				INTEGER,
			iqudc12GenlockDolbyELineUserLine525i29
				INTEGER,
			iqudc12GenlockDolbyELineUserLine625i25
				INTEGER,
			iqudc12GenlockDolbyELineUserLine720p50
				INTEGER,
			iqudc12GenlockDolbyELineUserLine720p59
				INTEGER,
			iqudc12GenlockDolbyELineUserLine1080i25
				INTEGER,
			iqudc12GenlockDolbyELineUserLine1080i29
				INTEGER,
			iqudc12GenlockDolbyELineUserLine1080p50
				INTEGER,
			iqudc12GenlockDolbyELineUserLine1080p59
				INTEGER,
			iqudc12GenlockDolbyELineAutoAlign1
				INTEGER,
			iqudc12GenlockDolbyELineAutoAlign2
				INTEGER,
			iqudc12GenlockDolbyELineAutoAlign3
				INTEGER,
			iqudc12GenlockDolbyELineAutoAlign4
				INTEGER,
			iqudc12GenlockDolbyELineAutoAlign5
				INTEGER,
			iqudc12GenlockDolbyELineAutoAlign6
				INTEGER,
			iqudc12GenlockDolbyELineAutoAlign7
				INTEGER,
			iqudc12GenlockDolbyELineAutoAlign8
				INTEGER,
			iqudc12BlankingHANCVBIBlankingStandard
				INTEGER,
			iqudc12BlankingHANCVBIBlankingBlankAll
				INTEGER,
			iqudc12BlankingHANCVBIBlankingPassAll
				INTEGER,
			iqudc12BlankingHANCVBIBlankingBlank1
				INTEGER,
			iqudc12BlankingHANCVBIBlankingBlank2
				INTEGER,
			iqudc12BlankingHANCVBIBlankingBlank3
				INTEGER,
			iqudc12BlankingHANCVBIBlankingBlank4
				INTEGER,
			iqudc12BlankingHANCVBIBlankingBlank5
				INTEGER,
			iqudc12BlankingHANCVBIBlankingBlank6
				INTEGER,
			iqudc12BlankingHANCVBIBlankingBlank7
				INTEGER,
			iqudc12BlankingHANCVBIBlankingBlank8
				INTEGER,
			iqudc12BlankingHANCVBIBlankingBlank9
				INTEGER,
			iqudc12BlankingHANCVBIBlankingBlank10
				INTEGER,
			iqudc12BlankingHANCVBIBlankingBlank11
				INTEGER,
			iqudc12BlankingHANCVBIBlankingBlank12
				INTEGER,
			iqudc12BlankingHANCVBIBlankingBlank13
				INTEGER,
			iqudc12BlankingHANCVBIBlankingBlank14
				INTEGER,
			iqudc12BlankingHANCVBIBlankingBlank15
				INTEGER,
			iqudc12BlankingHANCVBIBlankingBlank16
				INTEGER,
			iqudc12BlankingHANCVBIBlankingBlank17
				INTEGER,
			iqudc12BlankingHANCVBIBlankingBlank18
				INTEGER,
			iqudc12BlankingHANCVBIBlankingBlank19
				INTEGER,
			iqudc12BlankingHANCVBIBlankingBlank20
				INTEGER,
			iqudc12BlankingHANCVBIBlankingBlank21
				INTEGER,
			iqudc12BlankingHANCVBIBlankingBlank22
				INTEGER,
			iqudc12BlankingHANCVBIBlankingBlank23
				INTEGER,
			iqudc12BlankingHANCVBIBlankingBlank24
				INTEGER,
			iqudc12BlankingHANCVBIBlankingBlank25
				INTEGER,
			iqudc12BlankingHANCVBIBlankingBlank26
				INTEGER,
			iqudc12BlankingHANCVBIBlankingBlank27
				INTEGER,
			iqudc12BlankingHANCVBIBlankingBlank28
				INTEGER,
			iqudc12BlankingHANCVBIBlankingBlank29
				INTEGER,
			iqudc12BlankingHANCVBIBlankingBlank30
				INTEGER,
			iqudc12BlankingHANCVBIBlankingBlank31
				INTEGER,
			iqudc12BlankingHANCVBIBlankingBlank32
				INTEGER,
			iqudc12BlankingHANCVBIBlankingBlank33
				INTEGER,
			iqudc12BlankingHANCVBIBlankingBlank34
				INTEGER,
			iqudc12BlankingHANCVBIBlankingBlank35
				INTEGER,
			iqudc12BlankingHANCVBIBlankingBlank36
				INTEGER,
			iqudc12BlankingHANCVBIBlankingBlankHANC
				INTEGER,
			iqudc12MenuWSSCtrlEnableMapper
				INTEGER,
			iqudc12MenuWSSCtrlForceEnable
				INTEGER,
			iqudc12MenuWSSCtrlIPWSSSignal
				INTEGER,
			iqudc12MenuWSSCtrlOPWSS43
				INTEGER,
			iqudc12MenuWSSCtrlDispMem43
				INTEGER,
			iqudc12WSSCtrlWidescreenIP2016
				INTEGER,
			iqudc12WSSCtrlWidescreenIPPriority
				INTEGER,
			iqudc12WSSCtrlWidescreenIPWSSInEnable
				INTEGER,
			iqudc12WSSCtrlWidescreenIPVIInEnable
				INTEGER,
			iqudc12WSSCtrlWidescreenOP2016
				INTEGER,
			iqudc12WSSCtrlWidescreenOPWSSOutEnable
				INTEGER,
			iqudc12WSSCtrlWidescreenOPVIOutEnable
				INTEGER,
			iqudc12MenuWSSCtrlLine1ReadAFD
				RollCallString,
			iqudc12MenuWSSCtrlLine1ReadAR
				RollCallString,
			iqudc12MenuWSSCtrlLine1WriteAFD
				RollCallString,
			iqudc12MenuWSSCtrlLine1WriteAR
				RollCallString,
			iqudc12MenuWSSCtrlPreset
				INTEGER,
			iqudc12MenuWSSCtrlPreset43
				INTEGER,
			iqudc12MenuWSSCtrlPreset169
				INTEGER,
			iqudc12MenuWSSCtrlBlank62523
				INTEGER,
			iqudc12MenuWSSCtrlBlank625336
				INTEGER,
			iqudc12MenuWSSCtrlBlank52521
				INTEGER,
			iqudc12MenuWSSCtrlBlank52522
				INTEGER,
			iqudc12MenuWSSCtrlBlank525283
				INTEGER,
			iqudc12MenuWSSCtrlBlank525284
				INTEGER,
			iqudc12AncillaryDataSMPTE20162016IPF1Status
				RollCallString,
			iqudc12AncillaryDataSMPTE20162016OPF1Line
				INTEGER,
			iqudc12AncillaryDataSMPTE20162016Follow
				INTEGER,
			iqudc12AncillaryDataSDVBILine7
				INTEGER,
			iqudc12AncillaryDataSDVBILine8
				INTEGER,
			iqudc12AncillaryDataSDVBILine9
				INTEGER,
			iqudc12AncillaryDataSDVBILine10
				INTEGER,
			iqudc12AncillaryDataSDVBILine11
				INTEGER,
			iqudc12AncillaryDataSDVBILine12
				INTEGER,
			iqudc12AncillaryDataSDVBILine13
				INTEGER,
			iqudc12AncillaryDataSDVBILine14
				INTEGER,
			iqudc12AncillaryDataSDVBILine15
				INTEGER,
			iqudc12AncillaryDataSDVBILine16
				INTEGER,
			iqudc12AncillaryDataSDVBILine17
				INTEGER,
			iqudc12AncillaryDataSDVBILine18
				INTEGER,
			iqudc12AncillaryDataSDVBILine19
				INTEGER,
			iqudc12AncillaryDataSDVBILine20
				INTEGER,
			iqudc12AncillaryDataSDVBILine21
				INTEGER,
			iqudc12AncillaryDataSDVBILine22
				INTEGER,
			iqudc12AncillaryDataSDVBILine23
				INTEGER,
			iqudc12AncillaryDataSDVBIVIout
				INTEGER,
			iqudc12AncillaryDataSDVBIVIIPStatus
				INTEGER,
			iqudc12AncillaryDataSDVBIWSSIPStatus
				INTEGER,
			iqudc12AncillaryDataSDVBIVITCIPStatus
				INTEGER,
			iqudc12AncillaryDataSDVBIWSTIPStatus
				INTEGER,
			iqudc12AncillaryDataSDVBICC608IPStatus
				INTEGER,
			iqudc12AncillaryDataSDVBIWSTLine7
				RollCallString,
			iqudc12AncillaryDataSDVBIWSTLine8
				RollCallString,
			iqudc12AncillaryDataSDVBIWSTLine9
				RollCallString,
			iqudc12AncillaryDataSDVBIWSTLine10
				RollCallString,
			iqudc12AncillaryDataSDVBIWSTLine11
				RollCallString,
			iqudc12AncillaryDataSDVBIWSTLine12
				RollCallString,
			iqudc12AncillaryDataSDVBIWSTLine13
				RollCallString,
			iqudc12AncillaryDataSDVBIWSTLine14
				RollCallString,
			iqudc12AncillaryDataSDVBIWSTLine15
				RollCallString,
			iqudc12AncillaryDataSDVBIWSTLine16
				RollCallString,
			iqudc12AncillaryDataSDVBIWSTLine17
				RollCallString,
			iqudc12AncillaryDataSDVBIWSTLine18
				RollCallString,
			iqudc12AncillaryDataSDVBIWSTLine19
				RollCallString,
			iqudc12AncillaryDataSDVBIWSTLine20
				RollCallString,
			iqudc12AncillaryDataSDVBIWSTLine21
				RollCallString,
			iqudc12AncillaryDataSDVBIWSTLine22
				RollCallString,
			iqudc12HDVANCHDCaptionHDCaptionEnable
				INTEGER,
			iqudc12HDVANCHDCaptionHDCaptionIPLine
				RollCallString,
			iqudc12HDVANCHDCaptionHDCaptionOPLine
				INTEGER,
			iqudc12HDVANCHDCaptionHDFollowIPLine
				INTEGER,
			iqudc12HDVANCHDCaptionAllowMultipleOP47
				INTEGER,
			iqudc12HDCaptionOP47Packet2HDCaptionIPLine
				RollCallString,
			iqudc12HDCaptionOP47Packet2HDCaptionOPLine
				INTEGER,
			iqudc12HDCaptionOP47Packet3HDCaptionIPLine
				RollCallString,
			iqudc12HDCaptionOP47Packet3HDCaptionOPLine
				INTEGER,
			iqudc12TimecodeInputSelectRefVITCInp
				INTEGER,
			iqudc12TimecodeInputRefVITCStatus
				RollCallString,
			iqudc12TimecodeInputSelectInpVITCInp
				INTEGER,
			iqudc12TimecodeInputInputVITCStatus
				RollCallString,
			iqudc12TimecodeInputSelectATCLTCInpu
				INTEGER,
			iqudc12TimecodeInputInputATCLTCStatu
				RollCallString,
			iqudc12TimecodeInputInputATCLTCLine
				RollCallString,
			iqudc12TimecodeInputSelectATCVITCInp
				INTEGER,
			iqudc12TimecodeInputInputATCVITCStat
				RollCallString,
			iqudc12TimecodeInputIPHDATCVITCLin
				RollCallString,
			iqudc12TimecodeInputIPSDATCVITCLin
				RollCallString,
			iqudc12TimecodeInputRefreshrate
				INTEGER,
			iqudc12TimecodeFreerunHours
				INTEGER,
			iqudc12TimecodeFreerunMinutes
				INTEGER,
			iqudc12TimecodeFreerunSeconds
				INTEGER,
			iqudc12TimecodeFreerunApply
				INTEGER,
			iqudc12TimecodeOutputTimecodeValue
				RollCallString,
			iqudc12TimecodeOutputTimecodeSource
				RollCallString,
			iqudc12TimecodeOutputSourcePriority1
				INTEGER,
			iqudc12TimecodeOutputSourcePriority2
				INTEGER,
			iqudc12TimecodeOutputOffsetDirection
				INTEGER,
			iqudc12TimecodeOutputOffsetField
				INTEGER,
			iqudc12TimecodeOutputOffsetFrames
				INTEGER,
			iqudc12OutputInsertSDATCVITCEnable
				INTEGER,
			iqudc12OutputInsertSDATCVITCFollowInputLine
				INTEGER,
			iqudc12OutputInsertSDATCVITCOutputLine
				INTEGER,
			iqudc12OutputInsertHDATCLTCEnable
				INTEGER,
			iqudc12OutputInsertHDATCLTCFollowInputLine
				INTEGER,
			iqudc12OutputInsertHDATCLTCOutputLine
				INTEGER,
			iqudc12OutputInsertHDATCVITCEnable
				INTEGER,
			iqudc12OutputInsertHDATCVITCFollowInputLine
				INTEGER,
			iqudc12OutputInsertHDATCVITCOutputLineF1
				INTEGER,
			iqudc12TimecodeOutputATCVITCLegacy
				INTEGER,
			iqudc12TimecodeOutputOffifNoInput
				INTEGER,
			iqudc12Disembed18Disembed1Disembed11procamp
				INTEGER,
			iqudc12Disembed18Disembed1Disembed12procamp
				INTEGER,
			iqudc12Disembed18Disembed1Mute11
				INTEGER,
			iqudc12Disembed18Disembed1Mute12
				INTEGER,
			iqudc12Disembed18Disembed1Stereo1
				INTEGER,
			iqudc12Disembed18Disembed1Disembed11invert
				INTEGER,
			iqudc12Disembed18Disembed1Disembed12invert
				INTEGER,
			iqudc12Disembed18Disembed1dolbyLine
				RollCallString,
			iqudc12Disembed18Disembed2Disembed21procamp
				INTEGER,
			iqudc12Disembed18Disembed2Disembed22procamp
				INTEGER,
			iqudc12Disembed18Disembed2Mute21
				INTEGER,
			iqudc12Disembed18Disembed2Mute22
				INTEGER,
			iqudc12Disembed18Disembed2Stereo2
				INTEGER,
			iqudc12Disembed18Disembed2Disembed21invert
				INTEGER,
			iqudc12Disembed18Disembed2Disembed22invert
				INTEGER,
			iqudc12Disembed18Disembed2dolbyLine
				RollCallString,
			iqudc12Disembed18Disembed3Disembed31procamp
				INTEGER,
			iqudc12Disembed18Disembed3Disembed32procamp
				INTEGER,
			iqudc12Disembed18Disembed3Mute31
				INTEGER,
			iqudc12Disembed18Disembed3Mute32
				INTEGER,
			iqudc12Disembed18Disembed3Stereo3
				INTEGER,
			iqudc12Disembed18Disembed3Disembed31invert
				INTEGER,
			iqudc12Disembed18Disembed3Disembed32invert
				INTEGER,
			iqudc12Disembed18Disembed3dolbyLine
				RollCallString,
			iqudc12Disembed18Disembed4Disembed41procamp
				INTEGER,
			iqudc12Disembed18Disembed4Disembed42procamp
				INTEGER,
			iqudc12Disembed18Disembed4Mute41
				INTEGER,
			iqudc12Disembed18Disembed4Mute42
				INTEGER,
			iqudc12Disembed18Disembed4Stereo4
				INTEGER,
			iqudc12Disembed18Disembed4Disembed41invert
				INTEGER,
			iqudc12Disembed18Disembed4Disembed42invert
				INTEGER,
			iqudc12Disembed18Disembed4dolbyLine
				RollCallString,
			iqudc12Disembed18Disembed5Disembed51procamp
				INTEGER,
			iqudc12Disembed18Disembed5Disembed52procamp
				INTEGER,
			iqudc12Disembed18Disembed5Mute51
				INTEGER,
			iqudc12Disembed18Disembed5Mute52
				INTEGER,
			iqudc12Disembed18Disembed5Stereo5
				INTEGER,
			iqudc12Disembed18Disembed5Disembed51invert
				INTEGER,
			iqudc12Disembed18Disembed5Disembed52invert
				INTEGER,
			iqudc12Disembed18Disembed5dolbyLine
				RollCallString,
			iqudc12Disembed18Disembed6Disembed61procamp
				INTEGER,
			iqudc12Disembed18Disembed6Disembed62procamp
				INTEGER,
			iqudc12Disembed18Disembed6Mute61
				INTEGER,
			iqudc12Disembed18Disembed6Mute62
				INTEGER,
			iqudc12Disembed18Disembed6Stereo6
				INTEGER,
			iqudc12Disembed18Disembed6Disembed61invert
				INTEGER,
			iqudc12Disembed18Disembed6Disembed62invert
				INTEGER,
			iqudc12Disembed18Disembed6dolbyLine
				RollCallString,
			iqudc12Disembed18Disembed7Disembed71procamp
				INTEGER,
			iqudc12Disembed18Disembed7Disembed72procamp
				INTEGER,
			iqudc12Disembed18Disembed7Mute71
				INTEGER,
			iqudc12Disembed18Disembed7Mute72
				INTEGER,
			iqudc12Disembed18Disembed7Stereo7
				INTEGER,
			iqudc12Disembed18Disembed7Disembed71invert
				INTEGER,
			iqudc12Disembed18Disembed7Disembed72invert
				INTEGER,
			iqudc12Disembed18Disembed7dolbyLine
				RollCallString,
			iqudc12Disembed18Disembed8Disembed81procamp
				INTEGER,
			iqudc12Disembed18Disembed8Disembed82procamp
				INTEGER,
			iqudc12Disembed18Disembed8Mute81
				INTEGER,
			iqudc12Disembed18Disembed8Mute82
				INTEGER,
			iqudc12Disembed18Disembed8Stereo8
				INTEGER,
			iqudc12Disembed18Disembed8Disembed81invert
				INTEGER,
			iqudc12Disembed18Disembed8Disembed82invert
				INTEGER,
			iqudc12Disembed18Disembed8dolbyLine
				RollCallString,
			iqudc12AudioInputDisembed18ProcampSaveset
				INTEGER,
			iqudc12AESInput18AESInput1AESInput11procamp
				INTEGER,
			iqudc12AESInput18AESInput1AESInput12procamp
				INTEGER,
			iqudc12AESInput18AESInput1Mute11
				INTEGER,
			iqudc12AESInput18AESInput1Mute12
				INTEGER,
			iqudc12AESInput18AESInput1Stereo1
				INTEGER,
			iqudc12AESInput18AESInput1AESInput11invert
				INTEGER,
			iqudc12AESInput18AESInput1AESInput12invert
				INTEGER,
			iqudc12AESInput18AESInput1AESIO
				INTEGER,
			iqudc12AESInput18AESInput2AESInput21procamp
				INTEGER,
			iqudc12AESInput18AESInput2AESInput22procamp
				INTEGER,
			iqudc12AESInput18AESInput2Mute21
				INTEGER,
			iqudc12AESInput18AESInput2Mute22
				INTEGER,
			iqudc12AESInput18AESInput2Stereo2
				INTEGER,
			iqudc12AESInput18AESInput2AESInput21invert
				INTEGER,
			iqudc12AESInput18AESInput2AESInput22invert
				INTEGER,
			iqudc12AESInput18AESInput2AESIO
				INTEGER,
			iqudc12AESInput18AESInput3AESInput31procamp
				INTEGER,
			iqudc12AESInput18AESInput3AESInput32procamp
				INTEGER,
			iqudc12AESInput18AESInput3Mute31
				INTEGER,
			iqudc12AESInput18AESInput3Mute32
				INTEGER,
			iqudc12AESInput18AESInput3Stereo3
				INTEGER,
			iqudc12AESInput18AESInput3AESInput31invert
				INTEGER,
			iqudc12AESInput18AESInput3AESInput32invert
				INTEGER,
			iqudc12AESInput18AESInput3AESIO
				INTEGER,
			iqudc12AESInput18AESInput4AESInput41procamp
				INTEGER,
			iqudc12AESInput18AESInput4AESInput42procamp
				INTEGER,
			iqudc12AESInput18AESInput4Mute41
				INTEGER,
			iqudc12AESInput18AESInput4Mute42
				INTEGER,
			iqudc12AESInput18AESInput4Stereo4
				INTEGER,
			iqudc12AESInput18AESInput4AESInput41invert
				INTEGER,
			iqudc12AESInput18AESInput4AESInput42invert
				INTEGER,
			iqudc12AESInput18AESInput4AESIO
				INTEGER,
			iqudc12AESInput18AESInput5AESInput51procamp
				INTEGER,
			iqudc12AESInput18AESInput5AESInput52procamp
				INTEGER,
			iqudc12AESInput18AESInput5Mute51
				INTEGER,
			iqudc12AESInput18AESInput5Mute52
				INTEGER,
			iqudc12AESInput18AESInput5Stereo5
				INTEGER,
			iqudc12AESInput18AESInput5AESInput51invert
				INTEGER,
			iqudc12AESInput18AESInput5AESInput52invert
				INTEGER,
			iqudc12AESInput18AESInput5AESIO
				INTEGER,
			iqudc12AESInput18AESInput6AESInput61procamp
				INTEGER,
			iqudc12AESInput18AESInput6AESInput62procamp
				INTEGER,
			iqudc12AESInput18AESInput6Mute61
				INTEGER,
			iqudc12AESInput18AESInput6Mute62
				INTEGER,
			iqudc12AESInput18AESInput6Stereo6
				INTEGER,
			iqudc12AESInput18AESInput6AESInput61invert
				INTEGER,
			iqudc12AESInput18AESInput6AESInput62invert
				INTEGER,
			iqudc12AESInput18AESInput6AESIO
				INTEGER,
			iqudc12AESInput18AESInput7AESInput71procamp
				INTEGER,
			iqudc12AESInput18AESInput7AESInput72procamp
				INTEGER,
			iqudc12AESInput18AESInput7Mute71
				INTEGER,
			iqudc12AESInput18AESInput7Mute72
				INTEGER,
			iqudc12AESInput18AESInput7Stereo7
				INTEGER,
			iqudc12AESInput18AESInput7AESInput71invert
				INTEGER,
			iqudc12AESInput18AESInput7AESInput72invert
				INTEGER,
			iqudc12AESInput18AESInput7AESIO
				INTEGER,
			iqudc12AESInput18AESInput8AESInput81procamp
				INTEGER,
			iqudc12AESInput18AESInput8AESInput82procamp
				INTEGER,
			iqudc12AESInput18AESInput8Mute81
				INTEGER,
			iqudc12AESInput18AESInput8Mute82
				INTEGER,
			iqudc12AESInput18AESInput8Stereo8
				INTEGER,
			iqudc12AESInput18AESInput8AESInput81invert
				INTEGER,
			iqudc12AESInput18AESInput8AESInput82invert
				INTEGER,
			iqudc12AESInput18AESInput8AESIO
				INTEGER,
			iqudc12AnalogInput12AnalogInput1AnalogInput11proc
				INTEGER,
			iqudc12AnalogInput12AnalogInput1AnalogInput12proc
				INTEGER,
			iqudc12AnalogInput12AnalogInput1Mute11
				INTEGER,
			iqudc12AnalogInput12AnalogInput1Mute12
				INTEGER,
			iqudc12AnalogInput12AnalogInput1Stereo1
				INTEGER,
			iqudc12AnalogInput12AnalogInput1AnalogInput11inve
				INTEGER,
			iqudc12AnalogInput12AnalogInput1AnalogInput12inve
				INTEGER,
			iqudc12AnalogInput12AnalogInput2AnalogInput21proc
				INTEGER,
			iqudc12AnalogInput12AnalogInput2AnalogInput22proc
				INTEGER,
			iqudc12AnalogInput12AnalogInput2Mute21
				INTEGER,
			iqudc12AnalogInput12AnalogInput2Mute22
				INTEGER,
			iqudc12AnalogInput12AnalogInput2Stereo2
				INTEGER,
			iqudc12AnalogInput12AnalogInput2AnalogInput21inve
				INTEGER,
			iqudc12AnalogInput12AnalogInput2AnalogInput22inve
				INTEGER,
			iqudc12Embed18Embed1Embed11procamp
				INTEGER,
			iqudc12Embed18Embed1Embed12procamp
				INTEGER,
			iqudc12Embed18Embed1Mute11
				INTEGER,
			iqudc12Embed18Embed1Mute12
				INTEGER,
			iqudc12Embed18Embed1Stereo1
				INTEGER,
			iqudc12Embed18Embed1dolbyLine
				RollCallString,
			iqudc12Embed18Embed2Embed21procamp
				INTEGER,
			iqudc12Embed18Embed2Embed22procamp
				INTEGER,
			iqudc12Embed18Embed2Mute21
				INTEGER,
			iqudc12Embed18Embed2Mute22
				INTEGER,
			iqudc12Embed18Embed2Stereo2
				INTEGER,
			iqudc12Embed18Embed2dolbyLine
				RollCallString,
			iqudc12Embed18Embed3Embed31procamp
				INTEGER,
			iqudc12Embed18Embed3Embed32procamp
				INTEGER,
			iqudc12Embed18Embed3Mute31
				INTEGER,
			iqudc12Embed18Embed3Mute32
				INTEGER,
			iqudc12Embed18Embed3Stereo3
				INTEGER,
			iqudc12Embed18Embed3dolbyLine
				RollCallString,
			iqudc12Embed18Embed4Embed41procamp
				INTEGER,
			iqudc12Embed18Embed4Embed42procamp
				INTEGER,
			iqudc12Embed18Embed4Mute41
				INTEGER,
			iqudc12Embed18Embed4Mute42
				INTEGER,
			iqudc12Embed18Embed4Stereo4
				INTEGER,
			iqudc12Embed18Embed4dolbyLine
				RollCallString,
			iqudc12Embed18Embed5Embed51procamp
				INTEGER,
			iqudc12Embed18Embed5Embed52procamp
				INTEGER,
			iqudc12Embed18Embed5Mute51
				INTEGER,
			iqudc12Embed18Embed5Mute52
				INTEGER,
			iqudc12Embed18Embed5Stereo5
				INTEGER,
			iqudc12Embed18Embed5dolbyLine
				RollCallString,
			iqudc12Embed18Embed6Embed61procamp
				INTEGER,
			iqudc12Embed18Embed6Embed62procamp
				INTEGER,
			iqudc12Embed18Embed6Mute61
				INTEGER,
			iqudc12Embed18Embed6Mute62
				INTEGER,
			iqudc12Embed18Embed6Stereo6
				INTEGER,
			iqudc12Embed18Embed6dolbyLine
				RollCallString,
			iqudc12Embed18Embed7Embed71procamp
				INTEGER,
			iqudc12Embed18Embed7Embed72procamp
				INTEGER,
			iqudc12Embed18Embed7Mute71
				INTEGER,
			iqudc12Embed18Embed7Mute72
				INTEGER,
			iqudc12Embed18Embed7Stereo7
				INTEGER,
			iqudc12Embed18Embed7dolbyLine
				RollCallString,
			iqudc12Embed18Embed8Embed81procamp
				INTEGER,
			iqudc12Embed18Embed8Embed82procamp
				INTEGER,
			iqudc12Embed18Embed8Mute81
				INTEGER,
			iqudc12Embed18Embed8Mute82
				INTEGER,
			iqudc12Embed18Embed8Stereo8
				INTEGER,
			iqudc12Embed18Embed8dolbyLine
				RollCallString,
			iqudc12Embed18GroupEmbGroup1
				INTEGER,
			iqudc12Embed18GroupEmbGroup2
				INTEGER,
			iqudc12Embed18GroupEmbGroup3
				INTEGER,
			iqudc12Embed18GroupEmbGroup4
				INTEGER,
			iqudc12AESOutput18AESOutput1AESOutput11procam
				INTEGER,
			iqudc12AESOutput18AESOutput1AESOutput12procam
				INTEGER,
			iqudc12AESOutput18AESOutput1Mute11
				INTEGER,
			iqudc12AESOutput18AESOutput1Mute12
				INTEGER,
			iqudc12AESOutput18AESOutput1Stereo1
				INTEGER,
			iqudc12AESOutput18AESOutput2AESOutput21procam
				INTEGER,
			iqudc12AESOutput18AESOutput2AESOutput22procam
				INTEGER,
			iqudc12AESOutput18AESOutput2Mute21
				INTEGER,
			iqudc12AESOutput18AESOutput2Mute22
				INTEGER,
			iqudc12AESOutput18AESOutput2Stereo2
				INTEGER,
			iqudc12AESOutput18AESOutput3AESOutput31procam
				INTEGER,
			iqudc12AESOutput18AESOutput3AESOutput32procam
				INTEGER,
			iqudc12AESOutput18AESOutput3Mute31
				INTEGER,
			iqudc12AESOutput18AESOutput3Mute32
				INTEGER,
			iqudc12AESOutput18AESOutput3Stereo3
				INTEGER,
			iqudc12AESOutput18AESOutput4AESOutput41procam
				INTEGER,
			iqudc12AESOutput18AESOutput4AESOutput42procam
				INTEGER,
			iqudc12AESOutput18AESOutput4Mute41
				INTEGER,
			iqudc12AESOutput18AESOutput4Mute42
				INTEGER,
			iqudc12AESOutput18AESOutput4Stereo4
				INTEGER,
			iqudc12AESOutput18AESOutput5AESOutput51procam
				INTEGER,
			iqudc12AESOutput18AESOutput5AESOutput52procam
				INTEGER,
			iqudc12AESOutput18AESOutput5Mute51
				INTEGER,
			iqudc12AESOutput18AESOutput5Mute52
				INTEGER,
			iqudc12AESOutput18AESOutput5Stereo5
				INTEGER,
			iqudc12AESOutput18AESOutput6AESOutput61procam
				INTEGER,
			iqudc12AESOutput18AESOutput6AESOutput62procam
				INTEGER,
			iqudc12AESOutput18AESOutput6Mute61
				INTEGER,
			iqudc12AESOutput18AESOutput6Mute62
				INTEGER,
			iqudc12AESOutput18AESOutput6Stereo6
				INTEGER,
			iqudc12AESOutput18AESOutput7AESOutput71procam
				INTEGER,
			iqudc12AESOutput18AESOutput7AESOutput72procam
				INTEGER,
			iqudc12AESOutput18AESOutput7Mute71
				INTEGER,
			iqudc12AESOutput18AESOutput7Mute72
				INTEGER,
			iqudc12AESOutput18AESOutput7Stereo7
				INTEGER,
			iqudc12AESOutput18AESOutput8AESOutput81procam
				INTEGER,
			iqudc12AESOutput18AESOutput8AESOutput82procam
				INTEGER,
			iqudc12AESOutput18AESOutput8Mute81
				INTEGER,
			iqudc12AESOutput18AESOutput8Mute82
				INTEGER,
			iqudc12AESOutput18AESOutput8Stereo8
				INTEGER,
			iqudc12AnalogOutput12AnalogOutput1AnalogOutput11pro
				INTEGER,
			iqudc12AnalogOutput12AnalogOutput1AnalogOutput12pro
				INTEGER,
			iqudc12AnalogOutput12AnalogOutput1Mute11
				INTEGER,
			iqudc12AnalogOutput12AnalogOutput1Mute12
				INTEGER,
			iqudc12AnalogOutput12AnalogOutput1Stereo1
				INTEGER,
			iqudc12AnalogOutput12AnalogOutput2AnalogOutput21pro
				INTEGER,
			iqudc12AnalogOutput12AnalogOutput2AnalogOutput22pro
				INTEGER,
			iqudc12AnalogOutput12AnalogOutput2Mute21
				INTEGER,
			iqudc12AnalogOutput12AnalogOutput2Mute22
				INTEGER,
			iqudc12AnalogOutput12AnalogOutput2Stereo2
				INTEGER,
			iqudc12AudioOutputRoutingNamesOutName30
				RollCallString,
			iqudc12AudioOutputRoutingNamesOutName31
				RollCallString,
			iqudc12AudioOutputRoutingNamesOutName32
				RollCallString,
			iqudc12AudioOutputRoutingNamesOutName33
				RollCallString,
			iqudc12AudioOutputRoutingNamesOutName34
				RollCallString,
			iqudc12AudioOutputRoutingNamesOutName35
				RollCallString,
			iqudc12AudioOutputRoutingNamesOutName36
				RollCallString,
			iqudc12AudioOutputRoutingNamesOutName37
				RollCallString,
			iqudc12AudioOutputRoutingNamesOutName38
				RollCallString,
			iqudc12AudioOutputRoutingNamesOutName39
				RollCallString,
			iqudc12AudioOutputRoutingNamesOutName40
				RollCallString,
			iqudc12AudioOutputRoutingNamesOutName41
				RollCallString,
			iqudc12AudioOutputRoutingNamesOutName42
				RollCallString,
			iqudc12AudioOutputRoutingNamesLegacyEnable
				INTEGER,
			iqudc12AudioOutputRoutingNamesLegacyHide
				RollCallString,
			iqudc12AudSetupDelaySelectTotalDelayBus1
				RollCallString,
			iqudc12AudSetupDelaySelectTotalDelayBus2
				RollCallString,
			iqudc12AudSetupDelaySelectTotalDelayBus3
				RollCallString,
			iqudc12AudSetupDelaySelectTotalDelayBus4
				RollCallString,
			iqudc12AudSetupDelaySelectTotalDelayBus5
				RollCallString,
			iqudc12AudSetupDelaySelectTotalDelayBus6
				RollCallString,
			iqudc12AudSetupDelaySelectTotalDelayBus7
				RollCallString,
			iqudc12AudSetupDelaySelectTotalDelayBus8
				RollCallString,
			iqudc12AudSetupDelaySelectBus1Delay
				INTEGER,
			iqudc12AudSetupDelaySelectBus2Delay
				INTEGER,
			iqudc12AudSetupDelaySelectBus3Delay
				INTEGER,
			iqudc12AudSetupDelaySelectBus4Delay
				INTEGER,
			iqudc12AudSetupDelaySelectBus5Delay
				INTEGER,
			iqudc12AudSetupDelaySelectBus6Delay
				INTEGER,
			iqudc12AudSetupDelaySelectBus7Delay
				INTEGER,
			iqudc12AudSetupDelaySelectBus8Delay
				INTEGER,
			iqudc12AudSetupDelaySelectBus1Fine
				INTEGER,
			iqudc12AudSetupDelaySelectBus2Fine
				INTEGER,
			iqudc12AudSetupDelaySelectBus3Fine
				INTEGER,
			iqudc12AudSetupDelaySelectBus4Fine
				INTEGER,
			iqudc12AudSetupDelaySelectBus5Fine
				INTEGER,
			iqudc12AudSetupDelaySelectBus6Fine
				INTEGER,
			iqudc12AudSetupDelaySelectBus7Fine
				INTEGER,
			iqudc12AudSetupDelaySelectBus8Fine
				INTEGER,
			iqudc12AudSetupDelaySelectBusBulkDelay
				INTEGER,
			iqudc12AudSetupDelaySelectThreshold
				INTEGER,
			iqudc12AudSetupDelaySelectRtrack14
				INTEGER,
			iqudc12AudSetupDelaySelectRtrack15
				INTEGER,
			iqudc12AudSetupDelaySelectRtrack16
				INTEGER,
			iqudc12AudSetupDelaySelectRtrack17
				INTEGER,
			iqudc12AudSetupDelaySelectEnableBulk
				INTEGER,
			iqudc12AudSetupDelaySelectEnableVideo
				INTEGER,
			iqudc12AudioAudSetupRollTrack14
				RollCallString,
			iqudc12AudioAudSetupRollTrack15
				RollCallString,
			iqudc12AudioAudSetupRollTrack16
				RollCallString,
			iqudc12AudioAudSetupRollTrack17
				RollCallString,
			iqudc12AudioAudSetupCurrentVidDelay
				RollCallString,
			iqudc12AudioAudSetupMinVidAudDelay
				RollCallString,
			iqudc12AudioAudSetupCurrRTrack14Delay
				RollCallString,
			iqudc12AudioAudSetupCurrRlTrack15Delay
				RollCallString,
			iqudc12AudioAudSetupCurrRTrack16Delay
				RollCallString,
			iqudc12AudioAudSetupCurrRTrack17Delay
				RollCallString,
			iqudc12AudSetupTonesFreq0
				INTEGER,
			iqudc12AudSetupTonesFreq1
				INTEGER,
			iqudc12AudSetupTonesFreq2
				INTEGER,
			iqudc12AudSetupTonesFreq3
				INTEGER,
			iqudc12AudSetupTonesFreq4
				INTEGER,
			iqudc12AudSetupTonesFreq5
				INTEGER,
			iqudc12AudSetupTonesFreq6
				INTEGER,
			iqudc12AudSetupTonesFreq7
				INTEGER,
			iqudc12AudSetupTonesIdent0
				INTEGER,
			iqudc12AudSetupTonesIdent1
				INTEGER,
			iqudc12AudSetupTonesIdent2
				INTEGER,
			iqudc12AudSetupTonesIdent3
				INTEGER,
			iqudc12AudSetupTonesIdent4
				INTEGER,
			iqudc12AudSetupTonesIdent5
				INTEGER,
			iqudc12AudSetupTonesIdent6
				INTEGER,
			iqudc12AudSetupTonesIdent7
				INTEGER,
			iqudc12AudioAudSetupNeg1Frame
				INTEGER,
			iqudc12AudioAudSetupNeg1ms
				INTEGER,
			iqudc12AudioAudSetupNeg4samp
				INTEGER,
			iqudc12AudioAudSetupPos4samp
				INTEGER,
			iqudc12AudioAudSetupPos1ms
				INTEGER,
			iqudc12AudioAudSetupPos1Frame
				INTEGER,
			iqudc12AudioAudSetupSilentLevel
				INTEGER,
			iqudc12AudioAudSetupOverloadLevel
				INTEGER,
			iqudc12AudioAudSetupLevelUpdateEnb
				INTEGER,
			iqudc12AudioAudSetupLevelTimeout
				INTEGER,
			iqudc12AudioAudSetupAudLevel
				RollCallString,
			iqudc12AudioAudSetupHeadroomIn
				INTEGER,
			iqudc12AudioAudSetupLineupIn
				INTEGER,
			iqudc12AudioAudSetupHeadroomOut
				INTEGER,
			iqudc12AudioAudSetupLineupOut
				INTEGER,
			iqudc12AudioAudSetupDialogHide
				RollCallString,
			iqudc12AudioAudioRoutingInputRouteDest1
				INTEGER,
			iqudc12AudioAudioRoutingInputRouteDest2
				INTEGER,
			iqudc12AudioAudioRoutingInputRouteDest3
				INTEGER,
			iqudc12AudioAudioRoutingInputRouteDest4
				INTEGER,
			iqudc12AudioAudioRoutingInputRouteDest5
				INTEGER,
			iqudc12AudioAudioRoutingInputRouteDest6
				INTEGER,
			iqudc12AudioAudioRoutingInputRouteDest7
				INTEGER,
			iqudc12AudioAudioRoutingInputRouteDest8
				INTEGER,
			iqudc12AudioAudioRoutingInputNameAnalog
				RollCallString,
			iqudc12AudioAudioRoutingInputNameDlby1
				RollCallString,
			iqudc12AudioAudioRoutingInputNameDlby2
				RollCallString,
			iqudc12AudioAudioRoutingInputNameDlby3
				RollCallString,
			iqudc12AudioAudioRoutingInputNameDlby4
				RollCallString,
			iqudc12AudioAudioRoutingInputNameDlby5
				RollCallString,
			iqudc12AudioAudioRoutingInputHideAES1
				RollCallString,
			iqudc12AudioAudioRoutingInputHideAES2
				RollCallString,
			iqudc12AudioAudioRoutingInputHideAES3
				RollCallString,
			iqudc12AudioAudioRoutingInputHideAES4
				RollCallString,
			iqudc12AudioAudioRoutingInputHideAES5
				RollCallString,
			iqudc12AudioAudioRoutingInputHideAES6
				RollCallString,
			iqudc12AudioAudioRoutingInputHideAES7
				RollCallString,
			iqudc12AudioAudioRoutingInputHideAES8
				RollCallString,
			iqudc12AudioAudioRoutingOutputHideAES1
				RollCallString,
			iqudc12AudioAudioRoutingOutputHideAES2
				RollCallString,
			iqudc12AudioAudioRoutingOutputHideAES3
				RollCallString,
			iqudc12AudioAudioRoutingOutputHideAES4
				RollCallString,
			iqudc12AudioAudioRoutingOutputHideAES5
				RollCallString,
			iqudc12AudioAudioRoutingOutputHideAES6
				RollCallString,
			iqudc12AudioAudioRoutingOutputHideAES7
				RollCallString,
			iqudc12AudioAudioRoutingOutputHideAES8
				RollCallString,
			iqudc12AudioAudioRoutingDolbyDecodeSource
				INTEGER,
			iqudc12AudioAudioRoutingDolbyDecodeNum
				INTEGER,
			iqudc12AudioAudioRoutingBus1RName
				RollCallString,
			iqudc12AudioAudioRoutingBus2RName
				RollCallString,
			iqudc12AudioAudioRoutingBus3RName
				RollCallString,
			iqudc12AudioAudioRoutingBus4RName
				RollCallString,
			iqudc12AudioAudioRoutingBus5RName
				RollCallString,
			iqudc12AudioAudioRoutingBus6RName
				RollCallString,
			iqudc12AudioAudioRoutingBus7RName
				RollCallString,
			iqudc12AudioAudioRoutingBus8RName
				RollCallString,
			iqudc12AudioAudioOutputRoutingOutDest1
				INTEGER,
			iqudc12AudioAudioOutputRoutingOutDest2
				INTEGER,
			iqudc12AudioAudioOutputRoutingOutDest3
				INTEGER,
			iqudc12AudioAudioOutputRoutingOutDest4
				INTEGER,
			iqudc12AudioAudioOutputRoutingOutDest5
				INTEGER,
			iqudc12AudioAudioOutputRoutingOutDest6
				INTEGER,
			iqudc12AudioAudioOutputRoutingOutDest7
				INTEGER,
			iqudc12AudioAudioOutputRoutingOutDest8
				INTEGER,
			iqudc12AudioAudioOutputRoutingOutDest9
				INTEGER,
			iqudc12AudioAudioOutputRoutingOutDest10
				INTEGER,
			iqudc12AudioAudioOutputRoutingOutDest11
				INTEGER,
			iqudc12AudioAudioOutputRoutingOutDest12
				INTEGER,
			iqudc12AudioAudioOutputRoutingOutDest13
				INTEGER,
			iqudc12AudioAudioOutputRoutingOutDest14
				INTEGER,
			iqudc12AudioAudioOutputRoutingOutDest15
				INTEGER,
			iqudc12AudioAudioOutputRoutingOutDest16
				INTEGER,
			iqudc12AudioAudioOutputRoutingOutDest17
				INTEGER,
			iqudc12AudioAudioOutputRoutingOutDest18
				INTEGER,
			iqudc12AudioAudioOutputRoutingOutDest19
				INTEGER,
			iqudc12AudioAudioOutputRoutingOutDest20
				INTEGER,
			iqudc12AudioAudioOutputRoutingOutDest21
				INTEGER,
			iqudc12AudioAudioOutputRoutingOutDest22
				INTEGER,
			iqudc12AudioAudioOutputRoutingOutDest23
				INTEGER,
			iqudc12AudioAudioOutputRoutingOutDest24
				INTEGER,
			iqudc12AudioAudioOutputRoutingOutDest25
				INTEGER,
			iqudc12AudioAudioOutputRoutingOutDest26
				INTEGER,
			iqudc12AudioAudioOutputRoutingOutDest27
				INTEGER,
			iqudc12AudioAudioOutputRoutingOutDest28
				INTEGER,
			iqudc12AudioAudioOutputRoutingOutDest29
				INTEGER,
			iqudc12AudioAudioOutputRoutingOutDest30
				INTEGER,
			iqudc12AudioAudioOutputRoutingOutDest31
				INTEGER,
			iqudc12AudioAudioOutputRoutingOutDest32
				INTEGER,
			iqudc12AudioAudioOutputRoutingOutDest33
				INTEGER,
			iqudc12AudioAudioOutputRoutingOutDest34
				INTEGER,
			iqudc12AudioAudioOutputRoutingOutDest35
				INTEGER,
			iqudc12AudioAudioOutputRoutingOutDest36
				INTEGER,
			iqudc12AudioAudioOutputRoutingDolbyEncEnb
				RollCallString,
			iqudc12AudioAudioOutputRoutingUpmixEnb
				RollCallString,
			iqudc12MenuAudioRoutingMatriBus1audsel
				INTEGER,
			iqudc12MenuAudioRoutingMatriBus2audsel
				INTEGER,
			iqudc12MenuAudioRoutingMatriBus3audsel
				INTEGER,
			iqudc12MenuAudioRoutingMatriBus4audsel
				INTEGER,
			iqudc12MenuAudioRoutingMatriBus5audsel
				INTEGER,
			iqudc12MenuAudioRoutingMatriBus6audsel
				INTEGER,
			iqudc12MenuAudioRoutingMatriBus7audsel
				INTEGER,
			iqudc12MenuAudioRoutingMatriBus8audsel
				INTEGER,
			iqudc12AudioOutRouteMatriEmbed12MatrixEmbed11audsel
				INTEGER,
			iqudc12AudioOutRouteMatriEmbed12MatrixEmbed12audsel
				INTEGER,
			iqudc12AudioOutRouteMatriEmbed12MatrixEmbed21audsel
				INTEGER,
			iqudc12AudioOutRouteMatriEmbed12MatrixEmbed22audsel
				INTEGER,
			iqudc12AudioOutRouteMatriEmbed34MatrixEmbed31audsel
				INTEGER,
			iqudc12AudioOutRouteMatriEmbed34MatrixEmbed32audsel
				INTEGER,
			iqudc12AudioOutRouteMatriEmbed34MatrixEmbed41audsel
				INTEGER,
			iqudc12AudioOutRouteMatriEmbed34MatrixEmbed42audsel
				INTEGER,
			iqudc12AudioOutRouteMatriEmbed56MatrixEmbed51audsel
				INTEGER,
			iqudc12AudioOutRouteMatriEmbed56MatrixEmbed52audsel
				INTEGER,
			iqudc12AudioOutRouteMatriEmbed56MatrixEmbed61audsel
				INTEGER,
			iqudc12AudioOutRouteMatriEmbed56MatrixEmbed62audsel
				INTEGER,
			iqudc12AudioOutRouteMatriEmbed78MatrixEmbed71audsel
				INTEGER,
			iqudc12AudioOutRouteMatriEmbed78MatrixEmbed72audsel
				INTEGER,
			iqudc12AudioOutRouteMatriEmbed78MatrixEmbed81audsel
				INTEGER,
			iqudc12AudioOutRouteMatriEmbed78MatrixEmbed82audsel
				INTEGER,
			iqudc12AudioOutRouteMatriAES12MatrixAES11audsel
				INTEGER,
			iqudc12AudioOutRouteMatriAES12MatrixAES12audsel
				INTEGER,
			iqudc12AudioOutRouteMatriAES12MatrixAES21audsel
				INTEGER,
			iqudc12AudioOutRouteMatriAES12MatrixAES22audsel
				INTEGER,
			iqudc12AudioOutRouteMatriAES34MatrixAES31audsel
				INTEGER,
			iqudc12AudioOutRouteMatriAES34MatrixAES32audsel
				INTEGER,
			iqudc12AudioOutRouteMatriAES34MatrixAES41audsel
				INTEGER,
			iqudc12AudioOutRouteMatriAES34MatrixAES42audsel
				INTEGER,
			iqudc12AudioOutRouteMatriAES56MatrixAES51audsel
				INTEGER,
			iqudc12AudioOutRouteMatriAES56MatrixAES52audsel
				INTEGER,
			iqudc12AudioOutRouteMatriAES56MatrixAES61audsel
				INTEGER,
			iqudc12AudioOutRouteMatriAES56MatrixAES62audsel
				INTEGER,
			iqudc12AudioOutRouteMatriAES78MatrixAES71audsel
				INTEGER,
			iqudc12AudioOutRouteMatriAES78MatrixAES72audsel
				INTEGER,
			iqudc12AudioOutRouteMatriAES78MatrixAES81audsel
				INTEGER,
			iqudc12AudioOutRouteMatriAES78MatrixAES82audsel
				INTEGER,
			iqudc12AudioOutRouteMatriAnlg12MatrixAnlg11audsel
				INTEGER,
			iqudc12AudioOutRouteMatriAnlg12MatrixAnlg12audsel
				INTEGER,
			iqudc12AudioOutRouteMatriAnlg12MatrixAnlg21audsel
				INTEGER,
			iqudc12AudioOutRouteMatriAnlg12MatrixAnlg22audsel
				INTEGER,
			iqudc12AudioOutRouteMatriDefaultsEmbOut
				INTEGER,
			iqudc12AudioOutRouteMatriDefaultsAESOut
				INTEGER,
			iqudc12AudioOutRouteMatriDefaultsAnlgOut
				INTEGER,
			iqudc12UpMixerLoud14Source1ProcGain
				INTEGER,
			iqudc12UpMixerLoud14Source1Mute
				INTEGER,
			iqudc12UpMixerLoud14Source1Src
				INTEGER,
			iqudc12UpMixerLoud14Source2ProcGain
				INTEGER,
			iqudc12UpMixerLoud14Source2Mute
				INTEGER,
			iqudc12UpMixerLoud14Source2Src
				INTEGER,
			iqudc12UpMixerLoud14Source3ProcGain
				INTEGER,
			iqudc12UpMixerLoud14Source3Mute
				INTEGER,
			iqudc12UpMixerLoud14Source3Src
				INTEGER,
			iqudc12UpMixerLoud14Source4ProcGain
				INTEGER,
			iqudc12UpMixerLoud14Source4Mute
				INTEGER,
			iqudc12UpMixerLoud14Source4Src
				INTEGER,
			iqudc12MenuUpMixerLoud14Mode
				INTEGER,
			iqudc12MenuUpMixerLoud14Status
				RollCallString,
			iqudc12MenuUpMixerLoud14XfadeBypass
				INTEGER,
			iqudc12MenuUpMixerLoud14XfadeUpmix
				INTEGER,
			iqudc12MenuUpMixerLoud14Detect
				INTEGER,
			iqudc12MenuUpMixerLoud14CenterWidth
				INTEGER,
			iqudc12MenuUpMixerLoud14Surround
				INTEGER,
			iqudc12MenuUpMixerLoud14AlgorithmType
				INTEGER,
			iqudc12UpMixerLoud58LoudnessPreset1
				INTEGER,
			iqudc12UpMixerLoud58LoudnessMasterLevel1
				INTEGER,
			iqudc12UpMixerLoud58LoudnessName1
				RollCallString,
			iqudc12UpMixerLoud58LoudnessBypass1
				INTEGER,
			iqudc12UpMixerLoud58LoudnessPreset2
				INTEGER,
			iqudc12UpMixerLoud58LoudnessMasterLevel2
				INTEGER,
			iqudc12UpMixerLoud58LoudnessName2
				RollCallString,
			iqudc12UpMixerLoud58LoudnessBypass2
				INTEGER,
			iqudc12UpMixerLoud58Source5ProcGain
				INTEGER,
			iqudc12UpMixerLoud58Source5Mute
				INTEGER,
			iqudc12UpMixerLoud58Source5Src
				INTEGER,
			iqudc12UpMixerLoud58Source6ProcGain
				INTEGER,
			iqudc12UpMixerLoud58Source6Mute
				INTEGER,
			iqudc12UpMixerLoud58Source6Src
				INTEGER,
			iqudc12UpMixerLoud58Source7ProcGain
				INTEGER,
			iqudc12UpMixerLoud58Source7Mute
				INTEGER,
			iqudc12UpMixerLoud58Source7Src
				INTEGER,
			iqudc12UpMixerLoud58Source8ProcGain
				INTEGER,
			iqudc12UpMixerLoud58Source8Mute
				INTEGER,
			iqudc12UpMixerLoud58Source8Src
				INTEGER,
			iqudc12MenuUpMixerLoud58UpmixHide
				RollCallString,
			iqudc12MenuUpMixerLoud58Chan1Name
				RollCallString,
			iqudc12MenuUpMixerLoud58Chan2Name
				RollCallString,
			iqudc12MenuUpMixerLoud58Chan3Name
				RollCallString,
			iqudc12MenuUpMixerLoud58Chan4Name
				RollCallString,
			iqudc12MenuUpMixerLoud58Chan5Name
				RollCallString,
			iqudc12MenuUpMixerLoud58Chan6Name
				RollCallString,
			iqudc12MenuUpMixerLoud58Chan7Name
				RollCallString,
			iqudc12MenuUpMixerLoud58Chan8Name
				RollCallString,
			iqudc12MenuUpMixerLoud58Chan1NameIn
				RollCallString,
			iqudc12MenuUpMixerLoud58Chan2NameIn
				RollCallString,
			iqudc12MenuUpMixerLoud58Chan3NameIn
				RollCallString,
			iqudc12MenuUpMixerLoud58Chan4NameIn
				RollCallString,
			iqudc12MenuUpMixerLoud58Chan5NameIn
				RollCallString,
			iqudc12MenuUpMixerLoud58Chan6NameIn
				RollCallString,
			iqudc12MenuUpMixerLoud58Chan7NameIn
				RollCallString,
			iqudc12MenuUpMixerLoud58Chan8NameIn
				RollCallString,
			iqudc12MenuUpMixerLoud58DialogHide
				RollCallString,
			iqudc12LoudCustomBlock1Name
				RollCallString,
			iqudc12LoudCustomBlock1inagcfreeze
				INTEGER,
			iqudc12LoudCustomBlock1inagcgate
				INTEGER,
			iqudc12LoudCustomBlock1inagcratio
				INTEGER,
			iqudc12LoudCustomBlock1inagcrange
				INTEGER,
			iqudc12LoudCustomBlock1inagcthresh
				INTEGER,
			iqudc12LoudCustomBlock1inagcattack
				INTEGER,
			iqudc12LoudCustomBlock1inagcrelease
				INTEGER,
			iqudc12LoudCustomBlock1peqfreq1
				INTEGER,
			iqudc12LoudCustomBlock1peqq1
				INTEGER,
			iqudc12LoudCustomBlock1peqlevel1
				INTEGER,
			iqudc12LoudCustomBlock1peqfreq2
				INTEGER,
			iqudc12LoudCustomBlock1peqq2
				INTEGER,
			iqudc12LoudCustomBlock1peqlevel2
				INTEGER,
			iqudc12LoudCustomBlock1peqfreq3
				INTEGER,
			iqudc12LoudCustomBlock1peqq3
				INTEGER,
			iqudc12LoudCustomBlock1peqlevel3
				INTEGER,
			iqudc12LoudCustomBlock1mbagcatk1
				INTEGER,
			iqudc12LoudCustomBlock1mbagcrel1
				INTEGER,
			iqudc12LoudCustomBlock1mbagcthresh1
				INTEGER,
			iqudc12LoudCustomBlock1mbagcoutlev1
				INTEGER,
			iqudc12LoudCustomBlock1mbagclimthresh1
				INTEGER,
			iqudc12LoudCustomBlock1mbagcinfthr1
				INTEGER,
			iqudc12LoudCustomBlock1mbagcatk2
				INTEGER,
			iqudc12LoudCustomBlock1mbagcrel2
				INTEGER,
			iqudc12LoudCustomBlock1mbagcthresh2
				INTEGER,
			iqudc12LoudCustomBlock1mbagcoutlev2
				INTEGER,
			iqudc12LoudCustomBlock1mbagclimthresh2
				INTEGER,
			iqudc12LoudCustomBlock1mbagcinfthr2
				INTEGER,
			iqudc12LoudCustomBlock1mbagcatk3
				INTEGER,
			iqudc12LoudCustomBlock1mbagcrel3
				INTEGER,
			iqudc12LoudCustomBlock1mbagcthresh3
				INTEGER,
			iqudc12LoudCustomBlock1mbagcoutlev3
				INTEGER,
			iqudc12LoudCustomBlock1mbagclimthresh3
				INTEGER,
			iqudc12LoudCustomBlock1mbagcinfthr3
				INTEGER,
			iqudc12LoudCustomBlock1mbagcatk4
				INTEGER,
			iqudc12LoudCustomBlock1mbagcrel4
				INTEGER,
			iqudc12LoudCustomBlock1mbagcthresh4
				INTEGER,
			iqudc12LoudCustomBlock1mbagcoutlev4
				INTEGER,
			iqudc12LoudCustomBlock1mbagclimthresh4
				INTEGER,
			iqudc12LoudCustomBlock1mbagcinfthr4
				INTEGER,
			iqudc12LoudCustomBlock1mbagcatk5
				INTEGER,
			iqudc12LoudCustomBlock1mbagcrel5
				INTEGER,
			iqudc12LoudCustomBlock1mbagcthresh5
				INTEGER,
			iqudc12LoudCustomBlock1mbagcoutlev5
				INTEGER,
			iqudc12LoudCustomBlock1mbagclimthresh5
				INTEGER,
			iqudc12LoudCustomBlock1mbagcinfthr5
				INTEGER,
			iqudc12LoudCustomBlock1mbrange
				INTEGER,
			iqudc12LoudCustomBlock1mbprogrise
				INTEGER,
			iqudc12LoudCustomBlock1mbsoftclip1
				INTEGER,
			iqudc12LoudCustomBlock1mbsoftclip2
				INTEGER,
			iqudc12LoudCustomBlock1mbratio
				INTEGER,
			iqudc12LoudCustomBlock1mblimdrive
				INTEGER,
			iqudc12LoudCustomBlock1CustomPreset
				INTEGER,
			iqudc12LoudCustomBlock1Copyto2
				INTEGER,
			iqudc12LoudCustomBlock2Name
				RollCallString,
			iqudc12LoudCustomBlock2inagcfreeze
				INTEGER,
			iqudc12LoudCustomBlock2inagcgate
				INTEGER,
			iqudc12LoudCustomBlock2inagcratio
				INTEGER,
			iqudc12LoudCustomBlock2inagcrange
				INTEGER,
			iqudc12LoudCustomBlock2inagcthresh
				INTEGER,
			iqudc12LoudCustomBlock2inagcattack
				INTEGER,
			iqudc12LoudCustomBlock2inagcrelease
				INTEGER,
			iqudc12LoudCustomBlock2peqfreq1
				INTEGER,
			iqudc12LoudCustomBlock2peqq1
				INTEGER,
			iqudc12LoudCustomBlock2peqlevel1
				INTEGER,
			iqudc12LoudCustomBlock2peqfreq2
				INTEGER,
			iqudc12LoudCustomBlock2peqq2
				INTEGER,
			iqudc12LoudCustomBlock2peqlevel2
				INTEGER,
			iqudc12LoudCustomBlock2peqfreq3
				INTEGER,
			iqudc12LoudCustomBlock2peqq3
				INTEGER,
			iqudc12LoudCustomBlock2peqlevel3
				INTEGER,
			iqudc12LoudCustomBlock2mbagcatk1
				INTEGER,
			iqudc12LoudCustomBlock2mbagcrel1
				INTEGER,
			iqudc12LoudCustomBlock2mbagcthresh1
				INTEGER,
			iqudc12LoudCustomBlock2mbagcoutlev1
				INTEGER,
			iqudc12LoudCustomBlock2mbagclimthresh1
				INTEGER,
			iqudc12LoudCustomBlock2mbagcinfthr1
				INTEGER,
			iqudc12LoudCustomBlock2mbagcatk2
				INTEGER,
			iqudc12LoudCustomBlock2mbagcrel2
				INTEGER,
			iqudc12LoudCustomBlock2mbagcthresh2
				INTEGER,
			iqudc12LoudCustomBlock2mbagcoutlev2
				INTEGER,
			iqudc12LoudCustomBlock2mbagclimthresh2
				INTEGER,
			iqudc12LoudCustomBlock2mbagcinfthr2
				INTEGER,
			iqudc12LoudCustomBlock2mbagcatk3
				INTEGER,
			iqudc12LoudCustomBlock2mbagcrel3
				INTEGER,
			iqudc12LoudCustomBlock2mbagcthresh3
				INTEGER,
			iqudc12LoudCustomBlock2mbagcoutlev3
				INTEGER,
			iqudc12LoudCustomBlock2mbagclimthresh3
				INTEGER,
			iqudc12LoudCustomBlock2mbagcinfthr3
				INTEGER,
			iqudc12LoudCustomBlock2mbagcatk4
				INTEGER,
			iqudc12LoudCustomBlock2mbagcrel4
				INTEGER,
			iqudc12LoudCustomBlock2mbagcthresh4
				INTEGER,
			iqudc12LoudCustomBlock2mbagcoutlev4
				INTEGER,
			iqudc12LoudCustomBlock2mbagclimthresh4
				INTEGER,
			iqudc12LoudCustomBlock2mbagcinfthr4
				INTEGER,
			iqudc12LoudCustomBlock2mbagcatk5
				INTEGER,
			iqudc12LoudCustomBlock2mbagcrel5
				INTEGER,
			iqudc12LoudCustomBlock2mbagcthresh5
				INTEGER,
			iqudc12LoudCustomBlock2mbagcoutlev5
				INTEGER,
			iqudc12LoudCustomBlock2mbagclimthresh5
				INTEGER,
			iqudc12LoudCustomBlock2mbagcinfthr5
				INTEGER,
			iqudc12LoudCustomBlock2mbrange
				INTEGER,
			iqudc12LoudCustomBlock2mbprogrise
				INTEGER,
			iqudc12LoudCustomBlock2mbsoftclip1
				INTEGER,
			iqudc12LoudCustomBlock2mbsoftclip2
				INTEGER,
			iqudc12LoudCustomBlock2mbratio
				INTEGER,
			iqudc12LoudCustomBlock2mblimdrive
				INTEGER,
			iqudc12LoudCustomBlock2CustomPreset
				INTEGER,
			iqudc12LoudCustomBlock2Copyto1
				INTEGER,
			iqudc12LoudCustomMasterLevelCustom1
				INTEGER,
			iqudc12LoudCustomMasterLevelCustom2
				INTEGER,
			iqudc12LoudCustomMasterLevelGen51
				INTEGER,
			iqudc12LoudCustomMasterLevelLight51
				INTEGER,
			iqudc12LoudCustomMasterLevelHeavy51
				INTEGER,
			iqudc12LoudCustomMasterLevelLoud51
				INTEGER,
			iqudc12LoudCustomMasterLevelLoudLimit51
				INTEGER,
			iqudc12LoudCustomMasterLevelProtect51
				INTEGER,
			iqudc12LoudCustomMasterLevelGenSterA
				INTEGER,
			iqudc12LoudCustomMasterLevelLightSterA
				INTEGER,
			iqudc12LoudCustomMasterLevelHeavySterA
				INTEGER,
			iqudc12LoudCustomMasterLevelLoudSterA
				INTEGER,
			iqudc12LoudCustomMasterLevelLoudLimitSterA
				INTEGER,
			iqudc12LoudCustomMasterLevelProtectSterA
				INTEGER,
			iqudc12LoudCustomMasterLevelGenSterB
				INTEGER,
			iqudc12LoudCustomMasterLevelLightSterB
				INTEGER,
			iqudc12LoudCustomMasterLevelHeavySterB
				INTEGER,
			iqudc12LoudCustomMasterLevelLoudSterB
				INTEGER,
			iqudc12LoudCustomMasterLevelLoudLimitSterB
				INTEGER,
			iqudc12LoudCustomMasterLevelProtectSterB
				INTEGER,
			iqudc12MenuMixers13Select
				INTEGER,
			iqudc12Mixers13Source1ProcGain
				INTEGER,
			iqudc12Mixers13Source1Invert
				INTEGER,
			iqudc12Mixers13Source1Mute
				INTEGER,
			iqudc12Mixers13Source1Src
				INTEGER,
			iqudc12Mixers13Source1Name
				RollCallString,
			iqudc12Mixers13Source2ProcGain
				INTEGER,
			iqudc12Mixers13Source2Invert
				INTEGER,
			iqudc12Mixers13Source2Mute
				INTEGER,
			iqudc12Mixers13Source2Src
				INTEGER,
			iqudc12Mixers13Source2Name
				RollCallString,
			iqudc12Mixers13Source3ProcGain
				INTEGER,
			iqudc12Mixers13Source3Invert
				INTEGER,
			iqudc12Mixers13Source3Mute
				INTEGER,
			iqudc12Mixers13Source3Src
				INTEGER,
			iqudc12Mixers13Source3Name
				RollCallString,
			iqudc12MenuMixers13MixerLoRo
				INTEGER,
			iqudc12Mixers46Source4ProcGain
				INTEGER,
			iqudc12Mixers46Source4Invert
				INTEGER,
			iqudc12Mixers46Source4Mute
				INTEGER,
			iqudc12Mixers46Source4Src
				INTEGER,
			iqudc12Mixers46Source4Name
				RollCallString,
			iqudc12Mixers46Source5ProcGain
				INTEGER,
			iqudc12Mixers46Source5Invert
				INTEGER,
			iqudc12Mixers46Source5Mute
				INTEGER,
			iqudc12Mixers46Source5Src
				INTEGER,
			iqudc12Mixers46Source5Name
				RollCallString,
			iqudc12Mixers46Source6ProcGain
				INTEGER,
			iqudc12Mixers46Source6Invert
				INTEGER,
			iqudc12Mixers46Source6Mute
				INTEGER,
			iqudc12Mixers46Source6Src
				INTEGER,
			iqudc12Mixers46Source6Name
				RollCallString,
			iqudc12DolbyDecodeDolbyDecoderDetectMode
				INTEGER,
			iqudc12DolbyDecodeDolbyDecoderAESChannelSelect
				INTEGER,
			iqudc12DolbyDecodeDolbyDecoderPCMLatency
				INTEGER,
			iqudc12DolbyDecodeDolbyDecoderListeningModeDolb
				INTEGER,
			iqudc12DolbyDecodeDolbyDecoderDynamicRange
				INTEGER,
			iqudc12DolbyDecoderDownmixChannelProgramSelect
				INTEGER,
			iqudc12DolbyDecoderDownmixChannelDynamicRange
				INTEGER,
			iqudc12DolbyDecoderDownmixChannelOutputMode
				INTEGER,
			iqudc12DolbyDecoderDecoderStatusBitstreamFormat
				RollCallString,
			iqudc12DolbyDecoderDecoderStatusBitstreamStatus
				RollCallString,
			iqudc12DolbyDecoderDecoderStatusDCRCErrorCount
				RollCallString,
			iqudc12DolbyDecoderDecoderStatusDCRCErrorTime
				RollCallString,
			iqudc12DolbyDecoderDecoderStatusECRCErrorCount
				RollCallString,
			iqudc12DolbyDecoderDecoderStatusECRCErrorTime
				RollCallString,
			iqudc12DolbyDecoderDecoderStatusResetErrors
				INTEGER,
			iqudc12DolbyDecoderDecoderStatusResetTime
				RollCallString,
			iqudc12DolbyDecoderOutpuA1A2A1Gain
				INTEGER,
			iqudc12DolbyDecoderOutpuA1A2A2Gain
				INTEGER,
			iqudc12DolbyDecoderOutpuA1A2MuteA1
				INTEGER,
			iqudc12DolbyDecoderOutpuA1A2MuteA2
				INTEGER,
			iqudc12DolbyDecoderOutpuA1A2StereoA
				INTEGER,
			iqudc12DolbyDecoderOutpuB3B4B3Gain
				INTEGER,
			iqudc12DolbyDecoderOutpuB3B4B4Gain
				INTEGER,
			iqudc12DolbyDecoderOutpuB3B4MuteB3
				INTEGER,
			iqudc12DolbyDecoderOutpuB3B4MuteB4
				INTEGER,
			iqudc12DolbyDecoderOutpuB3B4StereoB
				INTEGER,
			iqudc12DolbyDecoderOutpuC5C6C5Gain
				INTEGER,
			iqudc12DolbyDecoderOutpuC5C6C6Gain
				INTEGER,
			iqudc12DolbyDecoderOutpuC5C6MuteC5
				INTEGER,
			iqudc12DolbyDecoderOutpuC5C6MuteC6
				INTEGER,
			iqudc12DolbyDecoderOutpuC5C6StereoC
				INTEGER,
			iqudc12DolbyDecoderOutpuD7D8D7Gain
				INTEGER,
			iqudc12DolbyDecoderOutpuD7D8D8Gain
				INTEGER,
			iqudc12DolbyDecoderOutpuD7D8MuteD7
				INTEGER,
			iqudc12DolbyDecoderOutpuD7D8MuteD8
				INTEGER,
			iqudc12DolbyDecoderOutpuD7D8StereoD
				INTEGER,
			iqudc12DolbyDecoderOutpuMLMRMLGain
				INTEGER,
			iqudc12DolbyDecoderOutpuMLMRMRGain
				INTEGER,
			iqudc12DolbyDecoderOutpuMLMRMuteML
				INTEGER,
			iqudc12DolbyDecoderOutpuMLMRMuteMR
				INTEGER,
			iqudc12DolbyDecoderOutpuMLMRStereoM
				INTEGER,
			iqudc12DolbyDecodeDolbyDecoderOutpuMasterGain
				INTEGER,
			iqudc12DolbyDecodeDolbyDecoderOutpuMasterMute
				INTEGER,
			iqudc12MenuDolbyDecodeHideDecoder
				RollCallString,
			iqudc12DolbyEncInp14Source1ProcGain
				INTEGER,
			iqudc12DolbyEncInp14Source1Mute
				INTEGER,
			iqudc12DolbyEncInp14Source1Src
				INTEGER,
			iqudc12DolbyEncInp14Source2ProcGain
				INTEGER,
			iqudc12DolbyEncInp14Source2Mute
				INTEGER,
			iqudc12DolbyEncInp14Source2Src
				INTEGER,
			iqudc12DolbyEncInp14Source3ProcGain
				INTEGER,
			iqudc12DolbyEncInp14Source3Mute
				INTEGER,
			iqudc12DolbyEncInp14Source3Src
				INTEGER,
			iqudc12DolbyEncInp14Source4ProcGain
				INTEGER,
			iqudc12DolbyEncInp14Source4Mute
				INTEGER,
			iqudc12DolbyEncInp14Source4Src
				INTEGER,
			iqudc12DolbyEncInp58Source5ProcGain
				INTEGER,
			iqudc12DolbyEncInp58Source5Mute
				INTEGER,
			iqudc12DolbyEncInp58Source5Src
				INTEGER,
			iqudc12DolbyEncInp58Source6ProcGain
				INTEGER,
			iqudc12DolbyEncInp58Source6Mute
				INTEGER,
			iqudc12DolbyEncInp58Source6Src
				INTEGER,
			iqudc12DolbyEncInp58Source7ProcGain
				INTEGER,
			iqudc12DolbyEncInp58Source7Mute
				INTEGER,
			iqudc12DolbyEncInp58Source7Src
				INTEGER,
			iqudc12DolbyEncInp58Source8ProcGain
				INTEGER,
			iqudc12DolbyEncInp58Source8Mute
				INTEGER,
			iqudc12DolbyEncInp58Source8Src
				INTEGER,
			iqudc12DolbyControlDolbyEncoderContrSampleRateConvers
				INTEGER,
			iqudc12DolbyControlDolbyEncoderContrMetaRevertMode
				INTEGER,
			iqudc12DolbyControlDolbyEncoderContrEncodingMode
				INTEGER,
			iqudc12DolbyControlDolbyEEncoderCntBitDepth
				INTEGER,
			iqudc12DolbyControlDolbyEEncoderCntMetadataSource
				INTEGER,
			iqudc12DolbyControlDolbyEEncoderCntInternalConfig
				INTEGER,
			iqudc12DolbyControlDolbyEEncoderCntDefaultAllMeta
				INTEGER,
			iqudc12DolbyControlDolbyIntMetaCntrCopyExtMetadata
				INTEGER,
			iqudc12DolbyControlDolbyIntMetaCntrDefaultProgramMet
				INTEGER,
			iqudc12DolbyControlDolbyIntMetaCntrDialogueNorm
				INTEGER,
			iqudc12DolbyControlDolbyIntMetaCntrChannelMode
				INTEGER,
			iqudc12DolbyControlDolbyIntMetaCntrLFEChannel
				INTEGER,
			iqudc12DolbyControlDolbyIntMetaCntrBitstreamMode
				INTEGER,
			iqudc12DolbyControlDolbyIntMetaCntrRFMode
				INTEGER,
			iqudc12DolbyControlDolbyIntMetaCntrLineMode
				INTEGER,
			iqudc12DolbyIntMetaCntrAudioProductionInExists
				INTEGER,
			iqudc12DolbyIntMetaCntrAudioProductionInMixLevel
				INTEGER,
			iqudc12DolbyIntMetaCntrAudioProductionInRoomType
				INTEGER,
			iqudc12DolbyControlDolbyIntMetaCntrCentreMixLevel
				INTEGER,
			iqudc12DolbyControlDolbyIntMetaCntrSurroundMixLevel
				INTEGER,
			iqudc12DolbyControlDolbyIntMetaCntrSurroundMode
				INTEGER,
			iqudc12DolbyControlDolbyIntMetaCntrCopyright
				INTEGER,
			iqudc12DolbyIntMetaCntrExtendedBSI1Exists
				INTEGER,
			iqudc12DolbyIntMetaCntrExtendedBSI1StereoDownmixMode
				INTEGER,
			iqudc12DolbyIntMetaCntrExtendedBSI1LtRtCentreMixLe
				INTEGER,
			iqudc12DolbyIntMetaCntrExtendedBSI1LtRtSurrMixLeve
				INTEGER,
			iqudc12DolbyIntMetaCntrExtendedBSI1LoRoCentreMixLe
				INTEGER,
			iqudc12DolbyIntMetaCntrExtendedBSI1LoRoSurrMixLeve
				INTEGER,
			iqudc12DolbyIntMetaCntrExtendedBSI2Exists
				INTEGER,
			iqudc12DolbyIntMetaCntrExtendedBSI2SurroundEXMode
				INTEGER,
			iqudc12DolbyIntMetaCntrExtendedBSI2LowpassFilter
				INTEGER,
			iqudc12DolbyIntMetaCntrExtendedBSI2LFEFIlter
				INTEGER,
			iqudc12DolbyIntMetaCntrExtendedBSI2SurrPhaseShiftFl
				INTEGER,
			iqudc12DolbyIntMetaCntrExtendedBSI2Surr3dBAttenuator
				INTEGER,
			iqudc12DolbyControlDolbyIntMetaCntrProgramDescription42510
				RollCallString,
			iqudc12DolbyControlDolbyIntMetaCntrProgramDescription42511
				RollCallString,
			iqudc12DolbyControlDolbyIntMetaCntrIntMetaSaveset
				INTEGER,
			iqudc12DolbyControlDolbyDEncoderCntInternalMode
				INTEGER,
			iqudc12DolbyControlDolbyDEncoderCntBitstreamFormat
				INTEGER,
			iqudc12DolbyControlDolbyDEncoderCntMetadataSource
				INTEGER,
			iqudc12DolbyControlDolbyDEncoderCntIntMetaDataRate
				INTEGER,
			iqudc12DolbyControlDolbyDEncoderCntStreamNumber
				INTEGER,
			iqudc12DolbyControlDolbyMetaProgSelMetaProgramSelect42413
				INTEGER,
			iqudc12DolbyControlDolbyMetaProgSelMetaProgramSelect42440
				INTEGER,
			iqudc12MenuDolbyControlHideEEncoder
				RollCallString,
			iqudc12MenuDolbyControlHideDEncoder
				RollCallString,
			iqudc12MenuDolbyControlResetModule
				INTEGER,
			iqudc12DolbyStatusMetaDolbyMetadataRS485PortConfig
				INTEGER,
			iqudc12DolbyStatusMetaDolbyMetadataInputMetadataSour
				INTEGER,
			iqudc12DolbyStatusMetaDolbyMetadataSMPTE2020Embedder
				INTEGER,
			iqudc12DolbyMetadataSMPTE2020SMPTE2020OPLine
				INTEGER,
			iqudc12DolbyMetadataSMPTE2020SMPTE2020IPLine
				RollCallString,
			iqudc12DolbyMetadataSMPTE2020OPEnable
				INTEGER,
			iqudc12DolbyMetadataSMPTE2020FollowIPLine
				INTEGER,
			iqudc12DolbyStatusMetaDolbyCommonStatusVideoSync
				RollCallString,
			iqudc12DolbyStatusMetaDolbyCommonStatusFrameRate
				RollCallString,
			iqudc12DolbyStatusMetaDolbyCommonStatusProgramConfig
				RollCallString,
			iqudc12DolbyStatusMetaDolbyCommonStatusFWVersion
				RollCallString,
			iqudc12DolbyStatusMetaDolbyCommonStatusDeviceName
				RollCallString,
			iqudc12DolbyCommonStatusChannelAssignmentDolbyA1
				RollCallString,
			iqudc12DolbyCommonStatusChannelAssignmentDolbyA2
				RollCallString,
			iqudc12DolbyCommonStatusChannelAssignmentDolbyB3
				RollCallString,
			iqudc12DolbyCommonStatusChannelAssignmentDolbyB4
				RollCallString,
			iqudc12DolbyCommonStatusChannelAssignmentDolbyC5
				RollCallString,
			iqudc12DolbyCommonStatusChannelAssignmentDolbyC6
				RollCallString,
			iqudc12DolbyCommonStatusChannelAssignmentDolbyD7
				RollCallString,
			iqudc12DolbyCommonStatusChannelAssignmentDolbyD8
				RollCallString,
			iqudc12DolbyCommonStatusChnlPairAssignmenDolby12
				RollCallString,
			iqudc12DolbyCommonStatusChnlPairAssignmenDolby34
				RollCallString,
			iqudc12DolbyCommonStatusChnlPairAssignmenDolby56
				RollCallString,
			iqudc12DolbyCommonStatusChnlPairAssignmenDolby78
				RollCallString,
			iqudc12DolbyStatusMetaDolbyExtProgStatP1Status
				RollCallString,
			iqudc12DolbyStatusMetaDolbyExtProgStatP2Status
				RollCallString,
			iqudc12DolbyStatusMetaDolbyExtProgStatP3Status
				RollCallString,
			iqudc12DolbyStatusMetaDolbyExtProgStatP4Status
				RollCallString,
			iqudc12DolbyStatusMetaDolbyExtProgStatP5Status
				RollCallString,
			iqudc12DolbyStatusMetaDolbyExtProgStatP6Status
				RollCallString,
			iqudc12DolbyStatusMetaDolbyExtProgStatP7Status
				RollCallString,
			iqudc12DolbyStatusMetaDolbyExtProgStatP8Status
				RollCallString,
			iqudc12DolbyStatusMetaDolbyMetadataStatProgramDescription42508
				RollCallString,
			iqudc12DolbyStatusMetaDolbyMetadataStatProgramDescription42509
				RollCallString,
			iqudc12DolbyStatusMetaDolbyMetadataStatDialogueNorm
				RollCallString,
			iqudc12DolbyStatusMetaDolbyMetadataStatChannelMode
				RollCallString,
			iqudc12DolbyStatusMetaDolbyMetadataStatLFE
				RollCallString,
			iqudc12DolbyStatusMetaDolbyMetadataStatBitstreamMode
				RollCallString,
			iqudc12DolbyStatusMetaDolbyMetadataStatRFMode
				RollCallString,
			iqudc12DolbyStatusMetaDolbyMetadataStatLineMode
				RollCallString,
			iqudc12DolbyStatusMetaDolbyMetadataStatCentreMixLevel
				RollCallString,
			iqudc12DolbyStatusMetaDolbyMetadataStatSurroundMixLevel
				RollCallString,
			iqudc12DolbyStatusMetaDolbyMetadataStatSurroundMode
				RollCallString,
			iqudc12DolbyStatusMetaDolbyMetadataStatCopyright
				RollCallString,
			iqudc12DolbyMetadataStatAudioProductionInAudioProdInfoExi
				RollCallString,
			iqudc12DolbyMetadataStatAudioProductionInMixLevel
				RollCallString,
			iqudc12DolbyMetadataStatAudioProductionInRoomType
				RollCallString,
			iqudc12DolbyMetadataStatExtendedBSI1ExtendedBSI1Exist
				RollCallString,
			iqudc12DolbyMetadataStatExtendedBSI1StereoDownmixMode
				RollCallString,
			iqudc12DolbyMetadataStatExtendedBSI1LtRtCentreMixLe
				RollCallString,
			iqudc12DolbyMetadataStatExtendedBSI1LtRtSurrMixLeve
				RollCallString,
			iqudc12DolbyMetadataStatExtendedBSI1LoRoCentreMixLe
				RollCallString,
			iqudc12DolbyMetadataStatExtendedBSI1LoRoSurrMixLeve
				RollCallString,
			iqudc12DolbyMetadataStatExtendedBSI2ExtendedBSI2Exist
				RollCallString,
			iqudc12DolbyMetadataStatExtendedBSI2SurroundEXMode
				RollCallString,
			iqudc12DolbyMetadataStatExtendedBSI2LowpassFilter
				RollCallString,
			iqudc12DolbyMetadataStatExtendedBSI2LFEFilter
				RollCallString,
			iqudc12DolbyMetadataStatExtendedBSI2SurrPhaseShiftFl
				RollCallString,
			iqudc12DolbyMetadataStatExtendedBSI2Surr3dBAtten
				RollCallString,
			iqudc12DolbyStatusMetaDolbyEncoderStatuStatus
				RollCallString,
			iqudc12DolbyStatusMetaDolbyEncoderStatuBitstreamStatus
				RollCallString,
			iqudc12DolbyStatusMetaDolbyEncoderStatuReversionStatus
				RollCallString,
			iqudc12DolbyStatusMetaDolbyEncoderStatuHWVersion
				RollCallString,
			iqudc12DolbyStatusMetaDolbyEncoderStatuOPProgramConfig
				RollCallString,
			iqudc12RollCallMemoriesMemoriesABCRecallMemory
				INTEGER,
			iqudc12RollCallMemoriesMemoriesABCSelMemory
				INTEGER,
			iqudc12RollCallMemoriesMemoriesABCSaveMemory
				INTEGER,
			iqudc12RollCallMemoriesMemoriesABCClearMemory
				INTEGER,
			iqudc12MemoriesABCMemoryNameChangeName
				RollCallString,
			iqudc12MemoriesABCMemoryNameLastUserMemory
				RollCallString,
			iqudc12RollCallMemoriesMemoriesABCMemoryName1
				RollCallString,
			iqudc12RollCallMemoriesMemoriesABCMemoryName2
				RollCallString,
			iqudc12RollCallMemoriesMemoriesABCMemoryName3
				RollCallString,
			iqudc12RollCallMemoriesMemoriesABCMemoryName4
				RollCallString,
			iqudc12RollCallMemoriesMemoriesABCMemoryName5
				RollCallString,
			iqudc12RollCallMemoriesMemoriesABCMemoryName6
				RollCallString,
			iqudc12RollCallMemoriesMemoriesABCMemoryName7
				RollCallString,
			iqudc12RollCallMemoriesMemoriesABCMemoryName8
				RollCallString,
			iqudc12RollCallMemoriesMemoriesABCMemoryName9
				RollCallString,
			iqudc12RollCallMemoriesMemoriesABCMemoryName10
				RollCallString,
			iqudc12RollCallMemoriesMemoriesABCMemoryName11
				RollCallString,
			iqudc12RollCallMemoriesMemoriesABCMemoryName12
				RollCallString,
			iqudc12RollCallMemoriesMemoriesABCMemoryName13
				RollCallString,
			iqudc12RollCallMemoriesMemoriesABCMemoryName14
				RollCallString,
			iqudc12RollCallMemoriesMemoriesABCMemoryName15
				RollCallString,
			iqudc12RollCallMemoriesMemoriesABCMemoryName16
				RollCallString,
			iqudc12Logging1AESInputAudLoggiLogAESInput1stat
				INTEGER,
			iqudc12Logging1AESInputAudLoggiAESInput1state
				RollCallString,
			iqudc12Logging1AESInputAudLoggiLogAESInput2stat
				INTEGER,
			iqudc12Logging1AESInputAudLoggiAESInput2state
				RollCallString,
			iqudc12Logging1AESInputAudLoggiLogAESInput3stat
				INTEGER,
			iqudc12Logging1AESInputAudLoggiAESInput3state
				RollCallString,
			iqudc12Logging1AESInputAudLoggiLogAESInput4stat
				INTEGER,
			iqudc12Logging1AESInputAudLoggiAESInput4state
				RollCallString,
			iqudc12Logging1AESInputAudLoggiLogAESInput5stat
				INTEGER,
			iqudc12Logging1AESInputAudLoggiAESInput5state
				RollCallString,
			iqudc12Logging1AESInputAudLoggiLogAESInput6stat
				INTEGER,
			iqudc12Logging1AESInputAudLoggiAESInput6state
				RollCallString,
			iqudc12Logging1AESInputAudLoggiLogAESInput7stat
				INTEGER,
			iqudc12Logging1AESInputAudLoggiAESInput7state
				RollCallString,
			iqudc12Logging1AESInputAudLoggiLogAESInput8stat
				INTEGER,
			iqudc12Logging1AESInputAudLoggiAESInput8state
				RollCallString,
			iqudc12Logging1OutEmbAudLoggingLogOutEmb11stat
				INTEGER,
			iqudc12Logging1OutEmbAudLoggingOutEmb11state
				RollCallString,
			iqudc12Logging1OutEmbAudLoggingLogOutEmb12stat
				INTEGER,
			iqudc12Logging1OutEmbAudLoggingOutEmb12state
				RollCallString,
			iqudc12Logging1OutEmbAudLoggingLogOutEmb21stat
				INTEGER,
			iqudc12Logging1OutEmbAudLoggingOutEmb21state
				RollCallString,
			iqudc12Logging1OutEmbAudLoggingLogOutEmb22stat
				INTEGER,
			iqudc12Logging1OutEmbAudLoggingOutEmb22state
				RollCallString,
			iqudc12Logging1OutEmbAudLoggingLogOutEmb31stat
				INTEGER,
			iqudc12Logging1OutEmbAudLoggingOutEmb31state
				RollCallString,
			iqudc12Logging1OutEmbAudLoggingLogOutEmb32stat
				INTEGER,
			iqudc12Logging1OutEmbAudLoggingOutEmb32state
				RollCallString,
			iqudc12Logging1OutEmbAudLoggingLogOutEmb41stat
				INTEGER,
			iqudc12Logging1OutEmbAudLoggingOutEmb41state
				RollCallString,
			iqudc12Logging1OutEmbAudLoggingLogOutEmb42stat
				INTEGER,
			iqudc12Logging1OutEmbAudLoggingOutEmb42state
				RollCallString,
			iqudc12Logging1OutEmbAudLoggingLogOutEmb51stat
				INTEGER,
			iqudc12Logging1OutEmbAudLoggingOutEmb51state
				RollCallString,
			iqudc12Logging1OutEmbAudLoggingLogOutEmb52stat
				INTEGER,
			iqudc12Logging1OutEmbAudLoggingOutEmb52state
				RollCallString,
			iqudc12Logging1OutEmbAudLoggingLogOutEmb61stat
				INTEGER,
			iqudc12Logging1OutEmbAudLoggingOutEmb61state
				RollCallString,
			iqudc12Logging1OutEmbAudLoggingLogOutEmb62stat
				INTEGER,
			iqudc12Logging1OutEmbAudLoggingOutEmb62state
				RollCallString,
			iqudc12Logging1OutEmbAudLoggingLogOutEmb71stat
				INTEGER,
			iqudc12Logging1OutEmbAudLoggingOutEmb71state
				RollCallString,
			iqudc12Logging1OutEmbAudLoggingLogOutEmb72stat
				INTEGER,
			iqudc12Logging1OutEmbAudLoggingOutEmb72state
				RollCallString,
			iqudc12Logging1OutEmbAudLoggingLogOutEmb81stat
				INTEGER,
			iqudc12Logging1OutEmbAudLoggingOutEmb81state
				RollCallString,
			iqudc12Logging1OutEmbAudLoggingLogOutEmb82stat
				INTEGER,
			iqudc12Logging1OutEmbAudLoggingOutEmb82state
				RollCallString,
			iqudc12Logging1AESOutputAudLoggLogAESOutput11st
				INTEGER,
			iqudc12Logging1AESOutputAudLoggAESOutput11state
				RollCallString,
			iqudc12Logging1AESOutputAudLoggLogAESOutput12st
				INTEGER,
			iqudc12Logging1AESOutputAudLoggAESOutput12state
				RollCallString,
			iqudc12Logging1AESOutputAudLoggLogAESOutput21st
				INTEGER,
			iqudc12Logging1AESOutputAudLoggAESOutput21state
				RollCallString,
			iqudc12Logging1AESOutputAudLoggLogAESOutput22st
				INTEGER,
			iqudc12Logging1AESOutputAudLoggAESOutput22state
				RollCallString,
			iqudc12Logging1AESOutputAudLoggLogAESOutput31st
				INTEGER,
			iqudc12Logging1AESOutputAudLoggAESOutput31state
				RollCallString,
			iqudc12Logging1AESOutputAudLoggLogAESOutput32st
				INTEGER,
			iqudc12Logging1AESOutputAudLoggAESOutput32state
				RollCallString,
			iqudc12Logging1AESOutputAudLoggLogAESOutput41st
				INTEGER,
			iqudc12Logging1AESOutputAudLoggAESOutput41state
				RollCallString,
			iqudc12Logging1AESOutputAudLoggLogAESOutput42st
				INTEGER,
			iqudc12Logging1AESOutputAudLoggAESOutput42state
				RollCallString,
			iqudc12Logging1AESOutputAudLoggLogAESOutput51st
				INTEGER,
			iqudc12Logging1AESOutputAudLoggAESOutput51state
				RollCallString,
			iqudc12Logging1AESOutputAudLoggLogAESOutput52st
				INTEGER,
			iqudc12Logging1AESOutputAudLoggAESOutput52state
				RollCallString,
			iqudc12Logging1AESOutputAudLoggLogAESOutput61st
				INTEGER,
			iqudc12Logging1AESOutputAudLoggAESOutput61state
				RollCallString,
			iqudc12Logging1AESOutputAudLoggLogAESOutput62st
				INTEGER,
			iqudc12Logging1AESOutputAudLoggAESOutput62state
				RollCallString,
			iqudc12Logging1AESOutputAudLoggLogAESOutput71st
				INTEGER,
			iqudc12Logging1AESOutputAudLoggAESOutput71state
				RollCallString,
			iqudc12Logging1AESOutputAudLoggLogAESOutput72st
				INTEGER,
			iqudc12Logging1AESOutputAudLoggAESOutput72state
				RollCallString,
			iqudc12Logging1AESOutputAudLoggLogAESOutput81st
				INTEGER,
			iqudc12Logging1AESOutputAudLoggAESOutput81state
				RollCallString,
			iqudc12Logging1AESOutputAudLoggLogAESOutput82st
				INTEGER,
			iqudc12Logging1AESOutputAudLoggAESOutput82state
				RollCallString,
			iqudc12Logging1AnlgOutAudLogginLogAnlgOut11stat
				INTEGER,
			iqudc12Logging1AnlgOutAudLogginAnlgOutput11state
				RollCallString,
			iqudc12Logging1AnlgOutAudLogginLogAnlgOut12stat
				INTEGER,
			iqudc12Logging1AnlgOutAudLogginAnlgOutput12state
				RollCallString,
			iqudc12Logging1AnlgOutAudLogginLogAnlgOut21stat
				INTEGER,
			iqudc12Logging1AnlgOutAudLogginAnlgOutput21state
				RollCallString,
			iqudc12Logging1AnlgOutAudLogginLogAnlgOut22stat
				INTEGER,
			iqudc12Logging1AnlgOutAudLogginAnlgOutput22state
				RollCallString,
			iqudc12Logging1DolbyDecoderLoggiLogBitstreamForma
				INTEGER,
			iqudc12Logging1DolbyDecoderLoggiBitstreamFormat
				RollCallString,
			iqudc12Logging1DolbyDecoderLoggiLogBitstreamStatu
				INTEGER,
			iqudc12Logging1DolbyDecoderLoggiBitstreamStatus
				RollCallString,
			iqudc12Logging1DolbyDecoderLoggiLogDCRCErrors
				INTEGER,
			iqudc12Logging1DolbyDecoderLoggiDCRCErrorCount
				RollCallString,
			iqudc12Logging1DolbyDecoderLoggiLogECRCErrors
				INTEGER,
			iqudc12Logging1DolbyDecoderLoggiECRCErrorCount
				RollCallString,
			iqudc12Logging1DolbyEncoderLoggiLogEncoderStatus
				INTEGER,
			iqudc12Logging1DolbyEncoderLoggiEncoderStatus
				RollCallString,
			iqudc12Logging1DolbyEncoderLoggiLogBitstreamStatu
				INTEGER,
			iqudc12Logging1DolbyEncoderLoggiBitstreamStatus
				RollCallString,
			iqudc12Logging1DolbyEncoderLoggiLogReversionStatu
				INTEGER,
			iqudc12Logging1DolbyEncoderLoggiReversionStatus
				RollCallString,
			iqudc12Logging1DolbyLoggingLogVideoSync
				INTEGER,
			iqudc12Logging1DolbyLoggingVideoSync
				RollCallString,
			iqudc12Logging1DolbyLoggingLogFrameRate
				INTEGER,
			iqudc12Logging1DolbyLoggingFrameRate
				RollCallString,
			iqudc12Logging1DolbyLoggingLogProgramConfig
				INTEGER,
			iqudc12Logging1DolbyLoggingProgramConfig
				RollCallString,
			iqudc12Logging1DolbyMetadataLoggLogSelectedProgra
				INTEGER,
			iqudc12Logging1DolbyMetadataLoggSelectedProgram
				RollCallString,
			iqudc12Logging1DolbyMetadataLoggLogProgramDescrip
				INTEGER,
			iqudc12Logging1DolbyMetadataLoggProgramDescriptor
				RollCallString,
			iqudc12Logging1DolbyMetadataLoggProgramDescPt2
				RollCallString,
			iqudc12Logging1DolbyMetadataLoggLogChannelMode
				INTEGER,
			iqudc12Logging1DolbyMetadataLoggChannelMode
				RollCallString,
			iqudc12Logging1DolbyMetadataLoggLogLFEChannel
				INTEGER,
			iqudc12Logging1DolbyMetadataLoggLFEChannel
				RollCallString,
			iqudc12Logging1DolbyMetadataLoggLogDialogueNorm
				INTEGER,
			iqudc12Logging1DolbyMetadataLoggDialogueNorm
				RollCallString,
			iqudc12Logging1VBIANCLoggingLogInputRefVITC
				INTEGER,
			iqudc12Logging1VBIANCLoggingInputRefVITC
				RollCallString,
			iqudc12Logging1VBIANCLoggingLogInputVITC
				INTEGER,
			iqudc12Logging1VBIANCLoggingInputVITC
				RollCallString,
			iqudc12Logging1VBIANCLoggingLogInputANCLine7
				INTEGER,
			iqudc12Logging1VBIANCLoggingInputANCLn7
				RollCallString,
			iqudc12Logging1VBIANCLoggingLogInputANCLine8
				INTEGER,
			iqudc12Logging1VBIANCLoggingInputANCLn8
				RollCallString,
			iqudc12Logging1VBIANCLoggingLogInputANCLine9
				INTEGER,
			iqudc12Logging1VBIANCLoggingInputANCLn9
				RollCallString,
			iqudc12Logging1VBIANCLoggingLogInputANCLine141203
				INTEGER,
			iqudc12Logging1VBIANCLoggingInputANCLn10
				RollCallString,
			iqudc12Logging1VBIANCLoggingLogInputANCLine141204
				INTEGER,
			iqudc12Logging1VBIANCLoggingInputANCLn11
				RollCallString,
			iqudc12Logging1VBIANCLoggingLogInputANCLine141205
				INTEGER,
			iqudc12Logging1VBIANCLoggingInputANCLn12
				RollCallString,
			iqudc12Logging1VBIANCLoggingLogInputANCLine141206
				INTEGER,
			iqudc12Logging1VBIANCLoggingInputANCLn13
				RollCallString,
			iqudc12Logging1VBIANCLoggingLogInputANCLine141207
				INTEGER,
			iqudc12Logging1VBIANCLoggingInputANCLn14
				RollCallString,
			iqudc12Logging1VBIANCLoggingLogInputANCLine141208
				INTEGER,
			iqudc12Logging1VBIANCLoggingInputANCLn15
				RollCallString,
			iqudc12Logging1VBIANCLoggingLogInputANCLine141209
				INTEGER,
			iqudc12Logging1VBIANCLoggingInputANCLn16
				RollCallString,
			iqudc12Logging1VBIANCLoggingLogInputANCLine141210
				INTEGER,
			iqudc12Logging1VBIANCLoggingInputANCLn17
				RollCallString,
			iqudc12Logging1VBIANCLoggingLogInputANCLine141211
				INTEGER,
			iqudc12Logging1VBIANCLoggingInputANCLn18
				RollCallString,
			iqudc12Logging1VBIANCLoggingLogInputANCLine141212
				INTEGER,
			iqudc12Logging1VBIANCLoggingInputANCLn19
				RollCallString,
			iqudc12Logging1VBIANCLoggingLogInputANCLine241213
				INTEGER,
			iqudc12Logging1VBIANCLoggingInputANCLn20
				RollCallString,
			iqudc12Logging1VBIANCLoggingLogInputANCLine241214
				INTEGER,
			iqudc12Logging1VBIANCLoggingInputANCLn21
				RollCallString,
			iqudc12Logging1VBIANCLoggingLogInputANCLine241215
				INTEGER,
			iqudc12Logging1VBIANCLoggingInputANCLn22
				RollCallString,
			iqudc12Logging1VBIANCLoggingLogInputANCLine241216
				INTEGER,
			iqudc12Logging1VBIANCLoggingInputANCLn23
				RollCallString,
			iqudc12Logging1VBIANCLoggingLogOutput1Timecod
				INTEGER,
			iqudc12Logging1VBIANCLoggingOutput1Timecode
				RollCallString,
			iqudc12Logging1VBIANCLoggingLogOutput1ANCLin41220
				INTEGER,
			iqudc12Logging1VBIANCLoggingOutput1ANCLn7
				RollCallString,
			iqudc12Logging1VBIANCLoggingLogOutput1ANCLin41221
				INTEGER,
			iqudc12Logging1VBIANCLoggingOutput1ANCLn8
				RollCallString,
			iqudc12Logging1VBIANCLoggingLogOutput1ANCLin41222
				INTEGER,
			iqudc12Logging1VBIANCLoggingOutput1ANCLn9
				RollCallString,
			iqudc12Logging1VBIANCLoggingLogOutput1ANCLin41223
				INTEGER,
			iqudc12Logging1VBIANCLoggingOutput1ANCLn10
				RollCallString,
			iqudc12Logging1VBIANCLoggingLogOutput1ANCLin41224
				INTEGER,
			iqudc12Logging1VBIANCLoggingOutput1ANCLn11
				RollCallString,
			iqudc12Logging1VBIANCLoggingLogOutput1ANCLin41225
				INTEGER,
			iqudc12Logging1VBIANCLoggingOutput1ANCLn12
				RollCallString,
			iqudc12Logging1VBIANCLoggingLogOutput1ANCLin41226
				INTEGER,
			iqudc12Logging1VBIANCLoggingOutput1ANCLn13
				RollCallString,
			iqudc12Logging1VBIANCLoggingLogOutput1ANCLin41227
				INTEGER,
			iqudc12Logging1VBIANCLoggingOutput1ANCLn14
				RollCallString,
			iqudc12Logging1VBIANCLoggingLogOutput1ANCLin41228
				INTEGER,
			iqudc12Logging1VBIANCLoggingOutput1ANCLn15
				RollCallString,
			iqudc12Logging1VBIANCLoggingLogOutput1ANCLin41229
				INTEGER,
			iqudc12Logging1VBIANCLoggingOutput1ANCLn16
				RollCallString,
			iqudc12Logging1VBIANCLoggingLogOutput1ANCLin41230
				INTEGER,
			iqudc12Logging1VBIANCLoggingOutput1ANCLn17
				RollCallString,
			iqudc12Logging1VBIANCLoggingLogOutput1ANCLin41231
				INTEGER,
			iqudc12Logging1VBIANCLoggingOutput1ANCLn18
				RollCallString,
			iqudc12Logging1VBIANCLoggingLogOutput1ANCLin41232
				INTEGER,
			iqudc12Logging1VBIANCLoggingOutput1ANCLn19
				RollCallString,
			iqudc12Logging1VBIANCLoggingLogOutput1ANCLin41233
				INTEGER,
			iqudc12Logging1VBIANCLoggingOutput1ANCLn20
				RollCallString,
			iqudc12Logging1VBIANCLoggingLogOutput1ANCLin41234
				INTEGER,
			iqudc12Logging1VBIANCLoggingOutput1ANCLn21
				RollCallString,
			iqudc12Logging1VBIANCLoggingLogOutput1ANCLin41235
				INTEGER,
			iqudc12Logging1VBIANCLoggingOutput1ANCLn22
				RollCallString,
			iqudc12Logging1VBIANCLoggingLogOutput1ANCLin
				INTEGER,
			iqudc12Logging1VBIANCLoggingOutput1ANCLn23
				RollCallString,
			iqudc12Logging1WideScreenLoggingLogInput1AFD
				INTEGER,
			iqudc12Logging1WideScreenLoggingInput1AFD
				RollCallString,
			iqudc12Logging1WideScreenLoggingLogInput1Aspect
				INTEGER,
			iqudc12Logging1WideScreenLoggingInput1Aspect
				RollCallString,
			iqudc12Logging1WideScreenLoggingLogInput12016St
				INTEGER,
			iqudc12Logging1WideScreenLoggingInput12016STATE
				RollCallString,
			iqudc12Logging1WideScreenLoggingLogInput12016AS
				INTEGER,
			iqudc12Logging1WideScreenLoggingInput12016ASPECT
				RollCallString,
			iqudc12Logging1WideScreenLoggingLogInput12016
				INTEGER,
			iqudc12Logging1WideScreenLoggingInput12016
				RollCallString,
			iqudc12Logging1WideScreenLoggingLogInput1WSSSta
				INTEGER,
			iqudc12Logging1WideScreenLoggingInput1WSSSTATE
				RollCallString,
			iqudc12Logging1WideScreenLoggingLogInput1WSSASP
				INTEGER,
			iqudc12Logging1WideScreenLoggingInput1WSSASPECT
				RollCallString,
			iqudc12Logging1WideScreenLoggingLogInput1WSS
				INTEGER,
			iqudc12Logging1WideScreenLoggingInput1WSS
				RollCallString,
			iqudc12Logging1WideScreenLoggingLogInput1VIStat
				INTEGER,
			iqudc12Logging1WideScreenLoggingInput1VISTATE
				RollCallString,
			iqudc12Logging1WideScreenLoggingLogInput1VIASPE
				INTEGER,
			iqudc12Logging1WideScreenLoggingInput1VIASPECT
				RollCallString,
			iqudc12Logging1WideScreenLoggingLogInput1VI
				INTEGER,
			iqudc12Logging1WideScreenLoggingInput1VI
				RollCallString,
			iqudc12Logging1WideScreenLoggingLogOutputAFD35944
				INTEGER,
			iqudc12Logging1WideScreenLoggingOutputAFD36944
				RollCallString,
			iqudc12Logging1WideScreenLoggingLogOutputAFD35945
				INTEGER,
			iqudc12Logging1WideScreenLoggingOutputAFD36945
				RollCallString,
			iqudc12Logging2VideoRefLogInp1Type
				INTEGER,
			iqudc12Logging2VideoRefInp1Type
				RollCallString,
			iqudc12Logging2VideoRefLogInp1State
				INTEGER,
			iqudc12Logging2VideoRefInp1State
				RollCallString,
			iqudc12Logging2VideoRefLogInp1Std
				INTEGER,
			iqudc12Logging2VideoRefInp1Std
				RollCallString,
			iqudc12Logging2VideoRefLogInp1SDIErrs
				INTEGER,
			iqudc12Logging2VideoRefInp1SDIErrs
				RollCallString,
			iqudc12Logging2VideoRefLogInp1SDIErrSec
				INTEGER,
			iqudc12Logging2VideoRefInp1SDIErrSec
				RollCallString,
			iqudc12Logging2VideoRefLogInp1ANCerrs
				INTEGER,
			iqudc12Logging2VideoRefInp1ANCerrs
				RollCallString,
			iqudc12Logging2VideoRefLogInp1ANCerrSec
				INTEGER,
			iqudc12Logging2VideoRefInp1ANCerrSec
				RollCallString,
			iqudc12Logging2VideoRefLogInp2Type
				INTEGER,
			iqudc12Logging2VideoRefInp2Type
				RollCallString,
			iqudc12Logging2VideoRefLogInp2State
				INTEGER,
			iqudc12Logging2VideoRefInp2State
				RollCallString,
			iqudc12Logging2VideoRefLogInp2Std
				INTEGER,
			iqudc12Logging2VideoRefInp2Std
				RollCallString,
			iqudc12Logging2VideoRefLogInp2SDIErrs
				INTEGER,
			iqudc12Logging2VideoRefInp2SDIErrs
				RollCallString,
			iqudc12Logging2VideoRefLogInp2SDIErrSec
				INTEGER,
			iqudc12Logging2VideoRefInp2SDIErrSec
				RollCallString,
			iqudc12Logging2VideoRefLogInp2ANCerrs
				INTEGER,
			iqudc12Logging2VideoRefInp2ANCerrs
				RollCallString,
			iqudc12Logging2VideoRefLogInp2ANCerrSec
				INTEGER,
			iqudc12Logging2VideoRefInp2ANCerrSec
				RollCallString,
			iqudc12Logging2VideoRefLogInp3Type
				INTEGER,
			iqudc12Logging2VideoRefInp3Type
				RollCallString,
			iqudc12Logging2VideoRefLogInp3State
				INTEGER,
			iqudc12Logging2VideoRefInp3State
				RollCallString,
			iqudc12Logging2VideoRefLogInp3Std
				INTEGER,
			iqudc12Logging2VideoRefInp3Std
				RollCallString,
			iqudc12Logging2VideoRefLogOutp1Type
				INTEGER,
			iqudc12Logging2VideoRefOutp1Type
				RollCallString,
			iqudc12Logging2VideoRefLogOutp1State
				INTEGER,
			iqudc12Logging2VideoRefOutp1State
				RollCallString,
			iqudc12Logging2VideoRefLogOutp1Std
				INTEGER,
			iqudc12Logging2VideoRefOutp1Std
				RollCallString,
			iqudc12Logging2VideoRefLogOutp2State
				INTEGER,
			iqudc12Logging2VideoRefOutp2State
				RollCallString,
			iqudc12Logging2VideoRefLogOutp2Std
				INTEGER,
			iqudc12Logging2VideoRefOutp2Std
				RollCallString,
			iqudc12Logging2VideoRefLogOutp1
				INTEGER,
			iqudc12Logging2VideoRefOutp1
				RollCallString,
			iqudc12Logging2VideoRefLogOutp1Capt
				INTEGER,
			iqudc12Logging2VideoRefOutp1Capt
				RollCallString,
			iqudc12Logging2VideoRefLogRefType
				INTEGER,
			iqudc12Logging2VideoRefRefType
				RollCallString,
			iqudc12Logging2VideoRefLogRefState
				INTEGER,
			iqudc12Logging2VideoRefRefState
				RollCallString,
			iqudc12Logging2VideoRefLogRefStd
				INTEGER,
			iqudc12Logging2VideoRefRefStd
				RollCallString,
			iqudc12Logging2VideoRefLogGenlockState
				INTEGER,
			iqudc12Logging2VideoRefGenlocState
				RollCallString,
			iqudc12Logging2VideoRefLogInp1Ident
				INTEGER,
			iqudc12Logging2VideoRefInp1Ident
				RollCallString,
			iqudc12Logging2VideoRefLogInp1Name
				INTEGER,
			iqudc12Logging2VideoRefInp1Name
				RollCallString,
			iqudc12Logging2VideoRefLogInp2Ident
				INTEGER,
			iqudc12Logging2VideoRefInp2Ident
				RollCallString,
			iqudc12Logging2VideoRefLogInp2Name
				INTEGER,
			iqudc12Logging2VideoRefInp2Name
				RollCallString,
			iqudc12Logging2VideoRefLogInp3Ident
				INTEGER,
			iqudc12Logging2VideoRefInp3Ident
				RollCallString,
			iqudc12Logging2VideoRefLogInp3Name
				INTEGER,
			iqudc12Logging2VideoRefInp3Name
				RollCallString,
			iqudc12Logging2VideoRefLogOutp2Type
				INTEGER,
			iqudc12Logging2VideoRefOutp2Type
				RollCallString,
			iqudc12Logging2VideoRefLogOutp2
				INTEGER,
			iqudc12Logging2VideoRefOutp2
				RollCallString,
			iqudc12Logging2VideoRefLogOutp2Capt
				INTEGER,
			iqudc12Logging2VideoRefOutp2Capt
				RollCallString,
			iqudc12Logging2VideoRefLogOutp3Type
				INTEGER,
			iqudc12Logging2VideoRefOutp3Type
				RollCallString,
			iqudc12Logging2VideoRefLogOutp3State
				INTEGER,
			iqudc12Logging2VideoRefOutp3State
				RollCallString,
			iqudc12Logging2VideoRefLogOutp3Std
				INTEGER,
			iqudc12Logging2VideoRefOutp3Std
				RollCallString,
			iqudc12Logging2VideoRefLogOutp3
				INTEGER,
			iqudc12Logging2VideoRefOutp3
				RollCallString,
			iqudc12Logging2VideoRefLogOutp3Capt
				INTEGER,
			iqudc12Logging2VideoRefOutp3Capt
				RollCallString,
			iqudc12Logging2InEmbAudLoggingInpEmb1state
				RollCallString,
			iqudc12Logging2InEmbAudLoggingInpEmb2state
				RollCallString,
			iqudc12Logging2InEmbAudLoggingInpEmb3state
				RollCallString,
			iqudc12Logging2InEmbAudLoggingInpEmb4state
				RollCallString,
			iqudc12Logging2InEmbAudLoggingInpEmb5state
				RollCallString,
			iqudc12Logging2InEmbAudLoggingInpEmb6state
				RollCallString,
			iqudc12Logging2InEmbAudLoggingInpEmb7state
				RollCallString,
			iqudc12Logging2InEmbAudLoggingInpEmb8state
				RollCallString,
			iqudc12Logging2In1EmbAudLoggingLogInp1Emb1stat
				INTEGER,
			iqudc12Logging2In1EmbAudLoggingInp1Emb1state
				RollCallString,
			iqudc12Logging2In1EmbAudLoggingLogInp1Emb2stat
				INTEGER,
			iqudc12Logging2In1EmbAudLoggingInp1Emb2state
				RollCallString,
			iqudc12Logging2In1EmbAudLoggingLogInp1Emb3stat
				INTEGER,
			iqudc12Logging2In1EmbAudLoggingInp1Emb3state
				RollCallString,
			iqudc12Logging2In1EmbAudLoggingLogInp1Emb4stat
				INTEGER,
			iqudc12Logging2In1EmbAudLoggingInp1Emb4state
				RollCallString,
			iqudc12Logging2In1EmbAudLoggingLogInp1Emb5stat
				INTEGER,
			iqudc12Logging2In1EmbAudLoggingInp1Emb5state
				RollCallString,
			iqudc12Logging2In1EmbAudLoggingLogInp1Emb6stat
				INTEGER,
			iqudc12Logging2In1EmbAudLoggingInp1Emb6state
				RollCallString,
			iqudc12Logging2In1EmbAudLoggingLogInp1Emb7stat
				INTEGER,
			iqudc12Logging2In1EmbAudLoggingInp1Emb7state
				RollCallString,
			iqudc12Logging2In1EmbAudLoggingLogInp1Emb8stat
				INTEGER,
			iqudc12Logging2In1EmbAudLoggingInp1Emb8state
				RollCallString,
			iqudc12Logging2In2EmbAudLoggingLogInp2Emb1stat
				INTEGER,
			iqudc12Logging2In2EmbAudLoggingInp2Emb1state
				RollCallString,
			iqudc12Logging2In2EmbAudLoggingLogInp2Emb2stat
				INTEGER,
			iqudc12Logging2In2EmbAudLoggingInp2Emb2state
				RollCallString,
			iqudc12Logging2In2EmbAudLoggingLogInp2Emb3stat
				INTEGER,
			iqudc12Logging2In2EmbAudLoggingInp2Emb3state
				RollCallString,
			iqudc12Logging2In2EmbAudLoggingLogInp2Emb4stat
				INTEGER,
			iqudc12Logging2In2EmbAudLoggingInp2Emb4state
				RollCallString,
			iqudc12Logging2In2EmbAudLoggingLogInp2Emb5stat
				INTEGER,
			iqudc12Logging2In2EmbAudLoggingInp2Emb5state
				RollCallString,
			iqudc12Logging2In2EmbAudLoggingLogInp2Emb6stat
				INTEGER,
			iqudc12Logging2In2EmbAudLoggingInp2Emb6state
				RollCallString,
			iqudc12Logging2In2EmbAudLoggingLogInp2Emb7stat
				INTEGER,
			iqudc12Logging2In2EmbAudLoggingInp2Emb7state
				RollCallString,
			iqudc12Logging2In2EmbAudLoggingLogInp2Emb8stat
				INTEGER,
			iqudc12Logging2In2EmbAudLoggingInp2Emb8state
				RollCallString,
			iqudc12Logging2DolbyEAlignLogOutEmb1dolby
				INTEGER,
			iqudc12Logging2DolbyEAlignOutEmb1Dolby
				RollCallString,
			iqudc12Logging2DolbyEAlignLogOutEmb2dolby
				INTEGER,
			iqudc12Logging2DolbyEAlignOutEmb2Dolby
				RollCallString,
			iqudc12Logging2DolbyEAlignLogOutEmb3dolby
				INTEGER,
			iqudc12Logging2DolbyEAlignOutEmb3Dolby
				RollCallString,
			iqudc12Logging2DolbyEAlignLogOutEmb4dolby
				INTEGER,
			iqudc12Logging2DolbyEAlignOutEmb4Dolby
				RollCallString,
			iqudc12Logging2DolbyEAlignLogOutEmb5dolby
				INTEGER,
			iqudc12Logging2DolbyEAlignOutEmb5Dolby
				RollCallString,
			iqudc12Logging2DolbyEAlignLogOutEmb6dolby
				INTEGER,
			iqudc12Logging2DolbyEAlignOutEmb6Dolby
				RollCallString,
			iqudc12Logging2DolbyEAlignLogOutEmb7dolby
				INTEGER,
			iqudc12Logging2DolbyEAlignOutEmb7Dolby
				RollCallString,
			iqudc12Logging2DolbyEAlignLogOutEmb8dolby
				INTEGER,
			iqudc12Logging2DolbyEAlignOutEmb8Dolby
				RollCallString,
			iqudc12Logging2MiscLoggingLogSerialNo
				INTEGER,
			iqudc12Logging2MiscLoggingSerialNo
				RollCallString,
			iqudc12Logging2MiscLoggingLogOSVersion
				INTEGER,
			iqudc12Logging2MiscLoggingOSVersion
				RollCallString,
			iqudc12Logging2MiscLoggingLogBuildNo
				INTEGER,
			iqudc12Logging2MiscLoggingBuildNo
				RollCallString,
			iqudc12Logging2MiscLoggingLogHardwareVer
				INTEGER,
			iqudc12Logging2MiscLoggingHardwareVer
				RollCallString,
			iqudc12Logging2MiscLoggingLogFirmwareVer
				INTEGER,
			iqudc12Logging2MiscLoggingFirmwareVer
				RollCallString,
			iqudc12Logging2MiscLoggingLogUpTime
				INTEGER,
			iqudc12Logging2MiscLoggingUpTime
				RollCallString,
			iqudc12Logging2MiscLoggingLogLicensedOpt
				INTEGER,
			iqudc12Logging2MiscLoggingLicensedOptions
				RollCallString,
			iqudc12Logging2MiscLoggingLogLicensedOpt2
				INTEGER,
			iqudc12Logging2MiscLoggingLicensedOptions2
				RollCallString,
			iqudc12Logging2MiscLoggingLogTemp1State
				INTEGER,
			iqudc12Logging2MiscLoggingTemp1State
				RollCallString,
			iqudc12Logging2MiscLoggingLogTemp1Name
				INTEGER,
			iqudc12Logging2MiscLoggingTemp1Name
				RollCallString,
			iqudc12Logging2MiscLoggingLogRearId
				INTEGER,
			iqudc12Logging2MiscLoggingRearID
				RollCallString,
			iqudc12Logging2MiscLoggingLogSlotWidth
				INTEGER,
			iqudc12Logging2MiscLoggingSlotWidth
				RollCallString,
			iqudc12Logging2MiscLoggingLogSlotStart
				INTEGER,
			iqudc12Logging2MiscLoggingSlotStart
				RollCallString,
			iqudc12Logging2MiscLoggingLogRearStatus
				INTEGER,
			iqudc12Logging2MiscLoggingRearSTATUS
				RollCallString,
			iqudc12Logging2MiscLoggingLogPowerUsage
				INTEGER,
			iqudc12Logging2MiscLoggingPowerUsage
				RollCallString,
			iqudc12RollCallMemoriesRollTrackDisableAll
				INTEGER,
			iqudc12RollCallMemoriesRollTrackIndex
				INTEGER,
			iqudc12RollCallMemoriesRollTrackSource
				INTEGER,
			iqudc12RollCallMemoriesRollTrackAddress
				RollCallString,
			iqudc12RollCallMemoriesRollTrackCommand
				RollCallString,
			iqudc12RollCallMemoriesRollTrackStatus
				RollCallString,
			iqudc12RollCallMemoriesRollTrackSending
				RollCallString,
			iqudc12RollCallMemoriesHideHideGpio
				INTEGER,
			iqudc12GPIOGPI1GPIO1Mode
				INTEGER,
			iqudc12GPIOGPI1GPI1IPHighSele
				INTEGER,
			iqudc12GPIOGPI1GPI1IPLowSelec
				INTEGER,
			iqudc12GPIOGPI1GPO1OPSelect
				INTEGER,
			iqudc12GPIOGPI1InvertGPIO1
				INTEGER,
			iqudc12GPIOGPI1Status
				RollCallString,
			iqudc12GPIOGPI2GPIO2Mode
				INTEGER,
			iqudc12GPIOGPI2GPI2IPHighSele
				INTEGER,
			iqudc12GPIOGPI2GPI2IPLowSelec
				INTEGER,
			iqudc12GPIOGPI2GPO2OPSelect
				INTEGER,
			iqudc12GPIOGPI2InvertGPIO2
				INTEGER,
			iqudc12GPIOGPI2Status
				RollCallString,
			iqudc12MenuSetupDisplay
				INTEGER,
			iqudc12MenuSetupProduct
				RollCallString,
			iqudc12MenuSetupRelease
				RollCallString,
			iqudc12MenuSetupBuild
				RollCallString,
			iqudc12MenuSetupKOS
				RollCallString,
			iqudc12MenuSetupSerialNo
				RollCallString,
			iqudc12MenuSetupFactoryDefault
				INTEGER,
			iqudc12MenuSetupRestart
				INTEGER,
			iqudc12MenuSetupDefaultSettings
				INTEGER,
			iqudc12MenuSetupSerialNumber
				RollCallString,
			iqudc12MenuSetupBoardID
				INTEGER,
			iqudc12MenuSetupSaveID
				INTEGER,
			iqudc12SetupFpgaBoardType
				RollCallString,
			iqudc12SetupFpgaFpgaSerialNo
				RollCallString,
			iqudc12SetupFpgaSoftVer
				RollCallString,
			iqudc12SetupFpgaFpgaVer
				RollCallString,
			iqudc12SetupFpgaTIVer
				RollCallString,
			iqudc12SetupFpgaDolbyModId
				RollCallString,
			iqudc12SetupFpgaProtVer
				RollCallString,
			iqudc12SetupFpgaProgCRC
				RollCallString,
			iqudc12SetupFpgaUptime
				RollCallString,
			iqudc12SetupFpgaENGVXPVer
				RollCallString,
			iqudc12SetupFpgaENGSharcVer
				RollCallString,
			iqudc12SetupFpgaENGAlteraVer
				RollCallString,
			iqudc12SetupFpgaENGVCCint
				RollCallString,
			iqudc12SetupFpgaENGVCCaux
				RollCallString,
			iqudc12SetupOptionsOption1
				RollCallString,
			iqudc12SetupOptionsOption2
				RollCallString,
			iqudc12SetupOptionsOption3
				RollCallString,
			iqudc12SetupOptionsOption4
				RollCallString,
			iqudc12SetupOptionsOption5
				RollCallString,
			iqudc12SetupOptionsOption6
				RollCallString,
			iqudc12SetupOptionsOption7
				RollCallString,
			iqudc12SetupOptionsOption8
				RollCallString,
			iqudc12SetupOptionsOption9
				RollCallString,
			iqudc12SetupOptionsOptionsMask
				INTEGER,
			iqudc12SetupDemoNonDemoRestart
				INTEGER,
			iqudc12SetupDemoRestartMode
				INTEGER,
			iqudc12SetupDemoRemainingDemo
				INTEGER,
			iqudc12SetupDemoRemaining24h
				INTEGER,
			iqudc12SetupDemoDolbyType
				INTEGER,
			iqudc12MenuSetupRestartHard
				INTEGER,
			iqudc12MenuSetupInput1Name
				RollCallString,
			iqudc12MenuSetupInput2Name
				RollCallString,
			iqudc12MenuSetupInput3Name
				RollCallString,
			iqudc12LoudMonBlk1SourceLSrc
				INTEGER,
			iqudc12LoudMonBlk1SourceRSrc
				INTEGER,
			iqudc12LoudMonBlk1SourceLSSrc
				INTEGER,
			iqudc12LoudMonBlk1SourceRSSrc
				INTEGER,
			iqudc12LoudMonBlk1SourceCSrc
				INTEGER,
			iqudc12LoudMonBlk2SourceLSrc
				INTEGER,
			iqudc12LoudMonBlk2SourceRSrc
				INTEGER,
			iqudc12LoudMonBlk2SourceLSSrc
				INTEGER,
			iqudc12LoudMonBlk2SourceRSSrc
				INTEGER,
			iqudc12LoudMonBlk2SourceCSrc
				INTEGER,
			iqudc12LoudMonitorBlock1ResetSession
				INTEGER,
			iqudc12LoudMonitorBlock1StartSession
				INTEGER,
			iqudc12LoudMonitorBlock1PauseSession
				INTEGER,
			iqudc12LoudMonitorBlock1StopSession
				INTEGER,
			iqudc12LoudMonitorBlock1IntegratedLevel
				RollCallString,
			iqudc12LoudMonitorBlock1ShortTermLevel
				RollCallString,
			iqudc12LoudMonitorBlock1MomentaryLevel
				RollCallString,
			iqudc12LoudMonitorBlock1LRA
				RollCallString,
			iqudc12LoudMonitorBlock1MTPL
				RollCallString,
			iqudc12LoudMonitorBlock1SessTime
				RollCallString,
			iqudc12LoudMonitorBlock1LiveLevel
				RollCallString,
			iqudc12LoudMonitorBlock1Units
				RollCallString,
			iqudc12LoudMonitorBlock1Proc1State
				INTEGER,
			iqudc12LoudMonitorBlock1Proc1Status
				RollCallString,
			iqudc12LoudMonitorBlock1Proc1UpdRate
				INTEGER,
			iqudc12LoudMonitorBlock1MSUpdate
				RollCallString,
			iqudc12LoudMonitorBlock1ILRAUpdate
				RollCallString,
			iqudc12LoudMonitorBlock1Proc1MinMax
				RollCallString,
			iqudc12LoudMonitorBlock2ResetSession
				INTEGER,
			iqudc12LoudMonitorBlock2PauseSession
				INTEGER,
			iqudc12LoudMonitorBlock2StartSession
				INTEGER,
			iqudc12LoudMonitorBlock2StopSession
				INTEGER,
			iqudc12LoudMonitorBlock2IntegratedLevel
				RollCallString,
			iqudc12LoudMonitorBlock2ShortTermLevel
				RollCallString,
			iqudc12LoudMonitorBlock2MomentaryLevel
				RollCallString,
			iqudc12LoudMonitorBlock2LRA
				RollCallString,
			iqudc12LoudMonitorBlock2MTPL
				RollCallString,
			iqudc12LoudMonitorBlock2SessTime
				RollCallString,
			iqudc12LoudMonitorBlock2LkfsDispMode
				INTEGER,
			iqudc12LoudMonitorBlock2Units
				RollCallString,
			iqudc12LoudMonitorBlock2LiveUnits
				RollCallString,
			iqudc12LoudMonitorBlock2Proc2State
				INTEGER,
			iqudc12LoudMonitorBlock2Proc2Status
				RollCallString,
			iqudc12LoudMonitorBlock2Proc2UpdRate
				INTEGER,
			iqudc12LoudMonitorBlock2Proc2MinMax
				RollCallString,
			iqudc12LoudMonitorBlock2RollcallUpdate
				INTEGER,
			iqudc12LoudMonitorBlock2Prog1ID
				RollCallString,
			iqudc12LoudMonitorBlock2Prog2ID
				RollCallString,
			iqudc12LoudMonitorBlock2Chan1ID
				RollCallString,
			iqudc12LoudMonitorBlock2Chan2ID
				RollCallString
		}

	iqudc12SlotIndex OBJECT-TYPE
		SYNTAX		Unsigned32
		MAX-ACCESS		not-accessible
		STATUS			current
		DESCRIPTION
				"The unique Index value for each slot.  Its value
					ranges between 1 and the value of slotNumber."
		::= { iqudc12CmdEntry 0 }


	iqudc12Video1VideoInputInput1Std OBJECT-TYPE
		SYNTAX		RollCallString
		MAX-ACCESS		read-only
		STATUS			current
		DESCRIPTION
				"TYPE: - Display
				 PAGE: - Video1
					Input 1 Std  cmdID= 40703  format=   "
		::= { iqudc12CmdEntry 40703 }


	iqudc12Video1VideoInputInput2Std OBJECT-TYPE
		SYNTAX		RollCallString
		MAX-ACCESS		read-only
		STATUS			current
		DESCRIPTION
				"TYPE: - Display
				 PAGE: - Video1
					Input 2 Std  cmdID= 40704  format=   "
		::= { iqudc12CmdEntry 40704 }


	iqudc12Video1VideoInputInputAnalogStd OBJECT-TYPE
		SYNTAX		RollCallString
		MAX-ACCESS		read-only
		STATUS			current
		DESCRIPTION
				"TYPE: - Display
				 PAGE: - Video1
					Input Analog Std  cmdID= 40705  format=   "
		::= { iqudc12CmdEntry 40705 }


	iqudc12Video1VideoInputIPSelect OBJECT-TYPE
		SYNTAX		INTEGER {
							val-Input-1(0),
							val-Input-2(1),
							val-Analog(2)
							}
		MAX-ACCESS		read-write
		STATUS			current
		DESCRIPTION
				"TYPE: - RadiobuttonList
				 PAGE: - Video1
					I/P Select  cmdID= 33024 
					Input 1  value= 0  
					Input 2  value= 1  
					Analog  value= 2  "
		::= { iqudc12CmdEntry 33024 }


	iqudc12VideoInputValidStandards108050p OBJECT-TYPE
		SYNTAX		INTEGER { disable(0), enable(1) }
		MAX-ACCESS		read-write
		STATUS			current
		DESCRIPTION
				"TYPE: - Checkbox
				 PAGE: - Video1
					1080/50p  cmdID= 33004 "
		::= { iqudc12CmdEntry 33004 }


	iqudc12VideoInputValidStandards108059p OBJECT-TYPE
		SYNTAX		INTEGER { disable(0), enable(1) }
		MAX-ACCESS		read-write
		STATUS			current
		DESCRIPTION
				"TYPE: - Checkbox
				 PAGE: - Video1
					1080/59p  cmdID= 33005 "
		::= { iqudc12CmdEntry 33005 }


	iqudc12VideoInputValidStandards108025i OBJECT-TYPE
		SYNTAX		INTEGER { disable(0), enable(1) }
		MAX-ACCESS		read-write
		STATUS			current
		DESCRIPTION
				"TYPE: - Checkbox
				 PAGE: - Video1
					1080/25i  cmdID= 33006 "
		::= { iqudc12CmdEntry 33006 }


	iqudc12VideoInputValidStandards108029i OBJECT-TYPE
		SYNTAX		INTEGER { disable(0), enable(1) }
		MAX-ACCESS		read-write
		STATUS			current
		DESCRIPTION
				"TYPE: - Checkbox
				 PAGE: - Video1
					1080/29i  cmdID= 33007 "
		::= { iqudc12CmdEntry 33007 }


	iqudc12VideoInputValidStandards72050p OBJECT-TYPE
		SYNTAX		INTEGER { disable(0), enable(1) }
		MAX-ACCESS		read-write
		STATUS			current
		DESCRIPTION
				"TYPE: - Checkbox
				 PAGE: - Video1
					720/50p  cmdID= 33010 "
		::= { iqudc12CmdEntry 33010 }


	iqudc12VideoInputValidStandards72059p OBJECT-TYPE
		SYNTAX		INTEGER { disable(0), enable(1) }
		MAX-ACCESS		read-write
		STATUS			current
		DESCRIPTION
				"TYPE: - Checkbox
				 PAGE: - Video1
					720/59p  cmdID= 33011 "
		::= { iqudc12CmdEntry 33011 }


	iqudc12VideoInputValidStandards62525i OBJECT-TYPE
		SYNTAX		INTEGER { disable(0), enable(1) }
		MAX-ACCESS		read-write
		STATUS			current
		DESCRIPTION
				"TYPE: - Checkbox
				 PAGE: - Video1
					625/25i  cmdID= 33009 "
		::= { iqudc12CmdEntry 33009 }


	iqudc12VideoInputValidStandards52529i OBJECT-TYPE
		SYNTAX		INTEGER { disable(0), enable(1) }
		MAX-ACCESS		read-write
		STATUS			current
		DESCRIPTION
				"TYPE: - Checkbox
				 PAGE: - Video1
					525/29i  cmdID= 33008 "
		::= { iqudc12CmdEntry 33008 }


	iqudc12VideoInputValidStandards108023psf OBJECT-TYPE
		SYNTAX		INTEGER { disable(0), enable(1) }
		MAX-ACCESS		read-write
		STATUS			current
		DESCRIPTION
				"TYPE: - Checkbox
				 PAGE: - Video1
					1080/23psf  cmdID= 33046 "
		::= { iqudc12CmdEntry 33046 }


	iqudc12VideoInputValidStandards108025psf OBJECT-TYPE
		SYNTAX		INTEGER { disable(0), enable(1) }
		MAX-ACCESS		read-write
		STATUS			current
		DESCRIPTION
				"TYPE: - Checkbox
				 PAGE: - Video1
					1080/25psf  cmdID= 33047 "
		::= { iqudc12CmdEntry 33047 }


	iqudc12VideoInputValidStandards108025p OBJECT-TYPE
		SYNTAX		INTEGER { disable(0), enable(1) }
		MAX-ACCESS		read-write
		STATUS			current
		DESCRIPTION
				"TYPE: - Checkbox
				 PAGE: - Video1
					1080/25p  cmdID= 33048 "
		::= { iqudc12CmdEntry 33048 }


	iqudc12VideoInputValidStandards108029p OBJECT-TYPE
		SYNTAX		INTEGER { disable(0), enable(1) }
		MAX-ACCESS		read-write
		STATUS			current
		DESCRIPTION
				"TYPE: - Checkbox
				 PAGE: - Video1
					1080/29p  cmdID= 33049 "
		::= { iqudc12CmdEntry 33049 }


	iqudc12VideoInputErrorsErrorReset OBJECT-TYPE
		SYNTAX		INTEGER { noAction(0),val-Error-Reset(1) }
		MAX-ACCESS		read-write
		STATUS			current
		DESCRIPTION
				"TYPE: - Button
				 PAGE: - Video1
					Error Reset  cmdID= 33014  value= 1  "
		::= { iqudc12CmdEntry 33014 }


	iqudc12VideoInputErrorsResetSec OBJECT-TYPE
		SYNTAX		RollCallString
		MAX-ACCESS		read-only
		STATUS			current
		DESCRIPTION
				"TYPE: - Display
				 PAGE: - Video1
					ResetSec  cmdID= 33015  format=   "
		::= { iqudc12CmdEntry 33015 }


	iqudc12VideoInputErrorsCRCErrs1 OBJECT-TYPE
		SYNTAX		RollCallString
		MAX-ACCESS		read-only
		STATUS			current
		DESCRIPTION
				"TYPE: - Display
				 PAGE: - Video1
					CRC Errs1  cmdID= 33016  format=   "
		::= { iqudc12CmdEntry 33016 }


	iqudc12VideoInputErrorsANCErrs1 OBJECT-TYPE
		SYNTAX		RollCallString
		MAX-ACCESS		read-only
		STATUS			current
		DESCRIPTION
				"TYPE: - Display
				 PAGE: - Video1
					ANC Errs1  cmdID= 33020  format=   "
		::= { iqudc12CmdEntry 33020 }


	iqudc12VideoInputErrorsCRCErrs2 OBJECT-TYPE
		SYNTAX		RollCallString
		MAX-ACCESS		read-only
		STATUS			current
		DESCRIPTION
				"TYPE: - Display
				 PAGE: - Video1
					CRC Errs2  cmdID= 33018  format=   "
		::= { iqudc12CmdEntry 33018 }


	iqudc12VideoInputErrorsANCErrs2 OBJECT-TYPE
		SYNTAX		RollCallString
		MAX-ACCESS		read-only
		STATUS			current
		DESCRIPTION
				"TYPE: - Display
				 PAGE: - Video1
					ANC Errs2  cmdID= 33022  format=   "
		::= { iqudc12CmdEntry 33022 }


	iqudc12VideoInputErrorsCRCErrSec1 OBJECT-TYPE
		SYNTAX		RollCallString
		MAX-ACCESS		read-only
		STATUS			current
		DESCRIPTION
				"TYPE: - Display
				 PAGE: - Video1
					CRC ErrSec1  cmdID= 33017  format=   "
		::= { iqudc12CmdEntry 33017 }


	iqudc12VideoInputErrorsANCErrSec1 OBJECT-TYPE
		SYNTAX		RollCallString
		MAX-ACCESS		read-only
		STATUS			current
		DESCRIPTION
				"TYPE: - Display
				 PAGE: - Video1
					ANC ErrSec1  cmdID= 33021  format=   "
		::= { iqudc12CmdEntry 33021 }


	iqudc12VideoInputErrorsCRCErrSec2 OBJECT-TYPE
		SYNTAX		RollCallString
		MAX-ACCESS		read-only
		STATUS			current
		DESCRIPTION
				"TYPE: - Display
				 PAGE: - Video1
					CRC ErrSec2  cmdID= 33019  format=   "
		::= { iqudc12CmdEntry 33019 }


	iqudc12VideoInputErrorsANCErrSec2 OBJECT-TYPE
		SYNTAX		RollCallString
		MAX-ACCESS		read-only
		STATUS			current
		DESCRIPTION
				"TYPE: - Display
				 PAGE: - Video1
					ANC ErrSec2  cmdID= 33023  format=   "
		::= { iqudc12CmdEntry 33023 }


	iqudc12Video1VideoInputSDAnlgEncode OBJECT-TYPE
		SYNTAX		INTEGER {
							val-SMPTE(0),
							val-BetaCam(1),
							val-MII(2)
							}
		MAX-ACCESS		read-write
		STATUS			current
		DESCRIPTION
				"TYPE: - RadiobuttonList
				 PAGE: - Video1
					SD Anlg Encode  cmdID= 33037 
					SMPTE  value= 0  
					BetaCam  value= 1  
					MII  value= 2  "
		::= { iqudc12CmdEntry 33037 }


	iqudc12Video1VideoInputAnlgType OBJECT-TYPE
		SYNTAX		INTEGER {
							val-Composite-SD(0),
							val-Y-C-SD(1),
							val-YPbPr-SD-HD(2),
							val-GBR(3)
							}
		MAX-ACCESS		read-write
		STATUS			current
		DESCRIPTION
				"TYPE: - RadiobuttonList
				 PAGE: - Video1
					Anlg Type  cmdID= 33040 
					Composite (SD)  value= 0  
					Y/C (SD)  value= 1  
					YPbPr (SD/HD)  value= 2  
					GBR  value= 3  "
		::= { iqudc12CmdEntry 33040 }


	iqudc12Video1VideoInputPedComposDec OBJECT-TYPE
		SYNTAX		INTEGER {
							val-Pedestal-n-aNTSC-J(0),
							val-Pedestal-NTSC(1)
							}
		MAX-ACCESS		read-write
		STATUS			current
		DESCRIPTION
				"TYPE: - RadiobuttonList
				 PAGE: - Video1
					Ped Compos Dec  cmdID= 33042 
					Pedestal:n/aNTSC-J  value= 0  
					Pedestal:NTSC  value= 1  "
		::= { iqudc12CmdEntry 33042 }


	iqudc12Video1VideoInputYCDelay OBJECT-TYPE
		SYNTAX		INTEGER
		MAX-ACCESS		read-write
		STATUS			current
		DESCRIPTION
				"TYPE: - Number
				 PAGE: - Video1
					YC Delay  cmdID= 32999  min= -8  max= 7  step= 1  format= %0.0f  div_scale= 1 
					Min = -8  Max = 7  Step = 1 "
		::= { iqudc12CmdEntry 32999 }


	iqudc12Video1BackupBackupEnable OBJECT-TYPE
		SYNTAX		INTEGER { disable(0), enable(1) }
		MAX-ACCESS		read-write
		STATUS			current
		DESCRIPTION
				"TYPE: - Checkbox
				 PAGE: - Video1
					Backup Enable  cmdID= 39100 "
		::= { iqudc12CmdEntry 39100 }


	iqudc12Video1BackupORInput1State OBJECT-TYPE
		SYNTAX		RollCallString
		MAX-ACCESS		read-only
		STATUS			current
		DESCRIPTION
				"TYPE: - Display
				 PAGE: - Video1
					OR Input1 State  cmdID= 39101  format=   "
		::= { iqudc12CmdEntry 39101 }


	iqudc12Video1BackupORInput2State OBJECT-TYPE
		SYNTAX		RollCallString
		MAX-ACCESS		read-only
		STATUS			current
		DESCRIPTION
				"TYPE: - Display
				 PAGE: - Video1
					OR Input2 State  cmdID= 39102  format=   "
		::= { iqudc12CmdEntry 39102 }


	iqudc12Video1BackupRevertDelay OBJECT-TYPE
		SYNTAX		INTEGER
		MAX-ACCESS		read-write
		STATUS			current
		DESCRIPTION
				"TYPE: - Number
				 PAGE: - Video1
					Revert Delay  cmdID= 39141  min= 0  max= 1000  step= 10  format= %0.0f s  div_scale= 10 
					Min = 0 s  Max = 100 s  Step = 1 s "
		::= { iqudc12CmdEntry 39141 }


	iqudc12Video1BackupPriority OBJECT-TYPE
		SYNTAX		INTEGER {
							val-None(0),
							val-Priority-1(1),
							val-Priority-2(2)
							}
		MAX-ACCESS		read-write
		STATUS			current
		DESCRIPTION
				"TYPE: - RadiobuttonList
				 PAGE: - Video1
					Priority  cmdID= 39103 
					None  value= 0  
					Priority 1  value= 1  
					Priority 2  value= 2  "
		::= { iqudc12CmdEntry 39103 }


	iqudc12Video1BackupQualifyInvStd OBJECT-TYPE
		SYNTAX		INTEGER { disable(0), enable(1) }
		MAX-ACCESS		read-write
		STATUS			current
		DESCRIPTION
				"TYPE: - Checkbox
				 PAGE: - Video1
					Qualify Inv Std  cmdID= 39104 "
		::= { iqudc12CmdEntry 39104 }


	iqudc12Video1BackupQualifyCRCErr OBJECT-TYPE
		SYNTAX		INTEGER { disable(0), enable(1) }
		MAX-ACCESS		read-write
		STATUS			current
		DESCRIPTION
				"TYPE: - Checkbox
				 PAGE: - Video1
					Qualify CRC Err  cmdID= 39105 "
		::= { iqudc12CmdEntry 39105 }


	iqudc12Video1BackupQualifyANCErr OBJECT-TYPE
		SYNTAX		INTEGER { disable(0), enable(1) }
		MAX-ACCESS		read-write
		STATUS			current
		DESCRIPTION
				"TYPE: - Checkbox
				 PAGE: - Video1
					Qualify ANC Err  cmdID= 39106 "
		::= { iqudc12CmdEntry 39106 }


	iqudc12Video1BackupQualifyAudioFail OBJECT-TYPE
		SYNTAX		INTEGER { disable(0), enable(1) }
		MAX-ACCESS		read-write
		STATUS			current
		DESCRIPTION
				"TYPE: - Checkbox
				 PAGE: - Video1
					Qualify Audio Fail  cmdID= 39142 "
		::= { iqudc12CmdEntry 39142 }


	iqudc12BackupInput1SelStatInp1OK OBJECT-TYPE
		SYNTAX		RollCallString
		MAX-ACCESS		read-only
		STATUS			current
		DESCRIPTION
				"TYPE: - Display
				 PAGE: - Video1
					Stat Inp1 OK  cmdID= 39127  format=   "
		::= { iqudc12CmdEntry 39127 }


	iqudc12BackupInput1SelStatInp2FAIL OBJECT-TYPE
		SYNTAX		RollCallString
		MAX-ACCESS		read-only
		STATUS			current
		DESCRIPTION
				"TYPE: - Display
				 PAGE: - Video1
					Stat Inp2 FAIL  cmdID= 39128  format=   "
		::= { iqudc12CmdEntry 39128 }


	iqudc12BackupInput1SelStatInp2Err OBJECT-TYPE
		SYNTAX		RollCallString
		MAX-ACCESS		read-only
		STATUS			current
		DESCRIPTION
				"TYPE: - Display
				 PAGE: - Video1
					Stat Inp2 Err  cmdID= 39139  format=   "
		::= { iqudc12CmdEntry 39139 }


	iqudc12BackupInput1SelStatAUDFail2 OBJECT-TYPE
		SYNTAX		RollCallString
		MAX-ACCESS		read-only
		STATUS			current
		DESCRIPTION
				"TYPE: - Display
				 PAGE: - Video1
					Stat AUD Fail 2  cmdID= 39144  format=   "
		::= { iqudc12CmdEntry 39144 }


	iqudc12BackupInput1SelStatStd2 OBJECT-TYPE
		SYNTAX		RollCallString
		MAX-ACCESS		read-only
		STATUS			current
		DESCRIPTION
				"TYPE: - Display
				 PAGE: - Video1
					Stat Std 2  cmdID= 39173  format=   "
		::= { iqudc12CmdEntry 39173 }


	iqudc12BackupInput1SelStatGPI1 OBJECT-TYPE
		SYNTAX		RollCallString
		MAX-ACCESS		read-only
		STATUS			current
		DESCRIPTION
				"TYPE: - Display
				 PAGE: - Video1
					Stat GPI 1  cmdID= 39129  format=   "
		::= { iqudc12CmdEntry 39129 }


	iqudc12BackupInput1SelStatGPI2 OBJECT-TYPE
		SYNTAX		RollCallString
		MAX-ACCESS		read-only
		STATUS			current
		DESCRIPTION
				"TYPE: - Display
				 PAGE: - Video1
					Stat GPI 2  cmdID= 39130  format=   "
		::= { iqudc12CmdEntry 39130 }


	iqudc12BackupInput1SelEnblInp1OK OBJECT-TYPE
		SYNTAX		INTEGER { disable(0), enable(1) }
		MAX-ACCESS		read-write
		STATUS			current
		DESCRIPTION
				"TYPE: - Checkbox
				 PAGE: - Video1
					Enbl Inp1 OK  cmdID= 39107 "
		::= { iqudc12CmdEntry 39107 }


	iqudc12BackupInput1SelEnblInp2FAIL OBJECT-TYPE
		SYNTAX		INTEGER { disable(0), enable(1) }
		MAX-ACCESS		read-write
		STATUS			current
		DESCRIPTION
				"TYPE: - Checkbox
				 PAGE: - Video1
					Enbl Inp2 FAIL  cmdID= 39108 "
		::= { iqudc12CmdEntry 39108 }


	iqudc12BackupInput1SelEnblInp2Err OBJECT-TYPE
		SYNTAX		INTEGER { disable(0), enable(1) }
		MAX-ACCESS		read-write
		STATUS			current
		DESCRIPTION
				"TYPE: - Checkbox
				 PAGE: - Video1
					Enbl Inp2 Err  cmdID= 39135 "
		::= { iqudc12CmdEntry 39135 }


	iqudc12BackupInput1SelEnblGPI1 OBJECT-TYPE
		SYNTAX		INTEGER { disable(0), enable(1) }
		MAX-ACCESS		read-write
		STATUS			current
		DESCRIPTION
				"TYPE: - Checkbox
				 PAGE: - Video1
					Enbl GPI 1  cmdID= 39109 "
		::= { iqudc12CmdEntry 39109 }


	iqudc12BackupInput1SelEnblGPI2 OBJECT-TYPE
		SYNTAX		INTEGER { disable(0), enable(1) }
		MAX-ACCESS		read-write
		STATUS			current
		DESCRIPTION
				"TYPE: - Checkbox
				 PAGE: - Video1
					Enbl GPI 2  cmdID= 39110 "
		::= { iqudc12CmdEntry 39110 }


	iqudc12BackupInput1SelEnblStdInp2 OBJECT-TYPE
		SYNTAX		INTEGER { disable(0), enable(1) }
		MAX-ACCESS		read-write
		STATUS			current
		DESCRIPTION
				"TYPE: - Checkbox
				 PAGE: - Video1
					Enbl Std Inp2  cmdID= 39172 "
		::= { iqudc12CmdEntry 39172 }


	iqudc12BackupInput1SelDlyInp1OK OBJECT-TYPE
		SYNTAX		INTEGER
		MAX-ACCESS		read-write
		STATUS			current
		DESCRIPTION
				"TYPE: - Number
				 PAGE: - Video1
					Dly Inp1 OK  cmdID= 39115  min= 10  max= 100  step= 1  format= %0.1f s  div_scale= 10 
					Min = 1.0 s  Max = 10.0 s  Step = 0.1 s "
		::= { iqudc12CmdEntry 39115 }


	iqudc12BackupInput1SelDlyInp2FAIL OBJECT-TYPE
		SYNTAX		INTEGER
		MAX-ACCESS		read-write
		STATUS			current
		DESCRIPTION
				"TYPE: - Number
				 PAGE: - Video1
					Dly Inp2 FAIL  cmdID= 39116  min= 0  max= 100  step= 1  format= %0.1f s  div_scale= 10 
					Min = 0.0 s  Max = 10.0 s  Step = 0.1 s "
		::= { iqudc12CmdEntry 39116 }


	iqudc12BackupInput1SelDlyInp2Err OBJECT-TYPE
		SYNTAX		INTEGER
		MAX-ACCESS		read-write
		STATUS			current
		DESCRIPTION
				"TYPE: - Number
				 PAGE: - Video1
					Dly Inp2 Err  cmdID= 39137  min= 10  max= 100  step= 10  format= %0.0f s  div_scale= 10 
					Min = 1 s  Max = 10 s  Step = 1 s "
		::= { iqudc12CmdEntry 39137 }


	iqudc12BackupInput1SelDlyGPI1 OBJECT-TYPE
		SYNTAX		INTEGER
		MAX-ACCESS		read-write
		STATUS			current
		DESCRIPTION
				"TYPE: - Number
				 PAGE: - Video1
					Dly GPI 1  cmdID= 39117  min= 0  max= 100  step= 1  format= %0.1f s  div_scale= 10 
					Min = 0.0 s  Max = 10.0 s  Step = 0.1 s "
		::= { iqudc12CmdEntry 39117 }


	iqudc12BackupInput1SelDlyGPI2 OBJECT-TYPE
		SYNTAX		INTEGER
		MAX-ACCESS		read-write
		STATUS			current
		DESCRIPTION
				"TYPE: - Number
				 PAGE: - Video1
					Dly GPI 2  cmdID= 39118  min= 0  max= 100  step= 1  format= %0.1f s  div_scale= 10 
					Min = 0.0 s  Max = 10.0 s  Step = 0.1 s "
		::= { iqudc12CmdEntry 39118 }


	iqudc12BackupInput1SelDlyAud2FAIL OBJECT-TYPE
		SYNTAX		INTEGER
		MAX-ACCESS		read-write
		STATUS			current
		DESCRIPTION
				"TYPE: - Number
				 PAGE: - Video1
					Dly Aud2 FAIL  cmdID= 39145  min= 10  max= 100  step= 1  format= %0.1f s  div_scale= 10 
					Min = 1.0 s  Max = 10.0 s  Step = 0.1 s "
		::= { iqudc12CmdEntry 39145 }


	iqudc12BackupInput1SelDlyStd2 OBJECT-TYPE
		SYNTAX		INTEGER
		MAX-ACCESS		read-write
		STATUS			current
		DESCRIPTION
				"TYPE: - Number
				 PAGE: - Video1
					Dly Std 2  cmdID= 39171  min= 0  max= 100  step= 1  format= %0.1f s  div_scale= 10 
					Min = 0.0 s  Max = 10.0 s  Step = 0.1 s "
		::= { iqudc12CmdEntry 39171 }


	iqudc12BackupInput1SelGPI1State OBJECT-TYPE
		SYNTAX		INTEGER {
							val-High(1),
							val-Low(0)
							}
		MAX-ACCESS		read-write
		STATUS			current
		DESCRIPTION
				"TYPE: - RadiobuttonList
				 PAGE: - Video1
					GPI 1 State  cmdID= 39123 
					High  value= 1  
					Low  value= 0  "
		::= { iqudc12CmdEntry 39123 }


	iqudc12BackupInput1SelGPI2State OBJECT-TYPE
		SYNTAX		INTEGER {
							val-High(1),
							val-Low(0)
							}
		MAX-ACCESS		read-write
		STATUS			current
		DESCRIPTION
				"TYPE: - RadiobuttonList
				 PAGE: - Video1
					GPI 2 State  cmdID= 39124 
					High  value= 1  
					Low  value= 0  "
		::= { iqudc12CmdEntry 39124 }


	iqudc12BackupInput1SelInp12AudFailG1C39149 OBJECT-TYPE
		SYNTAX		INTEGER { disable(0), enable(1) }
		MAX-ACCESS		read-write
		STATUS			current
		DESCRIPTION
				"TYPE: - Checkbox
				 PAGE: - Video1
					Inp1 2 Aud Fail G1C  cmdID= 39149 "
		::= { iqudc12CmdEntry 39149 }


	iqudc12BackupInput1SelInp12AudFailG1C39150 OBJECT-TYPE
		SYNTAX		INTEGER { disable(0), enable(1) }
		MAX-ACCESS		read-write
		STATUS			current
		DESCRIPTION
				"TYPE: - Checkbox
				 PAGE: - Video1
					Inp1 2 Aud Fail G1C  cmdID= 39150 "
		::= { iqudc12CmdEntry 39150 }


	iqudc12BackupInput1SelInp12AudFailG2C39151 OBJECT-TYPE
		SYNTAX		INTEGER { disable(0), enable(1) }
		MAX-ACCESS		read-write
		STATUS			current
		DESCRIPTION
				"TYPE: - Checkbox
				 PAGE: - Video1
					Inp1 2 Aud Fail G2C  cmdID= 39151 "
		::= { iqudc12CmdEntry 39151 }


	iqudc12BackupInput1SelInp12AudFailG2C39152 OBJECT-TYPE
		SYNTAX		INTEGER { disable(0), enable(1) }
		MAX-ACCESS		read-write
		STATUS			current
		DESCRIPTION
				"TYPE: - Checkbox
				 PAGE: - Video1
					Inp1 2 Aud Fail G2C  cmdID= 39152 "
		::= { iqudc12CmdEntry 39152 }


	iqudc12BackupInput1SelInp12AudFailG3C39153 OBJECT-TYPE
		SYNTAX		INTEGER { disable(0), enable(1) }
		MAX-ACCESS		read-write
		STATUS			current
		DESCRIPTION
				"TYPE: - Checkbox
				 PAGE: - Video1
					Inp1 2 Aud Fail G3C  cmdID= 39153 "
		::= { iqudc12CmdEntry 39153 }


	iqudc12BackupInput1SelInp12AudFailG3C39154 OBJECT-TYPE
		SYNTAX		INTEGER { disable(0), enable(1) }
		MAX-ACCESS		read-write
		STATUS			current
		DESCRIPTION
				"TYPE: - Checkbox
				 PAGE: - Video1
					Inp1 2 Aud Fail G3C  cmdID= 39154 "
		::= { iqudc12CmdEntry 39154 }


	iqudc12BackupInput1SelInp12AudFailG4C39155 OBJECT-TYPE
		SYNTAX		INTEGER { disable(0), enable(1) }
		MAX-ACCESS		read-write
		STATUS			current
		DESCRIPTION
				"TYPE: - Checkbox
				 PAGE: - Video1
					Inp1 2 Aud Fail G4C  cmdID= 39155 "
		::= { iqudc12CmdEntry 39155 }


	iqudc12BackupInput1SelInp12AudFailG4C39156 OBJECT-TYPE
		SYNTAX		INTEGER { disable(0), enable(1) }
		MAX-ACCESS		read-write
		STATUS			current
		DESCRIPTION
				"TYPE: - Checkbox
				 PAGE: - Video1
					Inp1 2 Aud Fail G4C  cmdID= 39156 "
		::= { iqudc12CmdEntry 39156 }


	iqudc12BackupInput1SelInp12AudFailLoc OBJECT-TYPE
		SYNTAX		INTEGER { disable(0), enable(1) }
		MAX-ACCESS		read-write
		STATUS			current
		DESCRIPTION
				"TYPE: - Checkbox
				 PAGE: - Video1
					Inp1 2 Aud Fail Loc  cmdID= 39148 "
		::= { iqudc12CmdEntry 39148 }


	iqudc12BackupInput1SelSelAll OBJECT-TYPE
		SYNTAX		INTEGER { noAction(0),val-Sel-All(1) }
		MAX-ACCESS		read-write
		STATUS			current
		DESCRIPTION
				"TYPE: - Button
				 PAGE: - Video1
					Sel All  cmdID= 39146  value= 1  "
		::= { iqudc12CmdEntry 39146 }


	iqudc12BackupInput1SelSelNone OBJECT-TYPE
		SYNTAX		INTEGER { noAction(0),val-Sel-None(1) }
		MAX-ACCESS		read-write
		STATUS			current
		DESCRIPTION
				"TYPE: - Button
				 PAGE: - Video1
					Sel None  cmdID= 39147  value= 1  "
		::= { iqudc12CmdEntry 39147 }


	iqudc12BackupInput2SelStatInp2OK OBJECT-TYPE
		SYNTAX		RollCallString
		MAX-ACCESS		read-only
		STATUS			current
		DESCRIPTION
				"TYPE: - Display
				 PAGE: - Video1
					Stat Inp2 OK  cmdID= 39131  format=   "
		::= { iqudc12CmdEntry 39131 }


	iqudc12BackupInput2SelStatInp1FAIL OBJECT-TYPE
		SYNTAX		RollCallString
		MAX-ACCESS		read-only
		STATUS			current
		DESCRIPTION
				"TYPE: - Display
				 PAGE: - Video1
					Stat Inp1 FAIL  cmdID= 39132  format=   "
		::= { iqudc12CmdEntry 39132 }


	iqudc12BackupInput2SelStatInp1Err OBJECT-TYPE
		SYNTAX		RollCallString
		MAX-ACCESS		read-only
		STATUS			current
		DESCRIPTION
				"TYPE: - Display
				 PAGE: - Video1
					Stat Inp1 Err  cmdID= 39140  format=   "
		::= { iqudc12CmdEntry 39140 }


	iqudc12BackupInput2SelStatAUDFail1 OBJECT-TYPE
		SYNTAX		RollCallString
		MAX-ACCESS		read-only
		STATUS			current
		DESCRIPTION
				"TYPE: - Display
				 PAGE: - Video1
					Stat AUD Fail 1  cmdID= 39158  format=   "
		::= { iqudc12CmdEntry 39158 }


	iqudc12BackupInput2SelStatStd1 OBJECT-TYPE
		SYNTAX		RollCallString
		MAX-ACCESS		read-only
		STATUS			current
		DESCRIPTION
				"TYPE: - Display
				 PAGE: - Video1
					Stat Std 1  cmdID= 39176  format=   "
		::= { iqudc12CmdEntry 39176 }


	iqudc12BackupInput2SelStatGPI1 OBJECT-TYPE
		SYNTAX		RollCallString
		MAX-ACCESS		read-only
		STATUS			current
		DESCRIPTION
				"TYPE: - Display
				 PAGE: - Video1
					Stat GPI 1  cmdID= 39133  format=   "
		::= { iqudc12CmdEntry 39133 }


	iqudc12BackupInput2SelStatGPI2 OBJECT-TYPE
		SYNTAX		RollCallString
		MAX-ACCESS		read-only
		STATUS			current
		DESCRIPTION
				"TYPE: - Display
				 PAGE: - Video1
					Stat GPI 2  cmdID= 39134  format=   "
		::= { iqudc12CmdEntry 39134 }


	iqudc12BackupInput2SelEnblInp2OK OBJECT-TYPE
		SYNTAX		INTEGER { disable(0), enable(1) }
		MAX-ACCESS		read-write
		STATUS			current
		DESCRIPTION
				"TYPE: - Checkbox
				 PAGE: - Video1
					Enbl Inp2 OK  cmdID= 39111 "
		::= { iqudc12CmdEntry 39111 }


	iqudc12BackupInput2SelEnblInp1FAIL OBJECT-TYPE
		SYNTAX		INTEGER { disable(0), enable(1) }
		MAX-ACCESS		read-write
		STATUS			current
		DESCRIPTION
				"TYPE: - Checkbox
				 PAGE: - Video1
					Enbl Inp1 FAIL  cmdID= 39112 "
		::= { iqudc12CmdEntry 39112 }


	iqudc12BackupInput2SelEnblInp1Err OBJECT-TYPE
		SYNTAX		INTEGER { disable(0), enable(1) }
		MAX-ACCESS		read-write
		STATUS			current
		DESCRIPTION
				"TYPE: - Checkbox
				 PAGE: - Video1
					Enbl Inp1 Err  cmdID= 39136 "
		::= { iqudc12CmdEntry 39136 }


	iqudc12BackupInput2SelEnblGPI1 OBJECT-TYPE
		SYNTAX		INTEGER { disable(0), enable(1) }
		MAX-ACCESS		read-write
		STATUS			current
		DESCRIPTION
				"TYPE: - Checkbox
				 PAGE: - Video1
					Enbl GPI 1  cmdID= 39113 "
		::= { iqudc12CmdEntry 39113 }


	iqudc12BackupInput2SelEnblGPI2 OBJECT-TYPE
		SYNTAX		INTEGER { disable(0), enable(1) }
		MAX-ACCESS		read-write
		STATUS			current
		DESCRIPTION
				"TYPE: - Checkbox
				 PAGE: - Video1
					Enbl GPI 2  cmdID= 39114 "
		::= { iqudc12CmdEntry 39114 }


	iqudc12BackupInput2SelEnblAudInp1Err OBJECT-TYPE
		SYNTAX		INTEGER { disable(0), enable(1) }
		MAX-ACCESS		read-write
		STATUS			current
		DESCRIPTION
				"TYPE: - Checkbox
				 PAGE: - Video1
					Enbl Aud Inp1 Err  cmdID= 39157 "
		::= { iqudc12CmdEntry 39157 }


	iqudc12BackupInput2SelEnblStdInp1 OBJECT-TYPE
		SYNTAX		INTEGER { disable(0), enable(1) }
		MAX-ACCESS		read-write
		STATUS			current
		DESCRIPTION
				"TYPE: - Checkbox
				 PAGE: - Video1
					Enbl Std Inp 1  cmdID= 39175 "
		::= { iqudc12CmdEntry 39175 }


	iqudc12BackupInput2SelInp21AudFailG1C39163 OBJECT-TYPE
		SYNTAX		INTEGER { disable(0), enable(1) }
		MAX-ACCESS		read-write
		STATUS			current
		DESCRIPTION
				"TYPE: - Checkbox
				 PAGE: - Video1
					Inp2 1 Aud Fail G1C  cmdID= 39163 "
		::= { iqudc12CmdEntry 39163 }


	iqudc12BackupInput2SelInp21AudFailG1C39164 OBJECT-TYPE
		SYNTAX		INTEGER { disable(0), enable(1) }
		MAX-ACCESS		read-write
		STATUS			current
		DESCRIPTION
				"TYPE: - Checkbox
				 PAGE: - Video1
					Inp2 1 Aud Fail G1C  cmdID= 39164 "
		::= { iqudc12CmdEntry 39164 }


	iqudc12BackupInput2SelInp21AudFailG2C39165 OBJECT-TYPE
		SYNTAX		INTEGER { disable(0), enable(1) }
		MAX-ACCESS		read-write
		STATUS			current
		DESCRIPTION
				"TYPE: - Checkbox
				 PAGE: - Video1
					Inp2 1 Aud Fail G2C  cmdID= 39165 "
		::= { iqudc12CmdEntry 39165 }


	iqudc12BackupInput2SelInp21AudFailG2C39166 OBJECT-TYPE
		SYNTAX		INTEGER { disable(0), enable(1) }
		MAX-ACCESS		read-write
		STATUS			current
		DESCRIPTION
				"TYPE: - Checkbox
				 PAGE: - Video1
					Inp2 1 Aud Fail G2C  cmdID= 39166 "
		::= { iqudc12CmdEntry 39166 }


	iqudc12BackupInput2SelInp21AudFailG3C39167 OBJECT-TYPE
		SYNTAX		INTEGER { disable(0), enable(1) }
		MAX-ACCESS		read-write
		STATUS			current
		DESCRIPTION
				"TYPE: - Checkbox
				 PAGE: - Video1
					Inp2 1 Aud Fail G3C  cmdID= 39167 "
		::= { iqudc12CmdEntry 39167 }


	iqudc12BackupInput2SelInp21AudFailG3C39168 OBJECT-TYPE
		SYNTAX		INTEGER { disable(0), enable(1) }
		MAX-ACCESS		read-write
		STATUS			current
		DESCRIPTION
				"TYPE: - Checkbox
				 PAGE: - Video1
					Inp2 1 Aud Fail G3C  cmdID= 39168 "
		::= { iqudc12CmdEntry 39168 }


	iqudc12BackupInput2SelInp21AudFailG4C39169 OBJECT-TYPE
		SYNTAX		INTEGER { disable(0), enable(1) }
		MAX-ACCESS		read-write
		STATUS			current
		DESCRIPTION
				"TYPE: - Checkbox
				 PAGE: - Video1
					Inp2 1 Aud Fail G4C  cmdID= 39169 "
		::= { iqudc12CmdEntry 39169 }


	iqudc12BackupInput2SelInp21AudFailG4C39170 OBJECT-TYPE
		SYNTAX		INTEGER { disable(0), enable(1) }
		MAX-ACCESS		read-write
		STATUS			current
		DESCRIPTION
				"TYPE: - Checkbox
				 PAGE: - Video1
					Inp2 1 Aud Fail G4C  cmdID= 39170 "
		::= { iqudc12CmdEntry 39170 }


	iqudc12BackupInput2SelDlyInp2OK OBJECT-TYPE
		SYNTAX		INTEGER
		MAX-ACCESS		read-write
		STATUS			current
		DESCRIPTION
				"TYPE: - Number
				 PAGE: - Video1
					Dly Inp2 OK  cmdID= 39119  min= 10  max= 100  step= 1  format= %0.1f s  div_scale= 10 
					Min = 1.0 s  Max = 10.0 s  Step = 0.1 s "
		::= { iqudc12CmdEntry 39119 }


	iqudc12BackupInput2SelDlyInp1FAIL OBJECT-TYPE
		SYNTAX		INTEGER
		MAX-ACCESS		read-write
		STATUS			current
		DESCRIPTION
				"TYPE: - Number
				 PAGE: - Video1
					Dly Inp1 FAIL  cmdID= 39120  min= 0  max= 100  step= 1  format= %0.1f s  div_scale= 10 
					Min = 0.0 s  Max = 10.0 s  Step = 0.1 s "
		::= { iqudc12CmdEntry 39120 }


	iqudc12BackupInput2SelDlyInp1Err OBJECT-TYPE
		SYNTAX		INTEGER
		MAX-ACCESS		read-write
		STATUS			current
		DESCRIPTION
				"TYPE: - Number
				 PAGE: - Video1
					Dly Inp1 Err  cmdID= 39138  min= 10  max= 100  step= 10  format= %0.0f s  div_scale= 10 
					Min = 1 s  Max = 10 s  Step = 1 s "
		::= { iqudc12CmdEntry 39138 }


	iqudc12BackupInput2SelDlyGPI1 OBJECT-TYPE
		SYNTAX		INTEGER
		MAX-ACCESS		read-write
		STATUS			current
		DESCRIPTION
				"TYPE: - Number
				 PAGE: - Video1
					Dly GPI 1  cmdID= 39121  min= 0  max= 100  step= 1  format= %0.1f s  div_scale= 10 
					Min = 0.0 s  Max = 10.0 s  Step = 0.1 s "
		::= { iqudc12CmdEntry 39121 }


	iqudc12BackupInput2SelDlyGPI2 OBJECT-TYPE
		SYNTAX		INTEGER
		MAX-ACCESS		read-write
		STATUS			current
		DESCRIPTION
				"TYPE: - Number
				 PAGE: - Video1
					Dly GPI 2  cmdID= 39122  min= 0  max= 100  step= 1  format= %0.1f s  div_scale= 10 
					Min = 0.0 s  Max = 10.0 s  Step = 0.1 s "
		::= { iqudc12CmdEntry 39122 }


	iqudc12BackupInput2SelDlyAud1FAIL OBJECT-TYPE
		SYNTAX		INTEGER
		MAX-ACCESS		read-write
		STATUS			current
		DESCRIPTION
				"TYPE: - Number
				 PAGE: - Video1
					Dly Aud1 FAIL  cmdID= 39159  min= 10  max= 100  step= 1  format= %0.1f s  div_scale= 10 
					Min = 1.0 s  Max = 10.0 s  Step = 0.1 s "
		::= { iqudc12CmdEntry 39159 }


	iqudc12BackupInput2SelDlyStd1 OBJECT-TYPE
		SYNTAX		INTEGER
		MAX-ACCESS		read-write
		STATUS			current
		DESCRIPTION
				"TYPE: - Number
				 PAGE: - Video1
					Dly Std 1  cmdID= 39174  min= 0  max= 100  step= 1  format= %0.1f s  div_scale= 10 
					Min = 0.0 s  Max = 10.0 s  Step = 0.1 s "
		::= { iqudc12CmdEntry 39174 }


	iqudc12BackupInput2SelGPI1State OBJECT-TYPE
		SYNTAX		INTEGER {
							val-On(0),
							val-Off(1)
							}
		MAX-ACCESS		read-write
		STATUS			current
		DESCRIPTION
				"TYPE: - RadiobuttonList
				 PAGE: - Video1
					GPI 1 State  cmdID= 39125 
					On  value= 0  
					Off  value= 1  "
		::= { iqudc12CmdEntry 39125 }


	iqudc12BackupInput2SelGPI2State OBJECT-TYPE
		SYNTAX		INTEGER {
							val-On(0),
							val-Off(1)
							}
		MAX-ACCESS		read-write
		STATUS			current
		DESCRIPTION
				"TYPE: - RadiobuttonList
				 PAGE: - Video1
					GPI 2 State  cmdID= 39126 
					On  value= 0  
					Off  value= 1  "
		::= { iqudc12CmdEntry 39126 }


	iqudc12BackupInput2SelInp21AudFailLoc OBJECT-TYPE
		SYNTAX		INTEGER { disable(0), enable(1) }
		MAX-ACCESS		read-write
		STATUS			current
		DESCRIPTION
				"TYPE: - Checkbox
				 PAGE: - Video1
					Inp2 1 Aud Fail Loc  cmdID= 39162 "
		::= { iqudc12CmdEntry 39162 }


	iqudc12BackupInput2SelSelAll OBJECT-TYPE
		SYNTAX		INTEGER { noAction(0),val-Sel-All(1) }
		MAX-ACCESS		read-write
		STATUS			current
		DESCRIPTION
				"TYPE: - Button
				 PAGE: - Video1
					Sel All  cmdID= 39160  value= 1  "
		::= { iqudc12CmdEntry 39160 }


	iqudc12BackupInput2SelSelNone OBJECT-TYPE
		SYNTAX		INTEGER { noAction(0),val-Sel-None(1) }
		MAX-ACCESS		read-write
		STATUS			current
		DESCRIPTION
				"TYPE: - Button
				 PAGE: - Video1
					Sel None  cmdID= 39161  value= 1  "
		::= { iqudc12CmdEntry 39161 }


	iqudc12Video2VideoOutputConversionStandard OBJECT-TYPE
		SYNTAX		INTEGER {
							val-1080p(3),
							val-1080i(1),
							val-720p(2),
							val-SD(0)
							}
		MAX-ACCESS		read-write
		STATUS			current
		DESCRIPTION
				"TYPE: - RadiobuttonList
				 PAGE: - Video2
					Conversion Standard  cmdID= 40700 
					1080p  value= 3  
					1080i  value= 1  
					720p  value= 2  
					SD  value= 0  "
		::= { iqudc12CmdEntry 40700 }


	iqudc12Video2VideoOutputOutputAType OBJECT-TYPE
		SYNTAX		INTEGER {
							val-Processed(0),
							val-Reclocked(1)
							}
		MAX-ACCESS		read-write
		STATUS			current
		DESCRIPTION
				"TYPE: - RadiobuttonList
				 PAGE: - Video2
					Output A Type  cmdID= 40701 
					Processed  value= 0  
					Reclocked  value= 1  "
		::= { iqudc12CmdEntry 40701 }


	iqudc12Video2VideoOutputOutputBType OBJECT-TYPE
		SYNTAX		INTEGER {
							val-Processed(0),
							val-Reclocked(1)
							}
		MAX-ACCESS		read-write
		STATUS			current
		DESCRIPTION
				"TYPE: - RadiobuttonList
				 PAGE: - Video2
					Output B Type  cmdID= 40702 
					Processed  value= 0  
					Reclocked  value= 1  "
		::= { iqudc12CmdEntry 40702 }


	iqudc12Video2VideoOutputOutput1Std OBJECT-TYPE
		SYNTAX		RollCallString
		MAX-ACCESS		read-only
		STATUS			current
		DESCRIPTION
				"TYPE: - Display
				 PAGE: - Video2
					Output 1 Std  cmdID= 40706  format=   "
		::= { iqudc12CmdEntry 40706 }


	iqudc12VideoOutputVideoProcMasterGain OBJECT-TYPE
		SYNTAX		INTEGER
		MAX-ACCESS		read-write
		STATUS			current
		DESCRIPTION
				"TYPE: - Number
				 PAGE: - Video2
					Master Gain  cmdID= 33000  min= 0  max= 2000  step= 1  format= %d  div_scale= 1 
					Min = 0  Max = 2000  Step = 1 "
		::= { iqudc12CmdEntry 33000 }


	iqudc12VideoOutputVideoProcYGain OBJECT-TYPE
		SYNTAX		INTEGER
		MAX-ACCESS		read-write
		STATUS			current
		DESCRIPTION
				"TYPE: - Number
				 PAGE: - Video2
					Y Gain  cmdID= 33001  min= 0  max= 2000  step= 1  format= %d  div_scale= 1 
					Min = 0  Max = 2000  Step = 1 "
		::= { iqudc12CmdEntry 33001 }


	iqudc12VideoOutputVideoProcCGain OBJECT-TYPE
		SYNTAX		INTEGER
		MAX-ACCESS		read-write
		STATUS			current
		DESCRIPTION
				"TYPE: - Number
				 PAGE: - Video2
					C Gain  cmdID= 33003  min= 0  max= 2000  step= 1  format= %d  div_scale= 1 
					Min = 0  Max = 2000  Step = 1 "
		::= { iqudc12CmdEntry 33003 }


	iqudc12VideoOutputVideoProcBlackLevel OBJECT-TYPE
		SYNTAX		INTEGER
		MAX-ACCESS		read-write
		STATUS			current
		DESCRIPTION
				"TYPE: - Number
				 PAGE: - Video2
					Black Level  cmdID= 33002  min= -200  max= 200  step= 1  format= %0.0f mV  div_scale= 1 
					Min = -200 mV  Max = 200 mV  Step = 1 mV "
		::= { iqudc12CmdEntry 33002 }


	iqudc12VideoOutputVideoProcHueLevel OBJECT-TYPE
		SYNTAX		INTEGER
		MAX-ACCESS		read-write
		STATUS			current
		DESCRIPTION
				"TYPE: - Number
				 PAGE: - Video2
					Hue Level  cmdID= 33025  min= -180  max= 180  step= 1  format= %0.0f degrees  div_scale= 1 
					Min = -180 degrees  Max = 180 degrees  Step = 1 degrees "
		::= { iqudc12CmdEntry 33025 }


	iqudc12VideoOutputVideoProcActiveSig OBJECT-TYPE
		SYNTAX		INTEGER { disable(0), enable(1) }
		MAX-ACCESS		read-write
		STATUS			current
		DESCRIPTION
				"TYPE: - Checkbox
				 PAGE: - Video2
					ActiveSig  cmdID= 32998 "
		::= { iqudc12CmdEntry 32998 }


	iqudc12Video2VideoOutputDefaultOutput OBJECT-TYPE
		SYNTAX		INTEGER {
							val-Input(0),
							val-Black(1),
							val-Freeze(2),
							val-Out-Pattern(3)
							}
		MAX-ACCESS		read-write
		STATUS			current
		DESCRIPTION
				"TYPE: - RadiobuttonList
				 PAGE: - Video2
					Default Output  cmdID= 33026 
					Input  value= 0  
					Black  value= 1  
					Freeze  value= 2  
					Out Pattern  value= 3  "
		::= { iqudc12CmdEntry 33026 }


	iqudc12Video2VideoOutputOutputMode OBJECT-TYPE
		SYNTAX		INTEGER {
							val-Default-Video(0),
							val-Black(1),
							val-Freeze(2),
							val-Out-Pattern(3)
							}
		MAX-ACCESS		read-write
		STATUS			current
		DESCRIPTION
				"TYPE: - RadiobuttonList
				 PAGE: - Video2
					Output Mode  cmdID= 33027 
					Default Video  value= 0  
					Black  value= 1  
					Freeze  value= 2  
					Out Pattern  value= 3  "
		::= { iqudc12CmdEntry 33027 }


	iqudc12Video2VideoOutputPatternType OBJECT-TYPE
		SYNTAX		INTEGER {
							val-75-Color-Bars(0),
							val-100-Color-Bars(1),
							val-SMPTE-Bars(2),
							val-Tartan-Bars(9),
							val-Black(8),
							val-Pluge(3),
							val-Ramp(4),
							val-Sweep(5),
							val-Pulse-Bar(6),
							val-Burst(7)
							}
		MAX-ACCESS		read-write
		STATUS			current
		DESCRIPTION
				"TYPE: - RadiobuttonList
				 PAGE: - Video2
					Pattern Type  cmdID= 33028 
					75% Color Bars  value= 0  
					100% Color Bars  value= 1  
					SMPTE Bars  value= 2  
					Tartan Bars  value= 9  
					Black  value= 8  
					Pluge  value= 3  
					Ramp  value= 4  
					Sweep  value= 5  
					Pulse & Bar  value= 6  
					Burst  value= 7  "
		::= { iqudc12CmdEntry 33028 }


	iqudc12Video2VideoOutputSDAnlgEncode OBJECT-TYPE
		SYNTAX		INTEGER {
							val-SMPTE(0),
							val-BetaCam(1),
							val-MII(2)
							}
		MAX-ACCESS		read-write
		STATUS			current
		DESCRIPTION
				"TYPE: - RadiobuttonList
				 PAGE: - Video2
					SD Anlg Encode  cmdID= 33038 
					SMPTE  value= 0  
					BetaCam  value= 1  
					MII  value= 2  "
		::= { iqudc12CmdEntry 33038 }


	iqudc12Video2VideoOutputPedComposEnc OBJECT-TYPE
		SYNTAX		INTEGER {
							val-Pedestal-Off-NTSC-J(0),
							val-Pedestal-On-NTSC(1)
							}
		MAX-ACCESS		read-write
		STATUS			current
		DESCRIPTION
				"TYPE: - RadiobuttonList
				 PAGE: - Video2
					Ped Compos Enc  cmdID= 33041 
					Pedestal Off:NTSC-J  value= 0  
					Pedestal On:NTSC  value= 1  "
		::= { iqudc12CmdEntry 33041 }


	iqudc12Video2VideoOutputAnlgType OBJECT-TYPE
		SYNTAX		INTEGER {
							val-Composite-SD(0),
							val-Y-C-SD(1),
							val-YPbPr-SD-HD(2),
							val-GBR(3)
							}
		MAX-ACCESS		read-write
		STATUS			current
		DESCRIPTION
				"TYPE: - RadiobuttonList
				 PAGE: - Video2
					Anlg Type  cmdID= 33039 
					Composite (SD)  value= 0  
					Y/C (SD)  value= 1  
					YPbPr (SD/HD)  value= 2  
					GBR  value= 3  "
		::= { iqudc12CmdEntry 33039 }


	iqudc12VideoOutputUserCaptionsEnable OBJECT-TYPE
		SYNTAX		INTEGER { disable(0), enable(1) }
		MAX-ACCESS		read-write
		STATUS			current
		DESCRIPTION
				"TYPE: - Checkbox
				 PAGE: - Video2
					Enable  cmdID= 6080 "
		::= { iqudc12CmdEntry 6080 }


	iqudc12VideoOutputUserCaptionsEnableAlt OBJECT-TYPE
		SYNTAX		INTEGER { disable(0), enable(1) }
		MAX-ACCESS		read-write
		STATUS			current
		DESCRIPTION
				"TYPE: - Checkbox
				 PAGE: - Video2
					EnableAlt  cmdID= 6087 "
		::= { iqudc12CmdEntry 6087 }


	iqudc12VideoOutputUserCaptionsText OBJECT-TYPE
		SYNTAX		RollCallString
		MAX-ACCESS		read-write
		STATUS			current
		DESCRIPTION
				"TYPE: - Editstring
				 PAGE: - Video2
					Text  cmdID= 6085  "
		::= { iqudc12CmdEntry 6085 }


	iqudc12VideoOutputUserCaptionsTextAlt OBJECT-TYPE
		SYNTAX		RollCallString
		MAX-ACCESS		read-write
		STATUS			current
		DESCRIPTION
				"TYPE: - Editstring
				 PAGE: - Video2
					TextAlt  cmdID= 6086  "
		::= { iqudc12CmdEntry 6086 }


	iqudc12VideoOutputUserCaptionsXPos OBJECT-TYPE
		SYNTAX		INTEGER
		MAX-ACCESS		read-write
		STATUS			current
		DESCRIPTION
				"TYPE: - Number
				 PAGE: - Video2
					X Pos  cmdID= 6081  min= 0  max= 1000  step= 1  format= %0.1f  div_scale= 10 
					Min = 0.0  Max = 100.0  Step = 0.1 "
		::= { iqudc12CmdEntry 6081 }


	iqudc12VideoOutputUserCaptionsYPos OBJECT-TYPE
		SYNTAX		INTEGER
		MAX-ACCESS		read-write
		STATUS			current
		DESCRIPTION
				"TYPE: - Number
				 PAGE: - Video2
					Y Pos  cmdID= 6082  min= -1000  max= 0  step= 1  format= %0.1f  div_scale= 10 
					Min = -100.0  Max = 0.0  Step = 0.1 "
		::= { iqudc12CmdEntry 6082 }


	iqudc12VideoOutputUserCaptionsXSize OBJECT-TYPE
		SYNTAX		INTEGER
		MAX-ACCESS		read-write
		STATUS			current
		DESCRIPTION
				"TYPE: - Number
				 PAGE: - Video2
					X Size  cmdID= 6083  min= 1  max= 10  step= 1  format= %0.0f  div_scale= 1 
					Min = 1  Max = 10  Step = 1 "
		::= { iqudc12CmdEntry 6083 }


	iqudc12VideoOutputUserCaptionsYSize OBJECT-TYPE
		SYNTAX		INTEGER
		MAX-ACCESS		read-write
		STATUS			current
		DESCRIPTION
				"TYPE: - Number
				 PAGE: - Video2
					Y Size  cmdID= 6084  min= 1  max= 10  step= 1  format= %0.0f  div_scale= 1 
					Min = 1  Max = 10  Step = 1 "
		::= { iqudc12CmdEntry 6084 }


	iqudc12Video2VideoOutputOutStdnonConv OBJECT-TYPE
		SYNTAX		INTEGER {
							val-1080-59p-A(1),
							val-1080-29i(3),
							val-720-59p(5),
							val-525-29i(7),
							val-1080-50p-A(2),
							val-1080-25i(4),
							val-720-50p(6),
							val-625-25i(8)
							}
		MAX-ACCESS		read-write
		STATUS			current
		DESCRIPTION
				"TYPE: - RadiobuttonList
				 PAGE: - Video2
					OutStd-nonConv  cmdID= 36144 
					1080/59p-A  value= 1  
					1080/29i  value= 3  
					720/59p  value= 5  
					525/29i  value= 7  
					1080/50p-A  value= 2  
					1080/25i  value= 4  
					720/50p  value= 6  
					625/25i  value= 8  "
		::= { iqudc12CmdEntry 36144 }


	iqudc12Video2VideoOutputFollowStdnonConv OBJECT-TYPE
		SYNTAX		INTEGER {
							val-Manual-Selection(0),
							val-Follows-Input-Std(1),
							val-Follows-Ref-Std(2)
							}
		MAX-ACCESS		read-write
		STATUS			current
		DESCRIPTION
				"TYPE: - RadiobuttonList
				 PAGE: - Video2
					FollowStd-nonConv  cmdID= 36143 
					Manual Selection  value= 0  
					Follows Input Std.  value= 1  
					Follows Ref. Std.  value= 2  "
		::= { iqudc12CmdEntry 36143 }


	iqudc12Video2VideoOutputLastRefStd OBJECT-TYPE
		SYNTAX		INTEGER
		MAX-ACCESS		read-write
		STATUS			current
		DESCRIPTION
				"TYPE: - Number
				 PAGE: - Video2
					LastRefStd  cmdID= 36145  min= 0  max= 10  step= 1  format= %d  div_scale= 1 
					Min = 0  Max = 10  Step = 1 "
		::= { iqudc12CmdEntry 36145 }


	iqudc12Video2VideoOutputLastFrameRate OBJECT-TYPE
		SYNTAX		INTEGER
		MAX-ACCESS		read-write
		STATUS			current
		DESCRIPTION
				"TYPE: - Number
				 PAGE: - Video2
					LastFrameRate  cmdID= 36146  min= 0  max= 2  step= 1  format= %d  div_scale= 1 
					Min = 0  Max = 2  Step = 1 "
		::= { iqudc12CmdEntry 36146 }


	iqudc12PictureAdvancedHEnhanceEnable OBJECT-TYPE
		SYNTAX		INTEGER { disable(0), enable(1) }
		MAX-ACCESS		read-write
		STATUS			current
		DESCRIPTION
				"TYPE: - Checkbox
				 PAGE: - Video2
					Enable  cmdID= 6030 "
		::= { iqudc12CmdEntry 6030 }


	iqudc12PictureAdvancedHEnhanceFrequencyBand OBJECT-TYPE
		SYNTAX		INTEGER {
							val-Low(2),
							val-Medium(1),
							val-High(0)
							}
		MAX-ACCESS		read-write
		STATUS			current
		DESCRIPTION
				"TYPE: - RadiobuttonList
				 PAGE: - Video2
					Frequency Band  cmdID= 6031 
					Low  value= 2  
					Medium  value= 1  
					High  value= 0  "
		::= { iqudc12CmdEntry 6031 }


	iqudc12PictureAdvancedHEnhancePreset OBJECT-TYPE
		SYNTAX		INTEGER {
							val-Low(1),
							val-Medium(2),
							val-High(3),
							val-Super(4),
							val-Custom(0)
							}
		MAX-ACCESS		read-write
		STATUS			current
		DESCRIPTION
				"TYPE: - RadiobuttonList
				 PAGE: - Video2
					Preset  cmdID= 6034 
					Low  value= 1  
					Medium  value= 2  
					High  value= 3  
					Super  value= 4  
					Custom  value= 0  "
		::= { iqudc12CmdEntry 6034 }


	iqudc12PictureAdvancedHEnhanceGain OBJECT-TYPE
		SYNTAX		INTEGER
		MAX-ACCESS		read-write
		STATUS			current
		DESCRIPTION
				"TYPE: - Number
				 PAGE: - Video2
					Gain  cmdID= 6032  min= 0  max= 192  step= 8  format= %0.1f  div_scale= 16 
					Min = 0.0  Max = 12.0  Step = 0.5 "
		::= { iqudc12CmdEntry 6032 }


	iqudc12PictureAdvancedHEnhanceNoiseRejection OBJECT-TYPE
		SYNTAX		INTEGER
		MAX-ACCESS		read-write
		STATUS			current
		DESCRIPTION
				"TYPE: - Number
				 PAGE: - Video2
					Noise Rejection  cmdID= 6033  min= 0  max= 100  step= 1  format= %0.0f %%  div_scale= 1 
					Min = 0 %  Max = 100 %  Step = 1 % "
		::= { iqudc12CmdEntry 6033 }


	iqudc12PictureRGBLegaliserRange OBJECT-TYPE
		SYNTAX		INTEGER {
							val-700-mV(0),
							val-721-mV(1),
							val-735-mV(2),
							val-746-mV(3)
							}
		MAX-ACCESS		read-write
		STATUS			current
		DESCRIPTION
				"TYPE: - RadiobuttonList
				 PAGE: - Video2
					Range  cmdID= 6061 
					700 mV  value= 0  
					721 mV  value= 1  
					735 mV  value= 2  
					746 mV  value= 3  "
		::= { iqudc12CmdEntry 6061 }


	iqudc12PictureLumaClipperEnable OBJECT-TYPE
		SYNTAX		INTEGER { disable(0), enable(1) }
		MAX-ACCESS		read-write
		STATUS			current
		DESCRIPTION
				"TYPE: - Checkbox
				 PAGE: - Video2
					Enable  cmdID= 6070 "
		::= { iqudc12CmdEntry 6070 }


	iqudc12PictureLumaClipperWhitemax OBJECT-TYPE
		SYNTAX		INTEGER
		MAX-ACCESS		read-write
		STATUS			current
		DESCRIPTION
				"TYPE: - Number
				 PAGE: - Video2
					White max  cmdID= 6071  min= 90  max= 109  step= 1  format= %0.0f %%  div_scale= 1 
					Min = 90 %  Max = 109 %  Step = 1 % "
		::= { iqudc12CmdEntry 6071 }


	iqudc12PictureLumaClipperBlackmin OBJECT-TYPE
		SYNTAX		INTEGER
		MAX-ACCESS		read-write
		STATUS			current
		DESCRIPTION
				"TYPE: - Number
				 PAGE: - Video2
					Black min  cmdID= 6072  min= -7  max= 10  step= 1  format= %0.0f %%  div_scale= 1 
					Min = -7 %  Max = 10 %  Step = 1 % "
		::= { iqudc12CmdEntry 6072 }


	iqudc12PictureOutputPictureColorimetry OBJECT-TYPE
		SYNTAX		INTEGER {
							val-Auto(0),
							val-None(1),
							val-BT709toRec601(2),
							val-Rec601toBT709(3)
							}
		MAX-ACCESS		read-write
		STATUS			current
		DESCRIPTION
				"TYPE: - RadiobuttonList
				 PAGE: - Video2
					Colorimetry  cmdID= 6043 
					Auto  value= 0  
					None  value= 1  
					BT709toRec601  value= 2  
					Rec601toBT709  value= 3  "
		::= { iqudc12CmdEntry 6043 }


	iqudc12PictureEnhanceNoiseThreshold OBJECT-TYPE
		SYNTAX		INTEGER
		MAX-ACCESS		read-write
		STATUS			current
		DESCRIPTION
				"TYPE: - Number
				 PAGE: - Video2
					Noise Threshold  cmdID= 6041  min= 0  max= 255  step= 1  format= %0.0f  div_scale= 1 
					Min = 0  Max = 255  Step = 1 "
		::= { iqudc12CmdEntry 6041 }


	iqudc12PictureEnhanceSharpnessThreshold OBJECT-TYPE
		SYNTAX		INTEGER
		MAX-ACCESS		read-write
		STATUS			current
		DESCRIPTION
				"TYPE: - Number
				 PAGE: - Video2
					Sharpness Threshold  cmdID= 6042  min= 0  max= 255  step= 1  format= %0.0f  div_scale= 1 
					Min = 0  Max = 255  Step = 1 "
		::= { iqudc12CmdEntry 6042 }


	iqudc12PictureEnhanceSharpnessAmplitude OBJECT-TYPE
		SYNTAX		INTEGER
		MAX-ACCESS		read-write
		STATUS			current
		DESCRIPTION
				"TYPE: - Number
				 PAGE: - Video2
					Sharpness Amplitude  cmdID= 6044  min= 0  max= 255  step= 1  format= %0.0f  div_scale= 1 
					Min = 0  Max = 255  Step = 1 "
		::= { iqudc12CmdEntry 6044 }


	iqudc12PictureOutputPictureFilmCadence OBJECT-TYPE
		SYNTAX		RollCallString
		MAX-ACCESS		read-only
		STATUS			current
		DESCRIPTION
				"TYPE: - Display
				 PAGE: - Video2
					Film Cadence  cmdID= 40707  format=   "
		::= { iqudc12CmdEntry 40707 }


	iqudc12PictureOutputColorCorrectGreenOffset OBJECT-TYPE
		SYNTAX		INTEGER
		MAX-ACCESS		read-write
		STATUS			current
		DESCRIPTION
				"TYPE: - Number
				 PAGE: - Video2
					GreenOffset  cmdID= 40861  min= 0  max= 203200  step= 100  format= %0.2f %%  div_scale= 1016 
					Min = 0.00 %  Max = 200.00 %  Step = 0.10 % "
		::= { iqudc12CmdEntry 40861 }


	iqudc12PictureOutputColorCorrectBlueOffset OBJECT-TYPE
		SYNTAX		INTEGER
		MAX-ACCESS		read-write
		STATUS			current
		DESCRIPTION
				"TYPE: - Number
				 PAGE: - Video2
					BlueOffset  cmdID= 40862  min= 0  max= 203200  step= 100  format= %0.2f %%  div_scale= 1016 
					Min = 0.00 %  Max = 200.00 %  Step = 0.10 % "
		::= { iqudc12CmdEntry 40862 }


	iqudc12PictureOutputColorCorrectRedOffset OBJECT-TYPE
		SYNTAX		INTEGER
		MAX-ACCESS		read-write
		STATUS			current
		DESCRIPTION
				"TYPE: - Number
				 PAGE: - Video2
					RedOffset  cmdID= 40863  min= 0  max= 203200  step= 100  format= %0.2f %%  div_scale= 1016 
					Min = 0.00 %  Max = 200.00 %  Step = 0.10 % "
		::= { iqudc12CmdEntry 40863 }


	iqudc12PictureOutputColorCorrectGangOffset OBJECT-TYPE
		SYNTAX		INTEGER { disable(0), enable(1) }
		MAX-ACCESS		read-write
		STATUS			current
		DESCRIPTION
				"TYPE: - Checkbox
				 PAGE: - Video2
					GangOffset  cmdID= 40870 "
		::= { iqudc12CmdEntry 40870 }


	iqudc12PictureOutputColorCorrectGreenGain OBJECT-TYPE
		SYNTAX		INTEGER
		MAX-ACCESS		read-write
		STATUS			current
		DESCRIPTION
				"TYPE: - Number
				 PAGE: - Video2
					GreenGain  cmdID= 40864  min= 0  max= 2000  step= 1  format= %0.1f %%  div_scale= 10 
					Min = 0.0 %  Max = 200.0 %  Step = 0.1 % "
		::= { iqudc12CmdEntry 40864 }


	iqudc12PictureOutputColorCorrectBlueGain OBJECT-TYPE
		SYNTAX		INTEGER
		MAX-ACCESS		read-write
		STATUS			current
		DESCRIPTION
				"TYPE: - Number
				 PAGE: - Video2
					BlueGain  cmdID= 40865  min= 0  max= 2000  step= 1  format= %0.1f %%  div_scale= 10 
					Min = 0.0 %  Max = 200.0 %  Step = 0.1 % "
		::= { iqudc12CmdEntry 40865 }


	iqudc12PictureOutputColorCorrectRedGain OBJECT-TYPE
		SYNTAX		INTEGER
		MAX-ACCESS		read-write
		STATUS			current
		DESCRIPTION
				"TYPE: - Number
				 PAGE: - Video2
					RedGain  cmdID= 40866  min= 0  max= 2000  step= 1  format= %0.1f %%  div_scale= 10 
					Min = 0.0 %  Max = 200.0 %  Step = 0.1 % "
		::= { iqudc12CmdEntry 40866 }


	iqudc12PictureOutputColorCorrectGangGain OBJECT-TYPE
		SYNTAX		INTEGER { disable(0), enable(1) }
		MAX-ACCESS		read-write
		STATUS			current
		DESCRIPTION
				"TYPE: - Checkbox
				 PAGE: - Video2
					GangGain  cmdID= 40871 "
		::= { iqudc12CmdEntry 40871 }


	iqudc12PictureOutputColorCorrectGreenGamma OBJECT-TYPE
		SYNTAX		INTEGER
		MAX-ACCESS		read-write
		STATUS			current
		DESCRIPTION
				"TYPE: - Number
				 PAGE: - Video2
					GreenGamma  cmdID= 40867  min= 0  max= 1000  step= 1  format= %0.0f  div_scale= 1 
					Min = 0  Max = 1000  Step = 1 "
		::= { iqudc12CmdEntry 40867 }


	iqudc12PictureOutputColorCorrectBlueGamma OBJECT-TYPE
		SYNTAX		INTEGER
		MAX-ACCESS		read-write
		STATUS			current
		DESCRIPTION
				"TYPE: - Number
				 PAGE: - Video2
					BlueGamma  cmdID= 40868  min= 0  max= 1000  step= 1  format= %0.0f  div_scale= 1 
					Min = 0  Max = 1000  Step = 1 "
		::= { iqudc12CmdEntry 40868 }


	iqudc12PictureOutputColorCorrectRedGamma OBJECT-TYPE
		SYNTAX		INTEGER
		MAX-ACCESS		read-write
		STATUS			current
		DESCRIPTION
				"TYPE: - Number
				 PAGE: - Video2
					RedGamma  cmdID= 40869  min= 0  max= 1000  step= 1  format= %0.0f  div_scale= 1 
					Min = 0  Max = 1000  Step = 1 "
		::= { iqudc12CmdEntry 40869 }


	iqudc12PictureOutputColorCorrectGangGamma OBJECT-TYPE
		SYNTAX		INTEGER { disable(0), enable(1) }
		MAX-ACCESS		read-write
		STATUS			current
		DESCRIPTION
				"TYPE: - Checkbox
				 PAGE: - Video2
					GangGamma  cmdID= 40872 "
		::= { iqudc12CmdEntry 40872 }


	iqudc12PictureOutputOutputBorderLeft OBJECT-TYPE
		SYNTAX		INTEGER
		MAX-ACCESS		read-write
		STATUS			current
		DESCRIPTION
				"TYPE: - Number
				 PAGE: - Video2
					Left  cmdID= 6009  min= 0  max= 1920  step= 1  format= %0.0f  div_scale= 1 
					Min = 0  Max = 1920  Step = 1 "
		::= { iqudc12CmdEntry 6009 }


	iqudc12PictureOutputOutputBorderRight OBJECT-TYPE
		SYNTAX		INTEGER
		MAX-ACCESS		read-write
		STATUS			current
		DESCRIPTION
				"TYPE: - Number
				 PAGE: - Video2
					Right  cmdID= 6010  min= 0  max= 1920  step= 1  format= %0.0f  div_scale= 1 
					Min = 0  Max = 1920  Step = 1 "
		::= { iqudc12CmdEntry 6010 }


	iqudc12PictureOutputOutputBorderTop OBJECT-TYPE
		SYNTAX		INTEGER
		MAX-ACCESS		read-write
		STATUS			current
		DESCRIPTION
				"TYPE: - Number
				 PAGE: - Video2
					Top  cmdID= 6011  min= 0  max= 1080  step= 1  format= %0.0f  div_scale= 1 
					Min = 0  Max = 1080  Step = 1 "
		::= { iqudc12CmdEntry 6011 }


	iqudc12PictureOutputOutputBorderBottom OBJECT-TYPE
		SYNTAX		INTEGER
		MAX-ACCESS		read-write
		STATUS			current
		DESCRIPTION
				"TYPE: - Number
				 PAGE: - Video2
					Bottom  cmdID= 6012  min= 0  max= 1080  step= 1  format= %0.0f  div_scale= 1 
					Min = 0  Max = 1080  Step = 1 "
		::= { iqudc12CmdEntry 6012 }


	iqudc12PictureOutputOutputBorderRed OBJECT-TYPE
		SYNTAX		INTEGER
		MAX-ACCESS		read-write
		STATUS			current
		DESCRIPTION
				"TYPE: - Number
				 PAGE: - Video2
					Red  cmdID= 6013  min= 0  max= 255  step= 1  format= %0.0f  div_scale= 1 
					Min = 0  Max = 255  Step = 1 "
		::= { iqudc12CmdEntry 6013 }


	iqudc12PictureOutputOutputBorderGreen OBJECT-TYPE
		SYNTAX		INTEGER
		MAX-ACCESS		read-write
		STATUS			current
		DESCRIPTION
				"TYPE: - Number
				 PAGE: - Video2
					Green  cmdID= 6014  min= 0  max= 255  step= 1  format= %0.0f  div_scale= 1 
					Min = 0  Max = 255  Step = 1 "
		::= { iqudc12CmdEntry 6014 }


	iqudc12PictureOutputOutputBorderBlue OBJECT-TYPE
		SYNTAX		INTEGER
		MAX-ACCESS		read-write
		STATUS			current
		DESCRIPTION
				"TYPE: - Number
				 PAGE: - Video2
					Blue  cmdID= 6015  min= 0  max= 255  step= 1  format= %0.0f  div_scale= 1 
					Min = 0  Max = 255  Step = 1 "
		::= { iqudc12CmdEntry 6015 }


	iqudc12PictureOutputSharpnessHcoeffSharp OBJECT-TYPE
		SYNTAX		INTEGER {
							val-Auto(0),
							val-Sharp-1(1),
							val-Sharp-2(2)
							}
		MAX-ACCESS		read-write
		STATUS			current
		DESCRIPTION
				"TYPE: - RadiobuttonList
				 PAGE: - Video2
					H coeff Sharp  cmdID= 6046 
					Auto  value= 0  
					Sharp +1  value= 1  
					Sharp +2  value= 2  "
		::= { iqudc12CmdEntry 6046 }


	iqudc12PictureOutputSharpnessVcoeffSharp OBJECT-TYPE
		SYNTAX		INTEGER {
							val-Auto(0),
							val-Sharp-1(1),
							val-Sharp-2(2)
							}
		MAX-ACCESS		read-write
		STATUS			current
		DESCRIPTION
				"TYPE: - RadiobuttonList
				 PAGE: - Video2
					V coeff Sharp  cmdID= 6047 
					Auto  value= 0  
					Sharp +1  value= 1  
					Sharp +2  value= 2  "
		::= { iqudc12CmdEntry 6047 }


	iqudc12MenuARCCtrlRecallDisplayMemo OBJECT-TYPE
		SYNTAX		INTEGER {
							val-None-Selected(0),
							val-Display-Memory-1(1),
							val-Display-Memory-2(2),
							val-Display-Memory-3(3),
							val-Display-Memory-4(4),
							val-Display-Memory-5(5),
							val-Display-Memory-6(6),
							val-Display-Memory-7(7),
							val-Display-Memory-8(8),
							val-Display-Memory-9(9),
							val-Display-Memory-10(10),
							val-Display-Memory-11(11),
							val-Display-Memory-12(12),
							val-Display-Memory-13(13),
							val-Display-Memory-14(14),
							val-Display-Memory-15(15),
							val-Display-Memory-16(16),
							val-Display-Memory-17(17),
							val-Display-Memory-18(18),
							val-Display-Memory-19(19),
							val-Display-Memory-20(20),
							val-Display-Memory-21(21),
							val-Display-Memory-22(22),
							val-Display-Memory-23(23),
							val-Display-Memory-24(24),
							val-Display-Memory-25(25),
							val-Display-Memory-26(26),
							val-Display-Memory-27(27),
							val-Display-Memory-28(28),
							val-Display-Memory-29(29),
							val-Display-Memory-30(30),
							val-Display-Memory-31(31),
							val-Display-Memory-32(32)
							}
		MAX-ACCESS		read-write
		STATUS			current
		DESCRIPTION
				"TYPE: - RadiobuttonList
				 PAGE: - ARC Ctrl
					Recall Display Memo  cmdID= 38701 
					None Selected  value= 0  
					Display Memory 1  value= 1  
					Display Memory 2  value= 2  
					Display Memory 3  value= 3  
					Display Memory 4  value= 4  
					Display Memory 5  value= 5  
					Display Memory 6  value= 6  
					Display Memory 7  value= 7  
					Display Memory 8  value= 8  
					Display Memory 9  value= 9  
					Display Memory 10  value= 10  
					Display Memory 11  value= 11  
					Display Memory 12  value= 12  
					Display Memory 13  value= 13  
					Display Memory 14  value= 14  
					Display Memory 15  value= 15  
					Display Memory 16  value= 16  
					Display Memory 17  value= 17  
					Display Memory 18  value= 18  
					Display Memory 19  value= 19  
					Display Memory 20  value= 20  
					Display Memory 21  value= 21  
					Display Memory 22  value= 22  
					Display Memory 23  value= 23  
					Display Memory 24  value= 24  
					Display Memory 25  value= 25  
					Display Memory 26  value= 26  
					Display Memory 27  value= 27  
					Display Memory 28  value= 28  
					Display Memory 29  value= 29  
					Display Memory 30  value= 30  
					Display Memory 31  value= 31  
					Display Memory 32  value= 32  "
		::= { iqudc12CmdEntry 38701 }


	iqudc12MenuARCCtrlSelDisplayMemory OBJECT-TYPE
		SYNTAX		INTEGER {
							val-Display-Memory-1(1),
							val-Display-Memory-2(2),
							val-Display-Memory-3(3),
							val-Display-Memory-4(4),
							val-Display-Memory-5(5),
							val-Display-Memory-6(6),
							val-Display-Memory-7(7),
							val-Display-Memory-8(8),
							val-Display-Memory-9(9),
							val-Display-Memory-10(10),
							val-Display-Memory-11(11),
							val-Display-Memory-12(12),
							val-Display-Memory-13(13),
							val-Display-Memory-14(14),
							val-Display-Memory-15(15),
							val-Display-Memory-16(16),
							val-Display-Memory-17(17),
							val-Display-Memory-18(18),
							val-Display-Memory-19(19),
							val-Display-Memory-20(20),
							val-Display-Memory-21(21),
							val-Display-Memory-22(22),
							val-Display-Memory-23(23),
							val-Display-Memory-24(24),
							val-Display-Memory-25(25),
							val-Display-Memory-26(26),
							val-Display-Memory-27(27),
							val-Display-Memory-28(28),
							val-Display-Memory-29(29),
							val-Display-Memory-30(30),
							val-Display-Memory-31(31),
							val-Display-Memory-32(32)
							}
		MAX-ACCESS		read-write
		STATUS			current
		DESCRIPTION
				"TYPE: - RadiobuttonList
				 PAGE: - ARC Ctrl
					Sel Display Memory  cmdID= 6040 
					Display Memory 1  value= 1  
					Display Memory 2  value= 2  
					Display Memory 3  value= 3  
					Display Memory 4  value= 4  
					Display Memory 5  value= 5  
					Display Memory 6  value= 6  
					Display Memory 7  value= 7  
					Display Memory 8  value= 8  
					Display Memory 9  value= 9  
					Display Memory 10  value= 10  
					Display Memory 11  value= 11  
					Display Memory 12  value= 12  
					Display Memory 13  value= 13  
					Display Memory 14  value= 14  
					Display Memory 15  value= 15  
					Display Memory 16  value= 16  
					Display Memory 17  value= 17  
					Display Memory 18  value= 18  
					Display Memory 19  value= 19  
					Display Memory 20  value= 20  
					Display Memory 21  value= 21  
					Display Memory 22  value= 22  
					Display Memory 23  value= 23  
					Display Memory 24  value= 24  
					Display Memory 25  value= 25  
					Display Memory 26  value= 26  
					Display Memory 27  value= 27  
					Display Memory 28  value= 28  
					Display Memory 29  value= 29  
					Display Memory 30  value= 30  
					Display Memory 31  value= 31  
					Display Memory 32  value= 32  "
		::= { iqudc12CmdEntry 6040 }


	iqudc12MenuARCCtrlSaveset OBJECT-TYPE
		SYNTAX		INTEGER
		MAX-ACCESS		read-write
		STATUS			current
		DESCRIPTION
				"TYPE: - Number
				 PAGE: - ARC Ctrl
					Saveset  cmdID= 6045  min= 0  max= 33  step= 1  format= %d  div_scale= 1 
					Min = 0  Max = 33  Step = 1 "
		::= { iqudc12CmdEntry 6045 }


	iqudc12MenuARCCtrlSaveDispMemory OBJECT-TYPE
		SYNTAX		INTEGER { noAction(0),val-Save-Disp-Memory(1) }
		MAX-ACCESS		read-write
		STATUS			current
		DESCRIPTION
				"TYPE: - Button
				 PAGE: - ARC Ctrl
					Save Disp Memory  cmdID= 38705  value= 1  "
		::= { iqudc12CmdEntry 38705 }


	iqudc12ARCCtrlDispMemoryNameChangeName OBJECT-TYPE
		SYNTAX		RollCallString
		MAX-ACCESS		read-write
		STATUS			current
		DESCRIPTION
				"TYPE: - Editstring
				 PAGE: - ARC Ctrl
					Change Name  cmdID= 38703  "
		::= { iqudc12CmdEntry 38703 }


	iqudc12ARCCtrlARCSize OBJECT-TYPE
		SYNTAX		INTEGER
		MAX-ACCESS		read-write
		STATUS			current
		DESCRIPTION
				"TYPE: - Number
				 PAGE: - ARC Ctrl
					Size  cmdID= 6000  min= 600  max= 1500  step= 1  format= %0.1f %%  div_scale= 10 
					Min = 60.0 %  Max = 150.0 %  Step = 0.1 % "
		::= { iqudc12CmdEntry 6000 }


	iqudc12ARCCtrlARCAspect OBJECT-TYPE
		SYNTAX		INTEGER
		MAX-ACCESS		read-write
		STATUS			current
		DESCRIPTION
				"TYPE: - Number
				 PAGE: - ARC Ctrl
					Aspect  cmdID= 6001  min= 600  max= 2000  step= 1  format= %0.1f %%  div_scale= 10 
					Min = 60.0 %  Max = 200.0 %  Step = 0.1 % "
		::= { iqudc12CmdEntry 6001 }


	iqudc12ARCCtrlARCTilt OBJECT-TYPE
		SYNTAX		INTEGER
		MAX-ACCESS		read-write
		STATUS			current
		DESCRIPTION
				"TYPE: - Number
				 PAGE: - ARC Ctrl
					Tilt  cmdID= 6002  min= -750  max= 750  step= 1  format= %0.1f %%  div_scale= 10 
					Min = -75.0 %  Max = 75.0 %  Step = 0.1 % "
		::= { iqudc12CmdEntry 6002 }


	iqudc12ARCCtrlARCPan OBJECT-TYPE
		SYNTAX		INTEGER
		MAX-ACCESS		read-write
		STATUS			current
		DESCRIPTION
				"TYPE: - Number
				 PAGE: - ARC Ctrl
					Pan  cmdID= 6003  min= -750  max= 750  step= 1  format= %0.1f %%  div_scale= 10 
					Min = -75.0 %  Max = 75.0 %  Step = 0.1 % "
		::= { iqudc12CmdEntry 6003 }


	iqudc12ARCCtrlInputCropLeft OBJECT-TYPE
		SYNTAX		INTEGER
		MAX-ACCESS		read-write
		STATUS			current
		DESCRIPTION
				"TYPE: - Number
				 PAGE: - ARC Ctrl
					Left  cmdID= 6005  min= 0  max= 4095  step= 1  format= %0.0f  div_scale= 1 
					Min = 0  Max = 4095  Step = 1 "
		::= { iqudc12CmdEntry 6005 }


	iqudc12ARCCtrlInputCropRight OBJECT-TYPE
		SYNTAX		INTEGER
		MAX-ACCESS		read-write
		STATUS			current
		DESCRIPTION
				"TYPE: - Number
				 PAGE: - ARC Ctrl
					Right  cmdID= 6006  min= 0  max= 4095  step= 1  format= %0.0f  div_scale= 1 
					Min = 0  Max = 4095  Step = 1 "
		::= { iqudc12CmdEntry 6006 }


	iqudc12ARCCtrlInputCropTop OBJECT-TYPE
		SYNTAX		INTEGER
		MAX-ACCESS		read-write
		STATUS			current
		DESCRIPTION
				"TYPE: - Number
				 PAGE: - ARC Ctrl
					Top  cmdID= 6007  min= 0  max= 2047  step= 1  format= %0.0f  div_scale= 1 
					Min = 0  Max = 2047  Step = 1 "
		::= { iqudc12CmdEntry 6007 }


	iqudc12ARCCtrlInputCropBottom OBJECT-TYPE
		SYNTAX		INTEGER
		MAX-ACCESS		read-write
		STATUS			current
		DESCRIPTION
				"TYPE: - Number
				 PAGE: - ARC Ctrl
					Bottom  cmdID= 6008  min= 0  max= 2047  step= 1  format= %0.0f  div_scale= 1 
					Min = 0  Max = 2047  Step = 1 "
		::= { iqudc12CmdEntry 6008 }


	iqudc12MenuARCCtrlSelStdPreset OBJECT-TYPE
		SYNTAX		INTEGER {
							val-Full-Frame(0),
							val-Box-16-9-Top-16-9(1),
							val-4-3-Box14-9Top-16-9(2),
							val-Box-16-9-16-9(3),
							val-Box-4-3-4-3(4),
							val-4-3-box-16-9(5),
							val-16-9-box-4-3(6),
							val-4-3-box-14-9-16-9(7),
							val-16-9-box-14-9-4-3(8),
							val-4-3-702-16-9-PB(9),
							val-16-9-FH-702-16-9(10)
							}
		MAX-ACCESS		read-write
		STATUS			current
		DESCRIPTION
				"TYPE: - RadiobuttonList
				 PAGE: - ARC Ctrl
					Sel Std. Preset  cmdID= 38704 
					Full Frame  value= 0  
					Box 16:9 Top > 16:9  value= 1  
					4:3 Box14:9Top>16:9  value= 2  
					Box 16:9 > 16:9  value= 3  
					Box 4:3 > 4:3  value= 4  
					4:3 > box 16:9  value= 5  
					16:9 > box 4:3  value= 6  
					4:3 box 14:9 > 16:9  value= 7  
					16:9 box 14:9 > 4:3  value= 8  
					4:3 702 > 16:9 PB  value= 9  
					16:9 FH 702 > 16:9  value= 10  "
		::= { iqudc12CmdEntry 38704 }


	iqudc12MenuARCCtrlRecallStdPreset OBJECT-TYPE
		SYNTAX		INTEGER { noAction(0),val-Recall-Std-Preset(1) }
		MAX-ACCESS		read-write
		STATUS			current
		DESCRIPTION
				"TYPE: - Button
				 PAGE: - ARC Ctrl
					Recall Std Preset  cmdID= 38700  value= 1  "
		::= { iqudc12CmdEntry 38700 }


	iqudc12MenuARCCtrlDefaultALLMemory OBJECT-TYPE
		SYNTAX		INTEGER { noAction(0),val-Default-ALL-Memory(1) }
		MAX-ACCESS		read-write
		STATUS			current
		DESCRIPTION
				"TYPE: - Button
				 PAGE: - ARC Ctrl
					Default ALL Memory  cmdID= 38702  value= 1  "
		::= { iqudc12CmdEntry 38702 }


	iqudc12MenuARCCtrlLastDisplayMemory OBJECT-TYPE
		SYNTAX		RollCallString
		MAX-ACCESS		read-only
		STATUS			current
		DESCRIPTION
				"TYPE: - Display
				 PAGE: - ARC Ctrl
					Last Display Memory  cmdID= 38706  format=   "
		::= { iqudc12CmdEntry 38706 }


	iqudc12MenuARCCtrl43AFDMapping2 OBJECT-TYPE
		SYNTAX		INTEGER
		MAX-ACCESS		read-write
		STATUS			current
		DESCRIPTION
				"TYPE: - Number
				 PAGE: - ARC Ctrl
					4:3 AFD Mapping 2  cmdID= 39017  min= 2  max= 145  step= 1  format= 0  div_scale= 1 
					Min = 0  Max = 0  Step = 0 "
		::= { iqudc12CmdEntry 39017 }


	iqudc12MenuARCCtrl43AFDMapping3 OBJECT-TYPE
		SYNTAX		INTEGER
		MAX-ACCESS		read-write
		STATUS			current
		DESCRIPTION
				"TYPE: - Number
				 PAGE: - ARC Ctrl
					4:3 AFD Mapping 3  cmdID= 39018  min= 2  max= 145  step= 1  format= 0  div_scale= 1 
					Min = 0  Max = 0  Step = 0 "
		::= { iqudc12CmdEntry 39018 }


	iqudc12MenuARCCtrl43AFDMapping4 OBJECT-TYPE
		SYNTAX		INTEGER
		MAX-ACCESS		read-write
		STATUS			current
		DESCRIPTION
				"TYPE: - Number
				 PAGE: - ARC Ctrl
					4:3 AFD Mapping 4  cmdID= 39019  min= 2  max= 145  step= 1  format= 0  div_scale= 1 
					Min = 0  Max = 0  Step = 0 "
		::= { iqudc12CmdEntry 39019 }


	iqudc12MenuARCCtrl43AFDMapping8 OBJECT-TYPE
		SYNTAX		INTEGER
		MAX-ACCESS		read-write
		STATUS			current
		DESCRIPTION
				"TYPE: - Number
				 PAGE: - ARC Ctrl
					4:3 AFD Mapping 8  cmdID= 39023  min= 2  max= 145  step= 1  format= 0  div_scale= 1 
					Min = 0  Max = 0  Step = 0 "
		::= { iqudc12CmdEntry 39023 }


	iqudc12MenuARCCtrl43AFDMapping9 OBJECT-TYPE
		SYNTAX		INTEGER
		MAX-ACCESS		read-write
		STATUS			current
		DESCRIPTION
				"TYPE: - Number
				 PAGE: - ARC Ctrl
					4:3 AFD Mapping 9  cmdID= 39024  min= 2  max= 145  step= 1  format= 0  div_scale= 1 
					Min = 0  Max = 0  Step = 0 "
		::= { iqudc12CmdEntry 39024 }


	iqudc12MenuARCCtrl43AFDMapping10 OBJECT-TYPE
		SYNTAX		INTEGER
		MAX-ACCESS		read-write
		STATUS			current
		DESCRIPTION
				"TYPE: - Number
				 PAGE: - ARC Ctrl
					4:3 AFD Mapping 10  cmdID= 39025  min= 2  max= 145  step= 1  format= 0  div_scale= 1 
					Min = 0  Max = 0  Step = 0 "
		::= { iqudc12CmdEntry 39025 }


	iqudc12MenuARCCtrl43AFDMapping11 OBJECT-TYPE
		SYNTAX		INTEGER
		MAX-ACCESS		read-write
		STATUS			current
		DESCRIPTION
				"TYPE: - Number
				 PAGE: - ARC Ctrl
					4:3 AFD Mapping 11  cmdID= 39026  min= 2  max= 145  step= 1  format= 0  div_scale= 1 
					Min = 0  Max = 0  Step = 0 "
		::= { iqudc12CmdEntry 39026 }


	iqudc12MenuARCCtrl43AFDMapping12 OBJECT-TYPE
		SYNTAX		INTEGER
		MAX-ACCESS		read-write
		STATUS			current
		DESCRIPTION
				"TYPE: - Number
				 PAGE: - ARC Ctrl
					4:3 AFD Mapping 12  cmdID= 39027  min= 2  max= 145  step= 1  format= 0  div_scale= 1 
					Min = 0  Max = 0  Step = 0 "
		::= { iqudc12CmdEntry 39027 }


	iqudc12MenuARCCtrl43AFDMapping13 OBJECT-TYPE
		SYNTAX		INTEGER
		MAX-ACCESS		read-write
		STATUS			current
		DESCRIPTION
				"TYPE: - Number
				 PAGE: - ARC Ctrl
					4:3 AFD Mapping 13  cmdID= 39028  min= 2  max= 145  step= 1  format= 0  div_scale= 1 
					Min = 0  Max = 0  Step = 0 "
		::= { iqudc12CmdEntry 39028 }


	iqudc12MenuARCCtrl43AFDMapping14 OBJECT-TYPE
		SYNTAX		INTEGER
		MAX-ACCESS		read-write
		STATUS			current
		DESCRIPTION
				"TYPE: - Number
				 PAGE: - ARC Ctrl
					4:3 AFD Mapping 14  cmdID= 39029  min= 2  max= 145  step= 1  format= 0  div_scale= 1 
					Min = 0  Max = 0  Step = 0 "
		::= { iqudc12CmdEntry 39029 }


	iqudc12MenuARCCtrl43AFDMapping15 OBJECT-TYPE
		SYNTAX		INTEGER
		MAX-ACCESS		read-write
		STATUS			current
		DESCRIPTION
				"TYPE: - Number
				 PAGE: - ARC Ctrl
					4:3 AFD Mapping 15  cmdID= 39030  min= 2  max= 145  step= 1  format= 0  div_scale= 1 
					Min = 0  Max = 0  Step = 0 "
		::= { iqudc12CmdEntry 39030 }


	iqudc12MenuARCCtrl43AFDMapping16 OBJECT-TYPE
		SYNTAX		INTEGER
		MAX-ACCESS		read-write
		STATUS			current
		DESCRIPTION
				"TYPE: - Number
				 PAGE: - ARC Ctrl
					4:3 AFD Mapping 16  cmdID= 39031  min= 2  max= 145  step= 1  format= 0  div_scale= 1 
					Min = 0  Max = 0  Step = 0 "
		::= { iqudc12CmdEntry 39031 }


	iqudc12MenuARCCtrl169AFDMapping2 OBJECT-TYPE
		SYNTAX		INTEGER
		MAX-ACCESS		read-write
		STATUS			current
		DESCRIPTION
				"TYPE: - Number
				 PAGE: - ARC Ctrl
					16:9 AFD Mapping 2  cmdID= 39034  min= 2  max= 145  step= 1  format= 0  div_scale= 1 
					Min = 0  Max = 0  Step = 0 "
		::= { iqudc12CmdEntry 39034 }


	iqudc12MenuARCCtrl169AFDMapping3 OBJECT-TYPE
		SYNTAX		INTEGER
		MAX-ACCESS		read-write
		STATUS			current
		DESCRIPTION
				"TYPE: - Number
				 PAGE: - ARC Ctrl
					16:9 AFD Mapping 3  cmdID= 39035  min= 2  max= 145  step= 1  format= 0  div_scale= 1 
					Min = 0  Max = 0  Step = 0 "
		::= { iqudc12CmdEntry 39035 }


	iqudc12MenuARCCtrl169AFDMapping4 OBJECT-TYPE
		SYNTAX		INTEGER
		MAX-ACCESS		read-write
		STATUS			current
		DESCRIPTION
				"TYPE: - Number
				 PAGE: - ARC Ctrl
					16:9 AFD Mapping 4  cmdID= 39036  min= 2  max= 145  step= 1  format= 0  div_scale= 1 
					Min = 0  Max = 0  Step = 0 "
		::= { iqudc12CmdEntry 39036 }


	iqudc12MenuARCCtrl169AFDMapping8 OBJECT-TYPE
		SYNTAX		INTEGER
		MAX-ACCESS		read-write
		STATUS			current
		DESCRIPTION
				"TYPE: - Number
				 PAGE: - ARC Ctrl
					16:9 AFD Mapping 8  cmdID= 39040  min= 2  max= 145  step= 1  format= 0  div_scale= 1 
					Min = 0  Max = 0  Step = 0 "
		::= { iqudc12CmdEntry 39040 }


	iqudc12MenuARCCtrl169AFDMapping9 OBJECT-TYPE
		SYNTAX		INTEGER
		MAX-ACCESS		read-write
		STATUS			current
		DESCRIPTION
				"TYPE: - Number
				 PAGE: - ARC Ctrl
					16:9 AFD Mapping 9  cmdID= 39041  min= 2  max= 145  step= 1  format= 0  div_scale= 1 
					Min = 0  Max = 0  Step = 0 "
		::= { iqudc12CmdEntry 39041 }


	iqudc12MenuARCCtrl169AFDMapping10 OBJECT-TYPE
		SYNTAX		INTEGER
		MAX-ACCESS		read-write
		STATUS			current
		DESCRIPTION
				"TYPE: - Number
				 PAGE: - ARC Ctrl
					16:9 AFD Mapping 10  cmdID= 39042  min= 2  max= 145  step= 1  format= 0  div_scale= 1 
					Min = 0  Max = 0  Step = 0 "
		::= { iqudc12CmdEntry 39042 }


	iqudc12MenuARCCtrl169AFDMapping11 OBJECT-TYPE
		SYNTAX		INTEGER
		MAX-ACCESS		read-write
		STATUS			current
		DESCRIPTION
				"TYPE: - Number
				 PAGE: - ARC Ctrl
					16:9 AFD Mapping 11  cmdID= 39043  min= 2  max= 145  step= 1  format= 0  div_scale= 1 
					Min = 0  Max = 0  Step = 0 "
		::= { iqudc12CmdEntry 39043 }


	iqudc12MenuARCCtrl169AFDMapping12 OBJECT-TYPE
		SYNTAX		INTEGER
		MAX-ACCESS		read-write
		STATUS			current
		DESCRIPTION
				"TYPE: - Number
				 PAGE: - ARC Ctrl
					16:9 AFD Mapping 12  cmdID= 39044  min= 2  max= 145  step= 1  format= 0  div_scale= 1 
					Min = 0  Max = 0  Step = 0 "
		::= { iqudc12CmdEntry 39044 }


	iqudc12MenuARCCtrl169AFDMapping13 OBJECT-TYPE
		SYNTAX		INTEGER
		MAX-ACCESS		read-write
		STATUS			current
		DESCRIPTION
				"TYPE: - Number
				 PAGE: - ARC Ctrl
					16:9 AFD Mapping 13  cmdID= 39045  min= 2  max= 145  step= 1  format= 0  div_scale= 1 
					Min = 0  Max = 0  Step = 0 "
		::= { iqudc12CmdEntry 39045 }


	iqudc12MenuARCCtrl169AFDMapping14 OBJECT-TYPE
		SYNTAX		INTEGER
		MAX-ACCESS		read-write
		STATUS			current
		DESCRIPTION
				"TYPE: - Number
				 PAGE: - ARC Ctrl
					16:9 AFD Mapping 14  cmdID= 39046  min= 2  max= 145  step= 1  format= 0  div_scale= 1 
					Min = 0  Max = 0  Step = 0 "
		::= { iqudc12CmdEntry 39046 }


	iqudc12MenuARCCtrl169AFDMapping15 OBJECT-TYPE
		SYNTAX		INTEGER
		MAX-ACCESS		read-write
		STATUS			current
		DESCRIPTION
				"TYPE: - Number
				 PAGE: - ARC Ctrl
					16:9 AFD Mapping 15  cmdID= 39047  min= 2  max= 145  step= 1  format= 0  div_scale= 1 
					Min = 0  Max = 0  Step = 0 "
		::= { iqudc12CmdEntry 39047 }


	iqudc12MenuARCCtrl169AFDMapping16 OBJECT-TYPE
		SYNTAX		INTEGER
		MAX-ACCESS		read-write
		STATUS			current
		DESCRIPTION
				"TYPE: - Number
				 PAGE: - ARC Ctrl
					16:9 AFD Mapping 16  cmdID= 39048  min= 2  max= 145  step= 1  format= 0  div_scale= 1 
					Min = 0  Max = 0  Step = 0 "
		::= { iqudc12CmdEntry 39048 }


	iqudc12MenuARCCtrlNoSignalMapping OBJECT-TYPE
		SYNTAX		INTEGER
		MAX-ACCESS		read-write
		STATUS			current
		DESCRIPTION
				"TYPE: - Number
				 PAGE: - ARC Ctrl
					No Signal Mapping  cmdID= 39049  min= 2  max= 145  step= 1  format= 0  div_scale= 1 
					Min = 0  Max = 0  Step = 0 "
		::= { iqudc12CmdEntry 39049 }


	iqudc12MenuARCCtrlForceMapping1 OBJECT-TYPE
		SYNTAX		INTEGER
		MAX-ACCESS		read-write
		STATUS			current
		DESCRIPTION
				"TYPE: - Number
				 PAGE: - ARC Ctrl
					Force Mapping 1  cmdID= 39079  min= 2  max= 145  step= 1  format= 0  div_scale= 1 
					Min = 0  Max = 0  Step = 0 "
		::= { iqudc12CmdEntry 39079 }


	iqudc12MenuARCCtrlForceMapping2 OBJECT-TYPE
		SYNTAX		INTEGER
		MAX-ACCESS		read-write
		STATUS			current
		DESCRIPTION
				"TYPE: - Number
				 PAGE: - ARC Ctrl
					Force Mapping 2  cmdID= 39080  min= 2  max= 145  step= 1  format= 0  div_scale= 1 
					Min = 0  Max = 0  Step = 0 "
		::= { iqudc12CmdEntry 39080 }


	iqudc12MenuARCCtrlForceMapping3 OBJECT-TYPE
		SYNTAX		INTEGER
		MAX-ACCESS		read-write
		STATUS			current
		DESCRIPTION
				"TYPE: - Number
				 PAGE: - ARC Ctrl
					Force Mapping 3  cmdID= 39081  min= 2  max= 145  step= 1  format= 0  div_scale= 1 
					Min = 0  Max = 0  Step = 0 "
		::= { iqudc12CmdEntry 39081 }


	iqudc12MenuARCCtrlForceMapping4 OBJECT-TYPE
		SYNTAX		INTEGER
		MAX-ACCESS		read-write
		STATUS			current
		DESCRIPTION
				"TYPE: - Number
				 PAGE: - ARC Ctrl
					Force Mapping 4  cmdID= 39082  min= 2  max= 145  step= 1  format= 0  div_scale= 1 
					Min = 0  Max = 0  Step = 0 "
		::= { iqudc12CmdEntry 39082 }


	iqudc12MenuARCCtrl43ARCMapping2 OBJECT-TYPE
		SYNTAX		INTEGER
		MAX-ACCESS		read-write
		STATUS			current
		DESCRIPTION
				"TYPE: - Number
				 PAGE: - ARC Ctrl
					4:3 ARC Mapping  2  cmdID= 39050  min= 0  max= 32  step= 1  format= 0  div_scale= 1 
					Min = 0  Max = 0  Step = 0 "
		::= { iqudc12CmdEntry 39050 }


	iqudc12MenuARCCtrl43ARCMapping3 OBJECT-TYPE
		SYNTAX		INTEGER
		MAX-ACCESS		read-write
		STATUS			current
		DESCRIPTION
				"TYPE: - Number
				 PAGE: - ARC Ctrl
					4:3 ARC Mapping  3  cmdID= 39051  min= 0  max= 32  step= 1  format= 0  div_scale= 1 
					Min = 0  Max = 0  Step = 0 "
		::= { iqudc12CmdEntry 39051 }


	iqudc12MenuARCCtrl43ARCMapping4 OBJECT-TYPE
		SYNTAX		INTEGER
		MAX-ACCESS		read-write
		STATUS			current
		DESCRIPTION
				"TYPE: - Number
				 PAGE: - ARC Ctrl
					4:3 ARC Mapping  4  cmdID= 39052  min= 0  max= 32  step= 1  format= 0  div_scale= 1 
					Min = 0  Max = 0  Step = 0 "
		::= { iqudc12CmdEntry 39052 }


	iqudc12MenuARCCtrl43ARCMapping8 OBJECT-TYPE
		SYNTAX		INTEGER
		MAX-ACCESS		read-write
		STATUS			current
		DESCRIPTION
				"TYPE: - Number
				 PAGE: - ARC Ctrl
					4:3 ARC Mapping  8  cmdID= 39053  min= 0  max= 32  step= 1  format= 0  div_scale= 1 
					Min = 0  Max = 0  Step = 0 "
		::= { iqudc12CmdEntry 39053 }


	iqudc12MenuARCCtrl43ARCMapping9 OBJECT-TYPE
		SYNTAX		INTEGER
		MAX-ACCESS		read-write
		STATUS			current
		DESCRIPTION
				"TYPE: - Number
				 PAGE: - ARC Ctrl
					4:3 ARC Mapping  9  cmdID= 39054  min= 0  max= 32  step= 1  format= 0  div_scale= 1 
					Min = 0  Max = 0  Step = 0 "
		::= { iqudc12CmdEntry 39054 }


	iqudc12MenuARCCtrl43ARCMapping10 OBJECT-TYPE
		SYNTAX		INTEGER
		MAX-ACCESS		read-write
		STATUS			current
		DESCRIPTION
				"TYPE: - Number
				 PAGE: - ARC Ctrl
					4:3 ARC Mapping  10  cmdID= 39055  min= 0  max= 32  step= 1  format= 0  div_scale= 1 
					Min = 0  Max = 0  Step = 0 "
		::= { iqudc12CmdEntry 39055 }


	iqudc12MenuARCCtrl43ARCMapping11 OBJECT-TYPE
		SYNTAX		INTEGER
		MAX-ACCESS		read-write
		STATUS			current
		DESCRIPTION
				"TYPE: - Number
				 PAGE: - ARC Ctrl
					4:3 ARC Mapping  11  cmdID= 39056  min= 0  max= 32  step= 1  format= 0  div_scale= 1 
					Min = 0  Max = 0  Step = 0 "
		::= { iqudc12CmdEntry 39056 }


	iqudc12MenuARCCtrl43ARCMapping12 OBJECT-TYPE
		SYNTAX		INTEGER
		MAX-ACCESS		read-write
		STATUS			current
		DESCRIPTION
				"TYPE: - Number
				 PAGE: - ARC Ctrl
					4:3 ARC Mapping  12  cmdID= 39057  min= 0  max= 32  step= 1  format= 0  div_scale= 1 
					Min = 0  Max = 0  Step = 0 "
		::= { iqudc12CmdEntry 39057 }


	iqudc12MenuARCCtrl43ARCMapping13 OBJECT-TYPE
		SYNTAX		INTEGER
		MAX-ACCESS		read-write
		STATUS			current
		DESCRIPTION
				"TYPE: - Number
				 PAGE: - ARC Ctrl
					4:3 ARC Mapping  13  cmdID= 39058  min= 0  max= 32  step= 1  format= 0  div_scale= 1 
					Min = 0  Max = 0  Step = 0 "
		::= { iqudc12CmdEntry 39058 }


	iqudc12MenuARCCtrl43ARCMapping14 OBJECT-TYPE
		SYNTAX		INTEGER
		MAX-ACCESS		read-write
		STATUS			current
		DESCRIPTION
				"TYPE: - Number
				 PAGE: - ARC Ctrl
					4:3 ARC Mapping  14  cmdID= 39059  min= 0  max= 32  step= 1  format= 0  div_scale= 1 
					Min = 0  Max = 0  Step = 0 "
		::= { iqudc12CmdEntry 39059 }


	iqudc12MenuARCCtrl43ARCMapping15 OBJECT-TYPE
		SYNTAX		INTEGER
		MAX-ACCESS		read-write
		STATUS			current
		DESCRIPTION
				"TYPE: - Number
				 PAGE: - ARC Ctrl
					4:3 ARC Mapping  15  cmdID= 39060  min= 0  max= 32  step= 1  format= 0  div_scale= 1 
					Min = 0  Max = 0  Step = 0 "
		::= { iqudc12CmdEntry 39060 }


	iqudc12MenuARCCtrl43ARCMapping16 OBJECT-TYPE
		SYNTAX		INTEGER
		MAX-ACCESS		read-write
		STATUS			current
		DESCRIPTION
				"TYPE: - Number
				 PAGE: - ARC Ctrl
					4:3 ARC Mapping  16  cmdID= 39061  min= 0  max= 32  step= 1  format= 0  div_scale= 1 
					Min = 0  Max = 0  Step = 0 "
		::= { iqudc12CmdEntry 39061 }


	iqudc12MenuARCCtrl169ARCMapping2 OBJECT-TYPE
		SYNTAX		INTEGER
		MAX-ACCESS		read-write
		STATUS			current
		DESCRIPTION
				"TYPE: - Number
				 PAGE: - ARC Ctrl
					16:9 ARC Mapping  2  cmdID= 39062  min= 0  max= 32  step= 1  format= 0  div_scale= 1 
					Min = 0  Max = 0  Step = 0 "
		::= { iqudc12CmdEntry 39062 }


	iqudc12MenuARCCtrl169ARCMapping3 OBJECT-TYPE
		SYNTAX		INTEGER
		MAX-ACCESS		read-write
		STATUS			current
		DESCRIPTION
				"TYPE: - Number
				 PAGE: - ARC Ctrl
					16:9 ARC Mapping  3  cmdID= 39063  min= 0  max= 32  step= 1  format= 0  div_scale= 1 
					Min = 0  Max = 0  Step = 0 "
		::= { iqudc12CmdEntry 39063 }


	iqudc12MenuARCCtrl169ARCMapping4 OBJECT-TYPE
		SYNTAX		INTEGER
		MAX-ACCESS		read-write
		STATUS			current
		DESCRIPTION
				"TYPE: - Number
				 PAGE: - ARC Ctrl
					16:9 ARC Mapping  4  cmdID= 39064  min= 0  max= 32  step= 1  format= 0  div_scale= 1 
					Min = 0  Max = 0  Step = 0 "
		::= { iqudc12CmdEntry 39064 }


	iqudc12MenuARCCtrl169ARCMapping8 OBJECT-TYPE
		SYNTAX		INTEGER
		MAX-ACCESS		read-write
		STATUS			current
		DESCRIPTION
				"TYPE: - Number
				 PAGE: - ARC Ctrl
					16:9 ARC Mapping  8  cmdID= 39065  min= 0  max= 32  step= 1  format= 0  div_scale= 1 
					Min = 0  Max = 0  Step = 0 "
		::= { iqudc12CmdEntry 39065 }


	iqudc12MenuARCCtrl169ARCMapping9 OBJECT-TYPE
		SYNTAX		INTEGER
		MAX-ACCESS		read-write
		STATUS			current
		DESCRIPTION
				"TYPE: - Number
				 PAGE: - ARC Ctrl
					16:9 ARC Mapping  9  cmdID= 39066  min= 0  max= 32  step= 1  format= 0  div_scale= 1 
					Min = 0  Max = 0  Step = 0 "
		::= { iqudc12CmdEntry 39066 }


	iqudc12MenuARCCtrl169ARCMapping139067 OBJECT-TYPE
		SYNTAX		INTEGER
		MAX-ACCESS		read-write
		STATUS			current
		DESCRIPTION
				"TYPE: - Number
				 PAGE: - ARC Ctrl
					16:9 ARC Mapping  1  cmdID= 39067  min= 0  max= 32  step= 1  format= 0  div_scale= 1 
					Min = 0  Max = 0  Step = 0 "
		::= { iqudc12CmdEntry 39067 }


	iqudc12MenuARCCtrl169ARCMapping139068 OBJECT-TYPE
		SYNTAX		INTEGER
		MAX-ACCESS		read-write
		STATUS			current
		DESCRIPTION
				"TYPE: - Number
				 PAGE: - ARC Ctrl
					16:9 ARC Mapping  1  cmdID= 39068  min= 0  max= 32  step= 1  format= 0  div_scale= 1 
					Min = 0  Max = 0  Step = 0 "
		::= { iqudc12CmdEntry 39068 }


	iqudc12MenuARCCtrl169ARCMapping139069 OBJECT-TYPE
		SYNTAX		INTEGER
		MAX-ACCESS		read-write
		STATUS			current
		DESCRIPTION
				"TYPE: - Number
				 PAGE: - ARC Ctrl
					16:9 ARC Mapping  1  cmdID= 39069  min= 0  max= 32  step= 1  format= 0  div_scale= 1 
					Min = 0  Max = 0  Step = 0 "
		::= { iqudc12CmdEntry 39069 }


	iqudc12MenuARCCtrl169ARCMapping139070 OBJECT-TYPE
		SYNTAX		INTEGER
		MAX-ACCESS		read-write
		STATUS			current
		DESCRIPTION
				"TYPE: - Number
				 PAGE: - ARC Ctrl
					16:9 ARC Mapping  1  cmdID= 39070  min= 0  max= 32  step= 1  format= 0  div_scale= 1 
					Min = 0  Max = 0  Step = 0 "
		::= { iqudc12CmdEntry 39070 }


	iqudc12MenuARCCtrl169ARCMapping139071 OBJECT-TYPE
		SYNTAX		INTEGER
		MAX-ACCESS		read-write
		STATUS			current
		DESCRIPTION
				"TYPE: - Number
				 PAGE: - ARC Ctrl
					16:9 ARC Mapping  1  cmdID= 39071  min= 0  max= 32  step= 1  format= 0  div_scale= 1 
					Min = 0  Max = 0  Step = 0 "
		::= { iqudc12CmdEntry 39071 }


	iqudc12MenuARCCtrl169ARCMapping139072 OBJECT-TYPE
		SYNTAX		INTEGER
		MAX-ACCESS		read-write
		STATUS			current
		DESCRIPTION
				"TYPE: - Number
				 PAGE: - ARC Ctrl
					16:9 ARC Mapping  1  cmdID= 39072  min= 0  max= 32  step= 1  format= 0  div_scale= 1 
					Min = 0  Max = 0  Step = 0 "
		::= { iqudc12CmdEntry 39072 }


	iqudc12MenuARCCtrl169ARCMapping16 OBJECT-TYPE
		SYNTAX		INTEGER
		MAX-ACCESS		read-write
		STATUS			current
		DESCRIPTION
				"TYPE: - Number
				 PAGE: - ARC Ctrl
					16:9 ARC Mapping 16  cmdID= 39073  min= 0  max= 32  step= 1  format= 0  div_scale= 1 
					Min = 0  Max = 0  Step = 0 "
		::= { iqudc12CmdEntry 39073 }


	iqudc12MenuARCCtrlNoSignalARCMappi OBJECT-TYPE
		SYNTAX		INTEGER
		MAX-ACCESS		read-write
		STATUS			current
		DESCRIPTION
				"TYPE: - Number
				 PAGE: - ARC Ctrl
					No Signal ARC Mappi  cmdID= 39074  min= 0  max= 32  step= 1  format= 0  div_scale= 1 
					Min = 0  Max = 0  Step = 0 "
		::= { iqudc12CmdEntry 39074 }


	iqudc12MenuARCCtrlForceARCMapping1 OBJECT-TYPE
		SYNTAX		INTEGER
		MAX-ACCESS		read-write
		STATUS			current
		DESCRIPTION
				"TYPE: - Number
				 PAGE: - ARC Ctrl
					Force ARC Mapping1  cmdID= 39078  min= 0  max= 32  step= 1  format= 0  div_scale= 1 
					Min = 0  Max = 0  Step = 0 "
		::= { iqudc12CmdEntry 39078 }


	iqudc12MenuARCCtrlForceARCMapping2 OBJECT-TYPE
		SYNTAX		INTEGER
		MAX-ACCESS		read-write
		STATUS			current
		DESCRIPTION
				"TYPE: - Number
				 PAGE: - ARC Ctrl
					Force ARC Mapping2  cmdID= 39084  min= 0  max= 32  step= 1  format= 0  div_scale= 1 
					Min = 0  Max = 0  Step = 0 "
		::= { iqudc12CmdEntry 39084 }


	iqudc12MenuARCCtrlForceARCMapping3 OBJECT-TYPE
		SYNTAX		INTEGER
		MAX-ACCESS		read-write
		STATUS			current
		DESCRIPTION
				"TYPE: - Number
				 PAGE: - ARC Ctrl
					Force ARC Mapping3  cmdID= 39085  min= 0  max= 32  step= 1  format= 0  div_scale= 1 
					Min = 0  Max = 0  Step = 0 "
		::= { iqudc12CmdEntry 39085 }


	iqudc12MenuARCCtrlForceARCMapping4 OBJECT-TYPE
		SYNTAX		INTEGER
		MAX-ACCESS		read-write
		STATUS			current
		DESCRIPTION
				"TYPE: - Number
				 PAGE: - ARC Ctrl
					Force ARC Mapping4  cmdID= 39083  min= 0  max= 32  step= 1  format= 0  div_scale= 1 
					Min = 0  Max = 0  Step = 0 "
		::= { iqudc12CmdEntry 39083 }


	iqudc12MenuARCCtrlForceIndex OBJECT-TYPE
		SYNTAX		INTEGER
		MAX-ACCESS		read-write
		STATUS			current
		DESCRIPTION
				"TYPE: - Number
				 PAGE: - ARC Ctrl
					Force Index  cmdID= 38741  min= 0  max= 3  step= 1  format= %0.0f  div_scale= 1 
					Min = 0  Max = 3  Step = 1 "
		::= { iqudc12CmdEntry 38741 }


	iqudc12GenlockBlankingGenlockStandard OBJECT-TYPE
		SYNTAX		INTEGER {
							val-525-29i(7),
							val-625-25i(8),
							val-720-59p(5),
							val-720-50p(6),
							val-1080-25i(4),
							val-1080-29i(3),
							val-1080-50p(2),
							val-1080-59p(1)
							}
		MAX-ACCESS		read-write
		STATUS			current
		DESCRIPTION
				"TYPE: - RadiobuttonList
				 PAGE: - Genlock/Blanking
					Standard  cmdID= 37203 
					525/29i  value= 7  
					625/25i  value= 8  
					720/59p  value= 5  
					720/50p  value= 6  
					1080/25i  value= 4  
					1080/29i  value= 3  
					1080/50p  value= 2  
					1080/59p  value= 1  "
		::= { iqudc12CmdEntry 37203 }


	iqudc12GenlockBlankingGenlockDelayMode OBJECT-TYPE
		SYNTAX		INTEGER {
							val-Free-Run(0),
							val-Lock-to-Reference(1),
							val-Manual-H-V(2)
							}
		MAX-ACCESS		read-write
		STATUS			current
		DESCRIPTION
				"TYPE: - RadiobuttonList
				 PAGE: - Genlock/Blanking
					Delay Mode  cmdID= 33029 
					Free Run  value= 0  
					Lock to Reference  value= 1  
					Manual H/V  value= 2  "
		::= { iqudc12CmdEntry 33029 }


	iqudc12GenlockSetDelayDelayFrames OBJECT-TYPE
		SYNTAX		INTEGER
		MAX-ACCESS		read-write
		STATUS			current
		DESCRIPTION
				"TYPE: - Number
				 PAGE: - Genlock/Blanking
					Delay Frames  cmdID= 33031  min= 0  max= 147  step= 1  format= %0.0f frames  div_scale= 1 
					Min = 0 frames  Max = 147 frames  Step = 1 frames "
		::= { iqudc12CmdEntry 33031 }


	iqudc12GenlockSetDelayVerticalPhase OBJECT-TYPE
		SYNTAX		INTEGER
		MAX-ACCESS		read-write
		STATUS			current
		DESCRIPTION
				"TYPE: - Number
				 PAGE: - Genlock/Blanking
					Vertical Phase  cmdID= 33033  min= -1125  max= 1125  step= 1  format= %0.0f lines  div_scale= 1 
					Min = -1125 lines  Max = 1125 lines  Step = 1 lines "
		::= { iqudc12CmdEntry 33033 }


	iqudc12GenlockSetDelayHorizontalPhase OBJECT-TYPE
		SYNTAX		INTEGER
		MAX-ACCESS		read-write
		STATUS			current
		DESCRIPTION
				"TYPE: - Number
				 PAGE: - Genlock/Blanking
					Horizontal Phase  cmdID= 33032  min= -4125  max= 4125  step= 1  format= %0.0f pixels  div_scale= 1 
					Min = -4125 pixels  Max = 4125 pixels  Step = 1 pixels "
		::= { iqudc12CmdEntry 33032 }


	iqudc12GenlockSetDelayVerticalDelay OBJECT-TYPE
		SYNTAX		INTEGER
		MAX-ACCESS		read-write
		STATUS			current
		DESCRIPTION
				"TYPE: - Number
				 PAGE: - Genlock/Blanking
					Vertical Delay  cmdID= 33045  min= 0  max= 1125  step= 1  format= %0.0f lines  div_scale= 1 
					Min = 0 lines  Max = 1125 lines  Step = 1 lines "
		::= { iqudc12CmdEntry 33045 }


	iqudc12GenlockSetDelayHorizontalDelay OBJECT-TYPE
		SYNTAX		INTEGER
		MAX-ACCESS		read-write
		STATUS			current
		DESCRIPTION
				"TYPE: - Number
				 PAGE: - Genlock/Blanking
					Horizontal Delay  cmdID= 33044  min= 0  max= 4125  step= 1  format= %0.0f pixels  div_scale= 1 
					Min = 0 pixels  Max = 4125 pixels  Step = 1 pixels "
		::= { iqudc12CmdEntry 33044 }


	iqudc12GenlockBlankingGenlockRefLogHide OBJECT-TYPE
		SYNTAX		RollCallString
		MAX-ACCESS		read-only
		STATUS			current
		DESCRIPTION
				"TYPE: - Display
				 PAGE: - Genlock/Blanking
					RefLogHide  cmdID= 33175  format=   "
		::= { iqudc12CmdEntry 33175 }


	iqudc12GenlockDolbyELineStandard OBJECT-TYPE
		SYNTAX		INTEGER {
							val-525-29i(7),
							val-625-25i(8),
							val-720-50p(6),
							val-720-59p(5),
							val-1080-25i(4),
							val-1080-29i(3),
							val-1080-50p(2),
							val-1080-59p(1)
							}
		MAX-ACCESS		read-write
		STATUS			current
		DESCRIPTION
				"TYPE: - RadiobuttonList
				 PAGE: - Genlock/Blanking
					Standard  cmdID= 38655 
					525/29i  value= 7  
					625/25i  value= 8  
					720/50p  value= 6  
					720/59p  value= 5  
					1080/25i  value= 4  
					1080/29i  value= 3  
					1080/50p  value= 2  
					1080/59p  value= 1  "
		::= { iqudc12CmdEntry 38655 }


	iqudc12GenlockDolbyELineAutoLineNo OBJECT-TYPE
		SYNTAX		INTEGER
		MAX-ACCESS		read-write
		STATUS			current
		DESCRIPTION
				"TYPE: - Number
				 PAGE: - Genlock/Blanking
					Auto Line No.  cmdID= 38656  min= 1  max= 1125  step= 1  format= %0.0f  div_scale= 1 
					Min = 1  Max = 1125  Step = 1 "
		::= { iqudc12CmdEntry 38656 }


	iqudc12DolbyELineUserDolbyELinePair1 OBJECT-TYPE
		SYNTAX		INTEGER {
							val-Default(0),
							val-User(1)
							}
		MAX-ACCESS		read-write
		STATUS			current
		DESCRIPTION
				"TYPE: - RadiobuttonList
				 PAGE: - Genlock/Blanking
					Pair1  cmdID= 38670 
					Default  value= 0  
					User  value= 1  "
		::= { iqudc12CmdEntry 38670 }


	iqudc12DolbyELineUserDolbyELinePair2 OBJECT-TYPE
		SYNTAX		INTEGER {
							val-Default(0),
							val-User(1)
							}
		MAX-ACCESS		read-write
		STATUS			current
		DESCRIPTION
				"TYPE: - RadiobuttonList
				 PAGE: - Genlock/Blanking
					Pair2  cmdID= 38671 
					Default  value= 0  
					User  value= 1  "
		::= { iqudc12CmdEntry 38671 }


	iqudc12DolbyELineUserDolbyELinePair3 OBJECT-TYPE
		SYNTAX		INTEGER {
							val-Default(0),
							val-User(1)
							}
		MAX-ACCESS		read-write
		STATUS			current
		DESCRIPTION
				"TYPE: - RadiobuttonList
				 PAGE: - Genlock/Blanking
					Pair3  cmdID= 38672 
					Default  value= 0  
					User  value= 1  "
		::= { iqudc12CmdEntry 38672 }


	iqudc12DolbyELineUserDolbyELinePair4 OBJECT-TYPE
		SYNTAX		INTEGER {
							val-Default(0),
							val-User(1)
							}
		MAX-ACCESS		read-write
		STATUS			current
		DESCRIPTION
				"TYPE: - RadiobuttonList
				 PAGE: - Genlock/Blanking
					Pair4  cmdID= 38673 
					Default  value= 0  
					User  value= 1  "
		::= { iqudc12CmdEntry 38673 }


	iqudc12DolbyELineUserDolbyELinePair5 OBJECT-TYPE
		SYNTAX		INTEGER {
							val-Default(0),
							val-User(1)
							}
		MAX-ACCESS		read-write
		STATUS			current
		DESCRIPTION
				"TYPE: - RadiobuttonList
				 PAGE: - Genlock/Blanking
					Pair5  cmdID= 38674 
					Default  value= 0  
					User  value= 1  "
		::= { iqudc12CmdEntry 38674 }


	iqudc12DolbyELineUserDolbyELinePair6 OBJECT-TYPE
		SYNTAX		INTEGER {
							val-Default(0),
							val-User(1)
							}
		MAX-ACCESS		read-write
		STATUS			current
		DESCRIPTION
				"TYPE: - RadiobuttonList
				 PAGE: - Genlock/Blanking
					Pair6  cmdID= 38675 
					Default  value= 0  
					User  value= 1  "
		::= { iqudc12CmdEntry 38675 }


	iqudc12DolbyELineUserDolbyELinePair7 OBJECT-TYPE
		SYNTAX		INTEGER {
							val-Default(0),
							val-User(1)
							}
		MAX-ACCESS		read-write
		STATUS			current
		DESCRIPTION
				"TYPE: - RadiobuttonList
				 PAGE: - Genlock/Blanking
					Pair7  cmdID= 38676 
					Default  value= 0  
					User  value= 1  "
		::= { iqudc12CmdEntry 38676 }


	iqudc12DolbyELineUserDolbyELinePair8 OBJECT-TYPE
		SYNTAX		INTEGER {
							val-Default(0),
							val-User(1)
							}
		MAX-ACCESS		read-write
		STATUS			current
		DESCRIPTION
				"TYPE: - RadiobuttonList
				 PAGE: - Genlock/Blanking
					Pair8  cmdID= 38677 
					Default  value= 0  
					User  value= 1  "
		::= { iqudc12CmdEntry 38677 }


	iqudc12GenlockDolbyELineUserLine525i29 OBJECT-TYPE
		SYNTAX		INTEGER
		MAX-ACCESS		read-write
		STATUS			current
		DESCRIPTION
				"TYPE: - Number
				 PAGE: - Genlock/Blanking
					UserLine525i29  cmdID= 38684  min= 1  max= 525  step= 1  format= %d  div_scale= 1 
					Min = 1  Max = 525  Step = 1 "
		::= { iqudc12CmdEntry 38684 }


	iqudc12GenlockDolbyELineUserLine625i25 OBJECT-TYPE
		SYNTAX		INTEGER
		MAX-ACCESS		read-write
		STATUS			current
		DESCRIPTION
				"TYPE: - Number
				 PAGE: - Genlock/Blanking
					UserLine625i25  cmdID= 38685  min= 1  max= 625  step= 1  format= %d  div_scale= 1 
					Min = 1  Max = 625  Step = 1 "
		::= { iqudc12CmdEntry 38685 }


	iqudc12GenlockDolbyELineUserLine720p50 OBJECT-TYPE
		SYNTAX		INTEGER
		MAX-ACCESS		read-write
		STATUS			current
		DESCRIPTION
				"TYPE: - Number
				 PAGE: - Genlock/Blanking
					UserLine720p50  cmdID= 38683  min= 1  max= 750  step= 1  format= %d  div_scale= 1 
					Min = 1  Max = 750  Step = 1 "
		::= { iqudc12CmdEntry 38683 }


	iqudc12GenlockDolbyELineUserLine720p59 OBJECT-TYPE
		SYNTAX		INTEGER
		MAX-ACCESS		read-write
		STATUS			current
		DESCRIPTION
				"TYPE: - Number
				 PAGE: - Genlock/Blanking
					UserLine720p59  cmdID= 38682  min= 1  max= 750  step= 1  format= %d  div_scale= 1 
					Min = 1  Max = 750  Step = 1 "
		::= { iqudc12CmdEntry 38682 }


	iqudc12GenlockDolbyELineUserLine1080i25 OBJECT-TYPE
		SYNTAX		INTEGER
		MAX-ACCESS		read-write
		STATUS			current
		DESCRIPTION
				"TYPE: - Number
				 PAGE: - Genlock/Blanking
					UserLine1080i25  cmdID= 38681  min= 1  max= 1125  step= 1  format= %d  div_scale= 1 
					Min = 1  Max = 1125  Step = 1 "
		::= { iqudc12CmdEntry 38681 }


	iqudc12GenlockDolbyELineUserLine1080i29 OBJECT-TYPE
		SYNTAX		INTEGER
		MAX-ACCESS		read-write
		STATUS			current
		DESCRIPTION
				"TYPE: - Number
				 PAGE: - Genlock/Blanking
					UserLine1080i29  cmdID= 38680  min= 1  max= 1125  step= 1  format= %d  div_scale= 1 
					Min = 1  Max = 1125  Step = 1 "
		::= { iqudc12CmdEntry 38680 }


	iqudc12GenlockDolbyELineUserLine1080p50 OBJECT-TYPE
		SYNTAX		INTEGER
		MAX-ACCESS		read-write
		STATUS			current
		DESCRIPTION
				"TYPE: - Number
				 PAGE: - Genlock/Blanking
					UserLine1080p50  cmdID= 38679  min= 1  max= 1125  step= 1  format= %d  div_scale= 1 
					Min = 1  Max = 1125  Step = 1 "
		::= { iqudc12CmdEntry 38679 }


	iqudc12GenlockDolbyELineUserLine1080p59 OBJECT-TYPE
		SYNTAX		INTEGER
		MAX-ACCESS		read-write
		STATUS			current
		DESCRIPTION
				"TYPE: - Number
				 PAGE: - Genlock/Blanking
					UserLine1080p59  cmdID= 38780  min= 1  max= 1125  step= 1  format= %d  div_scale= 1 
					Min = 1  Max = 1125  Step = 1 "
		::= { iqudc12CmdEntry 38780 }


	iqudc12GenlockDolbyELineAutoAlign1 OBJECT-TYPE
		SYNTAX		INTEGER { disable(0), enable(1) }
		MAX-ACCESS		read-write
		STATUS			current
		DESCRIPTION
				"TYPE: - Checkbox
				 PAGE: - Genlock/Blanking
					AutoAlign1  cmdID= 38110 "
		::= { iqudc12CmdEntry 38110 }


	iqudc12GenlockDolbyELineAutoAlign2 OBJECT-TYPE
		SYNTAX		INTEGER { disable(0), enable(1) }
		MAX-ACCESS		read-write
		STATUS			current
		DESCRIPTION
				"TYPE: - Checkbox
				 PAGE: - Genlock/Blanking
					AutoAlign2  cmdID= 38111 "
		::= { iqudc12CmdEntry 38111 }


	iqudc12GenlockDolbyELineAutoAlign3 OBJECT-TYPE
		SYNTAX		INTEGER { disable(0), enable(1) }
		MAX-ACCESS		read-write
		STATUS			current
		DESCRIPTION
				"TYPE: - Checkbox
				 PAGE: - Genlock/Blanking
					AutoAlign3  cmdID= 38112 "
		::= { iqudc12CmdEntry 38112 }


	iqudc12GenlockDolbyELineAutoAlign4 OBJECT-TYPE
		SYNTAX		INTEGER { disable(0), enable(1) }
		MAX-ACCESS		read-write
		STATUS			current
		DESCRIPTION
				"TYPE: - Checkbox
				 PAGE: - Genlock/Blanking
					AutoAlign4  cmdID= 38113 "
		::= { iqudc12CmdEntry 38113 }


	iqudc12GenlockDolbyELineAutoAlign5 OBJECT-TYPE
		SYNTAX		INTEGER { disable(0), enable(1) }
		MAX-ACCESS		read-write
		STATUS			current
		DESCRIPTION
				"TYPE: - Checkbox
				 PAGE: - Genlock/Blanking
					AutoAlign5  cmdID= 38114 "
		::= { iqudc12CmdEntry 38114 }


	iqudc12GenlockDolbyELineAutoAlign6 OBJECT-TYPE
		SYNTAX		INTEGER { disable(0), enable(1) }
		MAX-ACCESS		read-write
		STATUS			current
		DESCRIPTION
				"TYPE: - Checkbox
				 PAGE: - Genlock/Blanking
					AutoAlign6  cmdID= 38115 "
		::= { iqudc12CmdEntry 38115 }


	iqudc12GenlockDolbyELineAutoAlign7 OBJECT-TYPE
		SYNTAX		INTEGER { disable(0), enable(1) }
		MAX-ACCESS		read-write
		STATUS			current
		DESCRIPTION
				"TYPE: - Checkbox
				 PAGE: - Genlock/Blanking
					AutoAlign7  cmdID= 38116 "
		::= { iqudc12CmdEntry 38116 }


	iqudc12GenlockDolbyELineAutoAlign8 OBJECT-TYPE
		SYNTAX		INTEGER { disable(0), enable(1) }
		MAX-ACCESS		read-write
		STATUS			current
		DESCRIPTION
				"TYPE: - Checkbox
				 PAGE: - Genlock/Blanking
					AutoAlign8  cmdID= 38117 "
		::= { iqudc12CmdEntry 38117 }


	iqudc12BlankingHANCVBIBlankingStandard OBJECT-TYPE
		SYNTAX		INTEGER {
							val-525-29i(7),
							val-625-25i(8),
							val-720-50p(6),
							val-720-59p(5),
							val-1080-25i(4),
							val-1080-29i(3),
							val-1080-50p(2),
							val-1080-59p(1)
							}
		MAX-ACCESS		read-write
		STATUS			current
		DESCRIPTION
				"TYPE: - RadiobuttonList
				 PAGE: - Genlock/Blanking
					Standard  cmdID= 37200 
					525/29i  value= 7  
					625/25i  value= 8  
					720/50p  value= 6  
					720/59p  value= 5  
					1080/25i  value= 4  
					1080/29i  value= 3  
					1080/50p  value= 2  
					1080/59p  value= 1  "
		::= { iqudc12CmdEntry 37200 }


	iqudc12BlankingHANCVBIBlankingBlankAll OBJECT-TYPE
		SYNTAX		INTEGER { noAction(0),val-Blank-All(1) }
		MAX-ACCESS		read-write
		STATUS			current
		DESCRIPTION
				"TYPE: - Button
				 PAGE: - Genlock/Blanking
					Blank All  cmdID= 37201  value= 1  "
		::= { iqudc12CmdEntry 37201 }


	iqudc12BlankingHANCVBIBlankingPassAll OBJECT-TYPE
		SYNTAX		INTEGER { noAction(0),val-Pass-All(1) }
		MAX-ACCESS		read-write
		STATUS			current
		DESCRIPTION
				"TYPE: - Button
				 PAGE: - Genlock/Blanking
					Pass All  cmdID= 37202  value= 1  "
		::= { iqudc12CmdEntry 37202 }


	iqudc12BlankingHANCVBIBlankingBlank1 OBJECT-TYPE
		SYNTAX		INTEGER { disable(0), enable(1) }
		MAX-ACCESS		read-write
		STATUS			current
		DESCRIPTION
				"TYPE: - Checkbox
				 PAGE: - Genlock/Blanking
					Blank 1  cmdID= 37210 "
		::= { iqudc12CmdEntry 37210 }


	iqudc12BlankingHANCVBIBlankingBlank2 OBJECT-TYPE
		SYNTAX		INTEGER { disable(0), enable(1) }
		MAX-ACCESS		read-write
		STATUS			current
		DESCRIPTION
				"TYPE: - Checkbox
				 PAGE: - Genlock/Blanking
					Blank 2  cmdID= 37211 "
		::= { iqudc12CmdEntry 37211 }


	iqudc12BlankingHANCVBIBlankingBlank3 OBJECT-TYPE
		SYNTAX		INTEGER { disable(0), enable(1) }
		MAX-ACCESS		read-write
		STATUS			current
		DESCRIPTION
				"TYPE: - Checkbox
				 PAGE: - Genlock/Blanking
					Blank 3  cmdID= 37212 "
		::= { iqudc12CmdEntry 37212 }


	iqudc12BlankingHANCVBIBlankingBlank4 OBJECT-TYPE
		SYNTAX		INTEGER { disable(0), enable(1) }
		MAX-ACCESS		read-write
		STATUS			current
		DESCRIPTION
				"TYPE: - Checkbox
				 PAGE: - Genlock/Blanking
					Blank 4  cmdID= 37213 "
		::= { iqudc12CmdEntry 37213 }


	iqudc12BlankingHANCVBIBlankingBlank5 OBJECT-TYPE
		SYNTAX		INTEGER { disable(0), enable(1) }
		MAX-ACCESS		read-write
		STATUS			current
		DESCRIPTION
				"TYPE: - Checkbox
				 PAGE: - Genlock/Blanking
					Blank 5  cmdID= 37214 "
		::= { iqudc12CmdEntry 37214 }


	iqudc12BlankingHANCVBIBlankingBlank6 OBJECT-TYPE
		SYNTAX		INTEGER { disable(0), enable(1) }
		MAX-ACCESS		read-write
		STATUS			current
		DESCRIPTION
				"TYPE: - Checkbox
				 PAGE: - Genlock/Blanking
					Blank 6  cmdID= 37215 "
		::= { iqudc12CmdEntry 37215 }


	iqudc12BlankingHANCVBIBlankingBlank7 OBJECT-TYPE
		SYNTAX		INTEGER { disable(0), enable(1) }
		MAX-ACCESS		read-write
		STATUS			current
		DESCRIPTION
				"TYPE: - Checkbox
				 PAGE: - Genlock/Blanking
					Blank 7  cmdID= 37216 "
		::= { iqudc12CmdEntry 37216 }


	iqudc12BlankingHANCVBIBlankingBlank8 OBJECT-TYPE
		SYNTAX		INTEGER { disable(0), enable(1) }
		MAX-ACCESS		read-write
		STATUS			current
		DESCRIPTION
				"TYPE: - Checkbox
				 PAGE: - Genlock/Blanking
					Blank 8  cmdID= 37217 "
		::= { iqudc12CmdEntry 37217 }


	iqudc12BlankingHANCVBIBlankingBlank9 OBJECT-TYPE
		SYNTAX		INTEGER { disable(0), enable(1) }
		MAX-ACCESS		read-write
		STATUS			current
		DESCRIPTION
				"TYPE: - Checkbox
				 PAGE: - Genlock/Blanking
					Blank 9  cmdID= 37218 "
		::= { iqudc12CmdEntry 37218 }


	iqudc12BlankingHANCVBIBlankingBlank10 OBJECT-TYPE
		SYNTAX		INTEGER { disable(0), enable(1) }
		MAX-ACCESS		read-write
		STATUS			current
		DESCRIPTION
				"TYPE: - Checkbox
				 PAGE: - Genlock/Blanking
					Blank 10  cmdID= 37219 "
		::= { iqudc12CmdEntry 37219 }


	iqudc12BlankingHANCVBIBlankingBlank11 OBJECT-TYPE
		SYNTAX		INTEGER { disable(0), enable(1) }
		MAX-ACCESS		read-write
		STATUS			current
		DESCRIPTION
				"TYPE: - Checkbox
				 PAGE: - Genlock/Blanking
					Blank 11  cmdID= 37220 "
		::= { iqudc12CmdEntry 37220 }


	iqudc12BlankingHANCVBIBlankingBlank12 OBJECT-TYPE
		SYNTAX		INTEGER { disable(0), enable(1) }
		MAX-ACCESS		read-write
		STATUS			current
		DESCRIPTION
				"TYPE: - Checkbox
				 PAGE: - Genlock/Blanking
					Blank 12  cmdID= 37221 "
		::= { iqudc12CmdEntry 37221 }


	iqudc12BlankingHANCVBIBlankingBlank13 OBJECT-TYPE
		SYNTAX		INTEGER { disable(0), enable(1) }
		MAX-ACCESS		read-write
		STATUS			current
		DESCRIPTION
				"TYPE: - Checkbox
				 PAGE: - Genlock/Blanking
					Blank 13  cmdID= 37222 "
		::= { iqudc12CmdEntry 37222 }


	iqudc12BlankingHANCVBIBlankingBlank14 OBJECT-TYPE
		SYNTAX		INTEGER { disable(0), enable(1) }
		MAX-ACCESS		read-write
		STATUS			current
		DESCRIPTION
				"TYPE: - Checkbox
				 PAGE: - Genlock/Blanking
					Blank 14  cmdID= 37223 "
		::= { iqudc12CmdEntry 37223 }


	iqudc12BlankingHANCVBIBlankingBlank15 OBJECT-TYPE
		SYNTAX		INTEGER { disable(0), enable(1) }
		MAX-ACCESS		read-write
		STATUS			current
		DESCRIPTION
				"TYPE: - Checkbox
				 PAGE: - Genlock/Blanking
					Blank 15  cmdID= 37224 "
		::= { iqudc12CmdEntry 37224 }


	iqudc12BlankingHANCVBIBlankingBlank16 OBJECT-TYPE
		SYNTAX		INTEGER { disable(0), enable(1) }
		MAX-ACCESS		read-write
		STATUS			current
		DESCRIPTION
				"TYPE: - Checkbox
				 PAGE: - Genlock/Blanking
					Blank 16  cmdID= 37225 "
		::= { iqudc12CmdEntry 37225 }


	iqudc12BlankingHANCVBIBlankingBlank17 OBJECT-TYPE
		SYNTAX		INTEGER { disable(0), enable(1) }
		MAX-ACCESS		read-write
		STATUS			current
		DESCRIPTION
				"TYPE: - Checkbox
				 PAGE: - Genlock/Blanking
					Blank 17  cmdID= 37226 "
		::= { iqudc12CmdEntry 37226 }


	iqudc12BlankingHANCVBIBlankingBlank18 OBJECT-TYPE
		SYNTAX		INTEGER { disable(0), enable(1) }
		MAX-ACCESS		read-write
		STATUS			current
		DESCRIPTION
				"TYPE: - Checkbox
				 PAGE: - Genlock/Blanking
					Blank 18  cmdID= 37227 "
		::= { iqudc12CmdEntry 37227 }


	iqudc12BlankingHANCVBIBlankingBlank19 OBJECT-TYPE
		SYNTAX		INTEGER { disable(0), enable(1) }
		MAX-ACCESS		read-write
		STATUS			current
		DESCRIPTION
				"TYPE: - Checkbox
				 PAGE: - Genlock/Blanking
					Blank 19  cmdID= 37228 "
		::= { iqudc12CmdEntry 37228 }


	iqudc12BlankingHANCVBIBlankingBlank20 OBJECT-TYPE
		SYNTAX		INTEGER { disable(0), enable(1) }
		MAX-ACCESS		read-write
		STATUS			current
		DESCRIPTION
				"TYPE: - Checkbox
				 PAGE: - Genlock/Blanking
					Blank 20  cmdID= 37229 "
		::= { iqudc12CmdEntry 37229 }


	iqudc12BlankingHANCVBIBlankingBlank21 OBJECT-TYPE
		SYNTAX		INTEGER { disable(0), enable(1) }
		MAX-ACCESS		read-write
		STATUS			current
		DESCRIPTION
				"TYPE: - Checkbox
				 PAGE: - Genlock/Blanking
					Blank 21  cmdID= 37230 "
		::= { iqudc12CmdEntry 37230 }


	iqudc12BlankingHANCVBIBlankingBlank22 OBJECT-TYPE
		SYNTAX		INTEGER { disable(0), enable(1) }
		MAX-ACCESS		read-write
		STATUS			current
		DESCRIPTION
				"TYPE: - Checkbox
				 PAGE: - Genlock/Blanking
					Blank 22  cmdID= 37231 "
		::= { iqudc12CmdEntry 37231 }


	iqudc12BlankingHANCVBIBlankingBlank23 OBJECT-TYPE
		SYNTAX		INTEGER { disable(0), enable(1) }
		MAX-ACCESS		read-write
		STATUS			current
		DESCRIPTION
				"TYPE: - Checkbox
				 PAGE: - Genlock/Blanking
					Blank 23  cmdID= 37232 "
		::= { iqudc12CmdEntry 37232 }


	iqudc12BlankingHANCVBIBlankingBlank24 OBJECT-TYPE
		SYNTAX		INTEGER { disable(0), enable(1) }
		MAX-ACCESS		read-write
		STATUS			current
		DESCRIPTION
				"TYPE: - Checkbox
				 PAGE: - Genlock/Blanking
					Blank 24  cmdID= 37233 "
		::= { iqudc12CmdEntry 37233 }


	iqudc12BlankingHANCVBIBlankingBlank25 OBJECT-TYPE
		SYNTAX		INTEGER { disable(0), enable(1) }
		MAX-ACCESS		read-write
		STATUS			current
		DESCRIPTION
				"TYPE: - Checkbox
				 PAGE: - Genlock/Blanking
					Blank 25  cmdID= 37234 "
		::= { iqudc12CmdEntry 37234 }


	iqudc12BlankingHANCVBIBlankingBlank26 OBJECT-TYPE
		SYNTAX		INTEGER { disable(0), enable(1) }
		MAX-ACCESS		read-write
		STATUS			current
		DESCRIPTION
				"TYPE: - Checkbox
				 PAGE: - Genlock/Blanking
					Blank 26  cmdID= 37235 "
		::= { iqudc12CmdEntry 37235 }


	iqudc12BlankingHANCVBIBlankingBlank27 OBJECT-TYPE
		SYNTAX		INTEGER { disable(0), enable(1) }
		MAX-ACCESS		read-write
		STATUS			current
		DESCRIPTION
				"TYPE: - Checkbox
				 PAGE: - Genlock/Blanking
					Blank 27  cmdID= 37236 "
		::= { iqudc12CmdEntry 37236 }


	iqudc12BlankingHANCVBIBlankingBlank28 OBJECT-TYPE
		SYNTAX		INTEGER { disable(0), enable(1) }
		MAX-ACCESS		read-write
		STATUS			current
		DESCRIPTION
				"TYPE: - Checkbox
				 PAGE: - Genlock/Blanking
					Blank 28  cmdID= 37237 "
		::= { iqudc12CmdEntry 37237 }


	iqudc12BlankingHANCVBIBlankingBlank29 OBJECT-TYPE
		SYNTAX		INTEGER { disable(0), enable(1) }
		MAX-ACCESS		read-write
		STATUS			current
		DESCRIPTION
				"TYPE: - Checkbox
				 PAGE: - Genlock/Blanking
					Blank 29  cmdID= 37238 "
		::= { iqudc12CmdEntry 37238 }


	iqudc12BlankingHANCVBIBlankingBlank30 OBJECT-TYPE
		SYNTAX		INTEGER { disable(0), enable(1) }
		MAX-ACCESS		read-write
		STATUS			current
		DESCRIPTION
				"TYPE: - Checkbox
				 PAGE: - Genlock/Blanking
					Blank 30  cmdID= 37239 "
		::= { iqudc12CmdEntry 37239 }


	iqudc12BlankingHANCVBIBlankingBlank31 OBJECT-TYPE
		SYNTAX		INTEGER { disable(0), enable(1) }
		MAX-ACCESS		read-write
		STATUS			current
		DESCRIPTION
				"TYPE: - Checkbox
				 PAGE: - Genlock/Blanking
					Blank 31  cmdID= 37240 "
		::= { iqudc12CmdEntry 37240 }


	iqudc12BlankingHANCVBIBlankingBlank32 OBJECT-TYPE
		SYNTAX		INTEGER { disable(0), enable(1) }
		MAX-ACCESS		read-write
		STATUS			current
		DESCRIPTION
				"TYPE: - Checkbox
				 PAGE: - Genlock/Blanking
					Blank 32  cmdID= 37241 "
		::= { iqudc12CmdEntry 37241 }


	iqudc12BlankingHANCVBIBlankingBlank33 OBJECT-TYPE
		SYNTAX		INTEGER { disable(0), enable(1) }
		MAX-ACCESS		read-write
		STATUS			current
		DESCRIPTION
				"TYPE: - Checkbox
				 PAGE: - Genlock/Blanking
					Blank 33  cmdID= 37242 "
		::= { iqudc12CmdEntry 37242 }


	iqudc12BlankingHANCVBIBlankingBlank34 OBJECT-TYPE
		SYNTAX		INTEGER { disable(0), enable(1) }
		MAX-ACCESS		read-write
		STATUS			current
		DESCRIPTION
				"TYPE: - Checkbox
				 PAGE: - Genlock/Blanking
					Blank 34  cmdID= 37243 "
		::= { iqudc12CmdEntry 37243 }


	iqudc12BlankingHANCVBIBlankingBlank35 OBJECT-TYPE
		SYNTAX		INTEGER { disable(0), enable(1) }
		MAX-ACCESS		read-write
		STATUS			current
		DESCRIPTION
				"TYPE: - Checkbox
				 PAGE: - Genlock/Blanking
					Blank 35  cmdID= 37244 "
		::= { iqudc12CmdEntry 37244 }


	iqudc12BlankingHANCVBIBlankingBlank36 OBJECT-TYPE
		SYNTAX		INTEGER { disable(0), enable(1) }
		MAX-ACCESS		read-write
		STATUS			current
		DESCRIPTION
				"TYPE: - Checkbox
				 PAGE: - Genlock/Blanking
					Blank 36  cmdID= 37245 "
		::= { iqudc12CmdEntry 37245 }


	iqudc12BlankingHANCVBIBlankingBlankHANC OBJECT-TYPE
		SYNTAX		INTEGER { disable(0), enable(1) }
		MAX-ACCESS		read-write
		STATUS			current
		DESCRIPTION
				"TYPE: - Checkbox
				 PAGE: - Genlock/Blanking
					Blank HANC  cmdID= 37246 "
		::= { iqudc12CmdEntry 37246 }


	iqudc12MenuWSSCtrlEnableMapper OBJECT-TYPE
		SYNTAX		INTEGER { disable(0), enable(1) }
		MAX-ACCESS		read-write
		STATUS			current
		DESCRIPTION
				"TYPE: - Checkbox
				 PAGE: - WSS Ctrl
					EnableMapper  cmdID= 38747 "
		::= { iqudc12CmdEntry 38747 }


	iqudc12MenuWSSCtrlForceEnable OBJECT-TYPE
		SYNTAX		INTEGER { disable(0), enable(1) }
		MAX-ACCESS		read-write
		STATUS			current
		DESCRIPTION
				"TYPE: - Checkbox
				 PAGE: - WSS Ctrl
					ForceEnable  cmdID= 38749 "
		::= { iqudc12CmdEntry 38749 }


	iqudc12MenuWSSCtrlIPWSSSignal OBJECT-TYPE
		SYNTAX		INTEGER {
							val-4-3-box-16-9-top(2),
							val-4-3-box-14-9-top(3),
							val-4-3-box-16-9ctr(4),
							val-4-3-Coded-Frame(8),
							val-4-3-4-3(9),
							val-4-3-16-9(10),
							val-4-3-14-9(11),
							val-4-3-Reserved-12(12),
							val-4-3-4-3-SP-14-9(13),
							val-4-3-16-9-SP-14-9(14),
							val-4-3-16-9-SP-4-3(15),
							val-4-3-Unknown-All(16),
							val-16-9-box-16-9-top(130),
							val-16-9-box-14-9-top(131),
							val-16-9-box-16-9ctr(132),
							val-16-9-Coded-Frame(136),
							val-16-9-4-3(137),
							val-16-9-16-9(138),
							val-16-9-14-9(139),
							val-16-9-Reserved-12(140),
							val-16-9-4-3-SP-14-9(141),
							val-16-9-16-9-SP14-9(142),
							val-16-9-16-9-SP-4-3(143),
							val-16-9-Unknown-All(144),
							val-AFD-None(145),
							val-Force-Mode-1(146),
							val-Force-Mode-2(147),
							val-Force-Mode-3(148),
							val-Force-Mode-4(149)
							}
		MAX-ACCESS		read-write
		STATUS			current
		DESCRIPTION
				"TYPE: - RadiobuttonList
				 PAGE: - WSS Ctrl
					I/P WSS Signal  cmdID= 38740 
					4:3-box 16:9 top  value= 2  
					4:3-box 14:9 top  value= 3  
					4:3-box>16:9ctr  value= 4  
					4:3-Coded Frame  value= 8  
					4:3-4:3  value= 9  
					4:3-16:9  value= 10  
					4:3-14:9  value= 11  
					4:3 Reserved(12)  value= 12  
					4:3-4:3 SP 14:9  value= 13  
					4:3-16:9 SP 14:9  value= 14  
					4:3-16:9 SP 4:3  value= 15  
					4:3-Unknown(All)  value= 16  
					16:9-box 16:9 top  value= 130  
					16:9-box 14:9 top  value= 131  
					16:9-box>16:9ctr  value= 132  
					16:9-Coded Frame  value= 136  
					16:9-4:3  value= 137  
					16:9-16:9  value= 138  
					16:9-14:9  value= 139  
					16:9 Reserved(12)  value= 140  
					16:9-4:3 SP 14:9  value= 141  
					16:9-16:9 SP14:9  value= 142  
					16:9-16:9 SP 4:3  value= 143  
					16:9-Unknown(All)  value= 144  
					AFD None  value= 145  
					Force Mode-1  value= 146  
					Force Mode-2  value= 147  
					Force Mode-3  value= 148  
					Force Mode-4  value= 149  "
		::= { iqudc12CmdEntry 38740 }


	iqudc12MenuWSSCtrlOPWSS43 OBJECT-TYPE
		SYNTAX		INTEGER {
							val-4-3-box-16-9-top(2),
							val-4-3-box-14-9-top(3),
							val-4-3-box-16-9ctr(4),
							val-4-3-Coded-Frame(8),
							val-4-3-4-3(9),
							val-4-3-16-9(10),
							val-4-3-14-9(11),
							val-4-3-reserved-12(12),
							val-4-3-4-3-SP-14-9(13),
							val-4-3-16-9-SP14-9(14),
							val-4-3-16-9-SP-4-3(15),
							val-16-9-box-16-9-top(130),
							val-16-9-box-14-9-top(131),
							val-16-9-box-16-9ctr(132),
							val-16-9-Coded-Frame(136),
							val-16-9-4-3(137),
							val-16-9-16-9(138),
							val-16-9-14-9(139),
							val-16-9-reserved-12(140),
							val-16-9-4-3-SP-14-9(141),
							val-16-9-16-9-SP14-9(142),
							val-16-9-16-9-SP-4-3(143),
							val-Delete(145)
							}
		MAX-ACCESS		read-write
		STATUS			current
		DESCRIPTION
				"TYPE: - RadiobuttonList
				 PAGE: - WSS Ctrl
					O/P WSS 4:3  cmdID= 38745 
					4:3-box 16:9 top  value= 2  
					4:3-box 14:9 top  value= 3  
					4:3-box>16:9ctr  value= 4  
					4:3-Coded Frame  value= 8  
					4:3-4:3  value= 9  
					4:3-16:9  value= 10  
					4:3-14:9  value= 11  
					4:3-reserved-12  value= 12  
					4:3-4:3 SP 14:9  value= 13  
					4:3-16:9 SP14:9  value= 14  
					4:3-16:9 SP 4:3  value= 15  
					16:9-box 16:9 top  value= 130  
					16:9-box 14:9 top  value= 131  
					16:9-box>16:9ctr  value= 132  
					16:9-Coded Frame  value= 136  
					16:9-4:3  value= 137  
					16:9-16:9  value= 138  
					16:9-14:9  value= 139  
					16:9-reserved-12  value= 140  
					16:9-4:3 SP 14:9  value= 141  
					16:9-16:9 SP14:9  value= 142  
					16:9-16:9 SP 4:3  value= 143  
					Delete  value= 145  "
		::= { iqudc12CmdEntry 38745 }


	iqudc12MenuWSSCtrlDispMem43 OBJECT-TYPE
		SYNTAX		INTEGER {
							val-No-Change(0),
							val-Display-Memory-1(1),
							val-Display-Memory-2(2),
							val-Display-Memory-3(3),
							val-Display-Memory-4(4),
							val-Display-Memory-5(5),
							val-Display-Memory-6(6),
							val-Display-Memory-7(7),
							val-Display-Memory-8(8),
							val-Display-Memory-9(9),
							val-Display-Memory-10(10),
							val-Display-Memory-11(11),
							val-Display-Memory-12(12),
							val-Display-Memory-13(13),
							val-Display-Memory-14(14),
							val-Display-Memory-15(15),
							val-Display-Memory-16(16),
							val-Display-Memory-17(17),
							val-Display-Memory-18(18),
							val-Display-Memory-19(19),
							val-Display-Memory-20(20),
							val-Display-Memory-21(21),
							val-Display-Memory-22(22),
							val-Display-Memory-23(23),
							val-Display-Memory-24(24),
							val-Display-Memory-25(25),
							val-Display-Memory-26(26),
							val-Display-Memory-27(27),
							val-Display-Memory-28(28),
							val-Display-Memory-29(29),
							val-Display-Memory-30(30),
							val-Display-Memory-31(31),
							val-Display-Memory-32(32)
							}
		MAX-ACCESS		read-write
		STATUS			current
		DESCRIPTION
				"TYPE: - RadiobuttonList
				 PAGE: - WSS Ctrl
					Disp Mem 4:3  cmdID= 38748 
					No Change  value= 0  
					Display Memory 1  value= 1  
					Display Memory 2  value= 2  
					Display Memory 3  value= 3  
					Display Memory 4  value= 4  
					Display Memory 5  value= 5  
					Display Memory 6  value= 6  
					Display Memory 7  value= 7  
					Display Memory 8  value= 8  
					Display Memory 9  value= 9  
					Display Memory 10  value= 10  
					Display Memory 11  value= 11  
					Display Memory 12  value= 12  
					Display Memory 13  value= 13  
					Display Memory 14  value= 14  
					Display Memory 15  value= 15  
					Display Memory 16  value= 16  
					Display Memory 17  value= 17  
					Display Memory 18  value= 18  
					Display Memory 19  value= 19  
					Display Memory 20  value= 20  
					Display Memory 21  value= 21  
					Display Memory 22  value= 22  
					Display Memory 23  value= 23  
					Display Memory 24  value= 24  
					Display Memory 25  value= 25  
					Display Memory 26  value= 26  
					Display Memory 27  value= 27  
					Display Memory 28  value= 28  
					Display Memory 29  value= 29  
					Display Memory 30  value= 30  
					Display Memory 31  value= 31  
					Display Memory 32  value= 32  "
		::= { iqudc12CmdEntry 38748 }


	iqudc12WSSCtrlWidescreenIP2016 OBJECT-TYPE
		SYNTAX		INTEGER { disable(0), enable(1) }
		MAX-ACCESS		read-write
		STATUS			current
		DESCRIPTION
				"TYPE: - Checkbox
				 PAGE: - WSS Ctrl
					2016  cmdID= 38724 "
		::= { iqudc12CmdEntry 38724 }


	iqudc12WSSCtrlWidescreenIPPriority OBJECT-TYPE
		SYNTAX		INTEGER {
							val-WSS(0),
							val-VI(1)
							}
		MAX-ACCESS		read-write
		STATUS			current
		DESCRIPTION
				"TYPE: - RadiobuttonList
				 PAGE: - WSS Ctrl
					Priority  cmdID= 38750 
					WSS  value= 0  
					VI  value= 1  "
		::= { iqudc12CmdEntry 38750 }


	iqudc12WSSCtrlWidescreenIPWSSInEnable OBJECT-TYPE
		SYNTAX		INTEGER {
							val-Off(0),
							val-WSS-AFD(1),
							val-WSS-ETSI(2)
							}
		MAX-ACCESS		read-write
		STATUS			current
		DESCRIPTION
				"TYPE: - RadiobuttonList
				 PAGE: - WSS Ctrl
					WSS In Enable  cmdID= 38720 
					Off  value= 0  
					WSS AFD  value= 1  
					WSS ETSI  value= 2  "
		::= { iqudc12CmdEntry 38720 }


	iqudc12WSSCtrlWidescreenIPVIInEnable OBJECT-TYPE
		SYNTAX		INTEGER {
							val-Off(0),
							val-VI-SMPTE(1),
							val-VI-AFD(2),
							val-VI-AFD-2008(3)
							}
		MAX-ACCESS		read-write
		STATUS			current
		DESCRIPTION
				"TYPE: - RadiobuttonList
				 PAGE: - WSS Ctrl
					VI In Enable  cmdID= 38723 
					Off  value= 0  
					VI SMPTE  value= 1  
					VI AFD  value= 2  
					VI AFD 2008  value= 3  "
		::= { iqudc12CmdEntry 38723 }


	iqudc12WSSCtrlWidescreenOP2016 OBJECT-TYPE
		SYNTAX		INTEGER { disable(0), enable(1) }
		MAX-ACCESS		read-write
		STATUS			current
		DESCRIPTION
				"TYPE: - Checkbox
				 PAGE: - WSS Ctrl
					2016  cmdID= 38734 "
		::= { iqudc12CmdEntry 38734 }


	iqudc12WSSCtrlWidescreenOPWSSOutEnable OBJECT-TYPE
		SYNTAX		INTEGER {
							val-Off(0),
							val-WSS-AFD(1),
							val-WSS-ETSI(2)
							}
		MAX-ACCESS		read-write
		STATUS			current
		DESCRIPTION
				"TYPE: - RadiobuttonList
				 PAGE: - WSS Ctrl
					WSS Out Enable  cmdID= 38730 
					Off  value= 0  
					WSS AFD  value= 1  
					WSS ETSI  value= 2  "
		::= { iqudc12CmdEntry 38730 }


	iqudc12WSSCtrlWidescreenOPVIOutEnable OBJECT-TYPE
		SYNTAX		INTEGER {
							val-Off(0),
							val-VI-SMPTE(1),
							val-VI-AFD(2),
							val-VI-AFD-2008(3)
							}
		MAX-ACCESS		read-write
		STATUS			current
		DESCRIPTION
				"TYPE: - RadiobuttonList
				 PAGE: - WSS Ctrl
					VI Out Enable  cmdID= 38733 
					Off  value= 0  
					VI SMPTE  value= 1  
					VI AFD  value= 2  
					VI AFD 2008  value= 3  "
		::= { iqudc12CmdEntry 38733 }


	iqudc12MenuWSSCtrlLine1ReadAFD OBJECT-TYPE
		SYNTAX		RollCallString
		MAX-ACCESS		read-only
		STATUS			current
		DESCRIPTION
				"TYPE: - Display
				 PAGE: - WSS Ctrl
					Line1 Read AFD  cmdID= 39002  format=   "
		::= { iqudc12CmdEntry 39002 }


	iqudc12MenuWSSCtrlLine1ReadAR OBJECT-TYPE
		SYNTAX		RollCallString
		MAX-ACCESS		read-only
		STATUS			current
		DESCRIPTION
				"TYPE: - Display
				 PAGE: - WSS Ctrl
					Line1 Read AR  cmdID= 39003  format=   "
		::= { iqudc12CmdEntry 39003 }


	iqudc12MenuWSSCtrlLine1WriteAFD OBJECT-TYPE
		SYNTAX		RollCallString
		MAX-ACCESS		read-only
		STATUS			current
		DESCRIPTION
				"TYPE: - Display
				 PAGE: - WSS Ctrl
					Line1 Write AFD  cmdID= 39010  format=   "
		::= { iqudc12CmdEntry 39010 }


	iqudc12MenuWSSCtrlLine1WriteAR OBJECT-TYPE
		SYNTAX		RollCallString
		MAX-ACCESS		read-only
		STATUS			current
		DESCRIPTION
				"TYPE: - Display
				 PAGE: - WSS Ctrl
					Line1 Write AR  cmdID= 39011  format=   "
		::= { iqudc12CmdEntry 39011 }


	iqudc12MenuWSSCtrlPreset OBJECT-TYPE
		SYNTAX		INTEGER { noAction(0),val-Preset(1) }
		MAX-ACCESS		read-write
		STATUS			current
		DESCRIPTION
				"TYPE: - Button
				 PAGE: - WSS Ctrl
					Preset  cmdID= 39075  value= 1  "
		::= { iqudc12CmdEntry 39075 }


	iqudc12MenuWSSCtrlPreset43 OBJECT-TYPE
		SYNTAX		INTEGER { noAction(0),val-Preset4-3(1) }
		MAX-ACCESS		read-write
		STATUS			current
		DESCRIPTION
				"TYPE: - Button
				 PAGE: - WSS Ctrl
					Preset4:3  cmdID= 39076  value= 1  "
		::= { iqudc12CmdEntry 39076 }


	iqudc12MenuWSSCtrlPreset169 OBJECT-TYPE
		SYNTAX		INTEGER { noAction(0),val-Preset16-9(1) }
		MAX-ACCESS		read-write
		STATUS			current
		DESCRIPTION
				"TYPE: - Button
				 PAGE: - WSS Ctrl
					Preset16:9  cmdID= 39077  value= 1  "
		::= { iqudc12CmdEntry 39077 }


	iqudc12MenuWSSCtrlBlank62523 OBJECT-TYPE
		SYNTAX		INTEGER { disable(0), enable(1) }
		MAX-ACCESS		read-write
		STATUS			current
		DESCRIPTION
				"TYPE: - Checkbox
				 PAGE: - WSS Ctrl
					Blank625_23  cmdID= 43228 "
		::= { iqudc12CmdEntry 43228 }


	iqudc12MenuWSSCtrlBlank625336 OBJECT-TYPE
		SYNTAX		INTEGER { disable(0), enable(1) }
		MAX-ACCESS		read-write
		STATUS			current
		DESCRIPTION
				"TYPE: - Checkbox
				 PAGE: - WSS Ctrl
					Blank625_336  cmdID= 43229 "
		::= { iqudc12CmdEntry 43229 }


	iqudc12MenuWSSCtrlBlank52521 OBJECT-TYPE
		SYNTAX		INTEGER { disable(0), enable(1) }
		MAX-ACCESS		read-write
		STATUS			current
		DESCRIPTION
				"TYPE: - Checkbox
				 PAGE: - WSS Ctrl
					Blank525_21  cmdID= 43230 "
		::= { iqudc12CmdEntry 43230 }


	iqudc12MenuWSSCtrlBlank52522 OBJECT-TYPE
		SYNTAX		INTEGER { disable(0), enable(1) }
		MAX-ACCESS		read-write
		STATUS			current
		DESCRIPTION
				"TYPE: - Checkbox
				 PAGE: - WSS Ctrl
					Blank525_22  cmdID= 43231 "
		::= { iqudc12CmdEntry 43231 }


	iqudc12MenuWSSCtrlBlank525283 OBJECT-TYPE
		SYNTAX		INTEGER { disable(0), enable(1) }
		MAX-ACCESS		read-write
		STATUS			current
		DESCRIPTION
				"TYPE: - Checkbox
				 PAGE: - WSS Ctrl
					Blank525_283  cmdID= 43232 "
		::= { iqudc12CmdEntry 43232 }


	iqudc12MenuWSSCtrlBlank525284 OBJECT-TYPE
		SYNTAX		INTEGER { disable(0), enable(1) }
		MAX-ACCESS		read-write
		STATUS			current
		DESCRIPTION
				"TYPE: - Checkbox
				 PAGE: - WSS Ctrl
					Blank525_284  cmdID= 43233 "
		::= { iqudc12CmdEntry 43233 }


	iqudc12AncillaryDataSMPTE20162016IPF1Status OBJECT-TYPE
		SYNTAX		RollCallString
		MAX-ACCESS		read-only
		STATUS			current
		DESCRIPTION
				"TYPE: - Display
				 PAGE: - Ancillary Data
					2016 I/P F1 Status  cmdID= 42706  format=   "
		::= { iqudc12CmdEntry 42706 }


	iqudc12AncillaryDataSMPTE20162016OPF1Line OBJECT-TYPE
		SYNTAX		INTEGER
		MAX-ACCESS		read-write
		STATUS			current
		DESCRIPTION
				"TYPE: - Number
				 PAGE: - Ancillary Data
					2016 O/P F1 Line  cmdID= 42707  min= 2  max= 33  step= 1  format= Line %0.0f  div_scale= 1 
					Min = Line 2  Max = Line 33  Step = Line 1 "
		::= { iqudc12CmdEntry 42707 }


	iqudc12AncillaryDataSMPTE20162016Follow OBJECT-TYPE
		SYNTAX		INTEGER { disable(0), enable(1) }
		MAX-ACCESS		read-write
		STATUS			current
		DESCRIPTION
				"TYPE: - Checkbox
				 PAGE: - Ancillary Data
					2016 Follow  cmdID= 42729 "
		::= { iqudc12CmdEntry 42729 }


	iqudc12AncillaryDataSDVBILine7 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 7  cmdID= 42708 
					Off  value= 0  
					VITC Out  value= 3  
					WST  value= 4  "
		::= { iqudc12CmdEntry 42708 }


	iqudc12AncillaryDataSDVBILine8 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 8  cmdID= 42709 
					Off  value= 0  
					VITC Out  value= 3  
					WST  value= 4  "
		::= { iqudc12CmdEntry 42709 }


	iqudc12AncillaryDataSDVBILine9 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 9  cmdID= 42710 
					Off  value= 0  
					VITC Out  value= 3  
					WST  value= 4  "
		::= { iqudc12CmdEntry 42710 }


	iqudc12AncillaryDataSDVBILine10 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 10  cmdID= 42711 
					Off  value= 0  
					VITC Out  value= 3  
					WST  value= 4  "
		::= { iqudc12CmdEntry 42711 }


	iqudc12AncillaryDataSDVBILine11 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 11  cmdID= 42712 
					Off  value= 0  
					VITC Out  value= 3  
					WST  value= 4  "
		::= { iqudc12CmdEntry 42712 }


	iqudc12AncillaryDataSDVBILine12 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 12  cmdID= 42713 
					Off  value= 0  
					VITC Out  value= 3  
					WST  value= 4  "
		::= { iqudc12CmdEntry 42713 }


	iqudc12AncillaryDataSDVBILine13 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 13  cmdID= 42714 
					Off  value= 0  
					VITC Out  value= 3  
					WST  value= 4  "
		::= { iqudc12CmdEntry 42714 }


	iqudc12AncillaryDataSDVBILine14 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 14  cmdID= 42715 
					Off  value= 0  
					VITC Out  value= 3  
					WST  value= 4  "
		::= { iqudc12CmdEntry 42715 }


	iqudc12AncillaryDataSDVBILine15 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 15  cmdID= 42716 
					Off  value= 0  
					VITC Out  value= 3  
					WST  value= 4  "
		::= { iqudc12CmdEntry 42716 }


	iqudc12AncillaryDataSDVBILine16 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 16  cmdID= 42717 
					Off  value= 0  
					VITC Out  value= 3  
					WST  value= 4  "
		::= { iqudc12CmdEntry 42717 }


	iqudc12AncillaryDataSDVBILine17 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 17  cmdID= 42718 
					Off  value= 0  
					VITC Out  value= 3  
					WST  value= 4  "
		::= { iqudc12CmdEntry 42718 }


	iqudc12AncillaryDataSDVBILine18 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 18  cmdID= 42719 
					Off  value= 0  
					VITC Out  value= 3  
					WST  value= 4  "
		::= { iqudc12CmdEntry 42719 }


	iqudc12AncillaryDataSDVBILine19 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 19  cmdID= 42720 
					Off  value= 0  
					VITC Out  value= 3  
					WST  value= 4  "
		::= { iqudc12CmdEntry 42720 }


	iqudc12AncillaryDataSDVBILine20 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 20  cmdID= 42721 
					Off  value= 0  
					VITC Out  value= 3  
					WST  value= 4  "
		::= { iqudc12CmdEntry 42721 }


	iqudc12AncillaryDataSDVBILine21 OBJECT-TYPE
		SYNTAX		INTEGER {
							val-Off(0),
							val-VITC-Out(3),
							val-WST(4),
							val-CC608-525(5)
							}
		MAX-ACCESS		read-write
		STATUS			current
		DESCRIPTION
				"TYPE: - RadiobuttonList
				 PAGE: - Ancillary Data
					Line 21  cmdID= 42722 
					Off  value= 0  
					VITC Out  value= 3  
					WST  value= 4  
					CC608 525  value= 5  "
		::= { iqudc12CmdEntry 42722 }


	iqudc12AncillaryDataSDVBILine22 OBJECT-TYPE
		SYNTAX		INTEGER {
							val-Off(0),
							val-VITC-Out(3),
							val-WST(4)
							}
		MAX-ACCESS		read-write
		STATUS			current
		DESCRIPTION
				"TYPE: - RadiobuttonList
				 PAGE: - Ancillary Data
					Line 22  cmdID= 42723 
					Off  value= 0  
					VITC Out  value= 3  
					WST  value= 4  "
		::= { iqudc12CmdEntry 42723 }


	iqudc12AncillaryDataSDVBILine23 OBJECT-TYPE
		SYNTAX		INTEGER {
							val-Off(0),
							val-WSS-625(2)
							}
		MAX-ACCESS		read-write
		STATUS			current
		DESCRIPTION
				"TYPE: - RadiobuttonList
				 PAGE: - Ancillary Data
					Line 23  cmdID= 42724 
					Off  value= 0  
					WSS 625  value= 2  "
		::= { iqudc12CmdEntry 42724 }


	iqudc12AncillaryDataSDVBIVIout OBJECT-TYPE
		SYNTAX		INTEGER {
							val-Line-11(11),
							val-Line-14(14),
							val-NotUsed(0)
							}
		MAX-ACCESS		read-write
		STATUS			current
		DESCRIPTION
				"TYPE: - RadiobuttonList
				 PAGE: - Ancillary Data
					VI out  cmdID= 37247 
					Line 11  value= 11  
					Line 14  value= 14  
					NotUsed  value= 0  "
		::= { iqudc12CmdEntry 37247 }


	iqudc12AncillaryDataSDVBIVIIPStatus OBJECT-TYPE
		SYNTAX		INTEGER { disable(0), enable(1) }
		MAX-ACCESS		read-write
		STATUS			current
		DESCRIPTION
				"TYPE: - Checkbox
				 PAGE: - Ancillary Data
					VI I/P Status  cmdID= 42744 "
		::= { iqudc12CmdEntry 42744 }


	iqudc12AncillaryDataSDVBIWSSIPStatus OBJECT-TYPE
		SYNTAX		INTEGER { disable(0), enable(1) }
		MAX-ACCESS		read-write
		STATUS			current
		DESCRIPTION
				"TYPE: - Checkbox
				 PAGE: - Ancillary Data
					WSS I/P Status  cmdID= 42740 "
		::= { iqudc12CmdEntry 42740 }


	iqudc12AncillaryDataSDVBIVITCIPStatus OBJECT-TYPE
		SYNTAX		INTEGER { disable(0), enable(1) }
		MAX-ACCESS		read-write
		STATUS			current
		DESCRIPTION
				"TYPE: - Checkbox
				 PAGE: - Ancillary Data
					VITC I/P Status  cmdID= 42742 "
		::= { iqudc12CmdEntry 42742 }


	iqudc12AncillaryDataSDVBIWSTIPStatus OBJECT-TYPE
		SYNTAX		INTEGER { disable(0), enable(1) }
		MAX-ACCESS		read-write
		STATUS			current
		DESCRIPTION
				"TYPE: - Checkbox
				 PAGE: - Ancillary Data
					WST I/P Status  cmdID= 42741 "
		::= { iqudc12CmdEntry 42741 }


	iqudc12AncillaryDataSDVBICC608IPStatus OBJECT-TYPE
		SYNTAX		INTEGER { disable(0), enable(1) }
		MAX-ACCESS		read-write
		STATUS			current
		DESCRIPTION
				"TYPE: - Checkbox
				 PAGE: - Ancillary Data
					CC608 I/P Status  cmdID= 42743 "
		::= { iqudc12CmdEntry 42743 }


	iqudc12AncillaryDataSDVBIWSTLine7 OBJECT-TYPE
		SYNTAX		RollCallString
		MAX-ACCESS		read-only
		STATUS			current
		DESCRIPTION
				"TYPE: - Display
				 PAGE: - Ancillary Data
					WST Line 7  cmdID= 42745  format=   "
		::= { iqudc12CmdEntry 42745 }


	iqudc12AncillaryDataSDVBIWSTLine8 OBJECT-TYPE
		SYNTAX		RollCallString
		MAX-ACCESS		read-only
		STATUS			current
		DESCRIPTION
				"TYPE: - Display
				 PAGE: - Ancillary Data
					WST Line 8  cmdID= 42746  format=   "
		::= { iqudc12CmdEntry 42746 }


	iqudc12AncillaryDataSDVBIWSTLine9 OBJECT-TYPE
		SYNTAX		RollCallString
		MAX-ACCESS		read-only
		STATUS			current
		DESCRIPTION
				"TYPE: - Display
				 PAGE: - Ancillary Data
					WST Line 9  cmdID= 42747  format=   "
		::= { iqudc12CmdEntry 42747 }


	iqudc12AncillaryDataSDVBIWSTLine10 OBJECT-TYPE
		SYNTAX		RollCallString
		MAX-ACCESS		read-only
		STATUS			current
		DESCRIPTION
				"TYPE: - Display
				 PAGE: - Ancillary Data
					WST Line 10  cmdID= 42748  format=   "
		::= { iqudc12CmdEntry 42748 }


	iqudc12AncillaryDataSDVBIWSTLine11 OBJECT-TYPE
		SYNTAX		RollCallString
		MAX-ACCESS		read-only
		STATUS			current
		DESCRIPTION
				"TYPE: - Display
				 PAGE: - Ancillary Data
					WST Line 11  cmdID= 42749  format=   "
		::= { iqudc12CmdEntry 42749 }


	iqudc12AncillaryDataSDVBIWSTLine12 OBJECT-TYPE
		SYNTAX		RollCallString
		MAX-ACCESS		read-only
		STATUS			current
		DESCRIPTION
				"TYPE: - Display
				 PAGE: - Ancillary Data
					WST Line 12  cmdID= 42750  format=   "
		::= { iqudc12CmdEntry 42750 }


	iqudc12AncillaryDataSDVBIWSTLine13 OBJECT-TYPE
		SYNTAX		RollCallString
		MAX-ACCESS		read-only
		STATUS			current
		DESCRIPTION
				"TYPE: - Display
				 PAGE: - Ancillary Data
					WST Line 13  cmdID= 42751  format=   "
		::= { iqudc12CmdEntry 42751 }


	iqudc12AncillaryDataSDVBIWSTLine14 OBJECT-TYPE
		SYNTAX		RollCallString
		MAX-ACCESS		read-only
		STATUS			current
		DESCRIPTION
				"TYPE: - Display
				 PAGE: - Ancillary Data
					WST Line 14  cmdID= 42752  format=   "
		::= { iqudc12CmdEntry 42752 }


	iqudc12AncillaryDataSDVBIWSTLine15 OBJECT-TYPE
		SYNTAX		RollCallString
		MAX-ACCESS		read-only
		STATUS			current
		DESCRIPTION
				"TYPE: - Display
				 PAGE: - Ancillary Data
					WST Line 15  cmdID= 42753  format=   "
		::= { iqudc12CmdEntry 42753 }


	iqudc12AncillaryDataSDVBIWSTLine16 OBJECT-TYPE
		SYNTAX		RollCallString
		MAX-ACCESS		read-only
		STATUS			current
		DESCRIPTION
				"TYPE: - Display
				 PAGE: - Ancillary Data
					WST Line 16  cmdID= 42754  format=   "
		::= { iqudc12CmdEntry 42754 }


	iqudc12AncillaryDataSDVBIWSTLine17 OBJECT-TYPE
		SYNTAX		RollCallString
		MAX-ACCESS		read-only
		STATUS			current
		DESCRIPTION
				"TYPE: - Display
				 PAGE: - Ancillary Data
					WST Line 17  cmdID= 42755  format=   "
		::= { iqudc12CmdEntry 42755 }


	iqudc12AncillaryDataSDVBIWSTLine18 OBJECT-TYPE
		SYNTAX		RollCallString
		MAX-ACCESS		read-only
		STATUS			current
		DESCRIPTION
				"TYPE: - Display
				 PAGE: - Ancillary Data
					WST Line 18  cmdID= 42756  format=   "
		::= { iqudc12CmdEntry 42756 }


	iqudc12AncillaryDataSDVBIWSTLine19 OBJECT-TYPE
		SYNTAX		RollCallString
		MAX-ACCESS		read-only
		STATUS			current
		DESCRIPTION
				"TYPE: - Display
				 PAGE: - Ancillary Data
					WST Line 19  cmdID= 42757  format=   "
		::= { iqudc12CmdEntry 42757 }


	iqudc12AncillaryDataSDVBIWSTLine20 OBJECT-TYPE
		SYNTAX		RollCallString
		MAX-ACCESS		read-only
		STATUS			current
		DESCRIPTION
				"TYPE: - Display
				 PAGE: - Ancillary Data
					WST Line 20  cmdID= 42758  format=   "
		::= { iqudc12CmdEntry 42758 }


	iqudc12AncillaryDataSDVBIWSTLine21 OBJECT-TYPE
		SYNTAX		RollCallString
		MAX-ACCESS		read-only
		STATUS			current
		DESCRIPTION
				"TYPE: - Display
				 PAGE: - Ancillary Data
					WST Line 21  cmdID= 42759  format=   "
		::= { iqudc12CmdEntry 42759 }


	iqudc12AncillaryDataSDVBIWSTLine22 OBJECT-TYPE
		SYNTAX		RollCallString
		MAX-ACCESS		read-only
		STATUS			current
		DESCRIPTION
				"TYPE: - Display
				 PAGE: - Ancillary Data
					WST Line 22  cmdID= 42760  format=   "
		::= { iqudc12CmdEntry 42760 }


	iqudc12HDVANCHDCaptionHDCaptionEnable OBJECT-TYPE
		SYNTAX		INTEGER { disable(0), enable(1) }
		MAX-ACCESS		read-write
		STATUS			current
		DESCRIPTION
				"TYPE: - Checkbox
				 PAGE: - Ancillary Data
					HD Caption Enable  cmdID= 42701 "
		::= { iqudc12CmdEntry 42701 }


	iqudc12HDVANCHDCaptionHDCaptionIPLine OBJECT-TYPE
		SYNTAX		RollCallString
		MAX-ACCESS		read-only
		STATUS			current
		DESCRIPTION
				"TYPE: - Display
				 PAGE: - Ancillary Data
					HD Caption I/P Line  cmdID= 42726  format=   "
		::= { iqudc12CmdEntry 42726 }


	iqudc12HDVANCHDCaptionHDCaptionOPLine OBJECT-TYPE
		SYNTAX		INTEGER
		MAX-ACCESS		read-write
		STATUS			current
		DESCRIPTION
				"TYPE: - Number
				 PAGE: - Ancillary Data
					HD Caption O/P Line  cmdID= 42725  min= 2  max= 33  step= 1  format= Line %0.0f  div_scale= 1 
					Min = Line 2  Max = Line 33  Step = Line 1 "
		::= { iqudc12CmdEntry 42725 }


	iqudc12HDVANCHDCaptionHDFollowIPLine OBJECT-TYPE
		SYNTAX		INTEGER { disable(0), enable(1) }
		MAX-ACCESS		read-write
		STATUS			current
		DESCRIPTION
				"TYPE: - Checkbox
				 PAGE: - Ancillary Data
					HD Follow I/P Line  cmdID= 42700 "
		::= { iqudc12CmdEntry 42700 }


	iqudc12HDVANCHDCaptionAllowMultipleOP47 OBJECT-TYPE
		SYNTAX		INTEGER { disable(0), enable(1) }
		MAX-ACCESS		read-write
		STATUS			current
		DESCRIPTION
				"TYPE: - Checkbox
				 PAGE: - Ancillary Data
					AllowMultiple OP47  cmdID= 42702 "
		::= { iqudc12CmdEntry 42702 }


	iqudc12HDCaptionOP47Packet2HDCaptionIPLine OBJECT-TYPE
		SYNTAX		RollCallString
		MAX-ACCESS		read-only
		STATUS			current
		DESCRIPTION
				"TYPE: - Display
				 PAGE: - Ancillary Data
					HD Caption I/P Line  cmdID= 42727  format=   "
		::= { iqudc12CmdEntry 42727 }


	iqudc12HDCaptionOP47Packet2HDCaptionOPLine OBJECT-TYPE
		SYNTAX		INTEGER
		MAX-ACCESS		read-write
		STATUS			current
		DESCRIPTION
				"TYPE: - Number
				 PAGE: - Ancillary Data
					HD Caption O/P Line  cmdID= 42731  min= 2  max= 33  step= 1  format= Line %0.0f  div_scale= 1 
					Min = Line 2  Max = Line 33  Step = Line 1 "
		::= { iqudc12CmdEntry 42731 }


	iqudc12HDCaptionOP47Packet3HDCaptionIPLine OBJECT-TYPE
		SYNTAX		RollCallString
		MAX-ACCESS		read-only
		STATUS			current
		DESCRIPTION
				"TYPE: - Display
				 PAGE: - Ancillary Data
					HD Caption I/P Line  cmdID= 42728  format=   "
		::= { iqudc12CmdEntry 42728 }


	iqudc12HDCaptionOP47Packet3HDCaptionOPLine OBJECT-TYPE
		SYNTAX		INTEGER
		MAX-ACCESS		read-write
		STATUS			current
		DESCRIPTION
				"TYPE: - Number
				 PAGE: - Ancillary Data
					HD Caption O/P Line  cmdID= 42732  min= 2  max= 33  step= 1  format= Line %0.0f  div_scale= 1 
					Min = Line 2  Max = Line 33  Step = Line 1 "
		::= { iqudc12CmdEntry 42732 }


	iqudc12TimecodeInputSelectRefVITCInp OBJECT-TYPE
		SYNTAX		INTEGER { disable(0), enable(1) }
		MAX-ACCESS		read-write
		STATUS			current
		DESCRIPTION
				"TYPE: - Checkbox
				 PAGE: - Timecode
					Select Ref VITC Inp  cmdID= 31036 "
		::= { iqudc12CmdEntry 31036 }


	iqudc12TimecodeInputRefVITCStatus OBJECT-TYPE
		SYNTAX		RollCallString
		MAX-ACCESS		read-only
		STATUS			current
		DESCRIPTION
				"TYPE: - Display
				 PAGE: - Timecode
					Ref VITC Status  cmdID= 31000  format=   "
		::= { iqudc12CmdEntry 31000 }


	iqudc12TimecodeInputSelectInpVITCInp OBJECT-TYPE
		SYNTAX		INTEGER { disable(0), enable(1) }
		MAX-ACCESS		read-write
		STATUS			current
		DESCRIPTION
				"TYPE: - Checkbox
				 PAGE: - Timecode
					Select Inp VITC Inp  cmdID= 31037 "
		::= { iqudc12CmdEntry 31037 }


	iqudc12TimecodeInputInputVITCStatus OBJECT-TYPE
		SYNTAX		RollCallString
		MAX-ACCESS		read-only
		STATUS			current
		DESCRIPTION
				"TYPE: - Display
				 PAGE: - Timecode
					Input VITC Status  cmdID= 31001  format=   "
		::= { iqudc12CmdEntry 31001 }


	iqudc12TimecodeInputSelectATCLTCInpu OBJECT-TYPE
		SYNTAX		INTEGER { disable(0), enable(1) }
		MAX-ACCESS		read-write
		STATUS			current
		DESCRIPTION
				"TYPE: - Checkbox
				 PAGE: - Timecode
					Select ATC-LTC Inpu  cmdID= 31038 "
		::= { iqudc12CmdEntry 31038 }


	iqudc12TimecodeInputInputATCLTCStatu OBJECT-TYPE
		SYNTAX		RollCallString
		MAX-ACCESS		read-only
		STATUS			current
		DESCRIPTION
				"TYPE: - Display
				 PAGE: - Timecode
					Input ATC-LTC Statu  cmdID= 31002  format=   "
		::= { iqudc12CmdEntry 31002 }


	iqudc12TimecodeInputInputATCLTCLine OBJECT-TYPE
		SYNTAX		RollCallString
		MAX-ACCESS		read-only
		STATUS			current
		DESCRIPTION
				"TYPE: - Display
				 PAGE: - Timecode
					Input ATC-LTC Line  cmdID= 31006  format=   "
		::= { iqudc12CmdEntry 31006 }


	iqudc12TimecodeInputSelectATCVITCInp OBJECT-TYPE
		SYNTAX		INTEGER { disable(0), enable(1) }
		MAX-ACCESS		read-write
		STATUS			current
		DESCRIPTION
				"TYPE: - Checkbox
				 PAGE: - Timecode
					Select ATC-VITC Inp  cmdID= 31039 "
		::= { iqudc12CmdEntry 31039 }


	iqudc12TimecodeInputInputATCVITCStat OBJECT-TYPE
		SYNTAX		RollCallString
		MAX-ACCESS		read-only
		STATUS			current
		DESCRIPTION
				"TYPE: - Display
				 PAGE: - Timecode
					Input ATC-VITC Stat  cmdID= 31003  format=   "
		::= { iqudc12CmdEntry 31003 }


	iqudc12TimecodeInputIPHDATCVITCLin OBJECT-TYPE
		SYNTAX		RollCallString
		MAX-ACCESS		read-only
		STATUS			current
		DESCRIPTION
				"TYPE: - Display
				 PAGE: - Timecode
					I/P HD ATC-VITC Lin  cmdID= 31007  format=   "
		::= { iqudc12CmdEntry 31007 }


	iqudc12TimecodeInputIPSDATCVITCLin OBJECT-TYPE
		SYNTAX		RollCallString
		MAX-ACCESS		read-only
		STATUS			current
		DESCRIPTION
				"TYPE: - Display
				 PAGE: - Timecode
					I/P SD ATC-VITC Lin  cmdID= 31005  format=   "
		::= { iqudc12CmdEntry 31005 }


	iqudc12TimecodeInputRefreshrate OBJECT-TYPE
		SYNTAX		INTEGER {
							val-0-5-sec(500),
							val-1-sec(1000),
							val-2-sec(2000),
							val-5-sec(5000)
							}
		MAX-ACCESS		read-write
		STATUS			current
		DESCRIPTION
				"TYPE: - RadiobuttonList
				 PAGE: - Timecode
					Refresh rate  cmdID= 31022 
					0.5 sec  value= 500  
					1 sec  value= 1000  
					2 sec  value= 2000  
					5 sec  value= 5000  "
		::= { iqudc12CmdEntry 31022 }


	iqudc12TimecodeFreerunHours OBJECT-TYPE
		SYNTAX		INTEGER
		MAX-ACCESS		read-write
		STATUS			current
		DESCRIPTION
				"TYPE: - Number
				 PAGE: - Timecode
					Hours  cmdID= 31010  min= 0  max= 23  step= 1  format= %02.0f  div_scale= 1 
					Min = 00  Max = 23  Step = 01 "
		::= { iqudc12CmdEntry 31010 }


	iqudc12TimecodeFreerunMinutes OBJECT-TYPE
		SYNTAX		INTEGER
		MAX-ACCESS		read-write
		STATUS			current
		DESCRIPTION
				"TYPE: - Number
				 PAGE: - Timecode
					Minutes  cmdID= 31011  min= 0  max= 59  step= 1  format= %02.0f  div_scale= 1 
					Min = 00  Max = 59  Step = 01 "
		::= { iqudc12CmdEntry 31011 }


	iqudc12TimecodeFreerunSeconds OBJECT-TYPE
		SYNTAX		INTEGER
		MAX-ACCESS		read-write
		STATUS			current
		DESCRIPTION
				"TYPE: - Number
				 PAGE: - Timecode
					Seconds  cmdID= 31012  min= 0  max= 59  step= 1  format= %02.0f  div_scale= 1 
					Min = 00  Max = 59  Step = 01 "
		::= { iqudc12CmdEntry 31012 }


	iqudc12TimecodeFreerunApply OBJECT-TYPE
		SYNTAX		INTEGER { noAction(0),val-Apply(1) }
		MAX-ACCESS		read-write
		STATUS			current
		DESCRIPTION
				"TYPE: - Button
				 PAGE: - Timecode
					Apply  cmdID= 31013  value= 1  "
		::= { iqudc12CmdEntry 31013 }


	iqudc12TimecodeOutputTimecodeValue OBJECT-TYPE
		SYNTAX		RollCallString
		MAX-ACCESS		read-only
		STATUS			current
		DESCRIPTION
				"TYPE: - Display
				 PAGE: - Timecode
					Timecode Value  cmdID= 31008  format=   "
		::= { iqudc12CmdEntry 31008 }


	iqudc12TimecodeOutputTimecodeSource OBJECT-TYPE
		SYNTAX		RollCallString
		MAX-ACCESS		read-only
		STATUS			current
		DESCRIPTION
				"TYPE: - Display
				 PAGE: - Timecode
					Timecode Source  cmdID= 31009  format=   "
		::= { iqudc12CmdEntry 31009 }


	iqudc12TimecodeOutputSourcePriority1 OBJECT-TYPE
		SYNTAX		INTEGER {
							val-Ref-VITC(1),
							val-Inp-VITC(2),
							val-Inp-ATC-LTC(3),
							val-Inp-ATC-VITC(4),
							val-Free-Run(0)
							}
		MAX-ACCESS		read-write
		STATUS			current
		DESCRIPTION
				"TYPE: - RadiobuttonList
				 PAGE: - Timecode
					Source Priority 1  cmdID= 31014 
					Ref VITC  value= 1  
					Inp VITC  value= 2  
					Inp ATC-LTC  value= 3  
					Inp ATC-VITC  value= 4  
					Free Run  value= 0  "
		::= { iqudc12CmdEntry 31014 }


	iqudc12TimecodeOutputSourcePriority2 OBJECT-TYPE
		SYNTAX		INTEGER {
							val-Ref-VITC(1),
							val-Inp-VITC(2),
							val-Inp-ATC-LTC(3),
							val-Inp-ATC-VITC(4),
							val-Free-Run(0)
							}
		MAX-ACCESS		read-write
		STATUS			current
		DESCRIPTION
				"TYPE: - RadiobuttonList
				 PAGE: - Timecode
					Source Priority 2  cmdID= 31015 
					Ref VITC  value= 1  
					Inp VITC  value= 2  
					Inp ATC-LTC  value= 3  
					Inp ATC-VITC  value= 4  
					Free Run  value= 0  "
		::= { iqudc12CmdEntry 31015 }


	iqudc12TimecodeOutputOffsetDirection OBJECT-TYPE
		SYNTAX		INTEGER {
							val-Advanced(0),
							val-Delayed(1)
							}
		MAX-ACCESS		read-write
		STATUS			current
		DESCRIPTION
				"TYPE: - RadiobuttonList
				 PAGE: - Timecode
					Offset Direction  cmdID= 31018 
					Advanced  value= 0  
					Delayed  value= 1  "
		::= { iqudc12CmdEntry 31018 }


	iqudc12TimecodeOutputOffsetField OBJECT-TYPE
		SYNTAX		INTEGER {
							val-None(0),
							val-1-Field(1)
							}
		MAX-ACCESS		read-write
		STATUS			current
		DESCRIPTION
				"TYPE: - RadiobuttonList
				 PAGE: - Timecode
					Offset Field  cmdID= 31019 
					None  value= 0  
					1 Field  value= 1  "
		::= { iqudc12CmdEntry 31019 }


	iqudc12TimecodeOutputOffsetFrames OBJECT-TYPE
		SYNTAX		INTEGER {
							val-None(0),
							val-1-Frame(1),
							val-2-Frames(2),
							val-3-Frames(3),
							val-4-Frames(4),
							val-5-Frames(5)
							}
		MAX-ACCESS		read-write
		STATUS			current
		DESCRIPTION
				"TYPE: - RadiobuttonList
				 PAGE: - Timecode
					Offset Frames  cmdID= 31020 
					None  value= 0  
					1 Frame  value= 1  
					2 Frames  value= 2  
					3 Frames  value= 3  
					4 Frames  value= 4  
					5 Frames  value= 5  "
		::= { iqudc12CmdEntry 31020 }


	iqudc12OutputInsertSDATCVITCEnable OBJECT-TYPE
		SYNTAX		INTEGER { disable(0), enable(1) }
		MAX-ACCESS		read-write
		STATUS			current
		DESCRIPTION
				"TYPE: - Checkbox
				 PAGE: - Timecode
					Enable  cmdID= 31026 "
		::= { iqudc12CmdEntry 31026 }


	iqudc12OutputInsertSDATCVITCFollowInputLine OBJECT-TYPE
		SYNTAX		INTEGER { disable(0), enable(1) }
		MAX-ACCESS		read-write
		STATUS			current
		DESCRIPTION
				"TYPE: - Checkbox
				 PAGE: - Timecode
					Follow Input Line  cmdID= 31027 "
		::= { iqudc12CmdEntry 31027 }


	iqudc12OutputInsertSDATCVITCOutputLine OBJECT-TYPE
		SYNTAX		INTEGER
		MAX-ACCESS		read-write
		STATUS			current
		DESCRIPTION
				"TYPE: - Number
				 PAGE: - Timecode
					Output Line  cmdID= 31028  min= 2  max= 33  step= 1  format= Line %0.0f  div_scale= 1 
					Min = Line 2  Max = Line 33  Step = Line 1 "
		::= { iqudc12CmdEntry 31028 }


	iqudc12OutputInsertHDATCLTCEnable OBJECT-TYPE
		SYNTAX		INTEGER { disable(0), enable(1) }
		MAX-ACCESS		read-write
		STATUS			current
		DESCRIPTION
				"TYPE: - Checkbox
				 PAGE: - Timecode
					Enable  cmdID= 31029 "
		::= { iqudc12CmdEntry 31029 }


	iqudc12OutputInsertHDATCLTCFollowInputLine OBJECT-TYPE
		SYNTAX		INTEGER { disable(0), enable(1) }
		MAX-ACCESS		read-write
		STATUS			current
		DESCRIPTION
				"TYPE: - Checkbox
				 PAGE: - Timecode
					Follow Input Line  cmdID= 31030 "
		::= { iqudc12CmdEntry 31030 }


	iqudc12OutputInsertHDATCLTCOutputLine OBJECT-TYPE
		SYNTAX		INTEGER
		MAX-ACCESS		read-write
		STATUS			current
		DESCRIPTION
				"TYPE: - Number
				 PAGE: - Timecode
					Output Line  cmdID= 31031  min= 2  max= 33  step= 1  format= Line %0.0f  div_scale= 1 
					Min = Line 2  Max = Line 33  Step = Line 1 "
		::= { iqudc12CmdEntry 31031 }


	iqudc12OutputInsertHDATCVITCEnable OBJECT-TYPE
		SYNTAX		INTEGER { disable(0), enable(1) }
		MAX-ACCESS		read-write
		STATUS			current
		DESCRIPTION
				"TYPE: - Checkbox
				 PAGE: - Timecode
					Enable  cmdID= 31032 "
		::= { iqudc12CmdEntry 31032 }


	iqudc12OutputInsertHDATCVITCFollowInputLine OBJECT-TYPE
		SYNTAX		INTEGER { disable(0), enable(1) }
		MAX-ACCESS		read-write
		STATUS			current
		DESCRIPTION
				"TYPE: - Checkbox
				 PAGE: - Timecode
					Follow Input Line  cmdID= 31033 "
		::= { iqudc12CmdEntry 31033 }


	iqudc12OutputInsertHDATCVITCOutputLineF1 OBJECT-TYPE
		SYNTAX		INTEGER
		MAX-ACCESS		read-write
		STATUS			current
		DESCRIPTION
				"TYPE: - Number
				 PAGE: - Timecode
					Output Line F1  cmdID= 31034  min= 2  max= 33  step= 1  format= Line %0.0f  div_scale= 1 
					Min = Line 2  Max = Line 33  Step = Line 1 "
		::= { iqudc12CmdEntry 31034 }


	iqudc12TimecodeOutputATCVITCLegacy OBJECT-TYPE
		SYNTAX		INTEGER { disable(0), enable(1) }
		MAX-ACCESS		read-write
		STATUS			current
		DESCRIPTION
				"TYPE: - Checkbox
				 PAGE: - Timecode
					ATC-VITC Legacy  cmdID= 31021 "
		::= { iqudc12CmdEntry 31021 }


	iqudc12TimecodeOutputOffifNoInput OBJECT-TYPE
		SYNTAX		INTEGER { disable(0), enable(1) }
		MAX-ACCESS		read-write
		STATUS			current
		DESCRIPTION
				"TYPE: - Checkbox
				 PAGE: - Timecode
					Off if No Input  cmdID= 31016 "
		::= { iqudc12CmdEntry 31016 }


	iqudc12Disembed18Disembed1Disembed11procamp OBJECT-TYPE
		SYNTAX		INTEGER
		MAX-ACCESS		read-write
		STATUS			current
		DESCRIPTION
				"TYPE: - Number
				 PAGE: - AudioInput
					Disembed1_1_procamp  cmdID= 40000  min= -801  max= 120  step= 1  format= %0.1f dB  div_scale= 10 
					Min = -80.1 dB  Max = 12.0 dB  Step = 0.1 dB "
		::= { iqudc12CmdEntry 40000 }


	iqudc12Disembed18Disembed1Disembed12procamp OBJECT-TYPE
		SYNTAX		INTEGER
		MAX-ACCESS		read-write
		STATUS			current
		DESCRIPTION
				"TYPE: - Number
				 PAGE: - AudioInput
					Disembed1_2_procamp  cmdID= 40001  min= -801  max= 120  step= 1  format= %0.1f dB  div_scale= 10 
					Min = -80.1 dB  Max = 12.0 dB  Step = 0.1 dB "
		::= { iqudc12CmdEntry 40001 }


	iqudc12Disembed18Disembed1Mute11 OBJECT-TYPE
		SYNTAX		INTEGER { disable(0), enable(1) }
		MAX-ACCESS		read-write
		STATUS			current
		DESCRIPTION
				"TYPE: - Checkbox
				 PAGE: - AudioInput
					Mute1_1  cmdID= 40032 "
		::= { iqudc12CmdEntry 40032 }


	iqudc12Disembed18Disembed1Mute12 OBJECT-TYPE
		SYNTAX		INTEGER { disable(0), enable(1) }
		MAX-ACCESS		read-write
		STATUS			current
		DESCRIPTION
				"TYPE: - Checkbox
				 PAGE: - AudioInput
					Mute1_2  cmdID= 40033 "
		::= { iqudc12CmdEntry 40033 }


	iqudc12Disembed18Disembed1Stereo1 OBJECT-TYPE
		SYNTAX		INTEGER { disable(0), enable(1) }
		MAX-ACCESS		read-write
		STATUS			current
		DESCRIPTION
				"TYPE: - Checkbox
				 PAGE: - AudioInput
					Stereo1  cmdID= 40048 "
		::= { iqudc12CmdEntry 40048 }


	iqudc12Disembed18Disembed1Disembed11invert OBJECT-TYPE
		SYNTAX		INTEGER { disable(0), enable(1) }
		MAX-ACCESS		read-write
		STATUS			current
		DESCRIPTION
				"TYPE: - Checkbox
				 PAGE: - AudioInput
					Disembed1_1_invert  cmdID= 40016 "
		::= { iqudc12CmdEntry 40016 }


	iqudc12Disembed18Disembed1Disembed12invert OBJECT-TYPE
		SYNTAX		INTEGER { disable(0), enable(1) }
		MAX-ACCESS		read-write
		STATUS			current
		DESCRIPTION
				"TYPE: - Checkbox
				 PAGE: - AudioInput
					Disembed1_2_invert  cmdID= 40017 "
		::= { iqudc12CmdEntry 40017 }


	iqudc12Disembed18Disembed1dolbyLine OBJECT-TYPE
		SYNTAX		RollCallString
		MAX-ACCESS		read-only
		STATUS			current
		DESCRIPTION
				"TYPE: - Display
				 PAGE: - AudioInput
					dolbyLine  cmdID= 40073  format=   "
		::= { iqudc12CmdEntry 40073 }


	iqudc12Disembed18Disembed2Disembed21procamp OBJECT-TYPE
		SYNTAX		INTEGER
		MAX-ACCESS		read-write
		STATUS			current
		DESCRIPTION
				"TYPE: - Number
				 PAGE: - AudioInput
					Disembed2_1_procamp  cmdID= 40002  min= -801  max= 120  step= 1  format= %0.1f dB  div_scale= 10 
					Min = -80.1 dB  Max = 12.0 dB  Step = 0.1 dB "
		::= { iqudc12CmdEntry 40002 }


	iqudc12Disembed18Disembed2Disembed22procamp OBJECT-TYPE
		SYNTAX		INTEGER
		MAX-ACCESS		read-write
		STATUS			current
		DESCRIPTION
				"TYPE: - Number
				 PAGE: - AudioInput
					Disembed2_2_procamp  cmdID= 40003  min= -801  max= 120  step= 1  format= %0.1f dB  div_scale= 10 
					Min = -80.1 dB  Max = 12.0 dB  Step = 0.1 dB "
		::= { iqudc12CmdEntry 40003 }


	iqudc12Disembed18Disembed2Mute21 OBJECT-TYPE
		SYNTAX		INTEGER { disable(0), enable(1) }
		MAX-ACCESS		read-write
		STATUS			current
		DESCRIPTION
				"TYPE: - Checkbox
				 PAGE: - AudioInput
					Mute2_1  cmdID= 40034 "
		::= { iqudc12CmdEntry 40034 }


	iqudc12Disembed18Disembed2Mute22 OBJECT-TYPE
		SYNTAX		INTEGER { disable(0), enable(1) }
		MAX-ACCESS		read-write
		STATUS			current
		DESCRIPTION
				"TYPE: - Checkbox
				 PAGE: - AudioInput
					Mute2_2  cmdID= 40035 "
		::= { iqudc12CmdEntry 40035 }


	iqudc12Disembed18Disembed2Stereo2 OBJECT-TYPE
		SYNTAX		INTEGER { disable(0), enable(1) }
		MAX-ACCESS		read-write
		STATUS			current
		DESCRIPTION
				"TYPE: - Checkbox
				 PAGE: - AudioInput
					Stereo2  cmdID= 40049 "
		::= { iqudc12CmdEntry 40049 }


	iqudc12Disembed18Disembed2Disembed21invert OBJECT-TYPE
		SYNTAX		INTEGER { disable(0), enable(1) }
		MAX-ACCESS		read-write
		STATUS			current
		DESCRIPTION
				"TYPE: - Checkbox
				 PAGE: - AudioInput
					Disembed2_1_invert  cmdID= 40018 "
		::= { iqudc12CmdEntry 40018 }


	iqudc12Disembed18Disembed2Disembed22invert OBJECT-TYPE
		SYNTAX		INTEGER { disable(0), enable(1) }
		MAX-ACCESS		read-write
		STATUS			current
		DESCRIPTION
				"TYPE: - Checkbox
				 PAGE: - AudioInput
					Disembed2_2_invert  cmdID= 40019 "
		::= { iqudc12CmdEntry 40019 }


	iqudc12Disembed18Disembed2dolbyLine OBJECT-TYPE
		SYNTAX		RollCallString
		MAX-ACCESS		read-only
		STATUS			current
		DESCRIPTION
				"TYPE: - Display
				 PAGE: - AudioInput
					dolbyLine  cmdID= 40074  format=   "
		::= { iqudc12CmdEntry 40074 }


	iqudc12Disembed18Disembed3Disembed31procamp OBJECT-TYPE
		SYNTAX		INTEGER
		MAX-ACCESS		read-write
		STATUS			current
		DESCRIPTION
				"TYPE: - Number
				 PAGE: - AudioInput
					Disembed3_1_procamp  cmdID= 40004  min= -801  max= 120  step= 1  format= %0.1f dB  div_scale= 10 
					Min = -80.1 dB  Max = 12.0 dB  Step = 0.1 dB "
		::= { iqudc12CmdEntry 40004 }


	iqudc12Disembed18Disembed3Disembed32procamp OBJECT-TYPE
		SYNTAX		INTEGER
		MAX-ACCESS		read-write
		STATUS			current
		DESCRIPTION
				"TYPE: - Number
				 PAGE: - AudioInput
					Disembed3_2_procamp  cmdID= 40005  min= -801  max= 120  step= 1  format= %0.1f dB  div_scale= 10 
					Min = -80.1 dB  Max = 12.0 dB  Step = 0.1 dB "
		::= { iqudc12CmdEntry 40005 }


	iqudc12Disembed18Disembed3Mute31 OBJECT-TYPE
		SYNTAX		INTEGER { disable(0), enable(1) }
		MAX-ACCESS		read-write
		STATUS			current
		DESCRIPTION
				"TYPE: - Checkbox
				 PAGE: - AudioInput
					Mute3_1  cmdID= 40036 "
		::= { iqudc12CmdEntry 40036 }


	iqudc12Disembed18Disembed3Mute32 OBJECT-TYPE
		SYNTAX		INTEGER { disable(0), enable(1) }
		MAX-ACCESS		read-write
		STATUS			current
		DESCRIPTION
				"TYPE: - Checkbox
				 PAGE: - AudioInput
					Mute3_2  cmdID= 40037 "
		::= { iqudc12CmdEntry 40037 }


	iqudc12Disembed18Disembed3Stereo3 OBJECT-TYPE
		SYNTAX		INTEGER { disable(0), enable(1) }
		MAX-ACCESS		read-write
		STATUS			current
		DESCRIPTION
				"TYPE: - Checkbox
				 PAGE: - AudioInput
					Stereo3  cmdID= 40050 "
		::= { iqudc12CmdEntry 40050 }


	iqudc12Disembed18Disembed3Disembed31invert OBJECT-TYPE
		SYNTAX		INTEGER { disable(0), enable(1) }
		MAX-ACCESS		read-write
		STATUS			current
		DESCRIPTION
				"TYPE: - Checkbox
				 PAGE: - AudioInput
					Disembed3_1_invert  cmdID= 40020 "
		::= { iqudc12CmdEntry 40020 }


	iqudc12Disembed18Disembed3Disembed32invert OBJECT-TYPE
		SYNTAX		INTEGER { disable(0), enable(1) }
		MAX-ACCESS		read-write
		STATUS			current
		DESCRIPTION
				"TYPE: - Checkbox
				 PAGE: - AudioInput
					Disembed3_2_invert  cmdID= 40021 "
		::= { iqudc12CmdEntry 40021 }


	iqudc12Disembed18Disembed3dolbyLine OBJECT-TYPE
		SYNTAX		RollCallString
		MAX-ACCESS		read-only
		STATUS			current
		DESCRIPTION
				"TYPE: - Display
				 PAGE: - AudioInput
					dolbyLine  cmdID= 40075  format=   "
		::= { iqudc12CmdEntry 40075 }


	iqudc12Disembed18Disembed4Disembed41procamp OBJECT-TYPE
		SYNTAX		INTEGER
		MAX-ACCESS		read-write
		STATUS			current
		DESCRIPTION
				"TYPE: - Number
				 PAGE: - AudioInput
					Disembed4_1_procamp  cmdID= 40006  min= -801  max= 120  step= 1  format= %0.1f dB  div_scale= 10 
					Min = -80.1 dB  Max = 12.0 dB  Step = 0.1 dB "
		::= { iqudc12CmdEntry 40006 }


	iqudc12Disembed18Disembed4Disembed42procamp OBJECT-TYPE
		SYNTAX		INTEGER
		MAX-ACCESS		read-write
		STATUS			current
		DESCRIPTION
				"TYPE: - Number
				 PAGE: - AudioInput
					Disembed4_2_procamp  cmdID= 40007  min= -801  max= 120  step= 1  format= %0.1f dB  div_scale= 10 
					Min = -80.1 dB  Max = 12.0 dB  Step = 0.1 dB "
		::= { iqudc12CmdEntry 40007 }


	iqudc12Disembed18Disembed4Mute41 OBJECT-TYPE
		SYNTAX		INTEGER { disable(0), enable(1) }
		MAX-ACCESS		read-write
		STATUS			current
		DESCRIPTION
				"TYPE: - Checkbox
				 PAGE: - AudioInput
					Mute4_1  cmdID= 40038 "
		::= { iqudc12CmdEntry 40038 }


	iqudc12Disembed18Disembed4Mute42 OBJECT-TYPE
		SYNTAX		INTEGER { disable(0), enable(1) }
		MAX-ACCESS		read-write
		STATUS			current
		DESCRIPTION
				"TYPE: - Checkbox
				 PAGE: - AudioInput
					Mute4_2  cmdID= 40039 "
		::= { iqudc12CmdEntry 40039 }


	iqudc12Disembed18Disembed4Stereo4 OBJECT-TYPE
		SYNTAX		INTEGER { disable(0), enable(1) }
		MAX-ACCESS		read-write
		STATUS			current
		DESCRIPTION
				"TYPE: - Checkbox
				 PAGE: - AudioInput
					Stereo4  cmdID= 40051 "
		::= { iqudc12CmdEntry 40051 }


	iqudc12Disembed18Disembed4Disembed41invert OBJECT-TYPE
		SYNTAX		INTEGER { disable(0), enable(1) }
		MAX-ACCESS		read-write
		STATUS			current
		DESCRIPTION
				"TYPE: - Checkbox
				 PAGE: - AudioInput
					Disembed4_1_invert  cmdID= 40022 "
		::= { iqudc12CmdEntry 40022 }


	iqudc12Disembed18Disembed4Disembed42invert OBJECT-TYPE
		SYNTAX		INTEGER { disable(0), enable(1) }
		MAX-ACCESS		read-write
		STATUS			current
		DESCRIPTION
				"TYPE: - Checkbox
				 PAGE: - AudioInput
					Disembed4_2_invert  cmdID= 40023 "
		::= { iqudc12CmdEntry 40023 }


	iqudc12Disembed18Disembed4dolbyLine OBJECT-TYPE
		SYNTAX		RollCallString
		MAX-ACCESS		read-only
		STATUS			current
		DESCRIPTION
				"TYPE: - Display
				 PAGE: - AudioInput
					dolbyLine  cmdID= 40076  format=   "
		::= { iqudc12CmdEntry 40076 }


	iqudc12Disembed18Disembed5Disembed51procamp OBJECT-TYPE
		SYNTAX		INTEGER
		MAX-ACCESS		read-write
		STATUS			current
		DESCRIPTION
				"TYPE: - Number
				 PAGE: - AudioInput
					Disembed5_1_procamp  cmdID= 40008  min= -801  max= 120  step= 1  format= %0.1f dB  div_scale= 10 
					Min = -80.1 dB  Max = 12.0 dB  Step = 0.1 dB "
		::= { iqudc12CmdEntry 40008 }


	iqudc12Disembed18Disembed5Disembed52procamp OBJECT-TYPE
		SYNTAX		INTEGER
		MAX-ACCESS		read-write
		STATUS			current
		DESCRIPTION
				"TYPE: - Number
				 PAGE: - AudioInput
					Disembed5_2_procamp  cmdID= 40009  min= -801  max= 120  step= 1  format= %0.1f dB  div_scale= 10 
					Min = -80.1 dB  Max = 12.0 dB  Step = 0.1 dB "
		::= { iqudc12CmdEntry 40009 }


	iqudc12Disembed18Disembed5Mute51 OBJECT-TYPE
		SYNTAX		INTEGER { disable(0), enable(1) }
		MAX-ACCESS		read-write
		STATUS			current
		DESCRIPTION
				"TYPE: - Checkbox
				 PAGE: - AudioInput
					Mute5_1  cmdID= 40040 "
		::= { iqudc12CmdEntry 40040 }


	iqudc12Disembed18Disembed5Mute52 OBJECT-TYPE
		SYNTAX		INTEGER { disable(0), enable(1) }
		MAX-ACCESS		read-write
		STATUS			current
		DESCRIPTION
				"TYPE: - Checkbox
				 PAGE: - AudioInput
					Mute5_2  cmdID= 40041 "
		::= { iqudc12CmdEntry 40041 }


	iqudc12Disembed18Disembed5Stereo5 OBJECT-TYPE
		SYNTAX		INTEGER { disable(0), enable(1) }
		MAX-ACCESS		read-write
		STATUS			current
		DESCRIPTION
				"TYPE: - Checkbox
				 PAGE: - AudioInput
					Stereo5  cmdID= 40052 "
		::= { iqudc12CmdEntry 40052 }


	iqudc12Disembed18Disembed5Disembed51invert OBJECT-TYPE
		SYNTAX		INTEGER { disable(0), enable(1) }
		MAX-ACCESS		read-write
		STATUS			current
		DESCRIPTION
				"TYPE: - Checkbox
				 PAGE: - AudioInput
					Disembed5_1_invert  cmdID= 40024 "
		::= { iqudc12CmdEntry 40024 }


	iqudc12Disembed18Disembed5Disembed52invert OBJECT-TYPE
		SYNTAX		INTEGER { disable(0), enable(1) }
		MAX-ACCESS		read-write
		STATUS			current
		DESCRIPTION
				"TYPE: - Checkbox
				 PAGE: - AudioInput
					Disembed5_2_invert  cmdID= 40025 "
		::= { iqudc12CmdEntry 40025 }


	iqudc12Disembed18Disembed5dolbyLine OBJECT-TYPE
		SYNTAX		RollCallString
		MAX-ACCESS		read-only
		STATUS			current
		DESCRIPTION
				"TYPE: - Display
				 PAGE: - AudioInput
					dolbyLine  cmdID= 40077  format=   "
		::= { iqudc12CmdEntry 40077 }


	iqudc12Disembed18Disembed6Disembed61procamp OBJECT-TYPE
		SYNTAX		INTEGER
		MAX-ACCESS		read-write
		STATUS			current
		DESCRIPTION
				"TYPE: - Number
				 PAGE: - AudioInput
					Disembed6_1_procamp  cmdID= 40010  min= -801  max= 120  step= 1  format= %0.1f dB  div_scale= 10 
					Min = -80.1 dB  Max = 12.0 dB  Step = 0.1 dB "
		::= { iqudc12CmdEntry 40010 }


	iqudc12Disembed18Disembed6Disembed62procamp OBJECT-TYPE
		SYNTAX		INTEGER
		MAX-ACCESS		read-write
		STATUS			current
		DESCRIPTION
				"TYPE: - Number
				 PAGE: - AudioInput
					Disembed6_2_procamp  cmdID= 40011  min= -801  max= 120  step= 1  format= %0.1f dB  div_scale= 10 
					Min = -80.1 dB  Max = 12.0 dB  Step = 0.1 dB "
		::= { iqudc12CmdEntry 40011 }


	iqudc12Disembed18Disembed6Mute61 OBJECT-TYPE
		SYNTAX		INTEGER { disable(0), enable(1) }
		MAX-ACCESS		read-write
		STATUS			current
		DESCRIPTION
				"TYPE: - Checkbox
				 PAGE: - AudioInput
					Mute6_1  cmdID= 40042 "
		::= { iqudc12CmdEntry 40042 }


	iqudc12Disembed18Disembed6Mute62 OBJECT-TYPE
		SYNTAX		INTEGER { disable(0), enable(1) }
		MAX-ACCESS		read-write
		STATUS			current
		DESCRIPTION
				"TYPE: - Checkbox
				 PAGE: - AudioInput
					Mute6_2  cmdID= 40043 "
		::= { iqudc12CmdEntry 40043 }


	iqudc12Disembed18Disembed6Stereo6 OBJECT-TYPE
		SYNTAX		INTEGER { disable(0), enable(1) }
		MAX-ACCESS		read-write
		STATUS			current
		DESCRIPTION
				"TYPE: - Checkbox
				 PAGE: - AudioInput
					Stereo6  cmdID= 40053 "
		::= { iqudc12CmdEntry 40053 }


	iqudc12Disembed18Disembed6Disembed61invert OBJECT-TYPE
		SYNTAX		INTEGER { disable(0), enable(1) }
		MAX-ACCESS		read-write
		STATUS			current
		DESCRIPTION
				"TYPE: - Checkbox
				 PAGE: - AudioInput
					Disembed6_1_invert  cmdID= 40026 "
		::= { iqudc12CmdEntry 40026 }


	iqudc12Disembed18Disembed6Disembed62invert OBJECT-TYPE
		SYNTAX		INTEGER { disable(0), enable(1) }
		MAX-ACCESS		read-write
		STATUS			current
		DESCRIPTION
				"TYPE: - Checkbox
				 PAGE: - AudioInput
					Disembed6_2_invert  cmdID= 40027 "
		::= { iqudc12CmdEntry 40027 }


	iqudc12Disembed18Disembed6dolbyLine OBJECT-TYPE
		SYNTAX		RollCallString
		MAX-ACCESS		read-only
		STATUS			current
		DESCRIPTION
				"TYPE: - Display
				 PAGE: - AudioInput
					dolbyLine  cmdID= 40078  format=   "
		::= { iqudc12CmdEntry 40078 }


	iqudc12Disembed18Disembed7Disembed71procamp OBJECT-TYPE
		SYNTAX		INTEGER
		MAX-ACCESS		read-write
		STATUS			current
		DESCRIPTION
				"TYPE: - Number
				 PAGE: - AudioInput
					Disembed7_1_procamp  cmdID= 40012  min= -801  max= 120  step= 1  format= %0.1f dB  div_scale= 10 
					Min = -80.1 dB  Max = 12.0 dB  Step = 0.1 dB "
		::= { iqudc12CmdEntry 40012 }


	iqudc12Disembed18Disembed7Disembed72procamp OBJECT-TYPE
		SYNTAX		INTEGER
		MAX-ACCESS		read-write
		STATUS			current
		DESCRIPTION
				"TYPE: - Number
				 PAGE: - AudioInput
					Disembed7_2_procamp  cmdID= 40013  min= -801  max= 120  step= 1  format= %0.1f dB  div_scale= 10 
					Min = -80.1 dB  Max = 12.0 dB  Step = 0.1 dB "
		::= { iqudc12CmdEntry 40013 }


	iqudc12Disembed18Disembed7Mute71 OBJECT-TYPE
		SYNTAX		INTEGER { disable(0), enable(1) }
		MAX-ACCESS		read-write
		STATUS			current
		DESCRIPTION
				"TYPE: - Checkbox
				 PAGE: - AudioInput
					Mute7_1  cmdID= 40044 "
		::= { iqudc12CmdEntry 40044 }


	iqudc12Disembed18Disembed7Mute72 OBJECT-TYPE
		SYNTAX		INTEGER { disable(0), enable(1) }
		MAX-ACCESS		read-write
		STATUS			current
		DESCRIPTION
				"TYPE: - Checkbox
				 PAGE: - AudioInput
					Mute7_2  cmdID= 40045 "
		::= { iqudc12CmdEntry 40045 }


	iqudc12Disembed18Disembed7Stereo7 OBJECT-TYPE
		SYNTAX		INTEGER { disable(0), enable(1) }
		MAX-ACCESS		read-write
		STATUS			current
		DESCRIPTION
				"TYPE: - Checkbox
				 PAGE: - AudioInput
					Stereo7  cmdID= 40054 "
		::= { iqudc12CmdEntry 40054 }


	iqudc12Disembed18Disembed7Disembed71invert OBJECT-TYPE
		SYNTAX		INTEGER { disable(0), enable(1) }
		MAX-ACCESS		read-write
		STATUS			current
		DESCRIPTION
				"TYPE: - Checkbox
				 PAGE: - AudioInput
					Disembed7_1_invert  cmdID= 40028 "
		::= { iqudc12CmdEntry 40028 }


	iqudc12Disembed18Disembed7Disembed72invert OBJECT-TYPE
		SYNTAX		INTEGER { disable(0), enable(1) }
		MAX-ACCESS		read-write
		STATUS			current
		DESCRIPTION
				"TYPE: - Checkbox
				 PAGE: - AudioInput
					Disembed7_2_invert  cmdID= 40029 "
		::= { iqudc12CmdEntry 40029 }


	iqudc12Disembed18Disembed7dolbyLine OBJECT-TYPE
		SYNTAX		RollCallString
		MAX-ACCESS		read-only
		STATUS			current
		DESCRIPTION
				"TYPE: - Display
				 PAGE: - AudioInput
					dolbyLine  cmdID= 40079  format=   "
		::= { iqudc12CmdEntry 40079 }


	iqudc12Disembed18Disembed8Disembed81procamp OBJECT-TYPE
		SYNTAX		INTEGER
		MAX-ACCESS		read-write
		STATUS			current
		DESCRIPTION
				"TYPE: - Number
				 PAGE: - AudioInput
					Disembed8_1_procamp  cmdID= 40014  min= -801  max= 120  step= 1  format= %0.1f dB  div_scale= 10 
					Min = -80.1 dB  Max = 12.0 dB  Step = 0.1 dB "
		::= { iqudc12CmdEntry 40014 }


	iqudc12Disembed18Disembed8Disembed82procamp OBJECT-TYPE
		SYNTAX		INTEGER
		MAX-ACCESS		read-write
		STATUS			current
		DESCRIPTION
				"TYPE: - Number
				 PAGE: - AudioInput
					Disembed8_2_procamp  cmdID= 40015  min= -801  max= 120  step= 1  format= %0.1f dB  div_scale= 10 
					Min = -80.1 dB  Max = 12.0 dB  Step = 0.1 dB "
		::= { iqudc12CmdEntry 40015 }


	iqudc12Disembed18Disembed8Mute81 OBJECT-TYPE
		SYNTAX		INTEGER { disable(0), enable(1) }
		MAX-ACCESS		read-write
		STATUS			current
		DESCRIPTION
				"TYPE: - Checkbox
				 PAGE: - AudioInput
					Mute8_1  cmdID= 40046 "
		::= { iqudc12CmdEntry 40046 }


	iqudc12Disembed18Disembed8Mute82 OBJECT-TYPE
		SYNTAX		INTEGER { disable(0), enable(1) }
		MAX-ACCESS		read-write
		STATUS			current
		DESCRIPTION
				"TYPE: - Checkbox
				 PAGE: - AudioInput
					Mute8_2  cmdID= 40047 "
		::= { iqudc12CmdEntry 40047 }


	iqudc12Disembed18Disembed8Stereo8 OBJECT-TYPE
		SYNTAX		INTEGER { disable(0), enable(1) }
		MAX-ACCESS		read-write
		STATUS			current
		DESCRIPTION
				"TYPE: - Checkbox
				 PAGE: - AudioInput
					Stereo8  cmdID= 40055 "
		::= { iqudc12CmdEntry 40055 }


	iqudc12Disembed18Disembed8Disembed81invert OBJECT-TYPE
		SYNTAX		INTEGER { disable(0), enable(1) }
		MAX-ACCESS		read-write
		STATUS			current
		DESCRIPTION
				"TYPE: - Checkbox
				 PAGE: - AudioInput
					Disembed8_1_invert  cmdID= 40030 "
		::= { iqudc12CmdEntry 40030 }


	iqudc12Disembed18Disembed8Disembed82invert OBJECT-TYPE
		SYNTAX		INTEGER { disable(0), enable(1) }
		MAX-ACCESS		read-write
		STATUS			current
		DESCRIPTION
				"TYPE: - Checkbox
				 PAGE: - AudioInput
					Disembed8_2_invert  cmdID= 40031 "
		::= { iqudc12CmdEntry 40031 }


	iqudc12Disembed18Disembed8dolbyLine OBJECT-TYPE
		SYNTAX		RollCallString
		MAX-ACCESS		read-only
		STATUS			current
		DESCRIPTION
				"TYPE: - Display
				 PAGE: - AudioInput
					dolbyLine  cmdID= 40080  format=   "
		::= { iqudc12CmdEntry 40080 }


	iqudc12AudioInputDisembed18ProcampSaveset OBJECT-TYPE
		SYNTAX		INTEGER
		MAX-ACCESS		read-write
		STATUS			current
		DESCRIPTION
				"TYPE: - Number
				 PAGE: - AudioInput
					ProcampSaveset  cmdID= 40072  min= 0  max= 1  step= 1  format= %0.0f  div_scale= 1 
					Min = 0  Max = 1  Step = 1 "
		::= { iqudc12CmdEntry 40072 }


	iqudc12AESInput18AESInput1AESInput11procamp OBJECT-TYPE
		SYNTAX		INTEGER
		MAX-ACCESS		read-write
		STATUS			current
		DESCRIPTION
				"TYPE: - Number
				 PAGE: - AudioInput
					AESInput1_1_procamp  cmdID= 40100  min= -801  max= 120  step= 1  format= %0.1f dB  div_scale= 10 
					Min = -80.1 dB  Max = 12.0 dB  Step = 0.1 dB "
		::= { iqudc12CmdEntry 40100 }


	iqudc12AESInput18AESInput1AESInput12procamp OBJECT-TYPE
		SYNTAX		INTEGER
		MAX-ACCESS		read-write
		STATUS			current
		DESCRIPTION
				"TYPE: - Number
				 PAGE: - AudioInput
					AESInput1_2_procamp  cmdID= 40101  min= -801  max= 120  step= 1  format= %0.1f dB  div_scale= 10 
					Min = -80.1 dB  Max = 12.0 dB  Step = 0.1 dB "
		::= { iqudc12CmdEntry 40101 }


	iqudc12AESInput18AESInput1Mute11 OBJECT-TYPE
		SYNTAX		INTEGER { disable(0), enable(1) }
		MAX-ACCESS		read-write
		STATUS			current
		DESCRIPTION
				"TYPE: - Checkbox
				 PAGE: - AudioInput
					Mute1_1  cmdID= 40132 "
		::= { iqudc12CmdEntry 40132 }


	iqudc12AESInput18AESInput1Mute12 OBJECT-TYPE
		SYNTAX		INTEGER { disable(0), enable(1) }
		MAX-ACCESS		read-write
		STATUS			current
		DESCRIPTION
				"TYPE: - Checkbox
				 PAGE: - AudioInput
					Mute1_2  cmdID= 40133 "
		::= { iqudc12CmdEntry 40133 }


	iqudc12AESInput18AESInput1Stereo1 OBJECT-TYPE
		SYNTAX		INTEGER { disable(0), enable(1) }
		MAX-ACCESS		read-write
		STATUS			current
		DESCRIPTION
				"TYPE: - Checkbox
				 PAGE: - AudioInput
					Stereo1  cmdID= 40148 "
		::= { iqudc12CmdEntry 40148 }


	iqudc12AESInput18AESInput1AESInput11invert OBJECT-TYPE
		SYNTAX		INTEGER { disable(0), enable(1) }
		MAX-ACCESS		read-write
		STATUS			current
		DESCRIPTION
				"TYPE: - Checkbox
				 PAGE: - AudioInput
					AESInput1_1_invert  cmdID= 40116 "
		::= { iqudc12CmdEntry 40116 }


	iqudc12AESInput18AESInput1AESInput12invert OBJECT-TYPE
		SYNTAX		INTEGER { disable(0), enable(1) }
		MAX-ACCESS		read-write
		STATUS			current
		DESCRIPTION
				"TYPE: - Checkbox
				 PAGE: - AudioInput
					AESInput1_2_invert  cmdID= 40117 "
		::= { iqudc12CmdEntry 40117 }


	iqudc12AESInput18AESInput1AESIO OBJECT-TYPE
		SYNTAX		INTEGER {
							val-Set-Output(0),
							val-Set-Input(1)
							}
		MAX-ACCESS		read-write
		STATUS			current
		DESCRIPTION
				"TYPE: - RadiobuttonList
				 PAGE: - AudioInput
					AES I/O  cmdID= 40263 
					Set Output  value= 0  
					Set Input  value= 1  "
		::= { iqudc12CmdEntry 40263 }


	iqudc12AESInput18AESInput2AESInput21procamp OBJECT-TYPE
		SYNTAX		INTEGER
		MAX-ACCESS		read-write
		STATUS			current
		DESCRIPTION
				"TYPE: - Number
				 PAGE: - AudioInput
					AESInput2_1_procamp  cmdID= 40102  min= -801  max= 120  step= 1  format= %0.1f dB  div_scale= 10 
					Min = -80.1 dB  Max = 12.0 dB  Step = 0.1 dB "
		::= { iqudc12CmdEntry 40102 }


	iqudc12AESInput18AESInput2AESInput22procamp OBJECT-TYPE
		SYNTAX		INTEGER
		MAX-ACCESS		read-write
		STATUS			current
		DESCRIPTION
				"TYPE: - Number
				 PAGE: - AudioInput
					AESInput2_2_procamp  cmdID= 40103  min= -801  max= 120  step= 1  format= %0.1f dB  div_scale= 10 
					Min = -80.1 dB  Max = 12.0 dB  Step = 0.1 dB "
		::= { iqudc12CmdEntry 40103 }


	iqudc12AESInput18AESInput2Mute21 OBJECT-TYPE
		SYNTAX		INTEGER { disable(0), enable(1) }
		MAX-ACCESS		read-write
		STATUS			current
		DESCRIPTION
				"TYPE: - Checkbox
				 PAGE: - AudioInput
					Mute2_1  cmdID= 40134 "
		::= { iqudc12CmdEntry 40134 }


	iqudc12AESInput18AESInput2Mute22 OBJECT-TYPE
		SYNTAX		INTEGER { disable(0), enable(1) }
		MAX-ACCESS		read-write
		STATUS			current
		DESCRIPTION
				"TYPE: - Checkbox
				 PAGE: - AudioInput
					Mute2_2  cmdID= 40135 "
		::= { iqudc12CmdEntry 40135 }


	iqudc12AESInput18AESInput2Stereo2 OBJECT-TYPE
		SYNTAX		INTEGER { disable(0), enable(1) }
		MAX-ACCESS		read-write
		STATUS			current
		DESCRIPTION
				"TYPE: - Checkbox
				 PAGE: - AudioInput
					Stereo2  cmdID= 40149 "
		::= { iqudc12CmdEntry 40149 }


	iqudc12AESInput18AESInput2AESInput21invert OBJECT-TYPE
		SYNTAX		INTEGER { disable(0), enable(1) }
		MAX-ACCESS		read-write
		STATUS			current
		DESCRIPTION
				"TYPE: - Checkbox
				 PAGE: - AudioInput
					AESInput2_1_invert  cmdID= 40118 "
		::= { iqudc12CmdEntry 40118 }


	iqudc12AESInput18AESInput2AESInput22invert OBJECT-TYPE
		SYNTAX		INTEGER { disable(0), enable(1) }
		MAX-ACCESS		read-write
		STATUS			current
		DESCRIPTION
				"TYPE: - Checkbox
				 PAGE: - AudioInput
					AESInput2_2_invert  cmdID= 40119 "
		::= { iqudc12CmdEntry 40119 }


	iqudc12AESInput18AESInput2AESIO OBJECT-TYPE
		SYNTAX		INTEGER {
							val-Set-Output(0),
							val-Set-Input(1)
							}
		MAX-ACCESS		read-write
		STATUS			current
		DESCRIPTION
				"TYPE: - RadiobuttonList
				 PAGE: - AudioInput
					AES I/O  cmdID= 40264 
					Set Output  value= 0  
					Set Input  value= 1  "
		::= { iqudc12CmdEntry 40264 }


	iqudc12AESInput18AESInput3AESInput31procamp OBJECT-TYPE
		SYNTAX		INTEGER
		MAX-ACCESS		read-write
		STATUS			current
		DESCRIPTION
				"TYPE: - Number
				 PAGE: - AudioInput
					AESInput3_1_procamp  cmdID= 40104  min= -801  max= 120  step= 1  format= %0.1f dB  div_scale= 10 
					Min = -80.1 dB  Max = 12.0 dB  Step = 0.1 dB "
		::= { iqudc12CmdEntry 40104 }


	iqudc12AESInput18AESInput3AESInput32procamp OBJECT-TYPE
		SYNTAX		INTEGER
		MAX-ACCESS		read-write
		STATUS			current
		DESCRIPTION
				"TYPE: - Number
				 PAGE: - AudioInput
					AESInput3_2_procamp  cmdID= 40105  min= -801  max= 120  step= 1  format= %0.1f dB  div_scale= 10 
					Min = -80.1 dB  Max = 12.0 dB  Step = 0.1 dB "
		::= { iqudc12CmdEntry 40105 }


	iqudc12AESInput18AESInput3Mute31 OBJECT-TYPE
		SYNTAX		INTEGER { disable(0), enable(1) }
		MAX-ACCESS		read-write
		STATUS			current
		DESCRIPTION
				"TYPE: - Checkbox
				 PAGE: - AudioInput
					Mute3_1  cmdID= 40136 "
		::= { iqudc12CmdEntry 40136 }


	iqudc12AESInput18AESInput3Mute32 OBJECT-TYPE
		SYNTAX		INTEGER { disable(0), enable(1) }
		MAX-ACCESS		read-write
		STATUS			current
		DESCRIPTION
				"TYPE: - Checkbox
				 PAGE: - AudioInput
					Mute3_2  cmdID= 40137 "
		::= { iqudc12CmdEntry 40137 }


	iqudc12AESInput18AESInput3Stereo3 OBJECT-TYPE
		SYNTAX		INTEGER { disable(0), enable(1) }
		MAX-ACCESS		read-write
		STATUS			current
		DESCRIPTION
				"TYPE: - Checkbox
				 PAGE: - AudioInput
					Stereo3  cmdID= 40150 "
		::= { iqudc12CmdEntry 40150 }


	iqudc12AESInput18AESInput3AESInput31invert OBJECT-TYPE
		SYNTAX		INTEGER { disable(0), enable(1) }
		MAX-ACCESS		read-write
		STATUS			current
		DESCRIPTION
				"TYPE: - Checkbox
				 PAGE: - AudioInput
					AESInput3_1_invert  cmdID= 40120 "
		::= { iqudc12CmdEntry 40120 }


	iqudc12AESInput18AESInput3AESInput32invert OBJECT-TYPE
		SYNTAX		INTEGER { disable(0), enable(1) }
		MAX-ACCESS		read-write
		STATUS			current
		DESCRIPTION
				"TYPE: - Checkbox
				 PAGE: - AudioInput
					AESInput3_2_invert  cmdID= 40121 "
		::= { iqudc12CmdEntry 40121 }


	iqudc12AESInput18AESInput3AESIO OBJECT-TYPE
		SYNTAX		INTEGER {
							val-Set-Output(0),
							val-Set-Input(1)
							}
		MAX-ACCESS		read-write
		STATUS			current
		DESCRIPTION
				"TYPE: - RadiobuttonList
				 PAGE: - AudioInput
					AES I/O  cmdID= 40265 
					Set Output  value= 0  
					Set Input  value= 1  "
		::= { iqudc12CmdEntry 40265 }


	iqudc12AESInput18AESInput4AESInput41procamp OBJECT-TYPE
		SYNTAX		INTEGER
		MAX-ACCESS		read-write
		STATUS			current
		DESCRIPTION
				"TYPE: - Number
				 PAGE: - AudioInput
					AESInput4_1_procamp  cmdID= 40106  min= -801  max= 120  step= 1  format= %0.1f dB  div_scale= 10 
					Min = -80.1 dB  Max = 12.0 dB  Step = 0.1 dB "
		::= { iqudc12CmdEntry 40106 }


	iqudc12AESInput18AESInput4AESInput42procamp OBJECT-TYPE
		SYNTAX		INTEGER
		MAX-ACCESS		read-write
		STATUS			current
		DESCRIPTION
				"TYPE: - Number
				 PAGE: - AudioInput
					AESInput4_2_procamp  cmdID= 40107  min= -801  max= 120  step= 1  format= %0.1f dB  div_scale= 10 
					Min = -80.1 dB  Max = 12.0 dB  Step = 0.1 dB "
		::= { iqudc12CmdEntry 40107 }


	iqudc12AESInput18AESInput4Mute41 OBJECT-TYPE
		SYNTAX		INTEGER { disable(0), enable(1) }
		MAX-ACCESS		read-write
		STATUS			current
		DESCRIPTION
				"TYPE: - Checkbox
				 PAGE: - AudioInput
					Mute4_1  cmdID= 40138 "
		::= { iqudc12CmdEntry 40138 }


	iqudc12AESInput18AESInput4Mute42 OBJECT-TYPE
		SYNTAX		INTEGER { disable(0), enable(1) }
		MAX-ACCESS		read-write
		STATUS			current
		DESCRIPTION
				"TYPE: - Checkbox
				 PAGE: - AudioInput
					Mute4_2  cmdID= 40139 "
		::= { iqudc12CmdEntry 40139 }


	iqudc12AESInput18AESInput4Stereo4 OBJECT-TYPE
		SYNTAX		INTEGER { disable(0), enable(1) }
		MAX-ACCESS		read-write
		STATUS			current
		DESCRIPTION
				"TYPE: - Checkbox
				 PAGE: - AudioInput
					Stereo4  cmdID= 40151 "
		::= { iqudc12CmdEntry 40151 }


	iqudc12AESInput18AESInput4AESInput41invert OBJECT-TYPE
		SYNTAX		INTEGER { disable(0), enable(1) }
		MAX-ACCESS		read-write
		STATUS			current
		DESCRIPTION
				"TYPE: - Checkbox
				 PAGE: - AudioInput
					AESInput4_1_invert  cmdID= 40122 "
		::= { iqudc12CmdEntry 40122 }


	iqudc12AESInput18AESInput4AESInput42invert OBJECT-TYPE
		SYNTAX		INTEGER { disable(0), enable(1) }
		MAX-ACCESS		read-write
		STATUS			current
		DESCRIPTION
				"TYPE: - Checkbox
				 PAGE: - AudioInput
					AESInput4_2_invert  cmdID= 40123 "
		::= { iqudc12CmdEntry 40123 }


	iqudc12AESInput18AESInput4AESIO OBJECT-TYPE
		SYNTAX		INTEGER {
							val-Set-Output(0),
							val-Set-Input(1)
							}
		MAX-ACCESS		read-write
		STATUS			current
		DESCRIPTION
				"TYPE: - RadiobuttonList
				 PAGE: - AudioInput
					AES I/O  cmdID= 40266 
					Set Output  value= 0  
					Set Input  value= 1  "
		::= { iqudc12CmdEntry 40266 }


	iqudc12AESInput18AESInput5AESInput51procamp OBJECT-TYPE
		SYNTAX		INTEGER
		MAX-ACCESS		read-write
		STATUS			current
		DESCRIPTION
				"TYPE: - Number
				 PAGE: - AudioInput
					AESInput5_1_procamp  cmdID= 40108  min= -801  max= 120  step= 1  format= %0.1f dB  div_scale= 10 
					Min = -80.1 dB  Max = 12.0 dB  Step = 0.1 dB "
		::= { iqudc12CmdEntry 40108 }


	iqudc12AESInput18AESInput5AESInput52procamp OBJECT-TYPE
		SYNTAX		INTEGER
		MAX-ACCESS		read-write
		STATUS			current
		DESCRIPTION
				"TYPE: - Number
				 PAGE: - AudioInput
					AESInput5_2_procamp  cmdID= 40109  min= -801  max= 120  step= 1  format= %0.1f dB  div_scale= 10 
					Min = -80.1 dB  Max = 12.0 dB  Step = 0.1 dB "
		::= { iqudc12CmdEntry 40109 }


	iqudc12AESInput18AESInput5Mute51 OBJECT-TYPE
		SYNTAX		INTEGER { disable(0), enable(1) }
		MAX-ACCESS		read-write
		STATUS			current
		DESCRIPTION
				"TYPE: - Checkbox
				 PAGE: - AudioInput
					Mute5_1  cmdID= 40140 "
		::= { iqudc12CmdEntry 40140 }


	iqudc12AESInput18AESInput5Mute52 OBJECT-TYPE
		SYNTAX		INTEGER { disable(0), enable(1) }
		MAX-ACCESS		read-write
		STATUS			current
		DESCRIPTION
				"TYPE: - Checkbox
				 PAGE: - AudioInput
					Mute5_2  cmdID= 40141 "
		::= { iqudc12CmdEntry 40141 }


	iqudc12AESInput18AESInput5Stereo5 OBJECT-TYPE
		SYNTAX		INTEGER { disable(0), enable(1) }
		MAX-ACCESS		read-write
		STATUS			current
		DESCRIPTION
				"TYPE: - Checkbox
				 PAGE: - AudioInput
					Stereo5  cmdID= 40152 "
		::= { iqudc12CmdEntry 40152 }


	iqudc12AESInput18AESInput5AESInput51invert OBJECT-TYPE
		SYNTAX		INTEGER { disable(0), enable(1) }
		MAX-ACCESS		read-write
		STATUS			current
		DESCRIPTION
				"TYPE: - Checkbox
				 PAGE: - AudioInput
					AESInput5_1_invert  cmdID= 40124 "
		::= { iqudc12CmdEntry 40124 }


	iqudc12AESInput18AESInput5AESInput52invert OBJECT-TYPE
		SYNTAX		INTEGER { disable(0), enable(1) }
		MAX-ACCESS		read-write
		STATUS			current
		DESCRIPTION
				"TYPE: - Checkbox
				 PAGE: - AudioInput
					AESInput5_2_invert  cmdID= 40125 "
		::= { iqudc12CmdEntry 40125 }


	iqudc12AESInput18AESInput5AESIO OBJECT-TYPE
		SYNTAX		INTEGER {
							val-Set-Output(0),
							val-Set-Input(1)
							}
		MAX-ACCESS		read-write
		STATUS			current
		DESCRIPTION
				"TYPE: - RadiobuttonList
				 PAGE: - AudioInput
					AES I/O  cmdID= 40267 
					Set Output  value= 0  
					Set Input  value= 1  "
		::= { iqudc12CmdEntry 40267 }


	iqudc12AESInput18AESInput6AESInput61procamp OBJECT-TYPE
		SYNTAX		INTEGER
		MAX-ACCESS		read-write
		STATUS			current
		DESCRIPTION
				"TYPE: - Number
				 PAGE: - AudioInput
					AESInput6_1_procamp  cmdID= 40110  min= -801  max= 120  step= 1  format= %0.1f dB  div_scale= 10 
					Min = -80.1 dB  Max = 12.0 dB  Step = 0.1 dB "
		::= { iqudc12CmdEntry 40110 }


	iqudc12AESInput18AESInput6AESInput62procamp OBJECT-TYPE
		SYNTAX		INTEGER
		MAX-ACCESS		read-write
		STATUS			current
		DESCRIPTION
				"TYPE: - Number
				 PAGE: - AudioInput
					AESInput6_2_procamp  cmdID= 40111  min= -801  max= 120  step= 1  format= %0.1f dB  div_scale= 10 
					Min = -80.1 dB  Max = 12.0 dB  Step = 0.1 dB "
		::= { iqudc12CmdEntry 40111 }


	iqudc12AESInput18AESInput6Mute61 OBJECT-TYPE
		SYNTAX		INTEGER { disable(0), enable(1) }
		MAX-ACCESS		read-write
		STATUS			current
		DESCRIPTION
				"TYPE: - Checkbox
				 PAGE: - AudioInput
					Mute6_1  cmdID= 40142 "
		::= { iqudc12CmdEntry 40142 }


	iqudc12AESInput18AESInput6Mute62 OBJECT-TYPE
		SYNTAX		INTEGER { disable(0), enable(1) }
		MAX-ACCESS		read-write
		STATUS			current
		DESCRIPTION
				"TYPE: - Checkbox
				 PAGE: - AudioInput
					Mute6_2  cmdID= 40143 "
		::= { iqudc12CmdEntry 40143 }


	iqudc12AESInput18AESInput6Stereo6 OBJECT-TYPE
		SYNTAX		INTEGER { disable(0), enable(1) }
		MAX-ACCESS		read-write
		STATUS			current
		DESCRIPTION
				"TYPE: - Checkbox
				 PAGE: - AudioInput
					Stereo6  cmdID= 40153 "
		::= { iqudc12CmdEntry 40153 }


	iqudc12AESInput18AESInput6AESInput61invert OBJECT-TYPE
		SYNTAX		INTEGER { disable(0), enable(1) }
		MAX-ACCESS		read-write
		STATUS			current
		DESCRIPTION
				"TYPE: - Checkbox
				 PAGE: - AudioInput
					AESInput6_1_invert  cmdID= 40126 "
		::= { iqudc12CmdEntry 40126 }


	iqudc12AESInput18AESInput6AESInput62invert OBJECT-TYPE
		SYNTAX		INTEGER { disable(0), enable(1) }
		MAX-ACCESS		read-write
		STATUS			current
		DESCRIPTION
				"TYPE: - Checkbox
				 PAGE: - AudioInput
					AESInput6_2_invert  cmdID= 40127 "
		::= { iqudc12CmdEntry 40127 }


	iqudc12AESInput18AESInput6AESIO OBJECT-TYPE
		SYNTAX		INTEGER {
							val-Set-Output(0),
							val-Set-Input(1)
							}
		MAX-ACCESS		read-write
		STATUS			current
		DESCRIPTION
				"TYPE: - RadiobuttonList
				 PAGE: - AudioInput
					AES I/O  cmdID= 40268 
					Set Output  value= 0  
					Set Input  value= 1  "
		::= { iqudc12CmdEntry 40268 }


	iqudc12AESInput18AESInput7AESInput71procamp OBJECT-TYPE
		SYNTAX		INTEGER
		MAX-ACCESS		read-write
		STATUS			current
		DESCRIPTION
				"TYPE: - Number
				 PAGE: - AudioInput
					AESInput7_1_procamp  cmdID= 40112  min= -801  max= 120  step= 1  format= %0.1f dB  div_scale= 10 
					Min = -80.1 dB  Max = 12.0 dB  Step = 0.1 dB "
		::= { iqudc12CmdEntry 40112 }


	iqudc12AESInput18AESInput7AESInput72procamp OBJECT-TYPE
		SYNTAX		INTEGER
		MAX-ACCESS		read-write
		STATUS			current
		DESCRIPTION
				"TYPE: - Number
				 PAGE: - AudioInput
					AESInput7_2_procamp  cmdID= 40113  min= -801  max= 120  step= 1  format= %0.1f dB  div_scale= 10 
					Min = -80.1 dB  Max = 12.0 dB  Step = 0.1 dB "
		::= { iqudc12CmdEntry 40113 }


	iqudc12AESInput18AESInput7Mute71 OBJECT-TYPE
		SYNTAX		INTEGER { disable(0), enable(1) }
		MAX-ACCESS		read-write
		STATUS			current
		DESCRIPTION
				"TYPE: - Checkbox
				 PAGE: - AudioInput
					Mute7_1  cmdID= 40144 "
		::= { iqudc12CmdEntry 40144 }


	iqudc12AESInput18AESInput7Mute72 OBJECT-TYPE
		SYNTAX		INTEGER { disable(0), enable(1) }
		MAX-ACCESS		read-write
		STATUS			current
		DESCRIPTION
				"TYPE: - Checkbox
				 PAGE: - AudioInput
					Mute7_2  cmdID= 40145 "
		::= { iqudc12CmdEntry 40145 }


	iqudc12AESInput18AESInput7Stereo7 OBJECT-TYPE
		SYNTAX		INTEGER { disable(0), enable(1) }
		MAX-ACCESS		read-write
		STATUS			current
		DESCRIPTION
				"TYPE: - Checkbox
				 PAGE: - AudioInput
					Stereo7  cmdID= 40154 "
		::= { iqudc12CmdEntry 40154 }


	iqudc12AESInput18AESInput7AESInput71invert OBJECT-TYPE
		SYNTAX		INTEGER { disable(0), enable(1) }
		MAX-ACCESS		read-write
		STATUS			current
		DESCRIPTION
				"TYPE: - Checkbox
				 PAGE: - AudioInput
					AESInput7_1_invert  cmdID= 40128 "
		::= { iqudc12CmdEntry 40128 }


	iqudc12AESInput18AESInput7AESInput72invert OBJECT-TYPE
		SYNTAX		INTEGER { disable(0), enable(1) }
		MAX-ACCESS		read-write
		STATUS			current
		DESCRIPTION
				"TYPE: - Checkbox
				 PAGE: - AudioInput
					AESInput7_2_invert  cmdID= 40129 "
		::= { iqudc12CmdEntry 40129 }


	iqudc12AESInput18AESInput7AESIO OBJECT-TYPE
		SYNTAX		INTEGER {
							val-Set-Output(0),
							val-Set-Input(1)
							}
		MAX-ACCESS		read-write
		STATUS			current
		DESCRIPTION
				"TYPE: - RadiobuttonList
				 PAGE: - AudioInput
					AES I/O  cmdID= 40269 
					Set Output  value= 0  
					Set Input  value= 1  "
		::= { iqudc12CmdEntry 40269 }


	iqudc12AESInput18AESInput8AESInput81procamp OBJECT-TYPE
		SYNTAX		INTEGER
		MAX-ACCESS		read-write
		STATUS			current
		DESCRIPTION
				"TYPE: - Number
				 PAGE: - AudioInput
					AESInput8_1_procamp  cmdID= 40114  min= -801  max= 120  step= 1  format= %0.1f dB  div_scale= 10 
					Min = -80.1 dB  Max = 12.0 dB  Step = 0.1 dB "
		::= { iqudc12CmdEntry 40114 }


	iqudc12AESInput18AESInput8AESInput82procamp OBJECT-TYPE
		SYNTAX		INTEGER
		MAX-ACCESS		read-write
		STATUS			current
		DESCRIPTION
				"TYPE: - Number
				 PAGE: - AudioInput
					AESInput8_2_procamp  cmdID= 40115  min= -801  max= 120  step= 1  format= %0.1f dB  div_scale= 10 
					Min = -80.1 dB  Max = 12.0 dB  Step = 0.1 dB "
		::= { iqudc12CmdEntry 40115 }


	iqudc12AESInput18AESInput8Mute81 OBJECT-TYPE
		SYNTAX		INTEGER { disable(0), enable(1) }
		MAX-ACCESS		read-write
		STATUS			current
		DESCRIPTION
				"TYPE: - Checkbox
				 PAGE: - AudioInput
					Mute8_1  cmdID= 40146 "
		::= { iqudc12CmdEntry 40146 }


	iqudc12AESInput18AESInput8Mute82 OBJECT-TYPE
		SYNTAX		INTEGER { disable(0), enable(1) }
		MAX-ACCESS		read-write
		STATUS			current
		DESCRIPTION
				"TYPE: - Checkbox
				 PAGE: - AudioInput
					Mute8_2  cmdID= 40147 "
		::= { iqudc12CmdEntry 40147 }


	iqudc12AESInput18AESInput8Stereo8 OBJECT-TYPE
		SYNTAX		INTEGER { disable(0), enable(1) }
		MAX-ACCESS		read-write
		STATUS			current
		DESCRIPTION
				"TYPE: - Checkbox
				 PAGE: - AudioInput
					Stereo8  cmdID= 40155 "
		::= { iqudc12CmdEntry 40155 }


	iqudc12AESInput18AESInput8AESInput81invert OBJECT-TYPE
		SYNTAX		INTEGER { disable(0), enable(1) }
		MAX-ACCESS		read-write
		STATUS			current
		DESCRIPTION
				"TYPE: - Checkbox
				 PAGE: - AudioInput
					AESInput8_1_invert  cmdID= 40130 "
		::= { iqudc12CmdEntry 40130 }


	iqudc12AESInput18AESInput8AESInput82invert OBJECT-TYPE
		SYNTAX		INTEGER { disable(0), enable(1) }
		MAX-ACCESS		read-write
		STATUS			current
		DESCRIPTION
				"TYPE: - Checkbox
				 PAGE: - AudioInput
					AESInput8_2_invert  cmdID= 40131 "
		::= { iqudc12CmdEntry 40131 }


	iqudc12AESInput18AESInput8AESIO OBJECT-TYPE
		SYNTAX		INTEGER {
							val-Set-Output(0),
							val-Set-Input(1)
							}
		MAX-ACCESS		read-write
		STATUS			current
		DESCRIPTION
				"TYPE: - RadiobuttonList
				 PAGE: - AudioInput
					AES I/O  cmdID= 40270 
					Set Output  value= 0  
					Set Input  value= 1  "
		::= { iqudc12CmdEntry 40270 }


	iqudc12AnalogInput12AnalogInput1AnalogInput11proc OBJECT-TYPE
		SYNTAX		INTEGER
		MAX-ACCESS		read-write
		STATUS			current
		DESCRIPTION
				"TYPE: - Number
				 PAGE: - AudioInput
					AnalogInput1_1_proc  cmdID= 40181  min= -801  max= 120  step= 1  format= %0.1f dB  div_scale= 10 
					Min = -80.1 dB  Max = 12.0 dB  Step = 0.1 dB "
		::= { iqudc12CmdEntry 40181 }


	iqudc12AnalogInput12AnalogInput1AnalogInput12proc OBJECT-TYPE
		SYNTAX		INTEGER
		MAX-ACCESS		read-write
		STATUS			current
		DESCRIPTION
				"TYPE: - Number
				 PAGE: - AudioInput
					AnalogInput1_2_proc  cmdID= 40182  min= -801  max= 120  step= 1  format= %0.1f dB  div_scale= 10 
					Min = -80.1 dB  Max = 12.0 dB  Step = 0.1 dB "
		::= { iqudc12CmdEntry 40182 }


	iqudc12AnalogInput12AnalogInput1Mute11 OBJECT-TYPE
		SYNTAX		INTEGER { disable(0), enable(1) }
		MAX-ACCESS		read-write
		STATUS			current
		DESCRIPTION
				"TYPE: - Checkbox
				 PAGE: - AudioInput
					Mute1_1  cmdID= 40189 "
		::= { iqudc12CmdEntry 40189 }


	iqudc12AnalogInput12AnalogInput1Mute12 OBJECT-TYPE
		SYNTAX		INTEGER { disable(0), enable(1) }
		MAX-ACCESS		read-write
		STATUS			current
		DESCRIPTION
				"TYPE: - Checkbox
				 PAGE: - AudioInput
					Mute1_2  cmdID= 40190 "
		::= { iqudc12CmdEntry 40190 }


	iqudc12AnalogInput12AnalogInput1Stereo1 OBJECT-TYPE
		SYNTAX		INTEGER { disable(0), enable(1) }
		MAX-ACCESS		read-write
		STATUS			current
		DESCRIPTION
				"TYPE: - Checkbox
				 PAGE: - AudioInput
					Stereo1  cmdID= 40193 "
		::= { iqudc12CmdEntry 40193 }


	iqudc12AnalogInput12AnalogInput1AnalogInput11inve OBJECT-TYPE
		SYNTAX		INTEGER { disable(0), enable(1) }
		MAX-ACCESS		read-write
		STATUS			current
		DESCRIPTION
				"TYPE: - Checkbox
				 PAGE: - AudioInput
					AnalogInput1_1_inve  cmdID= 40185 "
		::= { iqudc12CmdEntry 40185 }


	iqudc12AnalogInput12AnalogInput1AnalogInput12inve OBJECT-TYPE
		SYNTAX		INTEGER { disable(0), enable(1) }
		MAX-ACCESS		read-write
		STATUS			current
		DESCRIPTION
				"TYPE: - Checkbox
				 PAGE: - AudioInput
					AnalogInput1_2_inve  cmdID= 40186 "
		::= { iqudc12CmdEntry 40186 }


	iqudc12AnalogInput12AnalogInput2AnalogInput21proc OBJECT-TYPE
		SYNTAX		INTEGER
		MAX-ACCESS		read-write
		STATUS			current
		DESCRIPTION
				"TYPE: - Number
				 PAGE: - AudioInput
					AnalogInput2_1_proc  cmdID= 40183  min= -801  max= 120  step= 1  format= %0.1f dB  div_scale= 10 
					Min = -80.1 dB  Max = 12.0 dB  Step = 0.1 dB "
		::= { iqudc12CmdEntry 40183 }


	iqudc12AnalogInput12AnalogInput2AnalogInput22proc OBJECT-TYPE
		SYNTAX		INTEGER
		MAX-ACCESS		read-write
		STATUS			current
		DESCRIPTION
				"TYPE: - Number
				 PAGE: - AudioInput
					AnalogInput2_2_proc  cmdID= 40184  min= -801  max= 120  step= 1  format= %0.1f dB  div_scale= 10 
					Min = -80.1 dB  Max = 12.0 dB  Step = 0.1 dB "
		::= { iqudc12CmdEntry 40184 }


	iqudc12AnalogInput12AnalogInput2Mute21 OBJECT-TYPE
		SYNTAX		INTEGER { disable(0), enable(1) }
		MAX-ACCESS		read-write
		STATUS			current
		DESCRIPTION
				"TYPE: - Checkbox
				 PAGE: - AudioInput
					Mute2_1  cmdID= 40191 "
		::= { iqudc12CmdEntry 40191 }


	iqudc12AnalogInput12AnalogInput2Mute22 OBJECT-TYPE
		SYNTAX		INTEGER { disable(0), enable(1) }
		MAX-ACCESS		read-write
		STATUS			current
		DESCRIPTION
				"TYPE: - Checkbox
				 PAGE: - AudioInput
					Mute2_2  cmdID= 40192 "
		::= { iqudc12CmdEntry 40192 }


	iqudc12AnalogInput12AnalogInput2Stereo2 OBJECT-TYPE
		SYNTAX		INTEGER { disable(0), enable(1) }
		MAX-ACCESS		read-write
		STATUS			current
		DESCRIPTION
				"TYPE: - Checkbox
				 PAGE: - AudioInput
					Stereo2  cmdID= 40194 "
		::= { iqudc12CmdEntry 40194 }


	iqudc12AnalogInput12AnalogInput2AnalogInput21inve OBJECT-TYPE
		SYNTAX		INTEGER { disable(0), enable(1) }
		MAX-ACCESS		read-write
		STATUS			current
		DESCRIPTION
				"TYPE: - Checkbox
				 PAGE: - AudioInput
					AnalogInput2_1_inve  cmdID= 40187 "
		::= { iqudc12CmdEntry 40187 }


	iqudc12AnalogInput12AnalogInput2AnalogInput22inve OBJECT-TYPE
		SYNTAX		INTEGER { disable(0), enable(1) }
		MAX-ACCESS		read-write
		STATUS			current
		DESCRIPTION
				"TYPE: - Checkbox
				 PAGE: - AudioInput
					AnalogInput2_2_inve  cmdID= 40188 "
		::= { iqudc12CmdEntry 40188 }


	iqudc12Embed18Embed1Embed11procamp OBJECT-TYPE
		SYNTAX		INTEGER
		MAX-ACCESS		read-write
		STATUS			current
		DESCRIPTION
				"TYPE: - Number
				 PAGE: - AudioOutput
					Embed1_1_procamp  cmdID= 40400  min= -801  max= 120  step= 1  format= %0.1f dB  div_scale= 10 
					Min = -80.1 dB  Max = 12.0 dB  Step = 0.1 dB "
		::= { iqudc12CmdEntry 40400 }


	iqudc12Embed18Embed1Embed12procamp OBJECT-TYPE
		SYNTAX		INTEGER
		MAX-ACCESS		read-write
		STATUS			current
		DESCRIPTION
				"TYPE: - Number
				 PAGE: - AudioOutput
					Embed1_2_procamp  cmdID= 40401  min= -801  max= 120  step= 1  format= %0.1f dB  div_scale= 10 
					Min = -80.1 dB  Max = 12.0 dB  Step = 0.1 dB "
		::= { iqudc12CmdEntry 40401 }


	iqudc12Embed18Embed1Mute11 OBJECT-TYPE
		SYNTAX		INTEGER { disable(0), enable(1) }
		MAX-ACCESS		read-write
		STATUS			current
		DESCRIPTION
				"TYPE: - Checkbox
				 PAGE: - AudioOutput
					Mute1_1  cmdID= 40432 "
		::= { iqudc12CmdEntry 40432 }


	iqudc12Embed18Embed1Mute12 OBJECT-TYPE
		SYNTAX		INTEGER { disable(0), enable(1) }
		MAX-ACCESS		read-write
		STATUS			current
		DESCRIPTION
				"TYPE: - Checkbox
				 PAGE: - AudioOutput
					Mute1_2  cmdID= 40433 "
		::= { iqudc12CmdEntry 40433 }


	iqudc12Embed18Embed1Stereo1 OBJECT-TYPE
		SYNTAX		INTEGER { disable(0), enable(1) }
		MAX-ACCESS		read-write
		STATUS			current
		DESCRIPTION
				"TYPE: - Checkbox
				 PAGE: - AudioOutput
					Stereo1  cmdID= 40448 "
		::= { iqudc12CmdEntry 40448 }


	iqudc12Embed18Embed1dolbyLine OBJECT-TYPE
		SYNTAX		RollCallString
		MAX-ACCESS		read-only
		STATUS			current
		DESCRIPTION
				"TYPE: - Display
				 PAGE: - AudioOutput
					dolbyLine  cmdID= 40081  format=   "
		::= { iqudc12CmdEntry 40081 }


	iqudc12Embed18Embed2Embed21procamp OBJECT-TYPE
		SYNTAX		INTEGER
		MAX-ACCESS		read-write
		STATUS			current
		DESCRIPTION
				"TYPE: - Number
				 PAGE: - AudioOutput
					Embed2_1_procamp  cmdID= 40402  min= -801  max= 120  step= 1  format= %0.1f dB  div_scale= 10 
					Min = -80.1 dB  Max = 12.0 dB  Step = 0.1 dB "
		::= { iqudc12CmdEntry 40402 }


	iqudc12Embed18Embed2Embed22procamp OBJECT-TYPE
		SYNTAX		INTEGER
		MAX-ACCESS		read-write
		STATUS			current
		DESCRIPTION
				"TYPE: - Number
				 PAGE: - AudioOutput
					Embed2_2_procamp  cmdID= 40403  min= -801  max= 120  step= 1  format= %0.1f dB  div_scale= 10 
					Min = -80.1 dB  Max = 12.0 dB  Step = 0.1 dB "
		::= { iqudc12CmdEntry 40403 }


	iqudc12Embed18Embed2Mute21 OBJECT-TYPE
		SYNTAX		INTEGER { disable(0), enable(1) }
		MAX-ACCESS		read-write
		STATUS			current
		DESCRIPTION
				"TYPE: - Checkbox
				 PAGE: - AudioOutput
					Mute2_1  cmdID= 40434 "
		::= { iqudc12CmdEntry 40434 }


	iqudc12Embed18Embed2Mute22 OBJECT-TYPE
		SYNTAX		INTEGER { disable(0), enable(1) }
		MAX-ACCESS		read-write
		STATUS			current
		DESCRIPTION
				"TYPE: - Checkbox
				 PAGE: - AudioOutput
					Mute2_2  cmdID= 40435 "
		::= { iqudc12CmdEntry 40435 }


	iqudc12Embed18Embed2Stereo2 OBJECT-TYPE
		SYNTAX		INTEGER { disable(0), enable(1) }
		MAX-ACCESS		read-write
		STATUS			current
		DESCRIPTION
				"TYPE: - Checkbox
				 PAGE: - AudioOutput
					Stereo2  cmdID= 40449 "
		::= { iqudc12CmdEntry 40449 }


	iqudc12Embed18Embed2dolbyLine OBJECT-TYPE
		SYNTAX		RollCallString
		MAX-ACCESS		read-only
		STATUS			current
		DESCRIPTION
				"TYPE: - Display
				 PAGE: - AudioOutput
					dolbyLine  cmdID= 40082  format=   "
		::= { iqudc12CmdEntry 40082 }


	iqudc12Embed18Embed3Embed31procamp OBJECT-TYPE
		SYNTAX		INTEGER
		MAX-ACCESS		read-write
		STATUS			current
		DESCRIPTION
				"TYPE: - Number
				 PAGE: - AudioOutput
					Embed3_1_procamp  cmdID= 40404  min= -801  max= 120  step= 1  format= %0.1f dB  div_scale= 10 
					Min = -80.1 dB  Max = 12.0 dB  Step = 0.1 dB "
		::= { iqudc12CmdEntry 40404 }


	iqudc12Embed18Embed3Embed32procamp OBJECT-TYPE
		SYNTAX		INTEGER
		MAX-ACCESS		read-write
		STATUS			current
		DESCRIPTION
				"TYPE: - Number
				 PAGE: - AudioOutput
					Embed3_2_procamp  cmdID= 40405  min= -801  max= 120  step= 1  format= %0.1f dB  div_scale= 10 
					Min = -80.1 dB  Max = 12.0 dB  Step = 0.1 dB "
		::= { iqudc12CmdEntry 40405 }


	iqudc12Embed18Embed3Mute31 OBJECT-TYPE
		SYNTAX		INTEGER { disable(0), enable(1) }
		MAX-ACCESS		read-write
		STATUS			current
		DESCRIPTION
				"TYPE: - Checkbox
				 PAGE: - AudioOutput
					Mute3_1  cmdID= 40436 "
		::= { iqudc12CmdEntry 40436 }


	iqudc12Embed18Embed3Mute32 OBJECT-TYPE
		SYNTAX		INTEGER { disable(0), enable(1) }
		MAX-ACCESS		read-write
		STATUS			current
		DESCRIPTION
				"TYPE: - Checkbox
				 PAGE: - AudioOutput
					Mute3_2  cmdID= 40437 "
		::= { iqudc12CmdEntry 40437 }


	iqudc12Embed18Embed3Stereo3 OBJECT-TYPE
		SYNTAX		INTEGER { disable(0), enable(1) }
		MAX-ACCESS		read-write
		STATUS			current
		DESCRIPTION
				"TYPE: - Checkbox
				 PAGE: - AudioOutput
					Stereo3  cmdID= 40450 "
		::= { iqudc12CmdEntry 40450 }


	iqudc12Embed18Embed3dolbyLine OBJECT-TYPE
		SYNTAX		RollCallString
		MAX-ACCESS		read-only
		STATUS			current
		DESCRIPTION
				"TYPE: - Display
				 PAGE: - AudioOutput
					dolbyLine  cmdID= 40083  format=   "
		::= { iqudc12CmdEntry 40083 }


	iqudc12Embed18Embed4Embed41procamp OBJECT-TYPE
		SYNTAX		INTEGER
		MAX-ACCESS		read-write
		STATUS			current
		DESCRIPTION
				"TYPE: - Number
				 PAGE: - AudioOutput
					Embed4_1_procamp  cmdID= 40406  min= -801  max= 120  step= 1  format= %0.1f dB  div_scale= 10 
					Min = -80.1 dB  Max = 12.0 dB  Step = 0.1 dB "
		::= { iqudc12CmdEntry 40406 }


	iqudc12Embed18Embed4Embed42procamp OBJECT-TYPE
		SYNTAX		INTEGER
		MAX-ACCESS		read-write
		STATUS			current
		DESCRIPTION
				"TYPE: - Number
				 PAGE: - AudioOutput
					Embed4_2_procamp  cmdID= 40407  min= -801  max= 120  step= 1  format= %0.1f dB  div_scale= 10 
					Min = -80.1 dB  Max = 12.0 dB  Step = 0.1 dB "
		::= { iqudc12CmdEntry 40407 }


	iqudc12Embed18Embed4Mute41 OBJECT-TYPE
		SYNTAX		INTEGER { disable(0), enable(1) }
		MAX-ACCESS		read-write
		STATUS			current
		DESCRIPTION
				"TYPE: - Checkbox
				 PAGE: - AudioOutput
					Mute4_1  cmdID= 40438 "
		::= { iqudc12CmdEntry 40438 }


	iqudc12Embed18Embed4Mute42 OBJECT-TYPE
		SYNTAX		INTEGER { disable(0), enable(1) }
		MAX-ACCESS		read-write
		STATUS			current
		DESCRIPTION
				"TYPE: - Checkbox
				 PAGE: - AudioOutput
					Mute4_2  cmdID= 40439 "
		::= { iqudc12CmdEntry 40439 }


	iqudc12Embed18Embed4Stereo4 OBJECT-TYPE
		SYNTAX		INTEGER { disable(0), enable(1) }
		MAX-ACCESS		read-write
		STATUS			current
		DESCRIPTION
				"TYPE: - Checkbox
				 PAGE: - AudioOutput
					Stereo4  cmdID= 40451 "
		::= { iqudc12CmdEntry 40451 }


	iqudc12Embed18Embed4dolbyLine OBJECT-TYPE
		SYNTAX		RollCallString
		MAX-ACCESS		read-only
		STATUS			current
		DESCRIPTION
				"TYPE: - Display
				 PAGE: - AudioOutput
					dolbyLine  cmdID= 40084  format=   "
		::= { iqudc12CmdEntry 40084 }


	iqudc12Embed18Embed5Embed51procamp OBJECT-TYPE
		SYNTAX		INTEGER
		MAX-ACCESS		read-write
		STATUS			current
		DESCRIPTION
				"TYPE: - Number
				 PAGE: - AudioOutput
					Embed5_1_procamp  cmdID= 40408  min= -801  max= 120  step= 1  format= %0.1f dB  div_scale= 10 
					Min = -80.1 dB  Max = 12.0 dB  Step = 0.1 dB "
		::= { iqudc12CmdEntry 40408 }


	iqudc12Embed18Embed5Embed52procamp OBJECT-TYPE
		SYNTAX		INTEGER
		MAX-ACCESS		read-write
		STATUS			current
		DESCRIPTION
				"TYPE: - Number
				 PAGE: - AudioOutput
					Embed5_2_procamp  cmdID= 40409  min= -801  max= 120  step= 1  format= %0.1f dB  div_scale= 10 
					Min = -80.1 dB  Max = 12.0 dB  Step = 0.1 dB "
		::= { iqudc12CmdEntry 40409 }


	iqudc12Embed18Embed5Mute51 OBJECT-TYPE
		SYNTAX		INTEGER { disable(0), enable(1) }
		MAX-ACCESS		read-write
		STATUS			current
		DESCRIPTION
				"TYPE: - Checkbox
				 PAGE: - AudioOutput
					Mute5_1  cmdID= 40440 "
		::= { iqudc12CmdEntry 40440 }


	iqudc12Embed18Embed5Mute52 OBJECT-TYPE
		SYNTAX		INTEGER { disable(0), enable(1) }
		MAX-ACCESS		read-write
		STATUS			current
		DESCRIPTION
				"TYPE: - Checkbox
				 PAGE: - AudioOutput
					Mute5_2  cmdID= 40441 "
		::= { iqudc12CmdEntry 40441 }


	iqudc12Embed18Embed5Stereo5 OBJECT-TYPE
		SYNTAX		INTEGER { disable(0), enable(1) }
		MAX-ACCESS		read-write
		STATUS			current
		DESCRIPTION
				"TYPE: - Checkbox
				 PAGE: - AudioOutput
					Stereo5  cmdID= 40452 "
		::= { iqudc12CmdEntry 40452 }


	iqudc12Embed18Embed5dolbyLine OBJECT-TYPE
		SYNTAX		RollCallString
		MAX-ACCESS		read-only
		STATUS			current
		DESCRIPTION
				"TYPE: - Display
				 PAGE: - AudioOutput
					dolbyLine  cmdID= 40085  format=   "
		::= { iqudc12CmdEntry 40085 }


	iqudc12Embed18Embed6Embed61procamp OBJECT-TYPE
		SYNTAX		INTEGER
		MAX-ACCESS		read-write
		STATUS			current
		DESCRIPTION
				"TYPE: - Number
				 PAGE: - AudioOutput
					Embed6_1_procamp  cmdID= 40410  min= -801  max= 120  step= 1  format= %0.1f dB  div_scale= 10 
					Min = -80.1 dB  Max = 12.0 dB  Step = 0.1 dB "
		::= { iqudc12CmdEntry 40410 }


	iqudc12Embed18Embed6Embed62procamp OBJECT-TYPE
		SYNTAX		INTEGER
		MAX-ACCESS		read-write
		STATUS			current
		DESCRIPTION
				"TYPE: - Number
				 PAGE: - AudioOutput
					Embed6_2_procamp  cmdID= 40411  min= -801  max= 120  step= 1  format= %0.1f dB  div_scale= 10 
					Min = -80.1 dB  Max = 12.0 dB  Step = 0.1 dB "
		::= { iqudc12CmdEntry 40411 }


	iqudc12Embed18Embed6Mute61 OBJECT-TYPE
		SYNTAX		INTEGER { disable(0), enable(1) }
		MAX-ACCESS		read-write
		STATUS			current
		DESCRIPTION
				"TYPE: - Checkbox
				 PAGE: - AudioOutput
					Mute6_1  cmdID= 40442 "
		::= { iqudc12CmdEntry 40442 }


	iqudc12Embed18Embed6Mute62 OBJECT-TYPE
		SYNTAX		INTEGER { disable(0), enable(1) }
		MAX-ACCESS		read-write
		STATUS			current
		DESCRIPTION
				"TYPE: - Checkbox
				 PAGE: - AudioOutput
					Mute6_2  cmdID= 40443 "
		::= { iqudc12CmdEntry 40443 }


	iqudc12Embed18Embed6Stereo6 OBJECT-TYPE
		SYNTAX		INTEGER { disable(0), enable(1) }
		MAX-ACCESS		read-write
		STATUS			current
		DESCRIPTION
				"TYPE: - Checkbox
				 PAGE: - AudioOutput
					Stereo6  cmdID= 40453 "
		::= { iqudc12CmdEntry 40453 }


	iqudc12Embed18Embed6dolbyLine OBJECT-TYPE
		SYNTAX		RollCallString
		MAX-ACCESS		read-only
		STATUS			current
		DESCRIPTION
				"TYPE: - Display
				 PAGE: - AudioOutput
					dolbyLine  cmdID= 40086  format=   "
		::= { iqudc12CmdEntry 40086 }


	iqudc12Embed18Embed7Embed71procamp OBJECT-TYPE
		SYNTAX		INTEGER
		MAX-ACCESS		read-write
		STATUS			current
		DESCRIPTION
				"TYPE: - Number
				 PAGE: - AudioOutput
					Embed7_1_procamp  cmdID= 40412  min= -801  max= 120  step= 1  format= %0.1f dB  div_scale= 10 
					Min = -80.1 dB  Max = 12.0 dB  Step = 0.1 dB "
		::= { iqudc12CmdEntry 40412 }


	iqudc12Embed18Embed7Embed72procamp OBJECT-TYPE
		SYNTAX		INTEGER
		MAX-ACCESS		read-write
		STATUS			current
		DESCRIPTION
				"TYPE: - Number
				 PAGE: - AudioOutput
					Embed7_2_procamp  cmdID= 40413  min= -801  max= 120  step= 1  format= %0.1f dB  div_scale= 10 
					Min = -80.1 dB  Max = 12.0 dB  Step = 0.1 dB "
		::= { iqudc12CmdEntry 40413 }


	iqudc12Embed18Embed7Mute71 OBJECT-TYPE
		SYNTAX		INTEGER { disable(0), enable(1) }
		MAX-ACCESS		read-write
		STATUS			current
		DESCRIPTION
				"TYPE: - Checkbox
				 PAGE: - AudioOutput
					Mute7_1  cmdID= 40444 "
		::= { iqudc12CmdEntry 40444 }


	iqudc12Embed18Embed7Mute72 OBJECT-TYPE
		SYNTAX		INTEGER { disable(0), enable(1) }
		MAX-ACCESS		read-write
		STATUS			current
		DESCRIPTION
				"TYPE: - Checkbox
				 PAGE: - AudioOutput
					Mute7_2  cmdID= 40445 "
		::= { iqudc12CmdEntry 40445 }


	iqudc12Embed18Embed7Stereo7 OBJECT-TYPE
		SYNTAX		INTEGER { disable(0), enable(1) }
		MAX-ACCESS		read-write
		STATUS			current
		DESCRIPTION
				"TYPE: - Checkbox
				 PAGE: - AudioOutput
					Stereo7  cmdID= 40454 "
		::= { iqudc12CmdEntry 40454 }


	iqudc12Embed18Embed7dolbyLine OBJECT-TYPE
		SYNTAX		RollCallString
		MAX-ACCESS		read-only
		STATUS			current
		DESCRIPTION
				"TYPE: - Display
				 PAGE: - AudioOutput
					dolbyLine  cmdID= 40087  format=   "
		::= { iqudc12CmdEntry 40087 }


	iqudc12Embed18Embed8Embed81procamp OBJECT-TYPE
		SYNTAX		INTEGER
		MAX-ACCESS		read-write
		STATUS			current
		DESCRIPTION
				"TYPE: - Number
				 PAGE: - AudioOutput
					Embed8_1_procamp  cmdID= 40414  min= -801  max= 120  step= 1  format= %0.1f dB  div_scale= 10 
					Min = -80.1 dB  Max = 12.0 dB  Step = 0.1 dB "
		::= { iqudc12CmdEntry 40414 }


	iqudc12Embed18Embed8Embed82procamp OBJECT-TYPE
		SYNTAX		INTEGER
		MAX-ACCESS		read-write
		STATUS			current
		DESCRIPTION
				"TYPE: - Number
				 PAGE: - AudioOutput
					Embed8_2_procamp  cmdID= 40415  min= -801  max= 120  step= 1  format= %0.1f dB  div_scale= 10 
					Min = -80.1 dB  Max = 12.0 dB  Step = 0.1 dB "
		::= { iqudc12CmdEntry 40415 }


	iqudc12Embed18Embed8Mute81 OBJECT-TYPE
		SYNTAX		INTEGER { disable(0), enable(1) }
		MAX-ACCESS		read-write
		STATUS			current
		DESCRIPTION
				"TYPE: - Checkbox
				 PAGE: - AudioOutput
					Mute8_1  cmdID= 40446 "
		::= { iqudc12CmdEntry 40446 }


	iqudc12Embed18Embed8Mute82 OBJECT-TYPE
		SYNTAX		INTEGER { disable(0), enable(1) }
		MAX-ACCESS		read-write
		STATUS			current
		DESCRIPTION
				"TYPE: - Checkbox
				 PAGE: - AudioOutput
					Mute8_2  cmdID= 40447 "
		::= { iqudc12CmdEntry 40447 }


	iqudc12Embed18Embed8Stereo8 OBJECT-TYPE
		SYNTAX		INTEGER { disable(0), enable(1) }
		MAX-ACCESS		read-write
		STATUS			current
		DESCRIPTION
				"TYPE: - Checkbox
				 PAGE: - AudioOutput
					Stereo8  cmdID= 40455 "
		::= { iqudc12CmdEntry 40455 }


	iqudc12Embed18Embed8dolbyLine OBJECT-TYPE
		SYNTAX		RollCallString
		MAX-ACCESS		read-only
		STATUS			current
		DESCRIPTION
				"TYPE: - Display
				 PAGE: - AudioOutput
					dolbyLine  cmdID= 40088  format=   "
		::= { iqudc12CmdEntry 40088 }


	iqudc12Embed18GroupEmbGroup1 OBJECT-TYPE
		SYNTAX		INTEGER { disable(0), enable(1) }
		MAX-ACCESS		read-write
		STATUS			current
		DESCRIPTION
				"TYPE: - Checkbox
				 PAGE: - AudioOutput
					EmbGroup1  cmdID= 36139 "
		::= { iqudc12CmdEntry 36139 }


	iqudc12Embed18GroupEmbGroup2 OBJECT-TYPE
		SYNTAX		INTEGER { disable(0), enable(1) }
		MAX-ACCESS		read-write
		STATUS			current
		DESCRIPTION
				"TYPE: - Checkbox
				 PAGE: - AudioOutput
					EmbGroup2  cmdID= 36140 "
		::= { iqudc12CmdEntry 36140 }


	iqudc12Embed18GroupEmbGroup3 OBJECT-TYPE
		SYNTAX		INTEGER { disable(0), enable(1) }
		MAX-ACCESS		read-write
		STATUS			current
		DESCRIPTION
				"TYPE: - Checkbox
				 PAGE: - AudioOutput
					EmbGroup3  cmdID= 36141 "
		::= { iqudc12CmdEntry 36141 }


	iqudc12Embed18GroupEmbGroup4 OBJECT-TYPE
		SYNTAX		INTEGER { disable(0), enable(1) }
		MAX-ACCESS		read-write
		STATUS			current
		DESCRIPTION
				"TYPE: - Checkbox
				 PAGE: - AudioOutput
					EmbGroup4  cmdID= 36142 "
		::= { iqudc12CmdEntry 36142 }


	iqudc12AESOutput18AESOutput1AESOutput11procam OBJECT-TYPE
		SYNTAX		INTEGER
		MAX-ACCESS		read-write
		STATUS			current
		DESCRIPTION
				"TYPE: - Number
				 PAGE: - AudioOutput
					AESOutput1_1_procam  cmdID= 40500  min= -801  max= 120  step= 1  format= %0.1f dB  div_scale= 10 
					Min = -80.1 dB  Max = 12.0 dB  Step = 0.1 dB "
		::= { iqudc12CmdEntry 40500 }


	iqudc12AESOutput18AESOutput1AESOutput12procam OBJECT-TYPE
		SYNTAX		INTEGER
		MAX-ACCESS		read-write
		STATUS			current
		DESCRIPTION
				"TYPE: - Number
				 PAGE: - AudioOutput
					AESOutput1_2_procam  cmdID= 40501  min= -801  max= 120  step= 1  format= %0.1f dB  div_scale= 10 
					Min = -80.1 dB  Max = 12.0 dB  Step = 0.1 dB "
		::= { iqudc12CmdEntry 40501 }


	iqudc12AESOutput18AESOutput1Mute11 OBJECT-TYPE
		SYNTAX		INTEGER { disable(0), enable(1) }
		MAX-ACCESS		read-write
		STATUS			current
		DESCRIPTION
				"TYPE: - Checkbox
				 PAGE: - AudioOutput
					Mute1_1  cmdID= 40532 "
		::= { iqudc12CmdEntry 40532 }


	iqudc12AESOutput18AESOutput1Mute12 OBJECT-TYPE
		SYNTAX		INTEGER { disable(0), enable(1) }
		MAX-ACCESS		read-write
		STATUS			current
		DESCRIPTION
				"TYPE: - Checkbox
				 PAGE: - AudioOutput
					Mute1_2  cmdID= 40533 "
		::= { iqudc12CmdEntry 40533 }


	iqudc12AESOutput18AESOutput1Stereo1 OBJECT-TYPE
		SYNTAX		INTEGER { disable(0), enable(1) }
		MAX-ACCESS		read-write
		STATUS			current
		DESCRIPTION
				"TYPE: - Checkbox
				 PAGE: - AudioOutput
					Stereo1  cmdID= 40548 "
		::= { iqudc12CmdEntry 40548 }


	iqudc12AESOutput18AESOutput2AESOutput21procam OBJECT-TYPE
		SYNTAX		INTEGER
		MAX-ACCESS		read-write
		STATUS			current
		DESCRIPTION
				"TYPE: - Number
				 PAGE: - AudioOutput
					AESOutput2_1_procam  cmdID= 40502  min= -801  max= 120  step= 1  format= %0.1f dB  div_scale= 10 
					Min = -80.1 dB  Max = 12.0 dB  Step = 0.1 dB "
		::= { iqudc12CmdEntry 40502 }


	iqudc12AESOutput18AESOutput2AESOutput22procam OBJECT-TYPE
		SYNTAX		INTEGER
		MAX-ACCESS		read-write
		STATUS			current
		DESCRIPTION
				"TYPE: - Number
				 PAGE: - AudioOutput
					AESOutput2_2_procam  cmdID= 40503  min= -801  max= 120  step= 1  format= %0.1f dB  div_scale= 10 
					Min = -80.1 dB  Max = 12.0 dB  Step = 0.1 dB "
		::= { iqudc12CmdEntry 40503 }


	iqudc12AESOutput18AESOutput2Mute21 OBJECT-TYPE
		SYNTAX		INTEGER { disable(0), enable(1) }
		MAX-ACCESS		read-write
		STATUS			current
		DESCRIPTION
				"TYPE: - Checkbox
				 PAGE: - AudioOutput
					Mute2_1  cmdID= 40534 "
		::= { iqudc12CmdEntry 40534 }


	iqudc12AESOutput18AESOutput2Mute22 OBJECT-TYPE
		SYNTAX		INTEGER { disable(0), enable(1) }
		MAX-ACCESS		read-write
		STATUS			current
		DESCRIPTION
				"TYPE: - Checkbox
				 PAGE: - AudioOutput
					Mute2_2  cmdID= 40535 "
		::= { iqudc12CmdEntry 40535 }


	iqudc12AESOutput18AESOutput2Stereo2 OBJECT-TYPE
		SYNTAX		INTEGER { disable(0), enable(1) }
		MAX-ACCESS		read-write
		STATUS			current
		DESCRIPTION
				"TYPE: - Checkbox
				 PAGE: - AudioOutput
					Stereo2  cmdID= 40549 "
		::= { iqudc12CmdEntry 40549 }


	iqudc12AESOutput18AESOutput3AESOutput31procam OBJECT-TYPE
		SYNTAX		INTEGER
		MAX-ACCESS		read-write
		STATUS			current
		DESCRIPTION
				"TYPE: - Number
				 PAGE: - AudioOutput
					AESOutput3_1_procam  cmdID= 40504  min= -801  max= 120  step= 1  format= %0.1f dB  div_scale= 10 
					Min = -80.1 dB  Max = 12.0 dB  Step = 0.1 dB "
		::= { iqudc12CmdEntry 40504 }


	iqudc12AESOutput18AESOutput3AESOutput32procam OBJECT-TYPE
		SYNTAX		INTEGER
		MAX-ACCESS		read-write
		STATUS			current
		DESCRIPTION
				"TYPE: - Number
				 PAGE: - AudioOutput
					AESOutput3_2_procam  cmdID= 40505  min= -801  max= 120  step= 1  format= %0.1f dB  div_scale= 10 
					Min = -80.1 dB  Max = 12.0 dB  Step = 0.1 dB "
		::= { iqudc12CmdEntry 40505 }


	iqudc12AESOutput18AESOutput3Mute31 OBJECT-TYPE
		SYNTAX		INTEGER { disable(0), enable(1) }
		MAX-ACCESS		read-write
		STATUS			current
		DESCRIPTION
				"TYPE: - Checkbox
				 PAGE: - AudioOutput
					Mute3_1  cmdID= 40536 "
		::= { iqudc12CmdEntry 40536 }


	iqudc12AESOutput18AESOutput3Mute32 OBJECT-TYPE
		SYNTAX		INTEGER { disable(0), enable(1) }
		MAX-ACCESS		read-write
		STATUS			current
		DESCRIPTION
				"TYPE: - Checkbox
				 PAGE: - AudioOutput
					Mute3_2  cmdID= 40537 "
		::= { iqudc12CmdEntry 40537 }


	iqudc12AESOutput18AESOutput3Stereo3 OBJECT-TYPE
		SYNTAX		INTEGER { disable(0), enable(1) }
		MAX-ACCESS		read-write
		STATUS			current
		DESCRIPTION
				"TYPE: - Checkbox
				 PAGE: - AudioOutput
					Stereo3  cmdID= 40550 "
		::= { iqudc12CmdEntry 40550 }


	iqudc12AESOutput18AESOutput4AESOutput41procam OBJECT-TYPE
		SYNTAX		INTEGER
		MAX-ACCESS		read-write
		STATUS			current
		DESCRIPTION
				"TYPE: - Number
				 PAGE: - AudioOutput
					AESOutput4_1_procam  cmdID= 40506  min= -801  max= 120  step= 1  format= %0.1f dB  div_scale= 10 
					Min = -80.1 dB  Max = 12.0 dB  Step = 0.1 dB "
		::= { iqudc12CmdEntry 40506 }


	iqudc12AESOutput18AESOutput4AESOutput42procam OBJECT-TYPE
		SYNTAX		INTEGER
		MAX-ACCESS		read-write
		STATUS			current
		DESCRIPTION
				"TYPE: - Number
				 PAGE: - AudioOutput
					AESOutput4_2_procam  cmdID= 40507  min= -801  max= 120  step= 1  format= %0.1f dB  div_scale= 10 
					Min = -80.1 dB  Max = 12.0 dB  Step = 0.1 dB "
		::= { iqudc12CmdEntry 40507 }


	iqudc12AESOutput18AESOutput4Mute41 OBJECT-TYPE
		SYNTAX		INTEGER { disable(0), enable(1) }
		MAX-ACCESS		read-write
		STATUS			current
		DESCRIPTION
				"TYPE: - Checkbox
				 PAGE: - AudioOutput
					Mute4_1  cmdID= 40538 "
		::= { iqudc12CmdEntry 40538 }


	iqudc12AESOutput18AESOutput4Mute42 OBJECT-TYPE
		SYNTAX		INTEGER { disable(0), enable(1) }
		MAX-ACCESS		read-write
		STATUS			current
		DESCRIPTION
				"TYPE: - Checkbox
				 PAGE: - AudioOutput
					Mute4_2  cmdID= 40539 "
		::= { iqudc12CmdEntry 40539 }


	iqudc12AESOutput18AESOutput4Stereo4 OBJECT-TYPE
		SYNTAX		INTEGER { disable(0), enable(1) }
		MAX-ACCESS		read-write
		STATUS			current
		DESCRIPTION
				"TYPE: - Checkbox
				 PAGE: - AudioOutput
					Stereo4  cmdID= 40551 "
		::= { iqudc12CmdEntry 40551 }


	iqudc12AESOutput18AESOutput5AESOutput51procam OBJECT-TYPE
		SYNTAX		INTEGER
		MAX-ACCESS		read-write
		STATUS			current
		DESCRIPTION
				"TYPE: - Number
				 PAGE: - AudioOutput
					AESOutput5_1_procam  cmdID= 40508  min= -801  max= 120  step= 1  format= %0.1f dB  div_scale= 10 
					Min = -80.1 dB  Max = 12.0 dB  Step = 0.1 dB "
		::= { iqudc12CmdEntry 40508 }


	iqudc12AESOutput18AESOutput5AESOutput52procam OBJECT-TYPE
		SYNTAX		INTEGER
		MAX-ACCESS		read-write
		STATUS			current
		DESCRIPTION
				"TYPE: - Number
				 PAGE: - AudioOutput
					AESOutput5_2_procam  cmdID= 40509  min= -801  max= 120  step= 1  format= %0.1f dB  div_scale= 10 
					Min = -80.1 dB  Max = 12.0 dB  Step = 0.1 dB "
		::= { iqudc12CmdEntry 40509 }


	iqudc12AESOutput18AESOutput5Mute51 OBJECT-TYPE
		SYNTAX		INTEGER { disable(0), enable(1) }
		MAX-ACCESS		read-write
		STATUS			current
		DESCRIPTION
				"TYPE: - Checkbox
				 PAGE: - AudioOutput
					Mute5_1  cmdID= 40540 "
		::= { iqudc12CmdEntry 40540 }


	iqudc12AESOutput18AESOutput5Mute52 OBJECT-TYPE
		SYNTAX		INTEGER { disable(0), enable(1) }
		MAX-ACCESS		read-write
		STATUS			current
		DESCRIPTION
				"TYPE: - Checkbox
				 PAGE: - AudioOutput
					Mute5_2  cmdID= 40541 "
		::= { iqudc12CmdEntry 40541 }


	iqudc12AESOutput18AESOutput5Stereo5 OBJECT-TYPE
		SYNTAX		INTEGER { disable(0), enable(1) }
		MAX-ACCESS		read-write
		STATUS			current
		DESCRIPTION
				"TYPE: - Checkbox
				 PAGE: - AudioOutput
					Stereo5  cmdID= 40552 "
		::= { iqudc12CmdEntry 40552 }


	iqudc12AESOutput18AESOutput6AESOutput61procam OBJECT-TYPE
		SYNTAX		INTEGER
		MAX-ACCESS		read-write
		STATUS			current
		DESCRIPTION
				"TYPE: - Number
				 PAGE: - AudioOutput
					AESOutput6_1_procam  cmdID= 40510  min= -801  max= 120  step= 1  format= %0.1f dB  div_scale= 10 
					Min = -80.1 dB  Max = 12.0 dB  Step = 0.1 dB "
		::= { iqudc12CmdEntry 40510 }


	iqudc12AESOutput18AESOutput6AESOutput62procam OBJECT-TYPE
		SYNTAX		INTEGER
		MAX-ACCESS		read-write
		STATUS			current
		DESCRIPTION
				"TYPE: - Number
				 PAGE: - AudioOutput
					AESOutput6_2_procam  cmdID= 40511  min= -801  max= 120  step= 1  format= %0.1f dB  div_scale= 10 
					Min = -80.1 dB  Max = 12.0 dB  Step = 0.1 dB "
		::= { iqudc12CmdEntry 40511 }


	iqudc12AESOutput18AESOutput6Mute61 OBJECT-TYPE
		SYNTAX		INTEGER { disable(0), enable(1) }
		MAX-ACCESS		read-write
		STATUS			current
		DESCRIPTION
				"TYPE: - Checkbox
				 PAGE: - AudioOutput
					Mute6_1  cmdID= 40542 "
		::= { iqudc12CmdEntry 40542 }


	iqudc12AESOutput18AESOutput6Mute62 OBJECT-TYPE
		SYNTAX		INTEGER { disable(0), enable(1) }
		MAX-ACCESS		read-write
		STATUS			current
		DESCRIPTION
				"TYPE: - Checkbox
				 PAGE: - AudioOutput
					Mute6_2  cmdID= 40543 "
		::= { iqudc12CmdEntry 40543 }


	iqudc12AESOutput18AESOutput6Stereo6 OBJECT-TYPE
		SYNTAX		INTEGER { disable(0), enable(1) }
		MAX-ACCESS		read-write
		STATUS			current
		DESCRIPTION
				"TYPE: - Checkbox
				 PAGE: - AudioOutput
					Stereo6  cmdID= 40553 "
		::= { iqudc12CmdEntry 40553 }


	iqudc12AESOutput18AESOutput7AESOutput71procam OBJECT-TYPE
		SYNTAX		INTEGER
		MAX-ACCESS		read-write
		STATUS			current
		DESCRIPTION
				"TYPE: - Number
				 PAGE: - AudioOutput
					AESOutput7_1_procam  cmdID= 40512  min= -801  max= 120  step= 1  format= %0.1f dB  div_scale= 10 
					Min = -80.1 dB  Max = 12.0 dB  Step = 0.1 dB "
		::= { iqudc12CmdEntry 40512 }


	iqudc12AESOutput18AESOutput7AESOutput72procam OBJECT-TYPE
		SYNTAX		INTEGER
		MAX-ACCESS		read-write
		STATUS			current
		DESCRIPTION
				"TYPE: - Number
				 PAGE: - AudioOutput
					AESOutput7_2_procam  cmdID= 40513  min= -801  max= 120  step= 1  format= %0.1f dB  div_scale= 10 
					Min = -80.1 dB  Max = 12.0 dB  Step = 0.1 dB "
		::= { iqudc12CmdEntry 40513 }


	iqudc12AESOutput18AESOutput7Mute71 OBJECT-TYPE
		SYNTAX		INTEGER { disable(0), enable(1) }
		MAX-ACCESS		read-write
		STATUS			current
		DESCRIPTION
				"TYPE: - Checkbox
				 PAGE: - AudioOutput
					Mute7_1  cmdID= 40544 "
		::= { iqudc12CmdEntry 40544 }


	iqudc12AESOutput18AESOutput7Mute72 OBJECT-TYPE
		SYNTAX		INTEGER { disable(0), enable(1) }
		MAX-ACCESS		read-write
		STATUS			current
		DESCRIPTION
				"TYPE: - Checkbox
				 PAGE: - AudioOutput
					Mute7_2  cmdID= 40545 "
		::= { iqudc12CmdEntry 40545 }


	iqudc12AESOutput18AESOutput7Stereo7 OBJECT-TYPE
		SYNTAX		INTEGER { disable(0), enable(1) }
		MAX-ACCESS		read-write
		STATUS			current
		DESCRIPTION
				"TYPE: - Checkbox
				 PAGE: - AudioOutput
					Stereo7  cmdID= 40554 "
		::= { iqudc12CmdEntry 40554 }


	iqudc12AESOutput18AESOutput8AESOutput81procam OBJECT-TYPE
		SYNTAX		INTEGER
		MAX-ACCESS		read-write
		STATUS			current
		DESCRIPTION
				"TYPE: - Number
				 PAGE: - AudioOutput
					AESOutput8_1_procam  cmdID= 40514  min= -801  max= 120  step= 1  format= %0.1f dB  div_scale= 10 
					Min = -80.1 dB  Max = 12.0 dB  Step = 0.1 dB "
		::= { iqudc12CmdEntry 40514 }


	iqudc12AESOutput18AESOutput8AESOutput82procam OBJECT-TYPE
		SYNTAX		INTEGER
		MAX-ACCESS		read-write
		STATUS			current
		DESCRIPTION
				"TYPE: - Number
				 PAGE: - AudioOutput
					AESOutput8_2_procam  cmdID= 40515  min= -801  max= 120  step= 1  format= %0.1f dB  div_scale= 10 
					Min = -80.1 dB  Max = 12.0 dB  Step = 0.1 dB "
		::= { iqudc12CmdEntry 40515 }


	iqudc12AESOutput18AESOutput8Mute81 OBJECT-TYPE
		SYNTAX		INTEGER { disable(0), enable(1) }
		MAX-ACCESS		read-write
		STATUS			current
		DESCRIPTION
				"TYPE: - Checkbox
				 PAGE: - AudioOutput
					Mute8_1  cmdID= 40546 "
		::= { iqudc12CmdEntry 40546 }


	iqudc12AESOutput18AESOutput8Mute82 OBJECT-TYPE
		SYNTAX		INTEGER { disable(0), enable(1) }
		MAX-ACCESS		read-write
		STATUS			current
		DESCRIPTION
				"TYPE: - Checkbox
				 PAGE: - AudioOutput
					Mute8_2  cmdID= 40547 "
		::= { iqudc12CmdEntry 40547 }


	iqudc12AESOutput18AESOutput8Stereo8 OBJECT-TYPE
		SYNTAX		INTEGER { disable(0), enable(1) }
		MAX-ACCESS		read-write
		STATUS			current
		DESCRIPTION
				"TYPE: - Checkbox
				 PAGE: - AudioOutput
					Stereo8  cmdID= 40555 "
		::= { iqudc12CmdEntry 40555 }


	iqudc12AnalogOutput12AnalogOutput1AnalogOutput11pro OBJECT-TYPE
		SYNTAX		INTEGER
		MAX-ACCESS		read-write
		STATUS			current
		DESCRIPTION
				"TYPE: - Number
				 PAGE: - AudioOutput
					AnalogOutput1_1_pro  cmdID= 40572  min= -801  max= 120  step= 1  format= %0.1f dB  div_scale= 10 
					Min = -80.1 dB  Max = 12.0 dB  Step = 0.1 dB "
		::= { iqudc12CmdEntry 40572 }


	iqudc12AnalogOutput12AnalogOutput1AnalogOutput12pro OBJECT-TYPE
		SYNTAX		INTEGER
		MAX-ACCESS		read-write
		STATUS			current
		DESCRIPTION
				"TYPE: - Number
				 PAGE: - AudioOutput
					AnalogOutput1_2_pro  cmdID= 40573  min= -801  max= 120  step= 1  format= %0.1f dB  div_scale= 10 
					Min = -80.1 dB  Max = 12.0 dB  Step = 0.1 dB "
		::= { iqudc12CmdEntry 40573 }


	iqudc12AnalogOutput12AnalogOutput1Mute11 OBJECT-TYPE
		SYNTAX		INTEGER { disable(0), enable(1) }
		MAX-ACCESS		read-write
		STATUS			current
		DESCRIPTION
				"TYPE: - Checkbox
				 PAGE: - AudioOutput
					Mute1_1  cmdID= 40576 "
		::= { iqudc12CmdEntry 40576 }


	iqudc12AnalogOutput12AnalogOutput1Mute12 OBJECT-TYPE
		SYNTAX		INTEGER { disable(0), enable(1) }
		MAX-ACCESS		read-write
		STATUS			current
		DESCRIPTION
				"TYPE: - Checkbox
				 PAGE: - AudioOutput
					Mute1_2  cmdID= 40577 "
		::= { iqudc12CmdEntry 40577 }


	iqudc12AnalogOutput12AnalogOutput1Stereo1 OBJECT-TYPE
		SYNTAX		INTEGER { disable(0), enable(1) }
		MAX-ACCESS		read-write
		STATUS			current
		DESCRIPTION
				"TYPE: - Checkbox
				 PAGE: - AudioOutput
					Stereo1  cmdID= 40580 "
		::= { iqudc12CmdEntry 40580 }


	iqudc12AnalogOutput12AnalogOutput2AnalogOutput21pro OBJECT-TYPE
		SYNTAX		INTEGER
		MAX-ACCESS		read-write
		STATUS			current
		DESCRIPTION
				"TYPE: - Number
				 PAGE: - AudioOutput
					AnalogOutput2_1_pro  cmdID= 40574  min= -801  max= 120  step= 1  format= %0.1f dB  div_scale= 10 
					Min = -80.1 dB  Max = 12.0 dB  Step = 0.1 dB "
		::= { iqudc12CmdEntry 40574 }


	iqudc12AnalogOutput12AnalogOutput2AnalogOutput22pro OBJECT-TYPE
		SYNTAX		INTEGER
		MAX-ACCESS		read-write
		STATUS			current
		DESCRIPTION
				"TYPE: - Number
				 PAGE: - AudioOutput
					AnalogOutput2_2_pro  cmdID= 40575  min= -801  max= 120  step= 1  format= %0.1f dB  div_scale= 10 
					Min = -80.1 dB  Max = 12.0 dB  Step = 0.1 dB "
		::= { iqudc12CmdEntry 40575 }


	iqudc12AnalogOutput12AnalogOutput2Mute21 OBJECT-TYPE
		SYNTAX		INTEGER { disable(0), enable(1) }
		MAX-ACCESS		read-write
		STATUS			current
		DESCRIPTION
				"TYPE: - Checkbox
				 PAGE: - AudioOutput
					Mute2_1  cmdID= 40578 "
		::= { iqudc12CmdEntry 40578 }


	iqudc12AnalogOutput12AnalogOutput2Mute22 OBJECT-TYPE
		SYNTAX		INTEGER { disable(0), enable(1) }
		MAX-ACCESS		read-write
		STATUS			current
		DESCRIPTION
				"TYPE: - Checkbox
				 PAGE: - AudioOutput
					Mute2_2  cmdID= 40579 "
		::= { iqudc12CmdEntry 40579 }


	iqudc12AnalogOutput12AnalogOutput2Stereo2 OBJECT-TYPE
		SYNTAX		INTEGER { disable(0), enable(1) }
		MAX-ACCESS		read-write
		STATUS			current
		DESCRIPTION
				"TYPE: - Checkbox
				 PAGE: - AudioOutput
					Stereo2  cmdID= 40581 "
		::= { iqudc12CmdEntry 40581 }


	iqudc12AudioOutputRoutingNamesOutName30 OBJECT-TYPE
		SYNTAX		RollCallString
		MAX-ACCESS		read-only
		STATUS			current
		DESCRIPTION
				"TYPE: - Display
				 PAGE: - AudioOutput
					Out Name 30  cmdID= 40368  format=   "
		::= { iqudc12CmdEntry 40368 }


	iqudc12AudioOutputRoutingNamesOutName31 OBJECT-TYPE
		SYNTAX		RollCallString
		MAX-ACCESS		read-only
		STATUS			current
		DESCRIPTION
				"TYPE: - Display
				 PAGE: - AudioOutput
					Out Name 31  cmdID= 40369  format=   "
		::= { iqudc12CmdEntry 40369 }


	iqudc12AudioOutputRoutingNamesOutName32 OBJECT-TYPE
		SYNTAX		RollCallString
		MAX-ACCESS		read-only
		STATUS			current
		DESCRIPTION
				"TYPE: - Display
				 PAGE: - AudioOutput
					Out Name 32  cmdID= 40370  format=   "
		::= { iqudc12CmdEntry 40370 }


	iqudc12AudioOutputRoutingNamesOutName33 OBJECT-TYPE
		SYNTAX		RollCallString
		MAX-ACCESS		read-only
		STATUS			current
		DESCRIPTION
				"TYPE: - Display
				 PAGE: - AudioOutput
					Out Name 33  cmdID= 40371  format=   "
		::= { iqudc12CmdEntry 40371 }


	iqudc12AudioOutputRoutingNamesOutName34 OBJECT-TYPE
		SYNTAX		RollCallString
		MAX-ACCESS		read-only
		STATUS			current
		DESCRIPTION
				"TYPE: - Display
				 PAGE: - AudioOutput
					Out Name 34  cmdID= 40372  format=   "
		::= { iqudc12CmdEntry 40372 }


	iqudc12AudioOutputRoutingNamesOutName35 OBJECT-TYPE
		SYNTAX		RollCallString
		MAX-ACCESS		read-only
		STATUS			current
		DESCRIPTION
				"TYPE: - Display
				 PAGE: - AudioOutput
					Out Name 35  cmdID= 40373  format=   "
		::= { iqudc12CmdEntry 40373 }


	iqudc12AudioOutputRoutingNamesOutName36 OBJECT-TYPE
		SYNTAX		RollCallString
		MAX-ACCESS		read-only
		STATUS			current
		DESCRIPTION
				"TYPE: - Display
				 PAGE: - AudioOutput
					Out Name 36  cmdID= 40374  format=   "
		::= { iqudc12CmdEntry 40374 }


	iqudc12AudioOutputRoutingNamesOutName37 OBJECT-TYPE
		SYNTAX		RollCallString
		MAX-ACCESS		read-only
		STATUS			current
		DESCRIPTION
				"TYPE: - Display
				 PAGE: - AudioOutput
					Out Name 37  cmdID= 40375  format=   "
		::= { iqudc12CmdEntry 40375 }


	iqudc12AudioOutputRoutingNamesOutName38 OBJECT-TYPE
		SYNTAX		RollCallString
		MAX-ACCESS		read-only
		STATUS			current
		DESCRIPTION
				"TYPE: - Display
				 PAGE: - AudioOutput
					Out Name 38  cmdID= 40376  format=   "
		::= { iqudc12CmdEntry 40376 }


	iqudc12AudioOutputRoutingNamesOutName39 OBJECT-TYPE
		SYNTAX		RollCallString
		MAX-ACCESS		read-only
		STATUS			current
		DESCRIPTION
				"TYPE: - Display
				 PAGE: - AudioOutput
					Out Name 39  cmdID= 40377  format=   "
		::= { iqudc12CmdEntry 40377 }


	iqudc12AudioOutputRoutingNamesOutName40 OBJECT-TYPE
		SYNTAX		RollCallString
		MAX-ACCESS		read-only
		STATUS			current
		DESCRIPTION
				"TYPE: - Display
				 PAGE: - AudioOutput
					Out Name 40  cmdID= 40378  format=   "
		::= { iqudc12CmdEntry 40378 }


	iqudc12AudioOutputRoutingNamesOutName41 OBJECT-TYPE
		SYNTAX		RollCallString
		MAX-ACCESS		read-only
		STATUS			current
		DESCRIPTION
				"TYPE: - Display
				 PAGE: - AudioOutput
					Out Name 41  cmdID= 40379  format=   "
		::= { iqudc12CmdEntry 40379 }


	iqudc12AudioOutputRoutingNamesOutName42 OBJECT-TYPE
		SYNTAX		RollCallString
		MAX-ACCESS		read-only
		STATUS			current
		DESCRIPTION
				"TYPE: - Display
				 PAGE: - AudioOutput
					Out Name 42  cmdID= 40380  format=   "
		::= { iqudc12CmdEntry 40380 }


	iqudc12AudioOutputRoutingNamesLegacyEnable OBJECT-TYPE
		SYNTAX		INTEGER { disable(0), enable(1) }
		MAX-ACCESS		read-write
		STATUS			current
		DESCRIPTION
				"TYPE: - Checkbox
				 PAGE: - AudioOutput
					LegacyEnable  cmdID= 40381 "
		::= { iqudc12CmdEntry 40381 }


	iqudc12AudioOutputRoutingNamesLegacyHide OBJECT-TYPE
		SYNTAX		RollCallString
		MAX-ACCESS		read-write
		STATUS			current
		DESCRIPTION
				"TYPE: - Editstring
				 PAGE: - AudioOutput
					LegacyHide  cmdID= 40382  "
		::= { iqudc12CmdEntry 40382 }


	iqudc12AudSetupDelaySelectTotalDelayBus1 OBJECT-TYPE
		SYNTAX		RollCallString
		MAX-ACCESS		read-only
		STATUS			current
		DESCRIPTION
				"TYPE: - Display
				 PAGE: - Audio
					TotalDelayBus1  cmdID= 40656  format=   "
		::= { iqudc12CmdEntry 40656 }


	iqudc12AudSetupDelaySelectTotalDelayBus2 OBJECT-TYPE
		SYNTAX		RollCallString
		MAX-ACCESS		read-only
		STATUS			current
		DESCRIPTION
				"TYPE: - Display
				 PAGE: - Audio
					TotalDelayBus2  cmdID= 40657  format=   "
		::= { iqudc12CmdEntry 40657 }


	iqudc12AudSetupDelaySelectTotalDelayBus3 OBJECT-TYPE
		SYNTAX		RollCallString
		MAX-ACCESS		read-only
		STATUS			current
		DESCRIPTION
				"TYPE: - Display
				 PAGE: - Audio
					TotalDelayBus3  cmdID= 40658  format=   "
		::= { iqudc12CmdEntry 40658 }


	iqudc12AudSetupDelaySelectTotalDelayBus4 OBJECT-TYPE
		SYNTAX		RollCallString
		MAX-ACCESS		read-only
		STATUS			current
		DESCRIPTION
				"TYPE: - Display
				 PAGE: - Audio
					TotalDelayBus4  cmdID= 40659  format=   "
		::= { iqudc12CmdEntry 40659 }


	iqudc12AudSetupDelaySelectTotalDelayBus5 OBJECT-TYPE
		SYNTAX		RollCallString
		MAX-ACCESS		read-only
		STATUS			current
		DESCRIPTION
				"TYPE: - Display
				 PAGE: - Audio
					TotalDelayBus5  cmdID= 40660  format=   "
		::= { iqudc12CmdEntry 40660 }


	iqudc12AudSetupDelaySelectTotalDelayBus6 OBJECT-TYPE
		SYNTAX		RollCallString
		MAX-ACCESS		read-only
		STATUS			current
		DESCRIPTION
				"TYPE: - Display
				 PAGE: - Audio
					TotalDelayBus6  cmdID= 40661  format=   "
		::= { iqudc12CmdEntry 40661 }


	iqudc12AudSetupDelaySelectTotalDelayBus7 OBJECT-TYPE
		SYNTAX		RollCallString
		MAX-ACCESS		read-only
		STATUS			current
		DESCRIPTION
				"TYPE: - Display
				 PAGE: - Audio
					TotalDelayBus7  cmdID= 40662  format=   "
		::= { iqudc12CmdEntry 40662 }


	iqudc12AudSetupDelaySelectTotalDelayBus8 OBJECT-TYPE
		SYNTAX		RollCallString
		MAX-ACCESS		read-only
		STATUS			current
		DESCRIPTION
				"TYPE: - Display
				 PAGE: - Audio
					TotalDelayBus8  cmdID= 40663  format=   "
		::= { iqudc12CmdEntry 40663 }


	iqudc12AudSetupDelaySelectBus1Delay OBJECT-TYPE
		SYNTAX		INTEGER
		MAX-ACCESS		read-write
		STATUS			current
		DESCRIPTION
				"TYPE: - Number
				 PAGE: - Audio
					Bus 1 Delay  cmdID= 40648  min= -1995  max= 1995  step= 1  format= %d  div_scale= 1 
					Min = -1995  Max = 1995  Step = 1 "
		::= { iqudc12CmdEntry 40648 }


	iqudc12AudSetupDelaySelectBus2Delay OBJECT-TYPE
		SYNTAX		INTEGER
		MAX-ACCESS		read-write
		STATUS			current
		DESCRIPTION
				"TYPE: - Number
				 PAGE: - Audio
					Bus 2 Delay  cmdID= 40649  min= -1995  max= 1995  step= 1  format= %d  div_scale= 1 
					Min = -1995  Max = 1995  Step = 1 "
		::= { iqudc12CmdEntry 40649 }


	iqudc12AudSetupDelaySelectBus3Delay OBJECT-TYPE
		SYNTAX		INTEGER
		MAX-ACCESS		read-write
		STATUS			current
		DESCRIPTION
				"TYPE: - Number
				 PAGE: - Audio
					Bus 3 Delay  cmdID= 40650  min= -1995  max= 1995  step= 1  format= %d  div_scale= 1 
					Min = -1995  Max = 1995  Step = 1 "
		::= { iqudc12CmdEntry 40650 }


	iqudc12AudSetupDelaySelectBus4Delay OBJECT-TYPE
		SYNTAX		INTEGER
		MAX-ACCESS		read-write
		STATUS			current
		DESCRIPTION
				"TYPE: - Number
				 PAGE: - Audio
					Bus 4 Delay  cmdID= 40651  min= -1995  max= 1995  step= 1  format= %d  div_scale= 1 
					Min = -1995  Max = 1995  Step = 1 "
		::= { iqudc12CmdEntry 40651 }


	iqudc12AudSetupDelaySelectBus5Delay OBJECT-TYPE
		SYNTAX		INTEGER
		MAX-ACCESS		read-write
		STATUS			current
		DESCRIPTION
				"TYPE: - Number
				 PAGE: - Audio
					Bus 5 Delay  cmdID= 40652  min= -1995  max= 1995  step= 1  format= %d  div_scale= 1 
					Min = -1995  Max = 1995  Step = 1 "
		::= { iqudc12CmdEntry 40652 }


	iqudc12AudSetupDelaySelectBus6Delay OBJECT-TYPE
		SYNTAX		INTEGER
		MAX-ACCESS		read-write
		STATUS			current
		DESCRIPTION
				"TYPE: - Number
				 PAGE: - Audio
					Bus 6 Delay  cmdID= 40653  min= -1995  max= 1995  step= 1  format= %d  div_scale= 1 
					Min = -1995  Max = 1995  Step = 1 "
		::= { iqudc12CmdEntry 40653 }


	iqudc12AudSetupDelaySelectBus7Delay OBJECT-TYPE
		SYNTAX		INTEGER
		MAX-ACCESS		read-write
		STATUS			current
		DESCRIPTION
				"TYPE: - Number
				 PAGE: - Audio
					Bus 7 Delay  cmdID= 40654  min= -1995  max= 1995  step= 1  format= %d  div_scale= 1 
					Min = -1995  Max = 1995  Step = 1 "
		::= { iqudc12CmdEntry 40654 }


	iqudc12AudSetupDelaySelectBus8Delay OBJECT-TYPE
		SYNTAX		INTEGER
		MAX-ACCESS		read-write
		STATUS			current
		DESCRIPTION
				"TYPE: - Number
				 PAGE: - Audio
					Bus 8 Delay  cmdID= 40655  min= -1995  max= 1995  step= 1  format= %d  div_scale= 1 
					Min = -1995  Max = 1995  Step = 1 "
		::= { iqudc12CmdEntry 40655 }


	iqudc12AudSetupDelaySelectBus1Fine OBJECT-TYPE
		SYNTAX		INTEGER
		MAX-ACCESS		read-write
		STATUS			current
		DESCRIPTION
				"TYPE: - Number
				 PAGE: - Audio
					Bus 1 Fine  cmdID= 36165  min= -240  max= 240  step= 1  format= %d  div_scale= 1 
					Min = -240  Max = 240  Step = 1 "
		::= { iqudc12CmdEntry 36165 }


	iqudc12AudSetupDelaySelectBus2Fine OBJECT-TYPE
		SYNTAX		INTEGER
		MAX-ACCESS		read-write
		STATUS			current
		DESCRIPTION
				"TYPE: - Number
				 PAGE: - Audio
					Bus 2 Fine  cmdID= 36166  min= -240  max= 240  step= 1  format= %d  div_scale= 1 
					Min = -240  Max = 240  Step = 1 "
		::= { iqudc12CmdEntry 36166 }


	iqudc12AudSetupDelaySelectBus3Fine OBJECT-TYPE
		SYNTAX		INTEGER
		MAX-ACCESS		read-write
		STATUS			current
		DESCRIPTION
				"TYPE: - Number
				 PAGE: - Audio
					Bus 3 Fine  cmdID= 36167  min= -240  max= 240  step= 1  format= %d  div_scale= 1 
					Min = -240  Max = 240  Step = 1 "
		::= { iqudc12CmdEntry 36167 }


	iqudc12AudSetupDelaySelectBus4Fine OBJECT-TYPE
		SYNTAX		INTEGER
		MAX-ACCESS		read-write
		STATUS			current
		DESCRIPTION
				"TYPE: - Number
				 PAGE: - Audio
					Bus 4 Fine  cmdID= 36168  min= -240  max= 240  step= 1  format= %d  div_scale= 1 
					Min = -240  Max = 240  Step = 1 "
		::= { iqudc12CmdEntry 36168 }


	iqudc12AudSetupDelaySelectBus5Fine OBJECT-TYPE
		SYNTAX		INTEGER
		MAX-ACCESS		read-write
		STATUS			current
		DESCRIPTION
				"TYPE: - Number
				 PAGE: - Audio
					Bus 5 Fine  cmdID= 36169  min= -240  max= 240  step= 1  format= %d  div_scale= 1 
					Min = -240  Max = 240  Step = 1 "
		::= { iqudc12CmdEntry 36169 }


	iqudc12AudSetupDelaySelectBus6Fine OBJECT-TYPE
		SYNTAX		INTEGER
		MAX-ACCESS		read-write
		STATUS			current
		DESCRIPTION
				"TYPE: - Number
				 PAGE: - Audio
					Bus 6 Fine  cmdID= 36170  min= -240  max= 240  step= 1  format= %d  div_scale= 1 
					Min = -240  Max = 240  Step = 1 "
		::= { iqudc12CmdEntry 36170 }


	iqudc12AudSetupDelaySelectBus7Fine OBJECT-TYPE
		SYNTAX		INTEGER
		MAX-ACCESS		read-write
		STATUS			current
		DESCRIPTION
				"TYPE: - Number
				 PAGE: - Audio
					Bus 7 Fine  cmdID= 36171  min= -240  max= 240  step= 1  format= %d  div_scale= 1 
					Min = -240  Max = 240  Step = 1 "
		::= { iqudc12CmdEntry 36171 }


	iqudc12AudSetupDelaySelectBus8Fine OBJECT-TYPE
		SYNTAX		INTEGER
		MAX-ACCESS		read-write
		STATUS			current
		DESCRIPTION
				"TYPE: - Number
				 PAGE: - Audio
					Bus 8 Fine  cmdID= 36172  min= -240  max= 240  step= 1  format= %d  div_scale= 1 
					Min = -240  Max = 240  Step = 1 "
		::= { iqudc12CmdEntry 36172 }


	iqudc12AudSetupDelaySelectBusBulkDelay OBJECT-TYPE
		SYNTAX		INTEGER
		MAX-ACCESS		read-write
		STATUS			current
		DESCRIPTION
				"TYPE: - Number
				 PAGE: - Audio
					Bus Bulk Delay  cmdID= 40647  min= -3210  max= 12000  step= 1  format= %d  div_scale= 1 
					Min = -3210  Max = 12000  Step = 1 "
		::= { iqudc12CmdEntry 40647 }


	iqudc12AudSetupDelaySelectThreshold OBJECT-TYPE
		SYNTAX		INTEGER
		MAX-ACCESS		read-write
		STATUS			current
		DESCRIPTION
				"TYPE: - Number
				 PAGE: - Audio
					Threshold  cmdID= 40646  min= 240  max= 3840  step= 1  format= %d  div_scale= 1 
					Min = 240  Max = 3840  Step = 1 "
		::= { iqudc12CmdEntry 40646 }


	iqudc12AudSetupDelaySelectRtrack14 OBJECT-TYPE
		SYNTAX		INTEGER { disable(0), enable(1) }
		MAX-ACCESS		read-write
		STATUS			current
		DESCRIPTION
				"TYPE: - Checkbox
				 PAGE: - Audio
					Rtrack14  cmdID= 40600 "
		::= { iqudc12CmdEntry 40600 }


	iqudc12AudSetupDelaySelectRtrack15 OBJECT-TYPE
		SYNTAX		INTEGER { disable(0), enable(1) }
		MAX-ACCESS		read-write
		STATUS			current
		DESCRIPTION
				"TYPE: - Checkbox
				 PAGE: - Audio
					Rtrack15  cmdID= 40608 "
		::= { iqudc12CmdEntry 40608 }


	iqudc12AudSetupDelaySelectRtrack16 OBJECT-TYPE
		SYNTAX		INTEGER { disable(0), enable(1) }
		MAX-ACCESS		read-write
		STATUS			current
		DESCRIPTION
				"TYPE: - Checkbox
				 PAGE: - Audio
					Rtrack16  cmdID= 40616 "
		::= { iqudc12CmdEntry 40616 }


	iqudc12AudSetupDelaySelectRtrack17 OBJECT-TYPE
		SYNTAX		INTEGER { disable(0), enable(1) }
		MAX-ACCESS		read-write
		STATUS			current
		DESCRIPTION
				"TYPE: - Checkbox
				 PAGE: - Audio
					Rtrack17  cmdID= 40624 "
		::= { iqudc12CmdEntry 40624 }


	iqudc12AudSetupDelaySelectEnableBulk OBJECT-TYPE
		SYNTAX		INTEGER { disable(0), enable(1) }
		MAX-ACCESS		read-write
		STATUS			current
		DESCRIPTION
				"TYPE: - Checkbox
				 PAGE: - Audio
					EnableBulk  cmdID= 40625 "
		::= { iqudc12CmdEntry 40625 }


	iqudc12AudSetupDelaySelectEnableVideo OBJECT-TYPE
		SYNTAX		INTEGER { disable(0), enable(1) }
		MAX-ACCESS		read-write
		STATUS			current
		DESCRIPTION
				"TYPE: - Checkbox
				 PAGE: - Audio
					EnableVideo  cmdID= 40632 "
		::= { iqudc12CmdEntry 40632 }


	iqudc12AudioAudSetupRollTrack14 OBJECT-TYPE
		SYNTAX		RollCallString
		MAX-ACCESS		read-only
		STATUS			current
		DESCRIPTION
				"TYPE: - Display
				 PAGE: - Audio
					RollTrack14  cmdID= 14  format=   "
		::= { iqudc12CmdEntry 14 }


	iqudc12AudioAudSetupRollTrack15 OBJECT-TYPE
		SYNTAX		RollCallString
		MAX-ACCESS		read-only
		STATUS			current
		DESCRIPTION
				"TYPE: - Display
				 PAGE: - Audio
					RollTrack15  cmdID= 15  format=   "
		::= { iqudc12CmdEntry 15 }


	iqudc12AudioAudSetupRollTrack16 OBJECT-TYPE
		SYNTAX		RollCallString
		MAX-ACCESS		read-only
		STATUS			current
		DESCRIPTION
				"TYPE: - Display
				 PAGE: - Audio
					RollTrack16  cmdID= 16  format=   "
		::= { iqudc12CmdEntry 16 }


	iqudc12AudioAudSetupRollTrack17 OBJECT-TYPE
		SYNTAX		RollCallString
		MAX-ACCESS		read-only
		STATUS			current
		DESCRIPTION
				"TYPE: - Display
				 PAGE: - Audio
					RollTrack17  cmdID= 17  format=   "
		::= { iqudc12CmdEntry 17 }


	iqudc12AudioAudSetupCurrentVidDelay OBJECT-TYPE
		SYNTAX		RollCallString
		MAX-ACCESS		read-only
		STATUS			current
		DESCRIPTION
				"TYPE: - Display
				 PAGE: - Audio
					CurrentVidDelay  cmdID= 33030  format=   "
		::= { iqudc12CmdEntry 33030 }


	iqudc12AudioAudSetupMinVidAudDelay OBJECT-TYPE
		SYNTAX		RollCallString
		MAX-ACCESS		read-only
		STATUS			current
		DESCRIPTION
				"TYPE: - Display
				 PAGE: - Audio
					MinVidAudDelay  cmdID= 33043  format=   "
		::= { iqudc12CmdEntry 33043 }


	iqudc12AudioAudSetupCurrRTrack14Delay OBJECT-TYPE
		SYNTAX		RollCallString
		MAX-ACCESS		read-only
		STATUS			current
		DESCRIPTION
				"TYPE: - Display
				 PAGE: - Audio
					CurrRTrack14Delay  cmdID= 40665  format=   "
		::= { iqudc12CmdEntry 40665 }


	iqudc12AudioAudSetupCurrRlTrack15Delay OBJECT-TYPE
		SYNTAX		RollCallString
		MAX-ACCESS		read-only
		STATUS			current
		DESCRIPTION
				"TYPE: - Display
				 PAGE: - Audio
					CurrRlTrack15Delay  cmdID= 40666  format=   "
		::= { iqudc12CmdEntry 40666 }


	iqudc12AudioAudSetupCurrRTrack16Delay OBJECT-TYPE
		SYNTAX		RollCallString
		MAX-ACCESS		read-only
		STATUS			current
		DESCRIPTION
				"TYPE: - Display
				 PAGE: - Audio
					CurrRTrack16Delay  cmdID= 40667  format=   "
		::= { iqudc12CmdEntry 40667 }


	iqudc12AudioAudSetupCurrRTrack17Delay OBJECT-TYPE
		SYNTAX		RollCallString
		MAX-ACCESS		read-only
		STATUS			current
		DESCRIPTION
				"TYPE: - Display
				 PAGE: - Audio
					CurrRTrack17Delay  cmdID= 40668  format=   "
		::= { iqudc12CmdEntry 40668 }


	iqudc12AudSetupTonesFreq0 OBJECT-TYPE
		SYNTAX		INTEGER
		MAX-ACCESS		read-write
		STATUS			current
		DESCRIPTION
				"TYPE: - Number
				 PAGE: - Audio
					Freq0  cmdID= 42600  min= 1  max= 160  step= 1  format= %d  div_scale= 1 
					Min = 1  Max = 160  Step = 1 "
		::= { iqudc12CmdEntry 42600 }


	iqudc12AudSetupTonesFreq1 OBJECT-TYPE
		SYNTAX		INTEGER
		MAX-ACCESS		read-write
		STATUS			current
		DESCRIPTION
				"TYPE: - Number
				 PAGE: - Audio
					Freq1  cmdID= 42601  min= 1  max= 160  step= 1  format= %d  div_scale= 1 
					Min = 1  Max = 160  Step = 1 "
		::= { iqudc12CmdEntry 42601 }


	iqudc12AudSetupTonesFreq2 OBJECT-TYPE
		SYNTAX		INTEGER
		MAX-ACCESS		read-write
		STATUS			current
		DESCRIPTION
				"TYPE: - Number
				 PAGE: - Audio
					Freq2  cmdID= 42602  min= 1  max= 160  step= 1  format= %d  div_scale= 1 
					Min = 1  Max = 160  Step = 1 "
		::= { iqudc12CmdEntry 42602 }


	iqudc12AudSetupTonesFreq3 OBJECT-TYPE
		SYNTAX		INTEGER
		MAX-ACCESS		read-write
		STATUS			current
		DESCRIPTION
				"TYPE: - Number
				 PAGE: - Audio
					Freq3  cmdID= 42603  min= 1  max= 160  step= 1  format= %d  div_scale= 1 
					Min = 1  Max = 160  Step = 1 "
		::= { iqudc12CmdEntry 42603 }


	iqudc12AudSetupTonesFreq4 OBJECT-TYPE
		SYNTAX		INTEGER
		MAX-ACCESS		read-write
		STATUS			current
		DESCRIPTION
				"TYPE: - Number
				 PAGE: - Audio
					Freq4  cmdID= 42604  min= 1  max= 160  step= 1  format= %d  div_scale= 1 
					Min = 1  Max = 160  Step = 1 "
		::= { iqudc12CmdEntry 42604 }


	iqudc12AudSetupTonesFreq5 OBJECT-TYPE
		SYNTAX		INTEGER
		MAX-ACCESS		read-write
		STATUS			current
		DESCRIPTION
				"TYPE: - Number
				 PAGE: - Audio
					Freq5  cmdID= 42605  min= 1  max= 160  step= 1  format= %d  div_scale= 1 
					Min = 1  Max = 160  Step = 1 "
		::= { iqudc12CmdEntry 42605 }


	iqudc12AudSetupTonesFreq6 OBJECT-TYPE
		SYNTAX		INTEGER
		MAX-ACCESS		read-write
		STATUS			current
		DESCRIPTION
				"TYPE: - Number
				 PAGE: - Audio
					Freq6  cmdID= 42606  min= 1  max= 160  step= 1  format= %d  div_scale= 1 
					Min = 1  Max = 160  Step = 1 "
		::= { iqudc12CmdEntry 42606 }


	iqudc12AudSetupTonesFreq7 OBJECT-TYPE
		SYNTAX		INTEGER
		MAX-ACCESS		read-write
		STATUS			current
		DESCRIPTION
				"TYPE: - Number
				 PAGE: - Audio
					Freq7  cmdID= 42607  min= 1  max= 160  step= 1  format= %d  div_scale= 1 
					Min = 1  Max = 160  Step = 1 "
		::= { iqudc12CmdEntry 42607 }


	iqudc12AudSetupTonesIdent0 OBJECT-TYPE
		SYNTAX		INTEGER { disable(0), enable(1) }
		MAX-ACCESS		read-write
		STATUS			current
		DESCRIPTION
				"TYPE: - Checkbox
				 PAGE: - Audio
					Ident0  cmdID= 42610 "
		::= { iqudc12CmdEntry 42610 }


	iqudc12AudSetupTonesIdent1 OBJECT-TYPE
		SYNTAX		INTEGER { disable(0), enable(1) }
		MAX-ACCESS		read-write
		STATUS			current
		DESCRIPTION
				"TYPE: - Checkbox
				 PAGE: - Audio
					Ident1  cmdID= 42611 "
		::= { iqudc12CmdEntry 42611 }


	iqudc12AudSetupTonesIdent2 OBJECT-TYPE
		SYNTAX		INTEGER { disable(0), enable(1) }
		MAX-ACCESS		read-write
		STATUS			current
		DESCRIPTION
				"TYPE: - Checkbox
				 PAGE: - Audio
					Ident2  cmdID= 42612 "
		::= { iqudc12CmdEntry 42612 }


	iqudc12AudSetupTonesIdent3 OBJECT-TYPE
		SYNTAX		INTEGER { disable(0), enable(1) }
		MAX-ACCESS		read-write
		STATUS			current
		DESCRIPTION
				"TYPE: - Checkbox
				 PAGE: - Audio
					Ident3  cmdID= 42613 "
		::= { iqudc12CmdEntry 42613 }


	iqudc12AudSetupTonesIdent4 OBJECT-TYPE
		SYNTAX		INTEGER { disable(0), enable(1) }
		MAX-ACCESS		read-write
		STATUS			current
		DESCRIPTION
				"TYPE: - Checkbox
				 PAGE: - Audio
					Ident4  cmdID= 42614 "
		::= { iqudc12CmdEntry 42614 }


	iqudc12AudSetupTonesIdent5 OBJECT-TYPE
		SYNTAX		INTEGER { disable(0), enable(1) }
		MAX-ACCESS		read-write
		STATUS			current
		DESCRIPTION
				"TYPE: - Checkbox
				 PAGE: - Audio
					Ident5  cmdID= 42615 "
		::= { iqudc12CmdEntry 42615 }


	iqudc12AudSetupTonesIdent6 OBJECT-TYPE
		SYNTAX		INTEGER { disable(0), enable(1) }
		MAX-ACCESS		read-write
		STATUS			current
		DESCRIPTION
				"TYPE: - Checkbox
				 PAGE: - Audio
					Ident6  cmdID= 42616 "
		::= { iqudc12CmdEntry 42616 }


	iqudc12AudSetupTonesIdent7 OBJECT-TYPE
		SYNTAX		INTEGER { disable(0), enable(1) }
		MAX-ACCESS		read-write
		STATUS			current
		DESCRIPTION
				"TYPE: - Checkbox
				 PAGE: - Audio
					Ident7  cmdID= 42617 "
		::= { iqudc12CmdEntry 42617 }


	iqudc12AudioAudSetupNeg1Frame OBJECT-TYPE
		SYNTAX		INTEGER { noAction(0),val-Neg1Frame(1) }
		MAX-ACCESS		read-write
		STATUS			current
		DESCRIPTION
				"TYPE: - Button
				 PAGE: - Audio
					Neg1Frame  cmdID= 40626  value= 1  "
		::= { iqudc12CmdEntry 40626 }


	iqudc12AudioAudSetupNeg1ms OBJECT-TYPE
		SYNTAX		INTEGER { noAction(0),val-Neg1ms(1) }
		MAX-ACCESS		read-write
		STATUS			current
		DESCRIPTION
				"TYPE: - Button
				 PAGE: - Audio
					Neg1ms  cmdID= 40627  value= 1  "
		::= { iqudc12CmdEntry 40627 }


	iqudc12AudioAudSetupNeg4samp OBJECT-TYPE
		SYNTAX		INTEGER { noAction(0),val-Neg4samp(1) }
		MAX-ACCESS		read-write
		STATUS			current
		DESCRIPTION
				"TYPE: - Button
				 PAGE: - Audio
					Neg4samp  cmdID= 40628  value= 1  "
		::= { iqudc12CmdEntry 40628 }


	iqudc12AudioAudSetupPos4samp OBJECT-TYPE
		SYNTAX		INTEGER { noAction(0),val-Pos4samp(1) }
		MAX-ACCESS		read-write
		STATUS			current
		DESCRIPTION
				"TYPE: - Button
				 PAGE: - Audio
					Pos4samp  cmdID= 40629  value= 1  "
		::= { iqudc12CmdEntry 40629 }


	iqudc12AudioAudSetupPos1ms OBJECT-TYPE
		SYNTAX		INTEGER { noAction(0),val-Pos1ms(1) }
		MAX-ACCESS		read-write
		STATUS			current
		DESCRIPTION
				"TYPE: - Button
				 PAGE: - Audio
					Pos1ms  cmdID= 40630  value= 1  "
		::= { iqudc12CmdEntry 40630 }


	iqudc12AudioAudSetupPos1Frame OBJECT-TYPE
		SYNTAX		INTEGER { noAction(0),val-Pos1Frame(1) }
		MAX-ACCESS		read-write
		STATUS			current
		DESCRIPTION
				"TYPE: - Button
				 PAGE: - Audio
					Pos1Frame  cmdID= 40631  value= 1  "
		::= { iqudc12CmdEntry 40631 }


	iqudc12AudioAudSetupSilentLevel OBJECT-TYPE
		SYNTAX		INTEGER
		MAX-ACCESS		read-write
		STATUS			current
		DESCRIPTION
				"TYPE: - Number
				 PAGE: - Audio
					SilentLevel  cmdID= 3061  min= -100  max= -2  step= 1  format= %0.0f dBFS  div_scale= 1 
					Min = -100 dBFS  Max = -2 dBFS  Step = 1 dBFS "
		::= { iqudc12CmdEntry 3061 }


	iqudc12AudioAudSetupOverloadLevel OBJECT-TYPE
		SYNTAX		INTEGER
		MAX-ACCESS		read-write
		STATUS			current
		DESCRIPTION
				"TYPE: - Number
				 PAGE: - Audio
					OverloadLevel  cmdID= 3064  min= -99  max= -1  step= 1  format= %0.0f dBFS  div_scale= 1 
					Min = -99 dBFS  Max = -1 dBFS  Step = 1 dBFS "
		::= { iqudc12CmdEntry 3064 }


	iqudc12AudioAudSetupLevelUpdateEnb OBJECT-TYPE
		SYNTAX		INTEGER { disable(0), enable(1) }
		MAX-ACCESS		read-write
		STATUS			current
		DESCRIPTION
				"TYPE: - Checkbox
				 PAGE: - Audio
					LevelUpdateEnb  cmdID= 38275 "
		::= { iqudc12CmdEntry 38275 }


	iqudc12AudioAudSetupLevelTimeout OBJECT-TYPE
		SYNTAX		INTEGER
		MAX-ACCESS		read-write
		STATUS			current
		DESCRIPTION
				"TYPE: - Number
				 PAGE: - Audio
					LevelTimeout  cmdID= 3065  min= 1  max= 20  step= 1  format= %d  div_scale= 1 
					Min = 1  Max = 20  Step = 1 "
		::= { iqudc12CmdEntry 3065 }


	iqudc12AudioAudSetupAudLevel OBJECT-TYPE
		SYNTAX		RollCallString
		MAX-ACCESS		read-only
		STATUS			current
		DESCRIPTION
				"TYPE: - Display
				 PAGE: - Audio
					AudLevel  cmdID= 38276  format=   "
		::= { iqudc12CmdEntry 38276 }


	iqudc12AudioAudSetupHeadroomIn OBJECT-TYPE
		SYNTAX		INTEGER
		MAX-ACCESS		read-write
		STATUS			current
		DESCRIPTION
				"TYPE: - Number
				 PAGE: - Audio
					HeadroomIn  cmdID= 3066  min= 4  max= 24  step= 1  format= %0.0fdB  div_scale= 1 
					Min = 4dB  Max = 24dB  Step = 1dB "
		::= { iqudc12CmdEntry 3066 }


	iqudc12AudioAudSetupLineupIn OBJECT-TYPE
		SYNTAX		INTEGER
		MAX-ACCESS		read-write
		STATUS			current
		DESCRIPTION
				"TYPE: - Number
				 PAGE: - Audio
					LineupIn  cmdID= 3067  min= -20  max= 20  step= 1  format= %0.0fdBu  div_scale= 1 
					Min = -20dBu  Max = 20dBu  Step = 1dBu "
		::= { iqudc12CmdEntry 3067 }


	iqudc12AudioAudSetupHeadroomOut OBJECT-TYPE
		SYNTAX		INTEGER
		MAX-ACCESS		read-write
		STATUS			current
		DESCRIPTION
				"TYPE: - Number
				 PAGE: - Audio
					HeadroomOut  cmdID= 3068  min= 4  max= 24  step= 1  format= %0.0fdB  div_scale= 1 
					Min = 4dB  Max = 24dB  Step = 1dB "
		::= { iqudc12CmdEntry 3068 }


	iqudc12AudioAudSetupLineupOut OBJECT-TYPE
		SYNTAX		INTEGER
		MAX-ACCESS		read-write
		STATUS			current
		DESCRIPTION
				"TYPE: - Number
				 PAGE: - Audio
					LineupOut  cmdID= 3069  min= -20  max= 20  step= 1  format= %0.0fdBu  div_scale= 1 
					Min = -20dBu  Max = 20dBu  Step = 1dBu "
		::= { iqudc12CmdEntry 3069 }


	iqudc12AudioAudSetupDialogHide OBJECT-TYPE
		SYNTAX		RollCallString
		MAX-ACCESS		read-only
		STATUS			current
		DESCRIPTION
				"TYPE: - Display
				 PAGE: - Audio
					DialogHide  cmdID= 36185  format=   "
		::= { iqudc12CmdEntry 36185 }


	iqudc12AudioAudioRoutingInputRouteDest1 OBJECT-TYPE
		SYNTAX		INTEGER
		MAX-ACCESS		read-write
		STATUS			current
		DESCRIPTION
				"TYPE: - Number
				 PAGE: - Audio
					Input Route Dest 1  cmdID= 40223  min= 0  max= 22  step= 1  format= 0  div_scale= 1 
					Min = 0  Max = 0  Step = 0 "
		::= { iqudc12CmdEntry 40223 }


	iqudc12AudioAudioRoutingInputRouteDest2 OBJECT-TYPE
		SYNTAX		INTEGER
		MAX-ACCESS		read-write
		STATUS			current
		DESCRIPTION
				"TYPE: - Number
				 PAGE: - Audio
					Input Route Dest 2  cmdID= 40224  min= 0  max= 22  step= 1  format= 0  div_scale= 1 
					Min = 0  Max = 0  Step = 0 "
		::= { iqudc12CmdEntry 40224 }


	iqudc12AudioAudioRoutingInputRouteDest3 OBJECT-TYPE
		SYNTAX		INTEGER
		MAX-ACCESS		read-write
		STATUS			current
		DESCRIPTION
				"TYPE: - Number
				 PAGE: - Audio
					Input Route Dest 3  cmdID= 40225  min= 0  max= 22  step= 1  format= 0  div_scale= 1 
					Min = 0  Max = 0  Step = 0 "
		::= { iqudc12CmdEntry 40225 }


	iqudc12AudioAudioRoutingInputRouteDest4 OBJECT-TYPE
		SYNTAX		INTEGER
		MAX-ACCESS		read-write
		STATUS			current
		DESCRIPTION
				"TYPE: - Number
				 PAGE: - Audio
					Input Route Dest 4  cmdID= 40226  min= 0  max= 22  step= 1  format= 0  div_scale= 1 
					Min = 0  Max = 0  Step = 0 "
		::= { iqudc12CmdEntry 40226 }


	iqudc12AudioAudioRoutingInputRouteDest5 OBJECT-TYPE
		SYNTAX		INTEGER
		MAX-ACCESS		read-write
		STATUS			current
		DESCRIPTION
				"TYPE: - Number
				 PAGE: - Audio
					Input Route Dest 5  cmdID= 40227  min= 0  max= 22  step= 1  format= 0  div_scale= 1 
					Min = 0  Max = 0  Step = 0 "
		::= { iqudc12CmdEntry 40227 }


	iqudc12AudioAudioRoutingInputRouteDest6 OBJECT-TYPE
		SYNTAX		INTEGER
		MAX-ACCESS		read-write
		STATUS			current
		DESCRIPTION
				"TYPE: - Number
				 PAGE: - Audio
					Input Route Dest 6  cmdID= 40228  min= 0  max= 22  step= 1  format= 0  div_scale= 1 
					Min = 0  Max = 0  Step = 0 "
		::= { iqudc12CmdEntry 40228 }


	iqudc12AudioAudioRoutingInputRouteDest7 OBJECT-TYPE
		SYNTAX		INTEGER
		MAX-ACCESS		read-write
		STATUS			current
		DESCRIPTION
				"TYPE: - Number
				 PAGE: - Audio
					Input Route Dest 7  cmdID= 40229  min= 0  max= 22  step= 1  format= 0  div_scale= 1 
					Min = 0  Max = 0  Step = 0 "
		::= { iqudc12CmdEntry 40229 }


	iqudc12AudioAudioRoutingInputRouteDest8 OBJECT-TYPE
		SYNTAX		INTEGER
		MAX-ACCESS		read-write
		STATUS			current
		DESCRIPTION
				"TYPE: - Number
				 PAGE: - Audio
					Input Route Dest 8  cmdID= 40230  min= 0  max= 22  step= 1  format= 0  div_scale= 1 
					Min = 0  Max = 0  Step = 0 "
		::= { iqudc12CmdEntry 40230 }


	iqudc12AudioAudioRoutingInputNameAnalog OBJECT-TYPE
		SYNTAX		RollCallString
		MAX-ACCESS		read-only
		STATUS			current
		DESCRIPTION
				"TYPE: - Display
				 PAGE: - Audio
					Input Name Analog  cmdID= 40216  format=   "
		::= { iqudc12CmdEntry 40216 }


	iqudc12AudioAudioRoutingInputNameDlby1 OBJECT-TYPE
		SYNTAX		RollCallString
		MAX-ACCESS		read-only
		STATUS			current
		DESCRIPTION
				"TYPE: - Display
				 PAGE: - Audio
					Input Name Dlby 1  cmdID= 40218  format=   "
		::= { iqudc12CmdEntry 40218 }


	iqudc12AudioAudioRoutingInputNameDlby2 OBJECT-TYPE
		SYNTAX		RollCallString
		MAX-ACCESS		read-only
		STATUS			current
		DESCRIPTION
				"TYPE: - Display
				 PAGE: - Audio
					Input Name Dlby 2  cmdID= 40219  format=   "
		::= { iqudc12CmdEntry 40219 }


	iqudc12AudioAudioRoutingInputNameDlby3 OBJECT-TYPE
		SYNTAX		RollCallString
		MAX-ACCESS		read-only
		STATUS			current
		DESCRIPTION
				"TYPE: - Display
				 PAGE: - Audio
					Input Name Dlby 3  cmdID= 40220  format=   "
		::= { iqudc12CmdEntry 40220 }


	iqudc12AudioAudioRoutingInputNameDlby4 OBJECT-TYPE
		SYNTAX		RollCallString
		MAX-ACCESS		read-only
		STATUS			current
		DESCRIPTION
				"TYPE: - Display
				 PAGE: - Audio
					Input Name Dlby 4  cmdID= 40221  format=   "
		::= { iqudc12CmdEntry 40221 }


	iqudc12AudioAudioRoutingInputNameDlby5 OBJECT-TYPE
		SYNTAX		RollCallString
		MAX-ACCESS		read-only
		STATUS			current
		DESCRIPTION
				"TYPE: - Display
				 PAGE: - Audio
					Input Name Dlby 5  cmdID= 40222  format=   "
		::= { iqudc12CmdEntry 40222 }


	iqudc12AudioAudioRoutingInputHideAES1 OBJECT-TYPE
		SYNTAX		RollCallString
		MAX-ACCESS		read-only
		STATUS			current
		DESCRIPTION
				"TYPE: - Display
				 PAGE: - Audio
					Input Hide AES 1  cmdID= 40233  format=   "
		::= { iqudc12CmdEntry 40233 }


	iqudc12AudioAudioRoutingInputHideAES2 OBJECT-TYPE
		SYNTAX		RollCallString
		MAX-ACCESS		read-only
		STATUS			current
		DESCRIPTION
				"TYPE: - Display
				 PAGE: - Audio
					Input Hide AES 2  cmdID= 40234  format=   "
		::= { iqudc12CmdEntry 40234 }


	iqudc12AudioAudioRoutingInputHideAES3 OBJECT-TYPE
		SYNTAX		RollCallString
		MAX-ACCESS		read-only
		STATUS			current
		DESCRIPTION
				"TYPE: - Display
				 PAGE: - Audio
					Input Hide AES 3  cmdID= 40235  format=   "
		::= { iqudc12CmdEntry 40235 }


	iqudc12AudioAudioRoutingInputHideAES4 OBJECT-TYPE
		SYNTAX		RollCallString
		MAX-ACCESS		read-only
		STATUS			current
		DESCRIPTION
				"TYPE: - Display
				 PAGE: - Audio
					Input Hide AES 4  cmdID= 40236  format=   "
		::= { iqudc12CmdEntry 40236 }


	iqudc12AudioAudioRoutingInputHideAES5 OBJECT-TYPE
		SYNTAX		RollCallString
		MAX-ACCESS		read-only
		STATUS			current
		DESCRIPTION
				"TYPE: - Display
				 PAGE: - Audio
					Input Hide AES 5  cmdID= 40237  format=   "
		::= { iqudc12CmdEntry 40237 }


	iqudc12AudioAudioRoutingInputHideAES6 OBJECT-TYPE
		SYNTAX		RollCallString
		MAX-ACCESS		read-only
		STATUS			current
		DESCRIPTION
				"TYPE: - Display
				 PAGE: - Audio
					Input Hide AES 6  cmdID= 40238  format=   "
		::= { iqudc12CmdEntry 40238 }


	iqudc12AudioAudioRoutingInputHideAES7 OBJECT-TYPE
		SYNTAX		RollCallString
		MAX-ACCESS		read-only
		STATUS			current
		DESCRIPTION
				"TYPE: - Display
				 PAGE: - Audio
					Input Hide AES 7  cmdID= 40239  format=   "
		::= { iqudc12CmdEntry 40239 }


	iqudc12AudioAudioRoutingInputHideAES8 OBJECT-TYPE
		SYNTAX		RollCallString
		MAX-ACCESS		read-only
		STATUS			current
		DESCRIPTION
				"TYPE: - Display
				 PAGE: - Audio
					Input Hide AES 8  cmdID= 40240  format=   "
		::= { iqudc12CmdEntry 40240 }


	iqudc12AudioAudioRoutingOutputHideAES1 OBJECT-TYPE
		SYNTAX		RollCallString
		MAX-ACCESS		read-only
		STATUS			current
		DESCRIPTION
				"TYPE: - Display
				 PAGE: - Audio
					Output Hide AES 1  cmdID= 40250  format=   "
		::= { iqudc12CmdEntry 40250 }


	iqudc12AudioAudioRoutingOutputHideAES2 OBJECT-TYPE
		SYNTAX		RollCallString
		MAX-ACCESS		read-only
		STATUS			current
		DESCRIPTION
				"TYPE: - Display
				 PAGE: - Audio
					Output Hide AES 2  cmdID= 40251  format=   "
		::= { iqudc12CmdEntry 40251 }


	iqudc12AudioAudioRoutingOutputHideAES3 OBJECT-TYPE
		SYNTAX		RollCallString
		MAX-ACCESS		read-only
		STATUS			current
		DESCRIPTION
				"TYPE: - Display
				 PAGE: - Audio
					Output Hide AES 3  cmdID= 40252  format=   "
		::= { iqudc12CmdEntry 40252 }


	iqudc12AudioAudioRoutingOutputHideAES4 OBJECT-TYPE
		SYNTAX		RollCallString
		MAX-ACCESS		read-only
		STATUS			current
		DESCRIPTION
				"TYPE: - Display
				 PAGE: - Audio
					Output Hide AES 4  cmdID= 40253  format=   "
		::= { iqudc12CmdEntry 40253 }


	iqudc12AudioAudioRoutingOutputHideAES5 OBJECT-TYPE
		SYNTAX		RollCallString
		MAX-ACCESS		read-only
		STATUS			current
		DESCRIPTION
				"TYPE: - Display
				 PAGE: - Audio
					Output Hide AES 5  cmdID= 40254  format=   "
		::= { iqudc12CmdEntry 40254 }


	iqudc12AudioAudioRoutingOutputHideAES6 OBJECT-TYPE
		SYNTAX		RollCallString
		MAX-ACCESS		read-only
		STATUS			current
		DESCRIPTION
				"TYPE: - Display
				 PAGE: - Audio
					Output Hide AES 6  cmdID= 40255  format=   "
		::= { iqudc12CmdEntry 40255 }


	iqudc12AudioAudioRoutingOutputHideAES7 OBJECT-TYPE
		SYNTAX		RollCallString
		MAX-ACCESS		read-only
		STATUS			current
		DESCRIPTION
				"TYPE: - Display
				 PAGE: - Audio
					Output Hide AES 7  cmdID= 40256  format=   "
		::= { iqudc12CmdEntry 40256 }


	iqudc12AudioAudioRoutingOutputHideAES8 OBJECT-TYPE
		SYNTAX		RollCallString
		MAX-ACCESS		read-only
		STATUS			current
		DESCRIPTION
				"TYPE: - Display
				 PAGE: - Audio
					Output Hide AES 8  cmdID= 40257  format=   "
		::= { iqudc12CmdEntry 40257 }


	iqudc12AudioAudioRoutingDolbyDecodeSource OBJECT-TYPE
		SYNTAX		INTEGER {
							val-Disembed-1(0),
							val-Disembed-2(1),
							val-Disembed-3(2),
							val-Disembed-4(3),
							val-Disembed-5(4),
							val-Disembed-6(5),
							val-Disembed-7(6),
							val-Disembed-8(7),
							val-AES-Input-1(8),
							val-AES-Input-2(9),
							val-AES-Input-3(10),
							val-AES-Input-4(11),
							val-AES-Input-5(12),
							val-AES-Input-6(13),
							val-AES-Input-7(14),
							val-AES-Input-8(15)
							}
		MAX-ACCESS		read-write
		STATUS			current
		DESCRIPTION
				"TYPE: - RadiobuttonList
				 PAGE: - Audio
					DolbyDecode Source  cmdID= 40241 
					Disembed 1  value= 0  
					Disembed 2  value= 1  
					Disembed 3  value= 2  
					Disembed 4  value= 3  
					Disembed 5  value= 4  
					Disembed 6  value= 5  
					Disembed 7  value= 6  
					Disembed 8  value= 7  
					AES Input 1  value= 8  
					AES Input 2  value= 9  
					AES Input 3  value= 10  
					AES Input 4  value= 11  
					AES Input 5  value= 12  
					AES Input 6  value= 13  
					AES Input 7  value= 14  
					AES Input 8  value= 15  "
		::= { iqudc12CmdEntry 40241 }


	iqudc12AudioAudioRoutingDolbyDecodeNum OBJECT-TYPE
		SYNTAX		INTEGER
		MAX-ACCESS		read-write
		STATUS			current
		DESCRIPTION
				"TYPE: - Number
				 PAGE: - Audio
					DolbyDecodeNum  cmdID= 40242  min= 0  max= 1  step= 1  format= 0  div_scale= 1 
					Min = 0  Max = 0  Step = 0 "
		::= { iqudc12CmdEntry 40242 }


	iqudc12AudioAudioRoutingBus1RName OBJECT-TYPE
		SYNTAX		RollCallString
		MAX-ACCESS		read-only
		STATUS			current
		DESCRIPTION
				"TYPE: - Display
				 PAGE: - Audio
					Bus1RName  cmdID= 40273  format=   "
		::= { iqudc12CmdEntry 40273 }


	iqudc12AudioAudioRoutingBus2RName OBJECT-TYPE
		SYNTAX		RollCallString
		MAX-ACCESS		read-only
		STATUS			current
		DESCRIPTION
				"TYPE: - Display
				 PAGE: - Audio
					Bus2RName  cmdID= 40274  format=   "
		::= { iqudc12CmdEntry 40274 }


	iqudc12AudioAudioRoutingBus3RName OBJECT-TYPE
		SYNTAX		RollCallString
		MAX-ACCESS		read-only
		STATUS			current
		DESCRIPTION
				"TYPE: - Display
				 PAGE: - Audio
					Bus3RName  cmdID= 40275  format=   "
		::= { iqudc12CmdEntry 40275 }


	iqudc12AudioAudioRoutingBus4RName OBJECT-TYPE
		SYNTAX		RollCallString
		MAX-ACCESS		read-only
		STATUS			current
		DESCRIPTION
				"TYPE: - Display
				 PAGE: - Audio
					Bus4RName  cmdID= 40276  format=   "
		::= { iqudc12CmdEntry 40276 }


	iqudc12AudioAudioRoutingBus5RName OBJECT-TYPE
		SYNTAX		RollCallString
		MAX-ACCESS		read-only
		STATUS			current
		DESCRIPTION
				"TYPE: - Display
				 PAGE: - Audio
					Bus5RName  cmdID= 40277  format=   "
		::= { iqudc12CmdEntry 40277 }


	iqudc12AudioAudioRoutingBus6RName OBJECT-TYPE
		SYNTAX		RollCallString
		MAX-ACCESS		read-only
		STATUS			current
		DESCRIPTION
				"TYPE: - Display
				 PAGE: - Audio
					Bus6RName  cmdID= 40278  format=   "
		::= { iqudc12CmdEntry 40278 }


	iqudc12AudioAudioRoutingBus7RName OBJECT-TYPE
		SYNTAX		RollCallString
		MAX-ACCESS		read-only
		STATUS			current
		DESCRIPTION
				"TYPE: - Display
				 PAGE: - Audio
					Bus7RName  cmdID= 40279  format=   "
		::= { iqudc12CmdEntry 40279 }


	iqudc12AudioAudioRoutingBus8RName OBJECT-TYPE
		SYNTAX		RollCallString
		MAX-ACCESS		read-only
		STATUS			current
		DESCRIPTION
				"TYPE: - Display
				 PAGE: - Audio
					Bus8RName  cmdID= 40280  format=   "
		::= { iqudc12CmdEntry 40280 }


	iqudc12AudioAudioOutputRoutingOutDest1 OBJECT-TYPE
		SYNTAX		INTEGER
		MAX-ACCESS		read-write
		STATUS			current
		DESCRIPTION
				"TYPE: - Number
				 PAGE: - Audio
					OutDest1  cmdID= 40293  min= 0  max= 47  step= 1  format= %d  div_scale= 1 
					Min = 0  Max = 47  Step = 1 "
		::= { iqudc12CmdEntry 40293 }


	iqudc12AudioAudioOutputRoutingOutDest2 OBJECT-TYPE
		SYNTAX		INTEGER
		MAX-ACCESS		read-write
		STATUS			current
		DESCRIPTION
				"TYPE: - Number
				 PAGE: - Audio
					OutDest2  cmdID= 40294  min= 0  max= 47  step= 1  format= %d  div_scale= 1 
					Min = 0  Max = 47  Step = 1 "
		::= { iqudc12CmdEntry 40294 }


	iqudc12AudioAudioOutputRoutingOutDest3 OBJECT-TYPE
		SYNTAX		INTEGER
		MAX-ACCESS		read-write
		STATUS			current
		DESCRIPTION
				"TYPE: - Number
				 PAGE: - Audio
					OutDest3  cmdID= 40295  min= 0  max= 47  step= 1  format= %d  div_scale= 1 
					Min = 0  Max = 47  Step = 1 "
		::= { iqudc12CmdEntry 40295 }


	iqudc12AudioAudioOutputRoutingOutDest4 OBJECT-TYPE
		SYNTAX		INTEGER
		MAX-ACCESS		read-write
		STATUS			current
		DESCRIPTION
				"TYPE: - Number
				 PAGE: - Audio
					OutDest4  cmdID= 40296  min= 0  max= 47  step= 1  format= %d  div_scale= 1 
					Min = 0  Max = 47  Step = 1 "
		::= { iqudc12CmdEntry 40296 }


	iqudc12AudioAudioOutputRoutingOutDest5 OBJECT-TYPE
		SYNTAX		INTEGER
		MAX-ACCESS		read-write
		STATUS			current
		DESCRIPTION
				"TYPE: - Number
				 PAGE: - Audio
					OutDest5  cmdID= 40297  min= 0  max= 47  step= 1  format= %d  div_scale= 1 
					Min = 0  Max = 47  Step = 1 "
		::= { iqudc12CmdEntry 40297 }


	iqudc12AudioAudioOutputRoutingOutDest6 OBJECT-TYPE
		SYNTAX		INTEGER
		MAX-ACCESS		read-write
		STATUS			current
		DESCRIPTION
				"TYPE: - Number
				 PAGE: - Audio
					OutDest6  cmdID= 40298  min= 0  max= 47  step= 1  format= %d  div_scale= 1 
					Min = 0  Max = 47  Step = 1 "
		::= { iqudc12CmdEntry 40298 }


	iqudc12AudioAudioOutputRoutingOutDest7 OBJECT-TYPE
		SYNTAX		INTEGER
		MAX-ACCESS		read-write
		STATUS			current
		DESCRIPTION
				"TYPE: - Number
				 PAGE: - Audio
					OutDest7  cmdID= 40299  min= 0  max= 47  step= 1  format= %d  div_scale= 1 
					Min = 0  Max = 47  Step = 1 "
		::= { iqudc12CmdEntry 40299 }


	iqudc12AudioAudioOutputRoutingOutDest8 OBJECT-TYPE
		SYNTAX		INTEGER
		MAX-ACCESS		read-write
		STATUS			current
		DESCRIPTION
				"TYPE: - Number
				 PAGE: - Audio
					OutDest8  cmdID= 40300  min= 0  max= 47  step= 1  format= %d  div_scale= 1 
					Min = 0  Max = 47  Step = 1 "
		::= { iqudc12CmdEntry 40300 }


	iqudc12AudioAudioOutputRoutingOutDest9 OBJECT-TYPE
		SYNTAX		INTEGER
		MAX-ACCESS		read-write
		STATUS			current
		DESCRIPTION
				"TYPE: - Number
				 PAGE: - Audio
					OutDest9  cmdID= 40301  min= 0  max= 47  step= 1  format= %d  div_scale= 1 
					Min = 0  Max = 47  Step = 1 "
		::= { iqudc12CmdEntry 40301 }


	iqudc12AudioAudioOutputRoutingOutDest10 OBJECT-TYPE
		SYNTAX		INTEGER
		MAX-ACCESS		read-write
		STATUS			current
		DESCRIPTION
				"TYPE: - Number
				 PAGE: - Audio
					OutDest10  cmdID= 40302  min= 0  max= 47  step= 1  format= %d  div_scale= 1 
					Min = 0  Max = 47  Step = 1 "
		::= { iqudc12CmdEntry 40302 }


	iqudc12AudioAudioOutputRoutingOutDest11 OBJECT-TYPE
		SYNTAX		INTEGER
		MAX-ACCESS		read-write
		STATUS			current
		DESCRIPTION
				"TYPE: - Number
				 PAGE: - Audio
					OutDest11  cmdID= 40303  min= 0  max= 47  step= 1  format= %d  div_scale= 1 
					Min = 0  Max = 47  Step = 1 "
		::= { iqudc12CmdEntry 40303 }


	iqudc12AudioAudioOutputRoutingOutDest12 OBJECT-TYPE
		SYNTAX		INTEGER
		MAX-ACCESS		read-write
		STATUS			current
		DESCRIPTION
				"TYPE: - Number
				 PAGE: - Audio
					OutDest12  cmdID= 40304  min= 0  max= 47  step= 1  format= %d  div_scale= 1 
					Min = 0  Max = 47  Step = 1 "
		::= { iqudc12CmdEntry 40304 }


	iqudc12AudioAudioOutputRoutingOutDest13 OBJECT-TYPE
		SYNTAX		INTEGER
		MAX-ACCESS		read-write
		STATUS			current
		DESCRIPTION
				"TYPE: - Number
				 PAGE: - Audio
					OutDest13  cmdID= 40305  min= 0  max= 47  step= 1  format= %d  div_scale= 1 
					Min = 0  Max = 47  Step = 1 "
		::= { iqudc12CmdEntry 40305 }


	iqudc12AudioAudioOutputRoutingOutDest14 OBJECT-TYPE
		SYNTAX		INTEGER
		MAX-ACCESS		read-write
		STATUS			current
		DESCRIPTION
				"TYPE: - Number
				 PAGE: - Audio
					OutDest14  cmdID= 40306  min= 0  max= 47  step= 1  format= %d  div_scale= 1 
					Min = 0  Max = 47  Step = 1 "
		::= { iqudc12CmdEntry 40306 }


	iqudc12AudioAudioOutputRoutingOutDest15 OBJECT-TYPE
		SYNTAX		INTEGER
		MAX-ACCESS		read-write
		STATUS			current
		DESCRIPTION
				"TYPE: - Number
				 PAGE: - Audio
					OutDest15  cmdID= 40307  min= 0  max= 47  step= 1  format= %d  div_scale= 1 
					Min = 0  Max = 47  Step = 1 "
		::= { iqudc12CmdEntry 40307 }


	iqudc12AudioAudioOutputRoutingOutDest16 OBJECT-TYPE
		SYNTAX		INTEGER
		MAX-ACCESS		read-write
		STATUS			current
		DESCRIPTION
				"TYPE: - Number
				 PAGE: - Audio
					OutDest16  cmdID= 40308  min= 0  max= 47  step= 1  format= %d  div_scale= 1 
					Min = 0  Max = 47  Step = 1 "
		::= { iqudc12CmdEntry 40308 }


	iqudc12AudioAudioOutputRoutingOutDest17 OBJECT-TYPE
		SYNTAX		INTEGER
		MAX-ACCESS		read-write
		STATUS			current
		DESCRIPTION
				"TYPE: - Number
				 PAGE: - Audio
					OutDest17  cmdID= 40309  min= 0  max= 47  step= 1  format= %d  div_scale= 1 
					Min = 0  Max = 47  Step = 1 "
		::= { iqudc12CmdEntry 40309 }


	iqudc12AudioAudioOutputRoutingOutDest18 OBJECT-TYPE
		SYNTAX		INTEGER
		MAX-ACCESS		read-write
		STATUS			current
		DESCRIPTION
				"TYPE: - Number
				 PAGE: - Audio
					OutDest18  cmdID= 40310  min= 0  max= 47  step= 1  format= %d  div_scale= 1 
					Min = 0  Max = 47  Step = 1 "
		::= { iqudc12CmdEntry 40310 }


	iqudc12AudioAudioOutputRoutingOutDest19 OBJECT-TYPE
		SYNTAX		INTEGER
		MAX-ACCESS		read-write
		STATUS			current
		DESCRIPTION
				"TYPE: - Number
				 PAGE: - Audio
					OutDest19  cmdID= 40311  min= 0  max= 47  step= 1  format= %d  div_scale= 1 
					Min = 0  Max = 47  Step = 1 "
		::= { iqudc12CmdEntry 40311 }


	iqudc12AudioAudioOutputRoutingOutDest20 OBJECT-TYPE
		SYNTAX		INTEGER
		MAX-ACCESS		read-write
		STATUS			current
		DESCRIPTION
				"TYPE: - Number
				 PAGE: - Audio
					OutDest20  cmdID= 40312  min= 0  max= 47  step= 1  format= %d  div_scale= 1 
					Min = 0  Max = 47  Step = 1 "
		::= { iqudc12CmdEntry 40312 }


	iqudc12AudioAudioOutputRoutingOutDest21 OBJECT-TYPE
		SYNTAX		INTEGER
		MAX-ACCESS		read-write
		STATUS			current
		DESCRIPTION
				"TYPE: - Number
				 PAGE: - Audio
					OutDest21  cmdID= 40313  min= 0  max= 47  step= 1  format= %d  div_scale= 1 
					Min = 0  Max = 47  Step = 1 "
		::= { iqudc12CmdEntry 40313 }


	iqudc12AudioAudioOutputRoutingOutDest22 OBJECT-TYPE
		SYNTAX		INTEGER
		MAX-ACCESS		read-write
		STATUS			current
		DESCRIPTION
				"TYPE: - Number
				 PAGE: - Audio
					OutDest22  cmdID= 40314  min= 0  max= 47  step= 1  format= %d  div_scale= 1 
					Min = 0  Max = 47  Step = 1 "
		::= { iqudc12CmdEntry 40314 }


	iqudc12AudioAudioOutputRoutingOutDest23 OBJECT-TYPE
		SYNTAX		INTEGER
		MAX-ACCESS		read-write
		STATUS			current
		DESCRIPTION
				"TYPE: - Number
				 PAGE: - Audio
					OutDest23  cmdID= 40315  min= 0  max= 47  step= 1  format= %d  div_scale= 1 
					Min = 0  Max = 47  Step = 1 "
		::= { iqudc12CmdEntry 40315 }


	iqudc12AudioAudioOutputRoutingOutDest24 OBJECT-TYPE
		SYNTAX		INTEGER
		MAX-ACCESS		read-write
		STATUS			current
		DESCRIPTION
				"TYPE: - Number
				 PAGE: - Audio
					OutDest24  cmdID= 40316  min= 0  max= 47  step= 1  format= %d  div_scale= 1 
					Min = 0  Max = 47  Step = 1 "
		::= { iqudc12CmdEntry 40316 }


	iqudc12AudioAudioOutputRoutingOutDest25 OBJECT-TYPE
		SYNTAX		INTEGER
		MAX-ACCESS		read-write
		STATUS			current
		DESCRIPTION
				"TYPE: - Number
				 PAGE: - Audio
					OutDest25  cmdID= 40317  min= 0  max= 47  step= 1  format= %d  div_scale= 1 
					Min = 0  Max = 47  Step = 1 "
		::= { iqudc12CmdEntry 40317 }


	iqudc12AudioAudioOutputRoutingOutDest26 OBJECT-TYPE
		SYNTAX		INTEGER
		MAX-ACCESS		read-write
		STATUS			current
		DESCRIPTION
				"TYPE: - Number
				 PAGE: - Audio
					OutDest26  cmdID= 40318  min= 0  max= 47  step= 1  format= %d  div_scale= 1 
					Min = 0  Max = 47  Step = 1 "
		::= { iqudc12CmdEntry 40318 }


	iqudc12AudioAudioOutputRoutingOutDest27 OBJECT-TYPE
		SYNTAX		INTEGER
		MAX-ACCESS		read-write
		STATUS			current
		DESCRIPTION
				"TYPE: - Number
				 PAGE: - Audio
					OutDest27  cmdID= 40319  min= 0  max= 47  step= 1  format= %d  div_scale= 1 
					Min = 0  Max = 47  Step = 1 "
		::= { iqudc12CmdEntry 40319 }


	iqudc12AudioAudioOutputRoutingOutDest28 OBJECT-TYPE
		SYNTAX		INTEGER
		MAX-ACCESS		read-write
		STATUS			current
		DESCRIPTION
				"TYPE: - Number
				 PAGE: - Audio
					OutDest28  cmdID= 40320  min= 0  max= 47  step= 1  format= %d  div_scale= 1 
					Min = 0  Max = 47  Step = 1 "
		::= { iqudc12CmdEntry 40320 }


	iqudc12AudioAudioOutputRoutingOutDest29 OBJECT-TYPE
		SYNTAX		INTEGER
		MAX-ACCESS		read-write
		STATUS			current
		DESCRIPTION
				"TYPE: - Number
				 PAGE: - Audio
					OutDest29  cmdID= 40321  min= 0  max= 47  step= 1  format= %d  div_scale= 1 
					Min = 0  Max = 47  Step = 1 "
		::= { iqudc12CmdEntry 40321 }


	iqudc12AudioAudioOutputRoutingOutDest30 OBJECT-TYPE
		SYNTAX		INTEGER
		MAX-ACCESS		read-write
		STATUS			current
		DESCRIPTION
				"TYPE: - Number
				 PAGE: - Audio
					OutDest30  cmdID= 40322  min= 0  max= 47  step= 1  format= %d  div_scale= 1 
					Min = 0  Max = 47  Step = 1 "
		::= { iqudc12CmdEntry 40322 }


	iqudc12AudioAudioOutputRoutingOutDest31 OBJECT-TYPE
		SYNTAX		INTEGER
		MAX-ACCESS		read-write
		STATUS			current
		DESCRIPTION
				"TYPE: - Number
				 PAGE: - Audio
					OutDest31  cmdID= 40323  min= 0  max= 47  step= 1  format= %d  div_scale= 1 
					Min = 0  Max = 47  Step = 1 "
		::= { iqudc12CmdEntry 40323 }


	iqudc12AudioAudioOutputRoutingOutDest32 OBJECT-TYPE
		SYNTAX		INTEGER
		MAX-ACCESS		read-write
		STATUS			current
		DESCRIPTION
				"TYPE: - Number
				 PAGE: - Audio
					OutDest32  cmdID= 40324  min= 0  max= 47  step= 1  format= %d  div_scale= 1 
					Min = 0  Max = 47  Step = 1 "
		::= { iqudc12CmdEntry 40324 }


	iqudc12AudioAudioOutputRoutingOutDest33 OBJECT-TYPE
		SYNTAX		INTEGER
		MAX-ACCESS		read-write
		STATUS			current
		DESCRIPTION
				"TYPE: - Number
				 PAGE: - Audio
					OutDest33  cmdID= 40325  min= 0  max= 47  step= 1  format= %d  div_scale= 1 
					Min = 0  Max = 47  Step = 1 "
		::= { iqudc12CmdEntry 40325 }


	iqudc12AudioAudioOutputRoutingOutDest34 OBJECT-TYPE
		SYNTAX		INTEGER
		MAX-ACCESS		read-write
		STATUS			current
		DESCRIPTION
				"TYPE: - Number
				 PAGE: - Audio
					OutDest34  cmdID= 40326  min= 0  max= 47  step= 1  format= %d  div_scale= 1 
					Min = 0  Max = 47  Step = 1 "
		::= { iqudc12CmdEntry 40326 }


	iqudc12AudioAudioOutputRoutingOutDest35 OBJECT-TYPE
		SYNTAX		INTEGER
		MAX-ACCESS		read-write
		STATUS			current
		DESCRIPTION
				"TYPE: - Number
				 PAGE: - Audio
					OutDest35  cmdID= 40327  min= 0  max= 47  step= 1  format= %d  div_scale= 1 
					Min = 0  Max = 47  Step = 1 "
		::= { iqudc12CmdEntry 40327 }


	iqudc12AudioAudioOutputRoutingOutDest36 OBJECT-TYPE
		SYNTAX		INTEGER
		MAX-ACCESS		read-write
		STATUS			current
		DESCRIPTION
				"TYPE: - Number
				 PAGE: - Audio
					OutDest36  cmdID= 40328  min= 0  max= 47  step= 1  format= %d  div_scale= 1 
					Min = 0  Max = 47  Step = 1 "
		::= { iqudc12CmdEntry 40328 }


	iqudc12AudioAudioOutputRoutingDolbyEncEnb OBJECT-TYPE
		SYNTAX		RollCallString
		MAX-ACCESS		read-only
		STATUS			current
		DESCRIPTION
				"TYPE: - Display
				 PAGE: - Audio
					DolbyEncEnb  cmdID= 40214  format=   "
		::= { iqudc12CmdEntry 40214 }


	iqudc12AudioAudioOutputRoutingUpmixEnb OBJECT-TYPE
		SYNTAX		RollCallString
		MAX-ACCESS		read-only
		STATUS			current
		DESCRIPTION
				"TYPE: - Display
				 PAGE: - Audio
					UpmixEnb  cmdID= 40213  format=   "
		::= { iqudc12CmdEntry 40213 }


	iqudc12MenuAudioRoutingMatriBus1audsel OBJECT-TYPE
		SYNTAX		INTEGER {
							val-Disemb1(0),
							val-Disemb2(1),
							val-Disemb3(2),
							val-Disemb4(3),
							val-Disemb5(4),
							val-Disemb6(5),
							val-Disemb7(6),
							val-Disemb8(7),
							val-AesInput1(8),
							val-AesInput2(9),
							val-AesInput3(10),
							val-AesInput4(11),
							val-AesInput5(12),
							val-AesInput6(13),
							val-AesInput7(14),
							val-AesInput8(15),
							val-AnglInput1(16),
							val-AnlgInput2(17),
							val-DolbyDec1(18),
							val-DolbyDec2(19),
							val-DolbyDec3(20),
							val-DolbyDec4(21),
							val-DolbyDec5(22)
							}
		MAX-ACCESS		read-write
		STATUS			current
		DESCRIPTION
				"TYPE: - RadiobuttonList
				 PAGE: - Audio Routing Matri
					Bus 1 aud sel  cmdID= 40200 
					Disemb1  value= 0  
					Disemb2  value= 1  
					Disemb3  value= 2  
					Disemb4  value= 3  
					Disemb5  value= 4  
					Disemb6  value= 5  
					Disemb7  value= 6  
					Disemb8  value= 7  
					AesInput1  value= 8  
					AesInput2  value= 9  
					AesInput3  value= 10  
					AesInput4  value= 11  
					AesInput5  value= 12  
					AesInput6  value= 13  
					AesInput7  value= 14  
					AesInput8  value= 15  
					AnglInput1  value= 16  
					AnlgInput2  value= 17  
					DolbyDec1  value= 18  
					DolbyDec2  value= 19  
					DolbyDec3  value= 20  
					DolbyDec4  value= 21  
					DolbyDec5  value= 22  "
		::= { iqudc12CmdEntry 40200 }


	iqudc12MenuAudioRoutingMatriBus2audsel OBJECT-TYPE
		SYNTAX		INTEGER {
							val-Disemb1(0),
							val-Disemb2(1),
							val-Disemb3(2),
							val-Disemb4(3),
							val-Disemb5(4),
							val-Disemb6(5),
							val-Disemb7(6),
							val-Disemb8(7),
							val-AesInput1(8),
							val-AesInput2(9),
							val-AesInput3(10),
							val-AesInput4(11),
							val-AesInput5(12),
							val-AesInput6(13),
							val-AesInput7(14),
							val-AesInput8(15),
							val-AnglInput1(16),
							val-AnlgInput2(17),
							val-DolbyDec1(18),
							val-DolbyDec2(19),
							val-DolbyDec3(20),
							val-DolbyDec4(21),
							val-DolbyDec5(22)
							}
		MAX-ACCESS		read-write
		STATUS			current
		DESCRIPTION
				"TYPE: - RadiobuttonList
				 PAGE: - Audio Routing Matri
					Bus 2 aud sel  cmdID= 40201 
					Disemb1  value= 0  
					Disemb2  value= 1  
					Disemb3  value= 2  
					Disemb4  value= 3  
					Disemb5  value= 4  
					Disemb6  value= 5  
					Disemb7  value= 6  
					Disemb8  value= 7  
					AesInput1  value= 8  
					AesInput2  value= 9  
					AesInput3  value= 10  
					AesInput4  value= 11  
					AesInput5  value= 12  
					AesInput6  value= 13  
					AesInput7  value= 14  
					AesInput8  value= 15  
					AnglInput1  value= 16  
					AnlgInput2  value= 17  
					DolbyDec1  value= 18  
					DolbyDec2  value= 19  
					DolbyDec3  value= 20  
					DolbyDec4  value= 21  
					DolbyDec5  value= 22  "
		::= { iqudc12CmdEntry 40201 }


	iqudc12MenuAudioRoutingMatriBus3audsel OBJECT-TYPE
		SYNTAX		INTEGER {
							val-Disemb1(0),
							val-Disemb2(1),
							val-Disemb3(2),
							val-Disemb4(3),
							val-Disemb5(4),
							val-Disemb6(5),
							val-Disemb7(6),
							val-Disemb8(7),
							val-AesInput1(8),
							val-AesInput2(9),
							val-AesInput3(10),
							val-AesInput4(11),
							val-AesInput5(12),
							val-AesInput6(13),
							val-AesInput7(14),
							val-AesInput8(15),
							val-AnglInput1(16),
							val-AnlgInput2(17),
							val-DolbyDec1(18),
							val-DolbyDec2(19),
							val-DolbyDec3(20),
							val-DolbyDec4(21),
							val-DolbyDec5(22)
							}
		MAX-ACCESS		read-write
		STATUS			current
		DESCRIPTION
				"TYPE: - RadiobuttonList
				 PAGE: - Audio Routing Matri
					Bus 3 aud sel  cmdID= 40202 
					Disemb1  value= 0  
					Disemb2  value= 1  
					Disemb3  value= 2  
					Disemb4  value= 3  
					Disemb5  value= 4  
					Disemb6  value= 5  
					Disemb7  value= 6  
					Disemb8  value= 7  
					AesInput1  value= 8  
					AesInput2  value= 9  
					AesInput3  value= 10  
					AesInput4  value= 11  
					AesInput5  value= 12  
					AesInput6  value= 13  
					AesInput7  value= 14  
					AesInput8  value= 15  
					AnglInput1  value= 16  
					AnlgInput2  value= 17  
					DolbyDec1  value= 18  
					DolbyDec2  value= 19  
					DolbyDec3  value= 20  
					DolbyDec4  value= 21  
					DolbyDec5  value= 22  "
		::= { iqudc12CmdEntry 40202 }


	iqudc12MenuAudioRoutingMatriBus4audsel OBJECT-TYPE
		SYNTAX		INTEGER {
							val-Disemb1(0),
							val-Disemb2(1),
							val-Disemb3(2),
							val-Disemb4(3),
							val-Disemb5(4),
							val-Disemb6(5),
							val-Disemb7(6),
							val-Disemb8(7),
							val-AesInput1(8),
							val-AesInput2(9),
							val-AesInput3(10),
							val-AesInput4(11),
							val-AesInput5(12),
							val-AesInput6(13),
							val-AesInput7(14),
							val-AesInput8(15),
							val-AnglInput1(16),
							val-AnlgInput2(17),
							val-DolbyDec1(18),
							val-DolbyDec2(19),
							val-DolbyDec3(20),
							val-DolbyDec4(21),
							val-DolbyDec5(22)
							}
		MAX-ACCESS		read-write
		STATUS			current
		DESCRIPTION
				"TYPE: - RadiobuttonList
				 PAGE: - Audio Routing Matri
					Bus 4 aud sel  cmdID= 40203 
					Disemb1  value= 0  
					Disemb2  value= 1  
					Disemb3  value= 2  
					Disemb4  value= 3  
					Disemb5  value= 4  
					Disemb6  value= 5  
					Disemb7  value= 6  
					Disemb8  value= 7  
					AesInput1  value= 8  
					AesInput2  value= 9  
					AesInput3  value= 10  
					AesInput4  value= 11  
					AesInput5  value= 12  
					AesInput6  value= 13  
					AesInput7  value= 14  
					AesInput8  value= 15  
					AnglInput1  value= 16  
					AnlgInput2  value= 17  
					DolbyDec1  value= 18  
					DolbyDec2  value= 19  
					DolbyDec3  value= 20  
					DolbyDec4  value= 21  
					DolbyDec5  value= 22  "
		::= { iqudc12CmdEntry 40203 }


	iqudc12MenuAudioRoutingMatriBus5audsel OBJECT-TYPE
		SYNTAX		INTEGER {
							val-Disemb1(0),
							val-Disemb2(1),
							val-Disemb3(2),
							val-Disemb4(3),
							val-Disemb5(4),
							val-Disemb6(5),
							val-Disemb7(6),
							val-Disemb8(7),
							val-AesInput1(8),
							val-AesInput2(9),
							val-AesInput3(10),
							val-AesInput4(11),
							val-AesInput5(12),
							val-AesInput6(13),
							val-AesInput7(14),
							val-AesInput8(15),
							val-AnglInput1(16),
							val-AnlgInput2(17),
							val-DolbyDec1(18),
							val-DolbyDec2(19),
							val-DolbyDec3(20),
							val-DolbyDec4(21),
							val-DolbyDec5(22)
							}
		MAX-ACCESS		read-write
		STATUS			current
		DESCRIPTION
				"TYPE: - RadiobuttonList
				 PAGE: - Audio Routing Matri
					Bus 5 aud sel  cmdID= 40204 
					Disemb1  value= 0  
					Disemb2  value= 1  
					Disemb3  value= 2  
					Disemb4  value= 3  
					Disemb5  value= 4  
					Disemb6  value= 5  
					Disemb7  value= 6  
					Disemb8  value= 7  
					AesInput1  value= 8  
					AesInput2  value= 9  
					AesInput3  value= 10  
					AesInput4  value= 11  
					AesInput5  value= 12  
					AesInput6  value= 13  
					AesInput7  value= 14  
					AesInput8  value= 15  
					AnglInput1  value= 16  
					AnlgInput2  value= 17  
					DolbyDec1  value= 18  
					DolbyDec2  value= 19  
					DolbyDec3  value= 20  
					DolbyDec4  value= 21  
					DolbyDec5  value= 22  "
		::= { iqudc12CmdEntry 40204 }


	iqudc12MenuAudioRoutingMatriBus6audsel OBJECT-TYPE
		SYNTAX		INTEGER {
							val-Disemb1(0),
							val-Disemb2(1),
							val-Disemb3(2),
							val-Disemb4(3),
							val-Disemb5(4),
							val-Disemb6(5),
							val-Disemb7(6),
							val-Disemb8(7),
							val-AesInput1(8),
							val-AesInput2(9),
							val-AesInput3(10),
							val-AesInput4(11),
							val-AesInput5(12),
							val-AesInput6(13),
							val-AesInput7(14),
							val-AesInput8(15),
							val-AnglInput1(16),
							val-AnlgInput2(17),
							val-DolbyDec1(18),
							val-DolbyDec2(19),
							val-DolbyDec3(20),
							val-DolbyDec4(21),
							val-DolbyDec5(22)
							}
		MAX-ACCESS		read-write
		STATUS			current
		DESCRIPTION
				"TYPE: - RadiobuttonList
				 PAGE: - Audio Routing Matri
					Bus 6 aud sel  cmdID= 40205 
					Disemb1  value= 0  
					Disemb2  value= 1  
					Disemb3  value= 2  
					Disemb4  value= 3  
					Disemb5  value= 4  
					Disemb6  value= 5  
					Disemb7  value= 6  
					Disemb8  value= 7  
					AesInput1  value= 8  
					AesInput2  value= 9  
					AesInput3  value= 10  
					AesInput4  value= 11  
					AesInput5  value= 12  
					AesInput6  value= 13  
					AesInput7  value= 14  
					AesInput8  value= 15  
					AnglInput1  value= 16  
					AnlgInput2  value= 17  
					DolbyDec1  value= 18  
					DolbyDec2  value= 19  
					DolbyDec3  value= 20  
					DolbyDec4  value= 21  
					DolbyDec5  value= 22  "
		::= { iqudc12CmdEntry 40205 }


	iqudc12MenuAudioRoutingMatriBus7audsel OBJECT-TYPE
		SYNTAX		INTEGER {
							val-Disemb1(0),
							val-Disemb2(1),
							val-Disemb3(2),
							val-Disemb4(3),
							val-Disemb5(4),
							val-Disemb6(5),
							val-Disemb7(6),
							val-Disemb8(7),
							val-AesInput1(8),
							val-AesInput2(9),
							val-AesInput3(10),
							val-AesInput4(11),
							val-AesInput5(12),
							val-AesInput6(13),
							val-AesInput7(14),
							val-AesInput8(15),
							val-AnglInput1(16),
							val-AnlgInput2(17),
							val-DolbyDec1(18),
							val-DolbyDec2(19),
							val-DolbyDec3(20),
							val-DolbyDec4(21),
							val-DolbyDec5(22)
							}
		MAX-ACCESS		read-write
		STATUS			current
		DESCRIPTION
				"TYPE: - RadiobuttonList
				 PAGE: - Audio Routing Matri
					Bus 7 aud sel  cmdID= 40206 
					Disemb1  value= 0  
					Disemb2  value= 1  
					Disemb3  value= 2  
					Disemb4  value= 3  
					Disemb5  value= 4  
					Disemb6  value= 5  
					Disemb7  value= 6  
					Disemb8  value= 7  
					AesInput1  value= 8  
					AesInput2  value= 9  
					AesInput3  value= 10  
					AesInput4  value= 11  
					AesInput5  value= 12  
					AesInput6  value= 13  
					AesInput7  value= 14  
					AesInput8  value= 15  
					AnglInput1  value= 16  
					AnlgInput2  value= 17  
					DolbyDec1  value= 18  
					DolbyDec2  value= 19  
					DolbyDec3  value= 20  
					DolbyDec4  value= 21  
					DolbyDec5  value= 22  "
		::= { iqudc12CmdEntry 40206 }


	iqudc12MenuAudioRoutingMatriBus8audsel OBJECT-TYPE
		SYNTAX		INTEGER {
							val-Disemb1(0),
							val-Disemb2(1),
							val-Disemb3(2),
							val-Disemb4(3),
							val-Disemb5(4),
							val-Disemb6(5),
							val-Disemb7(6),
							val-Disemb8(7),
							val-AesInput1(8),
							val-AesInput2(9),
							val-AesInput3(10),
							val-AesInput4(11),
							val-AesInput5(12),
							val-AesInput6(13),
							val-AesInput7(14),
							val-AesInput8(15),
							val-AnglInput1(16),
							val-AnlgInput2(17),
							val-DolbyDec1(18),
							val-DolbyDec2(19),
							val-DolbyDec3(20),
							val-DolbyDec4(21),
							val-DolbyDec5(22)
							}
		MAX-ACCESS		read-write
		STATUS			current
		DESCRIPTION
				"TYPE: - RadiobuttonList
				 PAGE: - Audio Routing Matri
					Bus 8 aud sel  cmdID= 40207 
					Disemb1  value= 0  
					Disemb2  value= 1  
					Disemb3  value= 2  
					Disemb4  value= 3  
					Disemb5  value= 4  
					Disemb6  value= 5  
					Disemb7  value= 6  
					Disemb8  value= 7  
					AesInput1  value= 8  
					AesInput2  value= 9  
					AesInput3  value= 10  
					AesInput4  value= 11  
					AesInput5  value= 12  
					AesInput6  value= 13  
					AesInput7  value= 14  
					AesInput8  value= 15  
					AnglInput1  value= 16  
					AnlgInput2  value= 17  
					DolbyDec1  value= 18  
					DolbyDec2  value= 19  
					DolbyDec3  value= 20  
					DolbyDec4  value= 21  
					DolbyDec5  value= 22  "
		::= { iqudc12CmdEntry 40207 }


	iqudc12AudioOutRouteMatriEmbed12MatrixEmbed11audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed12 Matrix
					Embed1_1 aud sel  cmdID= 40329 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40329 }


	iqudc12AudioOutRouteMatriEmbed12MatrixEmbed12audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed12 Matrix
					Embed1_2 aud sel  cmdID= 40330 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40330 }


	iqudc12AudioOutRouteMatriEmbed12MatrixEmbed21audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed12 Matrix
					Embed2_1 aud sel  cmdID= 40331 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40331 }


	iqudc12AudioOutRouteMatriEmbed12MatrixEmbed22audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed12 Matrix
					Embed2_2 aud sel  cmdID= 40332 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40332 }


	iqudc12AudioOutRouteMatriEmbed34MatrixEmbed31audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed34 Matrix
					Embed3_1 aud sel  cmdID= 40333 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40333 }


	iqudc12AudioOutRouteMatriEmbed34MatrixEmbed32audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed34 Matrix
					Embed3_2 aud sel  cmdID= 40334 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40334 }


	iqudc12AudioOutRouteMatriEmbed34MatrixEmbed41audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed34 Matrix
					Embed4_1 aud sel  cmdID= 40335 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40335 }


	iqudc12AudioOutRouteMatriEmbed34MatrixEmbed42audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed34 Matrix
					Embed4_2 aud sel  cmdID= 40336 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40336 }


	iqudc12AudioOutRouteMatriEmbed56MatrixEmbed51audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed56 Matrix
					Embed5_1 aud sel  cmdID= 40337 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40337 }


	iqudc12AudioOutRouteMatriEmbed56MatrixEmbed52audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed56 Matrix
					Embed5_2 aud sel  cmdID= 40338 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40338 }


	iqudc12AudioOutRouteMatriEmbed56MatrixEmbed61audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed56 Matrix
					Embed6_1 aud sel  cmdID= 40339 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40339 }


	iqudc12AudioOutRouteMatriEmbed56MatrixEmbed62audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed56 Matrix
					Embed6_2 aud sel  cmdID= 40340 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40340 }


	iqudc12AudioOutRouteMatriEmbed78MatrixEmbed71audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed78 Matrix
					Embed7_1 aud sel  cmdID= 40341 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40341 }


	iqudc12AudioOutRouteMatriEmbed78MatrixEmbed72audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed78 Matrix
					Embed7_2 aud sel  cmdID= 40342 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40342 }


	iqudc12AudioOutRouteMatriEmbed78MatrixEmbed81audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed78 Matrix
					Embed8_1 aud sel  cmdID= 40343 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40343 }


	iqudc12AudioOutRouteMatriEmbed78MatrixEmbed82audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - Embed78 Matrix
					Embed8_2 aud sel  cmdID= 40344 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40344 }


	iqudc12AudioOutRouteMatriAES12MatrixAES11audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES12 Matrix
					AES1_1 aud sel  cmdID= 40345 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40345 }


	iqudc12AudioOutRouteMatriAES12MatrixAES12audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES12 Matrix
					AES1_2 aud sel  cmdID= 40346 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40346 }


	iqudc12AudioOutRouteMatriAES12MatrixAES21audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES12 Matrix
					AES2_1 aud sel  cmdID= 40347 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40347 }


	iqudc12AudioOutRouteMatriAES12MatrixAES22audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES12 Matrix
					AES2_2 aud sel  cmdID= 40348 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40348 }


	iqudc12AudioOutRouteMatriAES34MatrixAES31audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES34 Matrix
					AES3_1 aud sel  cmdID= 40349 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40349 }


	iqudc12AudioOutRouteMatriAES34MatrixAES32audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES34 Matrix
					AES3_2 aud sel  cmdID= 40350 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40350 }


	iqudc12AudioOutRouteMatriAES34MatrixAES41audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES34 Matrix
					AES4_1 aud sel  cmdID= 40351 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40351 }


	iqudc12AudioOutRouteMatriAES34MatrixAES42audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES34 Matrix
					AES4_2 aud sel  cmdID= 40352 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40352 }


	iqudc12AudioOutRouteMatriAES56MatrixAES51audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES56 Matrix
					AES5_1 aud sel  cmdID= 40353 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40353 }


	iqudc12AudioOutRouteMatriAES56MatrixAES52audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES56 Matrix
					AES5_2 aud sel  cmdID= 40354 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40354 }


	iqudc12AudioOutRouteMatriAES56MatrixAES61audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES56 Matrix
					AES6_1 aud sel  cmdID= 40355 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40355 }


	iqudc12AudioOutRouteMatriAES56MatrixAES62audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES56 Matrix
					AES6_2 aud sel  cmdID= 40356 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40356 }


	iqudc12AudioOutRouteMatriAES78MatrixAES71audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES78 Matrix
					AES7_1 aud sel  cmdID= 40357 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40357 }


	iqudc12AudioOutRouteMatriAES78MatrixAES72audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES78 Matrix
					AES7_2 aud sel  cmdID= 40358 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40358 }


	iqudc12AudioOutRouteMatriAES78MatrixAES81audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES78 Matrix
					AES8_1 aud sel  cmdID= 40359 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40359 }


	iqudc12AudioOutRouteMatriAES78MatrixAES82audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-DlbyEncode-1(32),
							val-DlbyEncode-2(33),
							val-Tone-1(16),
							val-Tone-2(17),
							val-Tone-3(18),
							val-Tone-4(19),
							val-Tone-5(20),
							val-Tone-6(21),
							val-Tone-7(22),
							val-Tone-8(23)
							}
		MAX-ACCESS		read-write
		STATUS			current
		DESCRIPTION
				"TYPE: - RadiobuttonList
				 PAGE: - AES78 Matrix
					AES8_2 aud sel  cmdID= 40360 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					DlbyEncode 1  value= 32  
					DlbyEncode 2  value= 33  
					Tone 1  value= 16  
					Tone 2  value= 17  
					Tone 3  value= 18  
					Tone 4  value= 19  
					Tone 5  value= 20  
					Tone 6  value= 21  
					Tone 7  value= 22  
					Tone 8  value= 23  "
		::= { iqudc12CmdEntry 40360 }


	iqudc12AudioOutRouteMatriAnlg12MatrixAnlg11audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-Tone-1(16),
							val-Tone-2(17),
							val-Tone-3(18),
							val-Tone-4(19),
							val-Tone-5(20),
							val-Tone-6(21),
							val-Tone-7(22),
							val-Tone-8(23),
							val-Legacy1(32),
							val-Legacy2(33)
							}
		MAX-ACCESS		read-write
		STATUS			current
		DESCRIPTION
				"TYPE: - RadiobuttonList
				 PAGE: - Anlg12 Matrix
					Anlg1_1 aud sel  cmdID= 40361 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					Tone 1  value= 16  
					Tone 2  value= 17  
					Tone 3  value= 18  
					Tone 4  value= 19  
					Tone 5  value= 20  
					Tone 6  value= 21  
					Tone 7  value= 22  
					Tone 8  value= 23  
					Legacy1  value= 32  
					Legacy2  value= 33  "
		::= { iqudc12CmdEntry 40361 }


	iqudc12AudioOutRouteMatriAnlg12MatrixAnlg12audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-Tone-1(16),
							val-Tone-2(17),
							val-Tone-3(18),
							val-Tone-4(19),
							val-Tone-5(20),
							val-Tone-6(21),
							val-Tone-7(22),
							val-Tone-8(23),
							val-Legacy1(32),
							val-Legacy2(33)
							}
		MAX-ACCESS		read-write
		STATUS			current
		DESCRIPTION
				"TYPE: - RadiobuttonList
				 PAGE: - Anlg12 Matrix
					Anlg1_2 aud sel  cmdID= 40362 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					Tone 1  value= 16  
					Tone 2  value= 17  
					Tone 3  value= 18  
					Tone 4  value= 19  
					Tone 5  value= 20  
					Tone 6  value= 21  
					Tone 7  value= 22  
					Tone 8  value= 23  
					Legacy1  value= 32  
					Legacy2  value= 33  "
		::= { iqudc12CmdEntry 40362 }


	iqudc12AudioOutRouteMatriAnlg12MatrixAnlg21audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-Tone-1(16),
							val-Tone-2(17),
							val-Tone-3(18),
							val-Tone-4(19),
							val-Tone-5(20),
							val-Tone-6(21),
							val-Tone-7(22),
							val-Tone-8(23),
							val-Legacy1(32),
							val-Legacy2(33)
							}
		MAX-ACCESS		read-write
		STATUS			current
		DESCRIPTION
				"TYPE: - RadiobuttonList
				 PAGE: - Anlg12 Matrix
					Anlg2_1 aud sel  cmdID= 40363 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					Tone 1  value= 16  
					Tone 2  value= 17  
					Tone 3  value= 18  
					Tone 4  value= 19  
					Tone 5  value= 20  
					Tone 6  value= 21  
					Tone 7  value= 22  
					Tone 8  value= 23  
					Legacy1  value= 32  
					Legacy2  value= 33  "
		::= { iqudc12CmdEntry 40363 }


	iqudc12AudioOutRouteMatriAnlg12MatrixAnlg22audsel OBJECT-TYPE
		SYNTAX		INTEGER {
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Silence(34),
							val-Mixer1(35),
							val-Mixer2(36),
							val-Mixer3(37),
							val-Mixer4(38),
							val-Downmix1-1(39),
							val-Downmix1-2(40),
							val-Downmix2-1(41),
							val-Downmix2-2(42),
							val-UpmixL(24),
							val-UpmixR(25),
							val-UpmixC(26),
							val-UpmixLFE(27),
							val-UpmixLs(28),
							val-UpmixRs(29),
							val-Linacc7(30),
							val-Linacc8(31),
							val-Tone-1(16),
							val-Tone-2(17),
							val-Tone-3(18),
							val-Tone-4(19),
							val-Tone-5(20),
							val-Tone-6(21),
							val-Tone-7(22),
							val-Tone-8(23),
							val-Legacy1(32),
							val-Legacy2(33)
							}
		MAX-ACCESS		read-write
		STATUS			current
		DESCRIPTION
				"TYPE: - RadiobuttonList
				 PAGE: - Anlg12 Matrix
					Anlg2_2 aud sel  cmdID= 40364 
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Silence  value= 34  
					Mixer1  value= 35  
					Mixer2  value= 36  
					Mixer3  value= 37  
					Mixer4  value= 38  
					Downmix1_1  value= 39  
					Downmix1_2  value= 40  
					Downmix2_1  value= 41  
					Downmix2_2  value= 42  
					UpmixL  value= 24  
					UpmixR  value= 25  
					UpmixC  value= 26  
					UpmixLFE  value= 27  
					UpmixLs  value= 28  
					UpmixRs  value= 29  
					Linacc7  value= 30  
					Linacc8  value= 31  
					Tone 1  value= 16  
					Tone 2  value= 17  
					Tone 3  value= 18  
					Tone 4  value= 19  
					Tone 5  value= 20  
					Tone 6  value= 21  
					Tone 7  value= 22  
					Tone 8  value= 23  
					Legacy1  value= 32  
					Legacy2  value= 33  "
		::= { iqudc12CmdEntry 40364 }


	iqudc12AudioOutRouteMatriDefaultsEmbOut OBJECT-TYPE
		SYNTAX		INTEGER {
							val-Custom(10),
							val-Embed-Passthrough(0),
							val-AES-Passthrough(1),
							val-DisEm1-4(2),
							val-DisEm1-4-AESin1-4(3),
							val-DisEm1-4-AESin5-8(4),
							val-AESin1-4(5),
							val-AESin5-8(6),
							val-Anlg-in-1-2(7),
							val-Tone-1-2(8),
							val-Silent(9)
							}
		MAX-ACCESS		read-write
		STATUS			current
		DESCRIPTION
				"TYPE: - RadiobuttonList
					Emb Out  cmdID= 40365 
					Custom  value= 10  
					Embed Passthrough  value= 0  
					AES Passthrough  value= 1  
					DisEm1-4  value= 2  
					DisEm1-4 & AESin1-4  value= 3  
					DisEm1-4 & AESin5-8  value= 4  
					AESin1-4  value= 5  
					AESin5-8  value= 6  
					Anlg in 1-2  value= 7  
					Tone 1-2  value= 8  
					Silent  value= 9  "
		::= { iqudc12CmdEntry 40365 }


	iqudc12AudioOutRouteMatriDefaultsAESOut OBJECT-TYPE
		SYNTAX		INTEGER {
							val-Custom(11),
							val-Embed-Passthrough(0),
							val-DisEm1-4-AESout1-4(1),
							val-DisEm1-4-AESout5-8(4),
							val-AESin5-8-AESout1-4(2),
							val-AESin1-4-AESout5-8(3),
							val-Anlg-in-1-2(5),
							val-Tone-1-2(6),
							val-Silent(7),
							val-DisEm1-2-AESout1-2(8),
							val-Tone-1-2-AESout5-8(9),
							val-Silent-AESout5-8(10)
							}
		MAX-ACCESS		read-write
		STATUS			current
		DESCRIPTION
				"TYPE: - RadiobuttonList
					AES Out  cmdID= 40366 
					Custom  value= 11  
					Embed Passthrough  value= 0  
					DisEm1-4->AESout1-4  value= 1  
					DisEm1-4->AESout5-8  value= 4  
					AESin5-8->AESout1-4  value= 2  
					AESin1-4->AESout5-8  value= 3  
					Anlg in 1-2  value= 5  
					Tone 1-2  value= 6  
					Silent  value= 7  
					DisEm1-2->AESout1-2  value= 8  
					Tone 1-2->AESout5-8  value= 9  
					Silent->AESout5-8  value= 10  "
		::= { iqudc12CmdEntry 40366 }


	iqudc12AudioOutRouteMatriDefaultsAnlgOut OBJECT-TYPE
		SYNTAX		INTEGER {
							val-Custom(5),
							val-DisEmb1-2(0),
							val-AES-in-1-2(1),
							val-Anlg-in-1-2(2),
							val-Tone-1-2(3),
							val-Silent(4)
							}
		MAX-ACCESS		read-write
		STATUS			current
		DESCRIPTION
				"TYPE: - RadiobuttonList
					Anlg Out  cmdID= 40367 
					Custom  value= 5  
					DisEmb1-2  value= 0  
					AES in 1-2  value= 1  
					Anlg in 1-2  value= 2  
					Tone 1-2  value= 3  
					Silent  value= 4  "
		::= { iqudc12CmdEntry 40367 }


	iqudc12UpMixerLoud14Source1ProcGain OBJECT-TYPE
		SYNTAX		INTEGER
		MAX-ACCESS		read-write
		STATUS			current
		DESCRIPTION
				"TYPE: - Number
				 PAGE: - UpMixerLoud1_4
					ProcGain  cmdID= 40834  min= -801  max= 120  step= 1  format= %0.1f dB  div_scale= 10 
					Min = -80.1 dB  Max = 12.0 dB  Step = 0.1 dB "
		::= { iqudc12CmdEntry 40834 }


	iqudc12UpMixerLoud14Source1Mute OBJECT-TYPE
		SYNTAX		INTEGER { disable(0), enable(1) }
		MAX-ACCESS		read-write
		STATUS			current
		DESCRIPTION
				"TYPE: - Checkbox
				 PAGE: - UpMixerLoud1_4
					Mute  cmdID= 40840 "
		::= { iqudc12CmdEntry 40840 }


	iqudc12UpMixerLoud14Source1Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Mixer1(35),
							val-Mixer2(36),
							val-Mixer3(37),
							val-Mixer4(38),
							val-Downmix1-1(39),
							val-Downmix1-2(40),
							val-Downmix2-1(41),
							val-Downmix2-2(42),
							val-LinAcc7(30),
							val-LinAcc8(31)
							}
		MAX-ACCESS		read-write
		STATUS			current
		DESCRIPTION
				"TYPE: - RadiobuttonList
				 PAGE: - UpMixerLoud1_4
					Src  cmdID= 40846 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Mixer1  value= 35  
					Mixer2  value= 36  
					Mixer3  value= 37  
					Mixer4  value= 38  
					Downmix1_1  value= 39  
					Downmix1_2  value= 40  
					Downmix2_1  value= 41  
					Downmix2_2  value= 42  
					LinAcc7  value= 30  
					LinAcc8  value= 31  "
		::= { iqudc12CmdEntry 40846 }


	iqudc12UpMixerLoud14Source2ProcGain OBJECT-TYPE
		SYNTAX		INTEGER
		MAX-ACCESS		read-write
		STATUS			current
		DESCRIPTION
				"TYPE: - Number
				 PAGE: - UpMixerLoud1_4
					ProcGain  cmdID= 40835  min= -801  max= 120  step= 1  format= %0.1f dB  div_scale= 10 
					Min = -80.1 dB  Max = 12.0 dB  Step = 0.1 dB "
		::= { iqudc12CmdEntry 40835 }


	iqudc12UpMixerLoud14Source2Mute OBJECT-TYPE
		SYNTAX		INTEGER { disable(0), enable(1) }
		MAX-ACCESS		read-write
		STATUS			current
		DESCRIPTION
				"TYPE: - Checkbox
				 PAGE: - UpMixerLoud1_4
					Mute  cmdID= 40841 "
		::= { iqudc12CmdEntry 40841 }


	iqudc12UpMixerLoud14Source2Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Mixer1(35),
							val-Mixer2(36),
							val-Mixer3(37),
							val-Mixer4(38),
							val-Downmix1-1(39),
							val-Downmix1-2(40),
							val-Downmix2-1(41),
							val-Downmix2-2(42),
							val-LinAcc7(30),
							val-LinAcc8(31)
							}
		MAX-ACCESS		read-write
		STATUS			current
		DESCRIPTION
				"TYPE: - RadiobuttonList
				 PAGE: - UpMixerLoud1_4
					Src  cmdID= 40847 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Mixer1  value= 35  
					Mixer2  value= 36  
					Mixer3  value= 37  
					Mixer4  value= 38  
					Downmix1_1  value= 39  
					Downmix1_2  value= 40  
					Downmix2_1  value= 41  
					Downmix2_2  value= 42  
					LinAcc7  value= 30  
					LinAcc8  value= 31  "
		::= { iqudc12CmdEntry 40847 }


	iqudc12UpMixerLoud14Source3ProcGain OBJECT-TYPE
		SYNTAX		INTEGER
		MAX-ACCESS		read-write
		STATUS			current
		DESCRIPTION
				"TYPE: - Number
				 PAGE: - UpMixerLoud1_4
					ProcGain  cmdID= 40836  min= -801  max= 120  step= 1  format= %0.1f dB  div_scale= 10 
					Min = -80.1 dB  Max = 12.0 dB  Step = 0.1 dB "
		::= { iqudc12CmdEntry 40836 }


	iqudc12UpMixerLoud14Source3Mute OBJECT-TYPE
		SYNTAX		INTEGER { disable(0), enable(1) }
		MAX-ACCESS		read-write
		STATUS			current
		DESCRIPTION
				"TYPE: - Checkbox
				 PAGE: - UpMixerLoud1_4
					Mute  cmdID= 40842 "
		::= { iqudc12CmdEntry 40842 }


	iqudc12UpMixerLoud14Source3Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Mixer1(35),
							val-Mixer2(36),
							val-Mixer3(37),
							val-Mixer4(38),
							val-Downmix1-1(39),
							val-Downmix1-2(40),
							val-Downmix2-1(41),
							val-Downmix2-2(42),
							val-LinAcc7(30),
							val-LinAcc8(31)
							}
		MAX-ACCESS		read-write
		STATUS			current
		DESCRIPTION
				"TYPE: - RadiobuttonList
				 PAGE: - UpMixerLoud1_4
					Src  cmdID= 40848 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Mixer1  value= 35  
					Mixer2  value= 36  
					Mixer3  value= 37  
					Mixer4  value= 38  
					Downmix1_1  value= 39  
					Downmix1_2  value= 40  
					Downmix2_1  value= 41  
					Downmix2_2  value= 42  
					LinAcc7  value= 30  
					LinAcc8  value= 31  "
		::= { iqudc12CmdEntry 40848 }


	iqudc12UpMixerLoud14Source4ProcGain OBJECT-TYPE
		SYNTAX		INTEGER
		MAX-ACCESS		read-write
		STATUS			current
		DESCRIPTION
				"TYPE: - Number
				 PAGE: - UpMixerLoud1_4
					ProcGain  cmdID= 40837  min= -801  max= 120  step= 1  format= %0.1f dB  div_scale= 10 
					Min = -80.1 dB  Max = 12.0 dB  Step = 0.1 dB "
		::= { iqudc12CmdEntry 40837 }


	iqudc12UpMixerLoud14Source4Mute OBJECT-TYPE
		SYNTAX		INTEGER { disable(0), enable(1) }
		MAX-ACCESS		read-write
		STATUS			current
		DESCRIPTION
				"TYPE: - Checkbox
				 PAGE: - UpMixerLoud1_4
					Mute  cmdID= 40843 "
		::= { iqudc12CmdEntry 40843 }


	iqudc12UpMixerLoud14Source4Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Mixer1(35),
							val-Mixer2(36),
							val-Mixer3(37),
							val-Mixer4(38),
							val-Downmix1-1(39),
							val-Downmix1-2(40),
							val-Downmix2-1(41),
							val-Downmix2-2(42),
							val-LinAcc7(30),
							val-LinAcc8(31)
							}
		MAX-ACCESS		read-write
		STATUS			current
		DESCRIPTION
				"TYPE: - RadiobuttonList
				 PAGE: - UpMixerLoud1_4
					Src  cmdID= 40849 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Mixer1  value= 35  
					Mixer2  value= 36  
					Mixer3  value= 37  
					Mixer4  value= 38  
					Downmix1_1  value= 39  
					Downmix1_2  value= 40  
					Downmix2_1  value= 41  
					Downmix2_2  value= 42  
					LinAcc7  value= 30  
					LinAcc8  value= 31  "
		::= { iqudc12CmdEntry 40849 }


	iqudc12MenuUpMixerLoud14Mode OBJECT-TYPE
		SYNTAX		INTEGER {
							val-Auto(0),
							val-Always-Upmix(1),
							val-Bypass(2)
							}
		MAX-ACCESS		read-write
		STATUS			current
		DESCRIPTION
				"TYPE: - RadiobuttonList
				 PAGE: - UpMixerLoud1_4
					Mode  cmdID= 40854 
					Auto  value= 0  
					Always Upmix  value= 1  
					Bypass  value= 2  "
		::= { iqudc12CmdEntry 40854 }


	iqudc12MenuUpMixerLoud14Status OBJECT-TYPE
		SYNTAX		RollCallString
		MAX-ACCESS		read-only
		STATUS			current
		DESCRIPTION
				"TYPE: - Display
				 PAGE: - UpMixerLoud1_4
					Status  cmdID= 40855  format=   "
		::= { iqudc12CmdEntry 40855 }


	iqudc12MenuUpMixerLoud14XfadeBypass OBJECT-TYPE
		SYNTAX		INTEGER {
							val-Very-Slow(0),
							val-Slow(1),
							val-Medium(2),
							val-Fast(3),
							val-Very-Fast(4),
							val-Instant(5)
							}
		MAX-ACCESS		read-write
		STATUS			current
		DESCRIPTION
				"TYPE: - RadiobuttonList
				 PAGE: - UpMixerLoud1_4
					XfadeBypass  cmdID= 40856 
					Very Slow  value= 0  
					Slow  value= 1  
					Medium  value= 2  
					Fast  value= 3  
					Very Fast  value= 4  
					Instant  value= 5  "
		::= { iqudc12CmdEntry 40856 }


	iqudc12MenuUpMixerLoud14XfadeUpmix OBJECT-TYPE
		SYNTAX		INTEGER {
							val-Very-Slow(0),
							val-Slow(1),
							val-Medium(2),
							val-Fast(3),
							val-Very-Fast(4),
							val-Instant(5)
							}
		MAX-ACCESS		read-write
		STATUS			current
		DESCRIPTION
				"TYPE: - RadiobuttonList
				 PAGE: - UpMixerLoud1_4
					XfadeUpmix  cmdID= 40857 
					Very Slow  value= 0  
					Slow  value= 1  
					Medium  value= 2  
					Fast  value= 3  
					Very Fast  value= 4  
					Instant  value= 5  "
		::= { iqudc12CmdEntry 40857 }


	iqudc12MenuUpMixerLoud14Detect OBJECT-TYPE
		SYNTAX		INTEGER
		MAX-ACCESS		read-write
		STATUS			current
		DESCRIPTION
				"TYPE: - Number
				 PAGE: - UpMixerLoud1_4
					Detect  cmdID= 40858  min= -1500  max= 0  step= 1  format= %0.1f dB  div_scale= 10 
					Min = -150.0 dB  Max = 0.0 dB  Step = 0.1 dB "
		::= { iqudc12CmdEntry 40858 }


	iqudc12MenuUpMixerLoud14CenterWidth OBJECT-TYPE
		SYNTAX		INTEGER
		MAX-ACCESS		read-write
		STATUS			current
		DESCRIPTION
				"TYPE: - Number
				 PAGE: - UpMixerLoud1_4
					CenterWidth  cmdID= 40859  min= 0  max= 1000  step= 1  format= %0.1f %%  div_scale= 10 
					Min = 0.0 %  Max = 100.0 %  Step = 0.1 % "
		::= { iqudc12CmdEntry 40859 }


	iqudc12MenuUpMixerLoud14Surround OBJECT-TYPE
		SYNTAX		INTEGER
		MAX-ACCESS		read-write
		STATUS			current
		DESCRIPTION
				"TYPE: - Number
				 PAGE: - UpMixerLoud1_4
					Surround  cmdID= 40860  min= 0  max= 1000  step= 1  format= %0.1f %%  div_scale= 10 
					Min = 0.0 %  Max = 100.0 %  Step = 0.1 % "
		::= { iqudc12CmdEntry 40860 }


	iqudc12MenuUpMixerLoud14AlgorithmType OBJECT-TYPE
		SYNTAX		INTEGER {
							val-Upmix(0),
							val-Loudness5-1(1),
							val-Loudness1-2(2),
							val-Loudness1(3),
							val-Loudness2(4),
							val-UpmixLoudA(5)
							}
		MAX-ACCESS		read-write
		STATUS			current
		DESCRIPTION
				"TYPE: - RadiobuttonList
				 PAGE: - UpMixerLoud1_4
					Algorithm Type  cmdID= 36148 
					Upmix  value= 0  
					Loudness5.1  value= 1  
					Loudness1+2  value= 2  
					Loudness1  value= 3  
					Loudness2  value= 4  
					UpmixLoudA  value= 5  "
		::= { iqudc12CmdEntry 36148 }


	iqudc12UpMixerLoud58LoudnessPreset1 OBJECT-TYPE
		SYNTAX		INTEGER {
							val-General(0),
							val-Light(1),
							val-Heavy(2),
							val-Loud(3),
							val-Loud-Limit(4),
							val-Protection-Limit(5),
							val-Custom-1(6),
							val-Custom-2(7)
							}
		MAX-ACCESS		read-write
		STATUS			current
		DESCRIPTION
				"TYPE: - RadiobuttonList
				 PAGE: - UpMixerLoud5_8
					Preset1  cmdID= 36151 
					General  value= 0  
					Light  value= 1  
					Heavy  value= 2  
					Loud  value= 3  
					Loud Limit  value= 4  
					Protection Limit  value= 5  
					Custom 1  value= 6  
					Custom 2  value= 7  "
		::= { iqudc12CmdEntry 36151 }


	iqudc12UpMixerLoud58LoudnessMasterLevel1 OBJECT-TYPE
		SYNTAX		INTEGER
		MAX-ACCESS		read-write
		STATUS			current
		DESCRIPTION
				"TYPE: - Number
				 PAGE: - UpMixerLoud5_8
					MasterLevel1  cmdID= 36149  min= -310  max= 0  step= 1  format= %0.1f dB  div_scale= 10 
					Min = -31.0 dB  Max = 0.0 dB  Step = 0.1 dB "
		::= { iqudc12CmdEntry 36149 }


	iqudc12UpMixerLoud58LoudnessName1 OBJECT-TYPE
		SYNTAX		RollCallString
		MAX-ACCESS		read-only
		STATUS			current
		DESCRIPTION
				"TYPE: - Display
				 PAGE: - UpMixerLoud5_8
					Name1  cmdID= 36153  format=   "
		::= { iqudc12CmdEntry 36153 }


	iqudc12UpMixerLoud58LoudnessBypass1 OBJECT-TYPE
		SYNTAX		INTEGER { disable(0), enable(1) }
		MAX-ACCESS		read-write
		STATUS			current
		DESCRIPTION
				"TYPE: - Checkbox
				 PAGE: - UpMixerLoud5_8
					Bypass 1  cmdID= 36173 "
		::= { iqudc12CmdEntry 36173 }


	iqudc12UpMixerLoud58LoudnessPreset2 OBJECT-TYPE
		SYNTAX		INTEGER {
							val-General(0),
							val-Light(1),
							val-Heavy(2),
							val-Loud(3),
							val-Loud-Limit(4),
							val-Protection-Limit(5),
							val-Custom-1(6),
							val-Custom-2(7)
							}
		MAX-ACCESS		read-write
		STATUS			current
		DESCRIPTION
				"TYPE: - RadiobuttonList
				 PAGE: - UpMixerLoud5_8
					Preset2  cmdID= 36152 
					General  value= 0  
					Light  value= 1  
					Heavy  value= 2  
					Loud  value= 3  
					Loud Limit  value= 4  
					Protection Limit  value= 5  
					Custom 1  value= 6  
					Custom 2  value= 7  "
		::= { iqudc12CmdEntry 36152 }


	iqudc12UpMixerLoud58LoudnessMasterLevel2 OBJECT-TYPE
		SYNTAX		INTEGER
		MAX-ACCESS		read-write
		STATUS			current
		DESCRIPTION
				"TYPE: - Number
				 PAGE: - UpMixerLoud5_8
					MasterLevel2  cmdID= 36150  min= -310  max= 0  step= 1  format= %0.1f dB  div_scale= 10 
					Min = -31.0 dB  Max = 0.0 dB  Step = 0.1 dB "
		::= { iqudc12CmdEntry 36150 }


	iqudc12UpMixerLoud58LoudnessName2 OBJECT-TYPE
		SYNTAX		RollCallString
		MAX-ACCESS		read-only
		STATUS			current
		DESCRIPTION
				"TYPE: - Display
				 PAGE: - UpMixerLoud5_8
					Name2  cmdID= 36154  format=   "
		::= { iqudc12CmdEntry 36154 }


	iqudc12UpMixerLoud58LoudnessBypass2 OBJECT-TYPE
		SYNTAX		INTEGER { disable(0), enable(1) }
		MAX-ACCESS		read-write
		STATUS			current
		DESCRIPTION
				"TYPE: - Checkbox
				 PAGE: - UpMixerLoud5_8
					Bypass 2  cmdID= 36174 "
		::= { iqudc12CmdEntry 36174 }


	iqudc12UpMixerLoud58Source5ProcGain OBJECT-TYPE
		SYNTAX		INTEGER
		MAX-ACCESS		read-write
		STATUS			current
		DESCRIPTION
				"TYPE: - Number
				 PAGE: - UpMixerLoud5_8
					ProcGain  cmdID= 40838  min= -801  max= 120  step= 1  format= %0.1f dB  div_scale= 10 
					Min = -80.1 dB  Max = 12.0 dB  Step = 0.1 dB "
		::= { iqudc12CmdEntry 40838 }


	iqudc12UpMixerLoud58Source5Mute OBJECT-TYPE
		SYNTAX		INTEGER { disable(0), enable(1) }
		MAX-ACCESS		read-write
		STATUS			current
		DESCRIPTION
				"TYPE: - Checkbox
				 PAGE: - UpMixerLoud5_8
					Mute  cmdID= 40844 "
		::= { iqudc12CmdEntry 40844 }


	iqudc12UpMixerLoud58Source5Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Mixer1(35),
							val-Mixer2(36),
							val-Mixer3(37),
							val-Mixer4(38),
							val-Downmix1-1(39),
							val-Downmix1-2(40),
							val-Downmix2-1(41),
							val-Downmix2-2(42),
							val-LinAcc7(30),
							val-LinAcc8(31)
							}
		MAX-ACCESS		read-write
		STATUS			current
		DESCRIPTION
				"TYPE: - RadiobuttonList
				 PAGE: - UpMixerLoud5_8
					Src  cmdID= 40850 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Mixer1  value= 35  
					Mixer2  value= 36  
					Mixer3  value= 37  
					Mixer4  value= 38  
					Downmix1_1  value= 39  
					Downmix1_2  value= 40  
					Downmix2_1  value= 41  
					Downmix2_2  value= 42  
					LinAcc7  value= 30  
					LinAcc8  value= 31  "
		::= { iqudc12CmdEntry 40850 }


	iqudc12UpMixerLoud58Source6ProcGain OBJECT-TYPE
		SYNTAX		INTEGER
		MAX-ACCESS		read-write
		STATUS			current
		DESCRIPTION
				"TYPE: - Number
				 PAGE: - UpMixerLoud5_8
					ProcGain  cmdID= 40839  min= -801  max= 120  step= 1  format= %0.1f dB  div_scale= 10 
					Min = -80.1 dB  Max = 12.0 dB  Step = 0.1 dB "
		::= { iqudc12CmdEntry 40839 }


	iqudc12UpMixerLoud58Source6Mute OBJECT-TYPE
		SYNTAX		INTEGER { disable(0), enable(1) }
		MAX-ACCESS		read-write
		STATUS			current
		DESCRIPTION
				"TYPE: - Checkbox
				 PAGE: - UpMixerLoud5_8
					Mute  cmdID= 40845 "
		::= { iqudc12CmdEntry 40845 }


	iqudc12UpMixerLoud58Source6Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Mixer1(35),
							val-Mixer2(36),
							val-Mixer3(37),
							val-Mixer4(38),
							val-Downmix1-1(39),
							val-Downmix1-2(40),
							val-Downmix2-1(41),
							val-Downmix2-2(42),
							val-LinAcc7(30),
							val-LinAcc8(31)
							}
		MAX-ACCESS		read-write
		STATUS			current
		DESCRIPTION
				"TYPE: - RadiobuttonList
				 PAGE: - UpMixerLoud5_8
					Src  cmdID= 40851 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Mixer1  value= 35  
					Mixer2  value= 36  
					Mixer3  value= 37  
					Mixer4  value= 38  
					Downmix1_1  value= 39  
					Downmix1_2  value= 40  
					Downmix2_1  value= 41  
					Downmix2_2  value= 42  
					LinAcc7  value= 30  
					LinAcc8  value= 31  "
		::= { iqudc12CmdEntry 40851 }


	iqudc12UpMixerLoud58Source7ProcGain OBJECT-TYPE
		SYNTAX		INTEGER
		MAX-ACCESS		read-write
		STATUS			current
		DESCRIPTION
				"TYPE: - Number
				 PAGE: - UpMixerLoud5_8
					ProcGain  cmdID= 40873  min= -801  max= 120  step= 1  format= %0.1f dB  div_scale= 10 
					Min = -80.1 dB  Max = 12.0 dB  Step = 0.1 dB "
		::= { iqudc12CmdEntry 40873 }


	iqudc12UpMixerLoud58Source7Mute OBJECT-TYPE
		SYNTAX		INTEGER { disable(0), enable(1) }
		MAX-ACCESS		read-write
		STATUS			current
		DESCRIPTION
				"TYPE: - Checkbox
				 PAGE: - UpMixerLoud5_8
					Mute  cmdID= 40875 "
		::= { iqudc12CmdEntry 40875 }


	iqudc12UpMixerLoud58Source7Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Mixer1(35),
							val-Mixer2(36),
							val-Mixer3(37),
							val-Mixer4(38),
							val-Downmix1-1(39),
							val-Downmix1-2(40),
							val-Downmix2-1(41),
							val-Downmix2-2(42)
							}
		MAX-ACCESS		read-write
		STATUS			current
		DESCRIPTION
				"TYPE: - RadiobuttonList
				 PAGE: - UpMixerLoud5_8
					Src  cmdID= 40877 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Mixer1  value= 35  
					Mixer2  value= 36  
					Mixer3  value= 37  
					Mixer4  value= 38  
					Downmix1_1  value= 39  
					Downmix1_2  value= 40  
					Downmix2_1  value= 41  
					Downmix2_2  value= 42  "
		::= { iqudc12CmdEntry 40877 }


	iqudc12UpMixerLoud58Source8ProcGain OBJECT-TYPE
		SYNTAX		INTEGER
		MAX-ACCESS		read-write
		STATUS			current
		DESCRIPTION
				"TYPE: - Number
				 PAGE: - UpMixerLoud5_8
					ProcGain  cmdID= 40874  min= -801  max= 120  step= 1  format= %0.1f dB  div_scale= 10 
					Min = -80.1 dB  Max = 12.0 dB  Step = 0.1 dB "
		::= { iqudc12CmdEntry 40874 }


	iqudc12UpMixerLoud58Source8Mute OBJECT-TYPE
		SYNTAX		INTEGER { disable(0), enable(1) }
		MAX-ACCESS		read-write
		STATUS			current
		DESCRIPTION
				"TYPE: - Checkbox
				 PAGE: - UpMixerLoud5_8
					Mute  cmdID= 40876 "
		::= { iqudc12CmdEntry 40876 }


	iqudc12UpMixerLoud58Source8Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-Mixer1(35),
							val-Mixer2(36),
							val-Mixer3(37),
							val-Mixer4(38),
							val-Downmix1-1(39),
							val-Downmix1-2(40),
							val-Downmix2-1(41),
							val-Downmix2-2(42)
							}
		MAX-ACCESS		read-write
		STATUS			current
		DESCRIPTION
				"TYPE: - RadiobuttonList
				 PAGE: - UpMixerLoud5_8
					Src  cmdID= 40878 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					Mixer1  value= 35  
					Mixer2  value= 36  
					Mixer3  value= 37  
					Mixer4  value= 38  
					Downmix1_1  value= 39  
					Downmix1_2  value= 40  
					Downmix2_1  value= 41  
					Downmix2_2  value= 42  "
		::= { iqudc12CmdEntry 40878 }


	iqudc12MenuUpMixerLoud58UpmixHide OBJECT-TYPE
		SYNTAX		RollCallString
		MAX-ACCESS		read-only
		STATUS			current
		DESCRIPTION
				"TYPE: - Display
				 PAGE: - UpMixerLoud5_8
					UpmixHide  cmdID= 36155  format=   "
		::= { iqudc12CmdEntry 36155 }


	iqudc12MenuUpMixerLoud58Chan1Name OBJECT-TYPE
		SYNTAX		RollCallString
		MAX-ACCESS		read-only
		STATUS			current
		DESCRIPTION
				"TYPE: - Display
				 PAGE: - UpMixerLoud5_8
					Chan1Name  cmdID= 36158  format=   "
		::= { iqudc12CmdEntry 36158 }


	iqudc12MenuUpMixerLoud58Chan2Name OBJECT-TYPE
		SYNTAX		RollCallString
		MAX-ACCESS		read-only
		STATUS			current
		DESCRIPTION
				"TYPE: - Display
				 PAGE: - UpMixerLoud5_8
					Chan2Name  cmdID= 36159  format=   "
		::= { iqudc12CmdEntry 36159 }


	iqudc12MenuUpMixerLoud58Chan3Name OBJECT-TYPE
		SYNTAX		RollCallString
		MAX-ACCESS		read-only
		STATUS			current
		DESCRIPTION
				"TYPE: - Display
				 PAGE: - UpMixerLoud5_8
					Chan3Name  cmdID= 36160  format=   "
		::= { iqudc12CmdEntry 36160 }


	iqudc12MenuUpMixerLoud58Chan4Name OBJECT-TYPE
		SYNTAX		RollCallString
		MAX-ACCESS		read-only
		STATUS			current
		DESCRIPTION
				"TYPE: - Display
				 PAGE: - UpMixerLoud5_8
					Chan4Name  cmdID= 36161  format=   "
		::= { iqudc12CmdEntry 36161 }


	iqudc12MenuUpMixerLoud58Chan5Name OBJECT-TYPE
		SYNTAX		RollCallString
		MAX-ACCESS		read-only
		STATUS			current
		DESCRIPTION
				"TYPE: - Display
				 PAGE: - UpMixerLoud5_8
					Chan5Name  cmdID= 36162  format=   "
		::= { iqudc12CmdEntry 36162 }


	iqudc12MenuUpMixerLoud58Chan6Name OBJECT-TYPE
		SYNTAX		RollCallString
		MAX-ACCESS		read-only
		STATUS			current
		DESCRIPTION
				"TYPE: - Display
				 PAGE: - UpMixerLoud5_8
					Chan6Name  cmdID= 36163  format=   "
		::= { iqudc12CmdEntry 36163 }


	iqudc12MenuUpMixerLoud58Chan7Name OBJECT-TYPE
		SYNTAX		RollCallString
		MAX-ACCESS		read-only
		STATUS			current
		DESCRIPTION
				"TYPE: - Display
				 PAGE: - UpMixerLoud5_8
					Chan7Name  cmdID= 36183  format=   "
		::= { iqudc12CmdEntry 36183 }


	iqudc12MenuUpMixerLoud58Chan8Name OBJECT-TYPE
		SYNTAX		RollCallString
		MAX-ACCESS		read-only
		STATUS			current
		DESCRIPTION
				"TYPE: - Display
				 PAGE: - UpMixerLoud5_8
					Chan8Name  cmdID= 36184  format=   "
		::= { iqudc12CmdEntry 36184 }


	iqudc12MenuUpMixerLoud58Chan1NameIn OBJECT-TYPE
		SYNTAX		RollCallString
		MAX-ACCESS		read-only
		STATUS			current
		DESCRIPTION
				"TYPE: - Display
				 PAGE: - UpMixerLoud5_8
					Chan1NameIn  cmdID= 36175  format=   "
		::= { iqudc12CmdEntry 36175 }


	iqudc12MenuUpMixerLoud58Chan2NameIn OBJECT-TYPE
		SYNTAX		RollCallString
		MAX-ACCESS		read-only
		STATUS			current
		DESCRIPTION
				"TYPE: - Display
				 PAGE: - UpMixerLoud5_8
					Chan2NameIn  cmdID= 36176  format=   "
		::= { iqudc12CmdEntry 36176 }


	iqudc12MenuUpMixerLoud58Chan3NameIn OBJECT-TYPE
		SYNTAX		RollCallString
		MAX-ACCESS		read-only
		STATUS			current
		DESCRIPTION
				"TYPE: - Display
				 PAGE: - UpMixerLoud5_8
					Chan3NameIn  cmdID= 36177  format=   "
		::= { iqudc12CmdEntry 36177 }


	iqudc12MenuUpMixerLoud58Chan4NameIn OBJECT-TYPE
		SYNTAX		RollCallString
		MAX-ACCESS		read-only
		STATUS			current
		DESCRIPTION
				"TYPE: - Display
				 PAGE: - UpMixerLoud5_8
					Chan4NameIn  cmdID= 36178  format=   "
		::= { iqudc12CmdEntry 36178 }


	iqudc12MenuUpMixerLoud58Chan5NameIn OBJECT-TYPE
		SYNTAX		RollCallString
		MAX-ACCESS		read-only
		STATUS			current
		DESCRIPTION
				"TYPE: - Display
				 PAGE: - UpMixerLoud5_8
					Chan5NameIn  cmdID= 36179  format=   "
		::= { iqudc12CmdEntry 36179 }


	iqudc12MenuUpMixerLoud58Chan6NameIn OBJECT-TYPE
		SYNTAX		RollCallString
		MAX-ACCESS		read-only
		STATUS			current
		DESCRIPTION
				"TYPE: - Display
				 PAGE: - UpMixerLoud5_8
					Chan6NameIn  cmdID= 36180  format=   "
		::= { iqudc12CmdEntry 36180 }


	iqudc12MenuUpMixerLoud58Chan7NameIn OBJECT-TYPE
		SYNTAX		RollCallString
		MAX-ACCESS		read-only
		STATUS			current
		DESCRIPTION
				"TYPE: - Display
				 PAGE: - UpMixerLoud5_8
					Chan7NameIn  cmdID= 36181  format=   "
		::= { iqudc12CmdEntry 36181 }


	iqudc12MenuUpMixerLoud58Chan8NameIn OBJECT-TYPE
		SYNTAX		RollCallString
		MAX-ACCESS		read-only
		STATUS			current
		DESCRIPTION
				"TYPE: - Display
				 PAGE: - UpMixerLoud5_8
					Chan8NameIn  cmdID= 36182  format=   "
		::= { iqudc12CmdEntry 36182 }


	iqudc12MenuUpMixerLoud58DialogHide OBJECT-TYPE
		SYNTAX		RollCallString
		MAX-ACCESS		read-only
		STATUS			current
		DESCRIPTION
				"TYPE: - Display
				 PAGE: - UpMixerLoud5_8
					DialogHide  cmdID= 36164  format=   "
		::= { iqudc12CmdEntry 36164 }


	iqudc12LoudCustomBlock1Name OBJECT-TYPE
		SYNTAX		RollCallString
		MAX-ACCESS		read-write
		STATUS			current
		DESCRIPTION
				"TYPE: - Editstring
				 PAGE: - LoudCustom
					Name  cmdID= 36304  "
		::= { iqudc12CmdEntry 36304 }


	iqudc12LoudCustomBlock1inagcfreeze OBJECT-TYPE
		SYNTAX		INTEGER
		MAX-ACCESS		read-write
		STATUS			current
		DESCRIPTION
				"TYPE: - Number
				 PAGE: - LoudCustom
					inagc freeze  cmdID= 36200  min= -180  max= 0  step= 1  format= %0.1f dBFS  div_scale= 2 
					Min = -90.0 dBFS  Max = 0.0 dBFS  Step = 0.5 dBFS "
		::= { iqudc12CmdEntry 36200 }


	iqudc12LoudCustomBlock1inagcgate OBJECT-TYPE
		SYNTAX		INTEGER
		MAX-ACCESS		read-write
		STATUS			current
		DESCRIPTION
				"TYPE: - Number
				 PAGE: - LoudCustom
					inagc gate  cmdID= 36202  min= -180  max= 0  step= 1  format= %0.1f dBFS  div_scale= 2 
					Min = -90.0 dBFS  Max = 0.0 dBFS  Step = 0.5 dBFS "
		::= { iqudc12CmdEntry 36202 }


	iqudc12LoudCustomBlock1inagcratio OBJECT-TYPE
		SYNTAX		INTEGER
		MAX-ACCESS		read-write
		STATUS			current
		DESCRIPTION
				"TYPE: - Number
				 PAGE: - LoudCustom
					inagc ratio  cmdID= 36208  min= 0  max= 100  step= 1  format= %0.0f  div_scale= 1 
					Min = 0  Max = 100  Step = 1 "
		::= { iqudc12CmdEntry 36208 }


	iqudc12LoudCustomBlock1inagcrange OBJECT-TYPE
		SYNTAX		INTEGER
		MAX-ACCESS		read-write
		STATUS			current
		DESCRIPTION
				"TYPE: - Number
				 PAGE: - LoudCustom
					inagc range  cmdID= 36206  min= 0  max= 180  step= 1  format= %0.1f dB  div_scale= 5 
					Min = 0.0 dB  Max = 36.0 dB  Step = 0.2 dB "
		::= { iqudc12CmdEntry 36206 }


	iqudc12LoudCustomBlock1inagcthresh OBJECT-TYPE
		SYNTAX		INTEGER
		MAX-ACCESS		read-write
		STATUS			current
		DESCRIPTION
				"TYPE: - Number
				 PAGE: - LoudCustom
					inagc thresh  cmdID= 36204  min= -180  max= 0  step= 1  format= %0.1f dBFS  div_scale= 10 
					Min = -18.0 dBFS  Max = 0.0 dBFS  Step = 0.1 dBFS "
		::= { iqudc12CmdEntry 36204 }


	iqudc12LoudCustomBlock1inagcattack OBJECT-TYPE
		SYNTAX		INTEGER
		MAX-ACCESS		read-write
		STATUS			current
		DESCRIPTION
				"TYPE: - Number
				 PAGE: - LoudCustom
					inagc attack  cmdID= 36210  min= 1  max= 100  step= 1  format= %0.0f  div_scale= 1 
					Min = 1  Max = 100  Step = 1 "
		::= { iqudc12CmdEntry 36210 }


	iqudc12LoudCustomBlock1inagcrelease OBJECT-TYPE
		SYNTAX		INTEGER
		MAX-ACCESS		read-write
		STATUS			current
		DESCRIPTION
				"TYPE: - Number
				 PAGE: - LoudCustom
					inagc release  cmdID= 36212  min= 1  max= 100  step= 1  format= %0.0f  div_scale= 1 
					Min = 1  Max = 100  Step = 1 "
		::= { iqudc12CmdEntry 36212 }


	iqudc12LoudCustomBlock1peqfreq1 OBJECT-TYPE
		SYNTAX		INTEGER
		MAX-ACCESS		read-write
		STATUS			current
		DESCRIPTION
				"TYPE: - Number
				 PAGE: - LoudCustom
					peq freq 1  cmdID= 36276  min= 20  max= 20000  step= 1  format= %0.0f Hz  div_scale= 1 
					Min = 20 Hz  Max = 20000 Hz  Step = 1 Hz "
		::= { iqudc12CmdEntry 36276 }


	iqudc12LoudCustomBlock1peqq1 OBJECT-TYPE
		SYNTAX		INTEGER
		MAX-ACCESS		read-write
		STATUS			current
		DESCRIPTION
				"TYPE: - Number
				 PAGE: - LoudCustom
					peq q 1  cmdID= 36282  min= 1  max= 200  step= 1  format= %0.2f  div_scale= 20 
					Min = 0.05  Max = 10.00  Step = 0.05 "
		::= { iqudc12CmdEntry 36282 }


	iqudc12LoudCustomBlock1peqlevel1 OBJECT-TYPE
		SYNTAX		INTEGER
		MAX-ACCESS		read-write
		STATUS			current
		DESCRIPTION
				"TYPE: - Number
				 PAGE: - LoudCustom
					peq level 1  cmdID= 36288  min= -90  max= 90  step= 1  format= %0.1f dB  div_scale= 5 
					Min = -18.0 dB  Max = 18.0 dB  Step = 0.2 dB "
		::= { iqudc12CmdEntry 36288 }


	iqudc12LoudCustomBlock1peqfreq2 OBJECT-TYPE
		SYNTAX		INTEGER
		MAX-ACCESS		read-write
		STATUS			current
		DESCRIPTION
				"TYPE: - Number
				 PAGE: - LoudCustom
					peq freq 2  cmdID= 36277  min= 20  max= 20000  step= 1  format= %0.0f Hz  div_scale= 1 
					Min = 20 Hz  Max = 20000 Hz  Step = 1 Hz "
		::= { iqudc12CmdEntry 36277 }


	iqudc12LoudCustomBlock1peqq2 OBJECT-TYPE
		SYNTAX		INTEGER
		MAX-ACCESS		read-write
		STATUS			current
		DESCRIPTION
				"TYPE: - Number
				 PAGE: - LoudCustom
					peq q 2  cmdID= 36283  min= 1  max= 200  step= 1  format= %0.2f  div_scale= 20 
					Min = 0.05  Max = 10.00  Step = 0.05 "
		::= { iqudc12CmdEntry 36283 }


	iqudc12LoudCustomBlock1peqlevel2 OBJECT-TYPE
		SYNTAX		INTEGER
		MAX-ACCESS		read-write
		STATUS			current
		DESCRIPTION
				"TYPE: - Number
				 PAGE: - LoudCustom
					peq level 2  cmdID= 36289  min= -90  max= 90  step= 1  format= %0.1f dB  div_scale= 5 
					Min = -18.0 dB  Max = 18.0 dB  Step = 0.2 dB "
		::= { iqudc12CmdEntry 36289 }


	iqudc12LoudCustomBlock1peqfreq3 OBJECT-TYPE
		SYNTAX		INTEGER
		MAX-ACCESS		read-write
		STATUS			current
		DESCRIPTION
				"TYPE: - Number
				 PAGE: - LoudCustom
					peq freq 3  cmdID= 36278  min= 20  max= 20000  step= 1  format= %0.0f Hz  div_scale= 1 
					Min = 20 Hz  Max = 20000 Hz  Step = 1 Hz "
		::= { iqudc12CmdEntry 36278 }


	iqudc12LoudCustomBlock1peqq3 OBJECT-TYPE
		SYNTAX		INTEGER
		MAX-ACCESS		read-write
		STATUS			current
		DESCRIPTION
				"TYPE: - Number
				 PAGE: - LoudCustom
					peq q 3  cmdID= 36284  min= 1  max= 200  step= 1  format= %0.2f  div_scale= 20 
					Min = 0.05  Max = 10.00  Step = 0.05 "
		::= { iqudc12CmdEntry 36284 }


	iqudc12LoudCustomBlock1peqlevel3 OBJECT-TYPE
		SYNTAX		INTEGER
		MAX-ACCESS		read-write
		STATUS			current
		DESCRIPTION
				"TYPE: - Number
				 PAGE: - LoudCustom
					peq level 3  cmdID= 36290  min= -90  max= 90  step= 1  format= %0.1f dB  div_scale= 5 
					Min = -18.0 dB  Max = 18.0 dB  Step = 0.2 dB "
		::= { iqudc12CmdEntry 36290 }


	iqudc12LoudCustomBlock1mbagcatk1 OBJECT-TYPE
		SYNTAX		INTEGER
		MAX-ACCESS		read-write
		STATUS			current
		DESCRIPTION
				"TYPE: - Number
				 PAGE: - LoudCustom
					mbagc atk 1  cmdID= 36236  min= 0  max= 100  step= 1  format= %0.0f  div_scale= 1 
					Min = 0  Max = 100  Step = 1 "
		::= { iqudc12CmdEntry 36236 }


	iqudc12LoudCustomBlock1mbagcrel1 OBJECT-TYPE
		SYNTAX		INTEGER
		MAX-ACCESS		read-write
		STATUS			current
		DESCRIPTION
				"TYPE: - Number
				 PAGE: - LoudCustom
					mbagc rel 1  cmdID= 36226  min= 0  max= 100  step= 1  format= %0.0f  div_scale= 1 
					Min = 0  Max = 100  Step = 1 "
		::= { iqudc12CmdEntry 36226 }


	iqudc12LoudCustomBlock1mbagcthresh1 OBJECT-TYPE
		SYNTAX		INTEGER
		MAX-ACCESS		read-write
		STATUS			current
		DESCRIPTION
				"TYPE: - Number
				 PAGE: - LoudCustom
					mbagc thresh 1  cmdID= 36246  min= -120  max= 120  step= 1  format= %0.1f dB  div_scale= 10 
					Min = -12.0 dB  Max = 12.0 dB  Step = 0.1 dB "
		::= { iqudc12CmdEntry 36246 }


	iqudc12LoudCustomBlock1mbagcoutlev1 OBJECT-TYPE
		SYNTAX		INTEGER
		MAX-ACCESS		read-write
		STATUS			current
		DESCRIPTION
				"TYPE: - Number
				 PAGE: - LoudCustom
					mbagc outlev 1  cmdID= 36266  min= -120  max= 120  step= 1  format= %0.1f dB  div_scale= 10 
					Min = -12.0 dB  Max = 12.0 dB  Step = 0.1 dB "
		::= { iqudc12CmdEntry 36266 }


	iqudc12LoudCustomBlock1mbagclimthresh1 OBJECT-TYPE
		SYNTAX		INTEGER
		MAX-ACCESS		read-write
		STATUS			current
		DESCRIPTION
				"TYPE: - Number
				 PAGE: - LoudCustom
					mbagc limthresh 1  cmdID= 36256  min= 0  max= 180  step= 1  format= %0.1f dB  div_scale= 10 
					Min = 0.0 dB  Max = 18.0 dB  Step = 0.1 dB "
		::= { iqudc12CmdEntry 36256 }


	iqudc12LoudCustomBlock1mbagcinfthr1 OBJECT-TYPE
		SYNTAX		INTEGER { disable(0), enable(1) }
		MAX-ACCESS		read-write
		STATUS			current
		DESCRIPTION
				"TYPE: - Checkbox
				 PAGE: - LoudCustom
					mbagc infthr 1  cmdID= 36294 "
		::= { iqudc12CmdEntry 36294 }


	iqudc12LoudCustomBlock1mbagcatk2 OBJECT-TYPE
		SYNTAX		INTEGER
		MAX-ACCESS		read-write
		STATUS			current
		DESCRIPTION
				"TYPE: - Number
				 PAGE: - LoudCustom
					mbagc atk 2  cmdID= 36237  min= 0  max= 100  step= 1  format= %0.0f  div_scale= 1 
					Min = 0  Max = 100  Step = 1 "
		::= { iqudc12CmdEntry 36237 }


	iqudc12LoudCustomBlock1mbagcrel2 OBJECT-TYPE
		SYNTAX		INTEGER
		MAX-ACCESS		read-write
		STATUS			current
		DESCRIPTION
				"TYPE: - Number
				 PAGE: - LoudCustom
					mbagc rel 2  cmdID= 36227  min= 0  max= 100  step= 1  format= %0.0f  div_scale= 1 
					Min = 0  Max = 100  Step = 1 "
		::= { iqudc12CmdEntry 36227 }


	iqudc12LoudCustomBlock1mbagcthresh2 OBJECT-TYPE
		SYNTAX		INTEGER
		MAX-ACCESS		read-write
		STATUS			current
		DESCRIPTION
				"TYPE: - Number
				 PAGE: - LoudCustom
					mbagc thresh 2  cmdID= 36247  min= -120  max= 120  step= 1  format= %0.1f dB  div_scale= 10 
					Min = -12.0 dB  Max = 12.0 dB  Step = 0.1 dB "
		::= { iqudc12CmdEntry 36247 }


	iqudc12LoudCustomBlock1mbagcoutlev2 OBJECT-TYPE
		SYNTAX		INTEGER
		MAX-ACCESS		read-write
		STATUS			current
		DESCRIPTION
				"TYPE: - Number
				 PAGE: - LoudCustom
					mbagc outlev 2  cmdID= 36267  min= -120  max= 120  step= 1  format= %0.1f dB  div_scale= 10 
					Min = -12.0 dB  Max = 12.0 dB  Step = 0.1 dB "
		::= { iqudc12CmdEntry 36267 }


	iqudc12LoudCustomBlock1mbagclimthresh2 OBJECT-TYPE
		SYNTAX		INTEGER
		MAX-ACCESS		read-write
		STATUS			current
		DESCRIPTION
				"TYPE: - Number
				 PAGE: - LoudCustom
					mbagc limthresh 2  cmdID= 36257  min= 0  max= 180  step= 1  format= %0.1f dB  div_scale= 10 
					Min = 0.0 dB  Max = 18.0 dB  Step = 0.1 dB "
		::= { iqudc12CmdEntry 36257 }


	iqudc12LoudCustomBlock1mbagcinfthr2 OBJECT-TYPE
		SYNTAX		INTEGER { disable(0), enable(1) }
		MAX-ACCESS		read-write
		STATUS			current
		DESCRIPTION
				"TYPE: - Checkbox
				 PAGE: - LoudCustom
					mbagc infthr 2  cmdID= 36295 "
		::= { iqudc12CmdEntry 36295 }


	iqudc12LoudCustomBlock1mbagcatk3 OBJECT-TYPE
		SYNTAX		INTEGER
		MAX-ACCESS		read-write
		STATUS			current
		DESCRIPTION
				"TYPE: - Number
				 PAGE: - LoudCustom
					mbagc atk 3  cmdID= 36238  min= 0  max= 100  step= 1  format= %0.0f  div_scale= 1 
					Min = 0  Max = 100  Step = 1 "
		::= { iqudc12CmdEntry 36238 }


	iqudc12LoudCustomBlock1mbagcrel3 OBJECT-TYPE
		SYNTAX		INTEGER
		MAX-ACCESS		read-write
		STATUS			current
		DESCRIPTION
				"TYPE: - Number
				 PAGE: - LoudCustom
					mbagc rel 3  cmdID= 36228  min= 0  max= 100  step= 1  format= %0.0f  div_scale= 1 
					Min = 0  Max = 100  Step = 1 "
		::= { iqudc12CmdEntry 36228 }


	iqudc12LoudCustomBlock1mbagcthresh3 OBJECT-TYPE
		SYNTAX		INTEGER
		MAX-ACCESS		read-write
		STATUS			current
		DESCRIPTION
				"TYPE: - Number
				 PAGE: - LoudCustom
					mbagc thresh 3  cmdID= 36248  min= -120  max= 120  step= 1  format= %0.1f dB  div_scale= 10 
					Min = -12.0 dB  Max = 12.0 dB  Step = 0.1 dB "
		::= { iqudc12CmdEntry 36248 }


	iqudc12LoudCustomBlock1mbagcoutlev3 OBJECT-TYPE
		SYNTAX		INTEGER
		MAX-ACCESS		read-write
		STATUS			current
		DESCRIPTION
				"TYPE: - Number
				 PAGE: - LoudCustom
					mbagc outlev 3  cmdID= 36268  min= -120  max= 120  step= 1  format= %0.1f dB  div_scale= 10 
					Min = -12.0 dB  Max = 12.0 dB  Step = 0.1 dB "
		::= { iqudc12CmdEntry 36268 }


	iqudc12LoudCustomBlock1mbagclimthresh3 OBJECT-TYPE
		SYNTAX		INTEGER
		MAX-ACCESS		read-write
		STATUS			current
		DESCRIPTION
				"TYPE: - Number
				 PAGE: - LoudCustom
					mbagc limthresh 3  cmdID= 36258  min= 0  max= 180  step= 1  format= %0.1f dB  div_scale= 10 
					Min = 0.0 dB  Max = 18.0 dB  Step = 0.1 dB "
		::= { iqudc12CmdEntry 36258 }


	iqudc12LoudCustomBlock1mbagcinfthr3 OBJECT-TYPE
		SYNTAX		INTEGER { disable(0), enable(1) }
		MAX-ACCESS		read-write
		STATUS			current
		DESCRIPTION
				"TYPE: - Checkbox
				 PAGE: - LoudCustom
					mbagc infthr 3  cmdID= 36296 "
		::= { iqudc12CmdEntry 36296 }


	iqudc12LoudCustomBlock1mbagcatk4 OBJECT-TYPE
		SYNTAX		INTEGER
		MAX-ACCESS		read-write
		STATUS			current
		DESCRIPTION
				"TYPE: - Number
				 PAGE: - LoudCustom
					mbagc atk 4  cmdID= 36239  min= 0  max= 100  step= 1  format= %0.0f  div_scale= 1 
					Min = 0  Max = 100  Step = 1 "
		::= { iqudc12CmdEntry 36239 }


	iqudc12LoudCustomBlock1mbagcrel4 OBJECT-TYPE
		SYNTAX		INTEGER
		MAX-ACCESS		read-write
		STATUS			current
		DESCRIPTION
				"TYPE: - Number
				 PAGE: - LoudCustom
					mbagc rel 4  cmdID= 36229  min= 0  max= 100  step= 1  format= %0.0f  div_scale= 1 
					Min = 0  Max = 100  Step = 1 "
		::= { iqudc12CmdEntry 36229 }


	iqudc12LoudCustomBlock1mbagcthresh4 OBJECT-TYPE
		SYNTAX		INTEGER
		MAX-ACCESS		read-write
		STATUS			current
		DESCRIPTION
				"TYPE: - Number
				 PAGE: - LoudCustom
					mbagc thresh 4  cmdID= 36249  min= -120  max= 120  step= 1  format= %0.1f dB  div_scale= 10 
					Min = -12.0 dB  Max = 12.0 dB  Step = 0.1 dB "
		::= { iqudc12CmdEntry 36249 }


	iqudc12LoudCustomBlock1mbagcoutlev4 OBJECT-TYPE
		SYNTAX		INTEGER
		MAX-ACCESS		read-write
		STATUS			current
		DESCRIPTION
				"TYPE: - Number
				 PAGE: - LoudCustom
					mbagc outlev 4  cmdID= 36269  min= -120  max= 120  step= 1  format= %0.1f dB  div_scale= 10 
					Min = -12.0 dB  Max = 12.0 dB  Step = 0.1 dB "
		::= { iqudc12CmdEntry 36269 }


	iqudc12LoudCustomBlock1mbagclimthresh4 OBJECT-TYPE
		SYNTAX		INTEGER
		MAX-ACCESS		read-write
		STATUS			current
		DESCRIPTION
				"TYPE: - Number
				 PAGE: - LoudCustom
					mbagc limthresh 4  cmdID= 36259  min= 0  max= 180  step= 1  format= %0.1f dB  div_scale= 10 
					Min = 0.0 dB  Max = 18.0 dB  Step = 0.1 dB "
		::= { iqudc12CmdEntry 36259 }


	iqudc12LoudCustomBlock1mbagcinfthr4 OBJECT-TYPE
		SYNTAX		INTEGER { disable(0), enable(1) }
		MAX-ACCESS		read-write
		STATUS			current
		DESCRIPTION
				"TYPE: - Checkbox
				 PAGE: - LoudCustom
					mbagc infthr 4  cmdID= 36297 "
		::= { iqudc12CmdEntry 36297 }


	iqudc12LoudCustomBlock1mbagcatk5 OBJECT-TYPE
		SYNTAX		INTEGER
		MAX-ACCESS		read-write
		STATUS			current
		DESCRIPTION
				"TYPE: - Number
				 PAGE: - LoudCustom
					mbagc atk 5  cmdID= 36240  min= 0  max= 100  step= 1  format= %0.0f  div_scale= 1 
					Min = 0  Max = 100  Step = 1 "
		::= { iqudc12CmdEntry 36240 }


	iqudc12LoudCustomBlock1mbagcrel5 OBJECT-TYPE
		SYNTAX		INTEGER
		MAX-ACCESS		read-write
		STATUS			current
		DESCRIPTION
				"TYPE: - Number
				 PAGE: - LoudCustom
					mbagc rel 5  cmdID= 36230  min= 0  max= 100  step= 1  format= %0.0f  div_scale= 1 
					Min = 0  Max = 100  Step = 1 "
		::= { iqudc12CmdEntry 36230 }


	iqudc12LoudCustomBlock1mbagcthresh5 OBJECT-TYPE
		SYNTAX		INTEGER
		MAX-ACCESS		read-write
		STATUS			current
		DESCRIPTION
				"TYPE: - Number
				 PAGE: - LoudCustom
					mbagc thresh 5  cmdID= 36250  min= -120  max= 120  step= 1  format= %0.1f dB  div_scale= 10 
					Min = -12.0 dB  Max = 12.0 dB  Step = 0.1 dB "
		::= { iqudc12CmdEntry 36250 }


	iqudc12LoudCustomBlock1mbagcoutlev5 OBJECT-TYPE
		SYNTAX		INTEGER
		MAX-ACCESS		read-write
		STATUS			current
		DESCRIPTION
				"TYPE: - Number
				 PAGE: - LoudCustom
					mbagc outlev 5  cmdID= 36270  min= -120  max= 120  step= 1  format= %0.1f dB  div_scale= 10 
					Min = -12.0 dB  Max = 12.0 dB  Step = 0.1 dB "
		::= { iqudc12CmdEntry 36270 }


	iqudc12LoudCustomBlock1mbagclimthresh5 OBJECT-TYPE
		SYNTAX		INTEGER
		MAX-ACCESS		read-write
		STATUS			current
		DESCRIPTION
				"TYPE: - Number
				 PAGE: - LoudCustom
					mbagc limthresh 5  cmdID= 36260  min= 0  max= 180  step= 1  format= %0.1f dB  div_scale= 10 
					Min = 0.0 dB  Max = 18.0 dB  Step = 0.1 dB "
		::= { iqudc12CmdEntry 36260 }


	iqudc12LoudCustomBlock1mbagcinfthr5 OBJECT-TYPE
		SYNTAX		INTEGER { disable(0), enable(1) }
		MAX-ACCESS		read-write
		STATUS			current
		DESCRIPTION
				"TYPE: - Checkbox
				 PAGE: - LoudCustom
					mbagc infthr 5  cmdID= 36298 "
		::= { iqudc12CmdEntry 36298 }


	iqudc12LoudCustomBlock1mbrange OBJECT-TYPE
		SYNTAX		INTEGER
		MAX-ACCESS		read-write
		STATUS			current
		DESCRIPTION
				"TYPE: - Number
				 PAGE: - LoudCustom
					mb range  cmdID= 36216  min= 0  max= 180  step= 1  format= %0.1f dB  div_scale= 5 
					Min = 0.0 dB  Max = 36.0 dB  Step = 0.2 dB "
		::= { iqudc12CmdEntry 36216 }


	iqudc12LoudCustomBlock1mbprogrise OBJECT-TYPE
		SYNTAX		INTEGER
		MAX-ACCESS		read-write
		STATUS			current
		DESCRIPTION
				"TYPE: - Number
				 PAGE: - LoudCustom
					mb progrise  cmdID= 36214  min= 0  max= 100  step= 1  format= %0.0f  div_scale= 1 
					Min = 0  Max = 100  Step = 1 "
		::= { iqudc12CmdEntry 36214 }


	iqudc12LoudCustomBlock1mbsoftclip1 OBJECT-TYPE
		SYNTAX		INTEGER
		MAX-ACCESS		read-write
		STATUS			current
		DESCRIPTION
				"TYPE: - Number
				 PAGE: - LoudCustom
					mb softclip1  cmdID= 36218  min= 0  max= 180  step= 1  format= %0.1f dB  div_scale= 10 
					Min = 0.0 dB  Max = 18.0 dB  Step = 0.1 dB "
		::= { iqudc12CmdEntry 36218 }


	iqudc12LoudCustomBlock1mbsoftclip2 OBJECT-TYPE
		SYNTAX		INTEGER
		MAX-ACCESS		read-write
		STATUS			current
		DESCRIPTION
				"TYPE: - Number
				 PAGE: - LoudCustom
					mb softclip2  cmdID= 36220  min= 0  max= 180  step= 1  format= %0.1f dB  div_scale= 10 
					Min = 0.0 dB  Max = 18.0 dB  Step = 0.1 dB "
		::= { iqudc12CmdEntry 36220 }


	iqudc12LoudCustomBlock1mbratio OBJECT-TYPE
		SYNTAX		INTEGER
		MAX-ACCESS		read-write
		STATUS			current
		DESCRIPTION
				"TYPE: - Number
				 PAGE: - LoudCustom
					mb ratio  cmdID= 36222  min= 0  max= 100  step= 1  format= %0.0f  div_scale= 1 
					Min = 0  Max = 100  Step = 1 "
		::= { iqudc12CmdEntry 36222 }


	iqudc12LoudCustomBlock1mblimdrive OBJECT-TYPE
		SYNTAX		INTEGER
		MAX-ACCESS		read-write
		STATUS			current
		DESCRIPTION
				"TYPE: - Number
				 PAGE: - LoudCustom
					mb lim drive  cmdID= 36224  min= -60  max= 60  step= 1  format= %0.1f dB  div_scale= 10 
					Min = -6.0 dB  Max = 6.0 dB  Step = 0.1 dB "
		::= { iqudc12CmdEntry 36224 }


	iqudc12LoudCustomBlock1CustomPreset OBJECT-TYPE
		SYNTAX		INTEGER {
							val-General(0),
							val-Light(1),
							val-Heavy(2),
							val-Loud(3),
							val-LoudLimit(4),
							val-ProtectionLimit(5),
							val-Defaults(6),
							val-Custom(7)
							}
		MAX-ACCESS		read-write
		STATUS			current
		DESCRIPTION
				"TYPE: - RadiobuttonList
				 PAGE: - LoudCustom
					CustomPreset  cmdID= 36306 
					General  value= 0  
					Light  value= 1  
					Heavy  value= 2  
					Loud  value= 3  
					LoudLimit  value= 4  
					ProtectionLimit  value= 5  
					Defaults  value= 6  
					Custom  value= 7  "
		::= { iqudc12CmdEntry 36306 }


	iqudc12LoudCustomBlock1Copyto2 OBJECT-TYPE
		SYNTAX		INTEGER { noAction(0),val-Copy-to-2(1) }
		MAX-ACCESS		read-write
		STATUS			current
		DESCRIPTION
				"TYPE: - Button
				 PAGE: - LoudCustom
					Copy to 2  cmdID= 36309  value= 1  "
		::= { iqudc12CmdEntry 36309 }


	iqudc12LoudCustomBlock2Name OBJECT-TYPE
		SYNTAX		RollCallString
		MAX-ACCESS		read-write
		STATUS			current
		DESCRIPTION
				"TYPE: - Editstring
				 PAGE: - LoudCustom
					Name  cmdID= 36305  "
		::= { iqudc12CmdEntry 36305 }


	iqudc12LoudCustomBlock2inagcfreeze OBJECT-TYPE
		SYNTAX		INTEGER
		MAX-ACCESS		read-write
		STATUS			current
		DESCRIPTION
				"TYPE: - Number
				 PAGE: - LoudCustom
					inagc freeze  cmdID= 36201  min= -180  max= 0  step= 1  format= %0.1f dBFS  div_scale= 2 
					Min = -90.0 dBFS  Max = 0.0 dBFS  Step = 0.5 dBFS "
		::= { iqudc12CmdEntry 36201 }


	iqudc12LoudCustomBlock2inagcgate OBJECT-TYPE
		SYNTAX		INTEGER
		MAX-ACCESS		read-write
		STATUS			current
		DESCRIPTION
				"TYPE: - Number
				 PAGE: - LoudCustom
					inagc gate  cmdID= 36203  min= -180  max= 0  step= 1  format= %0.1f dBFS  div_scale= 2 
					Min = -90.0 dBFS  Max = 0.0 dBFS  Step = 0.5 dBFS "
		::= { iqudc12CmdEntry 36203 }


	iqudc12LoudCustomBlock2inagcratio OBJECT-TYPE
		SYNTAX		INTEGER
		MAX-ACCESS		read-write
		STATUS			current
		DESCRIPTION
				"TYPE: - Number
				 PAGE: - LoudCustom
					inagc ratio  cmdID= 36209  min= 0  max= 100  step= 1  format= %0.0f  div_scale= 1 
					Min = 0  Max = 100  Step = 1 "
		::= { iqudc12CmdEntry 36209 }


	iqudc12LoudCustomBlock2inagcrange OBJECT-TYPE
		SYNTAX		INTEGER
		MAX-ACCESS		read-write
		STATUS			current
		DESCRIPTION
				"TYPE: - Number
				 PAGE: - LoudCustom
					inagc range  cmdID= 36207  min= 0  max= 180  step= 1  format= %0.1f dB  div_scale= 5 
					Min = 0.0 dB  Max = 36.0 dB  Step = 0.2 dB "
		::= { iqudc12CmdEntry 36207 }


	iqudc12LoudCustomBlock2inagcthresh OBJECT-TYPE
		SYNTAX		INTEGER
		MAX-ACCESS		read-write
		STATUS			current
		DESCRIPTION
				"TYPE: - Number
				 PAGE: - LoudCustom
					inagc thresh  cmdID= 36205  min= -180  max= 0  step= 1  format= %0.1f dBFS  div_scale= 10 
					Min = -18.0 dBFS  Max = 0.0 dBFS  Step = 0.1 dBFS "
		::= { iqudc12CmdEntry 36205 }


	iqudc12LoudCustomBlock2inagcattack OBJECT-TYPE
		SYNTAX		INTEGER
		MAX-ACCESS		read-write
		STATUS			current
		DESCRIPTION
				"TYPE: - Number
				 PAGE: - LoudCustom
					inagc attack  cmdID= 36211  min= 1  max= 100  step= 1  format= %0.0f  div_scale= 1 
					Min = 1  Max = 100  Step = 1 "
		::= { iqudc12CmdEntry 36211 }


	iqudc12LoudCustomBlock2inagcrelease OBJECT-TYPE
		SYNTAX		INTEGER
		MAX-ACCESS		read-write
		STATUS			current
		DESCRIPTION
				"TYPE: - Number
				 PAGE: - LoudCustom
					inagc release  cmdID= 36213  min= 1  max= 100  step= 1  format= %0.0f  div_scale= 1 
					Min = 1  Max = 100  Step = 1 "
		::= { iqudc12CmdEntry 36213 }


	iqudc12LoudCustomBlock2peqfreq1 OBJECT-TYPE
		SYNTAX		INTEGER
		MAX-ACCESS		read-write
		STATUS			current
		DESCRIPTION
				"TYPE: - Number
				 PAGE: - LoudCustom
					peq freq 1  cmdID= 36279  min= 20  max= 20000  step= 1  format= %0.0f Hz  div_scale= 1 
					Min = 20 Hz  Max = 20000 Hz  Step = 1 Hz "
		::= { iqudc12CmdEntry 36279 }


	iqudc12LoudCustomBlock2peqq1 OBJECT-TYPE
		SYNTAX		INTEGER
		MAX-ACCESS		read-write
		STATUS			current
		DESCRIPTION
				"TYPE: - Number
				 PAGE: - LoudCustom
					peq q 1  cmdID= 36285  min= 1  max= 200  step= 1  format= %0.2f  div_scale= 20 
					Min = 0.05  Max = 10.00  Step = 0.05 "
		::= { iqudc12CmdEntry 36285 }


	iqudc12LoudCustomBlock2peqlevel1 OBJECT-TYPE
		SYNTAX		INTEGER
		MAX-ACCESS		read-write
		STATUS			current
		DESCRIPTION
				"TYPE: - Number
				 PAGE: - LoudCustom
					peq level 1  cmdID= 36291  min= -90  max= 90  step= 1  format= %0.1f dB  div_scale= 5 
					Min = -18.0 dB  Max = 18.0 dB  Step = 0.2 dB "
		::= { iqudc12CmdEntry 36291 }


	iqudc12LoudCustomBlock2peqfreq2 OBJECT-TYPE
		SYNTAX		INTEGER
		MAX-ACCESS		read-write
		STATUS			current
		DESCRIPTION
				"TYPE: - Number
				 PAGE: - LoudCustom
					peq freq 2  cmdID= 36280  min= 20  max= 20000  step= 1  format= %0.0f Hz  div_scale= 1 
					Min = 20 Hz  Max = 20000 Hz  Step = 1 Hz "
		::= { iqudc12CmdEntry 36280 }


	iqudc12LoudCustomBlock2peqq2 OBJECT-TYPE
		SYNTAX		INTEGER
		MAX-ACCESS		read-write
		STATUS			current
		DESCRIPTION
				"TYPE: - Number
				 PAGE: - LoudCustom
					peq q 2  cmdID= 36286  min= 1  max= 200  step= 1  format= %0.2f  div_scale= 20 
					Min = 0.05  Max = 10.00  Step = 0.05 "
		::= { iqudc12CmdEntry 36286 }


	iqudc12LoudCustomBlock2peqlevel2 OBJECT-TYPE
		SYNTAX		INTEGER
		MAX-ACCESS		read-write
		STATUS			current
		DESCRIPTION
				"TYPE: - Number
				 PAGE: - LoudCustom
					peq level 2  cmdID= 36292  min= -90  max= 90  step= 1  format= %0.1f dB  div_scale= 5 
					Min = -18.0 dB  Max = 18.0 dB  Step = 0.2 dB "
		::= { iqudc12CmdEntry 36292 }


	iqudc12LoudCustomBlock2peqfreq3 OBJECT-TYPE
		SYNTAX		INTEGER
		MAX-ACCESS		read-write
		STATUS			current
		DESCRIPTION
				"TYPE: - Number
				 PAGE: - LoudCustom
					peq freq 3  cmdID= 36281  min= 20  max= 20000  step= 1  format= %0.0f Hz  div_scale= 1 
					Min = 20 Hz  Max = 20000 Hz  Step = 1 Hz "
		::= { iqudc12CmdEntry 36281 }


	iqudc12LoudCustomBlock2peqq3 OBJECT-TYPE
		SYNTAX		INTEGER
		MAX-ACCESS		read-write
		STATUS			current
		DESCRIPTION
				"TYPE: - Number
				 PAGE: - LoudCustom
					peq q 3  cmdID= 36287  min= 1  max= 200  step= 1  format= %0.2f  div_scale= 20 
					Min = 0.05  Max = 10.00  Step = 0.05 "
		::= { iqudc12CmdEntry 36287 }


	iqudc12LoudCustomBlock2peqlevel3 OBJECT-TYPE
		SYNTAX		INTEGER
		MAX-ACCESS		read-write
		STATUS			current
		DESCRIPTION
				"TYPE: - Number
				 PAGE: - LoudCustom
					peq level 3  cmdID= 36293  min= -90  max= 90  step= 1  format= %0.1f dB  div_scale= 5 
					Min = -18.0 dB  Max = 18.0 dB  Step = 0.2 dB "
		::= { iqudc12CmdEntry 36293 }


	iqudc12LoudCustomBlock2mbagcatk1 OBJECT-TYPE
		SYNTAX		INTEGER
		MAX-ACCESS		read-write
		STATUS			current
		DESCRIPTION
				"TYPE: - Number
				 PAGE: - LoudCustom
					mbagc atk 1  cmdID= 36241  min= 0  max= 100  step= 1  format= %0.0f  div_scale= 1 
					Min = 0  Max = 100  Step = 1 "
		::= { iqudc12CmdEntry 36241 }


	iqudc12LoudCustomBlock2mbagcrel1 OBJECT-TYPE
		SYNTAX		INTEGER
		MAX-ACCESS		read-write
		STATUS			current
		DESCRIPTION
				"TYPE: - Number
				 PAGE: - LoudCustom
					mbagc rel 1  cmdID= 36231  min= 0  max= 100  step= 1  format= %0.0f  div_scale= 1 
					Min = 0  Max = 100  Step = 1 "
		::= { iqudc12CmdEntry 36231 }


	iqudc12LoudCustomBlock2mbagcthresh1 OBJECT-TYPE
		SYNTAX		INTEGER
		MAX-ACCESS		read-write
		STATUS			current
		DESCRIPTION
				"TYPE: - Number
				 PAGE: - LoudCustom
					mbagc thresh 1  cmdID= 36251  min= -120  max= 120  step= 1  format= %0.1f dB  div_scale= 10 
					Min = -12.0 dB  Max = 12.0 dB  Step = 0.1 dB "
		::= { iqudc12CmdEntry 36251 }


	iqudc12LoudCustomBlock2mbagcoutlev1 OBJECT-TYPE
		SYNTAX		INTEGER
		MAX-ACCESS		read-write
		STATUS			current
		DESCRIPTION
				"TYPE: - Number
				 PAGE: - LoudCustom
					mbagc outlev 1  cmdID= 36271  min= -120  max= 120  step= 1  format= %0.1f dB  div_scale= 10 
					Min = -12.0 dB  Max = 12.0 dB  Step = 0.1 dB "
		::= { iqudc12CmdEntry 36271 }


	iqudc12LoudCustomBlock2mbagclimthresh1 OBJECT-TYPE
		SYNTAX		INTEGER
		MAX-ACCESS		read-write
		STATUS			current
		DESCRIPTION
				"TYPE: - Number
				 PAGE: - LoudCustom
					mbagc limthresh 1  cmdID= 36261  min= 0  max= 180  step= 1  format= %0.1f dB  div_scale= 10 
					Min = 0.0 dB  Max = 18.0 dB  Step = 0.1 dB "
		::= { iqudc12CmdEntry 36261 }


	iqudc12LoudCustomBlock2mbagcinfthr1 OBJECT-TYPE
		SYNTAX		INTEGER { disable(0), enable(1) }
		MAX-ACCESS		read-write
		STATUS			current
		DESCRIPTION
				"TYPE: - Checkbox
				 PAGE: - LoudCustom
					mbagc infthr 1  cmdID= 36299 "
		::= { iqudc12CmdEntry 36299 }


	iqudc12LoudCustomBlock2mbagcatk2 OBJECT-TYPE
		SYNTAX		INTEGER
		MAX-ACCESS		read-write
		STATUS			current
		DESCRIPTION
				"TYPE: - Number
				 PAGE: - LoudCustom
					mbagc atk 2  cmdID= 36242  min= 0  max= 100  step= 1  format= %0.0f  div_scale= 1 
					Min = 0  Max = 100  Step = 1 "
		::= { iqudc12CmdEntry 36242 }


	iqudc12LoudCustomBlock2mbagcrel2 OBJECT-TYPE
		SYNTAX		INTEGER
		MAX-ACCESS		read-write
		STATUS			current
		DESCRIPTION
				"TYPE: - Number
				 PAGE: - LoudCustom
					mbagc rel 2  cmdID= 36232  min= 0  max= 100  step= 1  format= %0.0f  div_scale= 1 
					Min = 0  Max = 100  Step = 1 "
		::= { iqudc12CmdEntry 36232 }


	iqudc12LoudCustomBlock2mbagcthresh2 OBJECT-TYPE
		SYNTAX		INTEGER
		MAX-ACCESS		read-write
		STATUS			current
		DESCRIPTION
				"TYPE: - Number
				 PAGE: - LoudCustom
					mbagc thresh 2  cmdID= 36252  min= -120  max= 120  step= 1  format= %0.1f dB  div_scale= 10 
					Min = -12.0 dB  Max = 12.0 dB  Step = 0.1 dB "
		::= { iqudc12CmdEntry 36252 }


	iqudc12LoudCustomBlock2mbagcoutlev2 OBJECT-TYPE
		SYNTAX		INTEGER
		MAX-ACCESS		read-write
		STATUS			current
		DESCRIPTION
				"TYPE: - Number
				 PAGE: - LoudCustom
					mbagc outlev 2  cmdID= 36272  min= -120  max= 120  step= 1  format= %0.1f dB  div_scale= 10 
					Min = -12.0 dB  Max = 12.0 dB  Step = 0.1 dB "
		::= { iqudc12CmdEntry 36272 }


	iqudc12LoudCustomBlock2mbagclimthresh2 OBJECT-TYPE
		SYNTAX		INTEGER
		MAX-ACCESS		read-write
		STATUS			current
		DESCRIPTION
				"TYPE: - Number
				 PAGE: - LoudCustom
					mbagc limthresh 2  cmdID= 36262  min= 0  max= 180  step= 1  format= %0.1f dB  div_scale= 10 
					Min = 0.0 dB  Max = 18.0 dB  Step = 0.1 dB "
		::= { iqudc12CmdEntry 36262 }


	iqudc12LoudCustomBlock2mbagcinfthr2 OBJECT-TYPE
		SYNTAX		INTEGER { disable(0), enable(1) }
		MAX-ACCESS		read-write
		STATUS			current
		DESCRIPTION
				"TYPE: - Checkbox
				 PAGE: - LoudCustom
					mbagc infthr 2  cmdID= 36300 "
		::= { iqudc12CmdEntry 36300 }


	iqudc12LoudCustomBlock2mbagcatk3 OBJECT-TYPE
		SYNTAX		INTEGER
		MAX-ACCESS		read-write
		STATUS			current
		DESCRIPTION
				"TYPE: - Number
				 PAGE: - LoudCustom
					mbagc atk 3  cmdID= 36243  min= 0  max= 100  step= 1  format= %0.0f  div_scale= 1 
					Min = 0  Max = 100  Step = 1 "
		::= { iqudc12CmdEntry 36243 }


	iqudc12LoudCustomBlock2mbagcrel3 OBJECT-TYPE
		SYNTAX		INTEGER
		MAX-ACCESS		read-write
		STATUS			current
		DESCRIPTION
				"TYPE: - Number
				 PAGE: - LoudCustom
					mbagc rel 3  cmdID= 36233  min= 0  max= 100  step= 1  format= %0.0f  div_scale= 1 
					Min = 0  Max = 100  Step = 1 "
		::= { iqudc12CmdEntry 36233 }


	iqudc12LoudCustomBlock2mbagcthresh3 OBJECT-TYPE
		SYNTAX		INTEGER
		MAX-ACCESS		read-write
		STATUS			current
		DESCRIPTION
				"TYPE: - Number
				 PAGE: - LoudCustom
					mbagc thresh 3  cmdID= 36253  min= -120  max= 120  step= 1  format= %0.1f dB  div_scale= 10 
					Min = -12.0 dB  Max = 12.0 dB  Step = 0.1 dB "
		::= { iqudc12CmdEntry 36253 }


	iqudc12LoudCustomBlock2mbagcoutlev3 OBJECT-TYPE
		SYNTAX		INTEGER
		MAX-ACCESS		read-write
		STATUS			current
		DESCRIPTION
				"TYPE: - Number
				 PAGE: - LoudCustom
					mbagc outlev 3  cmdID= 36273  min= -120  max= 120  step= 1  format= %0.1f dB  div_scale= 10 
					Min = -12.0 dB  Max = 12.0 dB  Step = 0.1 dB "
		::= { iqudc12CmdEntry 36273 }


	iqudc12LoudCustomBlock2mbagclimthresh3 OBJECT-TYPE
		SYNTAX		INTEGER
		MAX-ACCESS		read-write
		STATUS			current
		DESCRIPTION
				"TYPE: - Number
				 PAGE: - LoudCustom
					mbagc limthresh 3  cmdID= 36263  min= 0  max= 180  step= 1  format= %0.1f dB  div_scale= 10 
					Min = 0.0 dB  Max = 18.0 dB  Step = 0.1 dB "
		::= { iqudc12CmdEntry 36263 }


	iqudc12LoudCustomBlock2mbagcinfthr3 OBJECT-TYPE
		SYNTAX		INTEGER { disable(0), enable(1) }
		MAX-ACCESS		read-write
		STATUS			current
		DESCRIPTION
				"TYPE: - Checkbox
				 PAGE: - LoudCustom
					mbagc infthr 3  cmdID= 36301 "
		::= { iqudc12CmdEntry 36301 }


	iqudc12LoudCustomBlock2mbagcatk4 OBJECT-TYPE
		SYNTAX		INTEGER
		MAX-ACCESS		read-write
		STATUS			current
		DESCRIPTION
				"TYPE: - Number
				 PAGE: - LoudCustom
					mbagc atk 4  cmdID= 36244  min= 0  max= 100  step= 1  format= %0.0f  div_scale= 1 
					Min = 0  Max = 100  Step = 1 "
		::= { iqudc12CmdEntry 36244 }


	iqudc12LoudCustomBlock2mbagcrel4 OBJECT-TYPE
		SYNTAX		INTEGER
		MAX-ACCESS		read-write
		STATUS			current
		DESCRIPTION
				"TYPE: - Number
				 PAGE: - LoudCustom
					mbagc rel 4  cmdID= 36234  min= 0  max= 100  step= 1  format= %0.0f  div_scale= 1 
					Min = 0  Max = 100  Step = 1 "
		::= { iqudc12CmdEntry 36234 }


	iqudc12LoudCustomBlock2mbagcthresh4 OBJECT-TYPE
		SYNTAX		INTEGER
		MAX-ACCESS		read-write
		STATUS			current
		DESCRIPTION
				"TYPE: - Number
				 PAGE: - LoudCustom
					mbagc thresh 4  cmdID= 36254  min= -120  max= 120  step= 1  format= %0.1f dB  div_scale= 10 
					Min = -12.0 dB  Max = 12.0 dB  Step = 0.1 dB "
		::= { iqudc12CmdEntry 36254 }


	iqudc12LoudCustomBlock2mbagcoutlev4 OBJECT-TYPE
		SYNTAX		INTEGER
		MAX-ACCESS		read-write
		STATUS			current
		DESCRIPTION
				"TYPE: - Number
				 PAGE: - LoudCustom
					mbagc outlev 4  cmdID= 36274  min= -120  max= 120  step= 1  format= %0.1f dB  div_scale= 10 
					Min = -12.0 dB  Max = 12.0 dB  Step = 0.1 dB "
		::= { iqudc12CmdEntry 36274 }


	iqudc12LoudCustomBlock2mbagclimthresh4 OBJECT-TYPE
		SYNTAX		INTEGER
		MAX-ACCESS		read-write
		STATUS			current
		DESCRIPTION
				"TYPE: - Number
				 PAGE: - LoudCustom
					mbagc limthresh 4  cmdID= 36264  min= 0  max= 180  step= 1  format= %0.1f dB  div_scale= 10 
					Min = 0.0 dB  Max = 18.0 dB  Step = 0.1 dB "
		::= { iqudc12CmdEntry 36264 }


	iqudc12LoudCustomBlock2mbagcinfthr4 OBJECT-TYPE
		SYNTAX		INTEGER { disable(0), enable(1) }
		MAX-ACCESS		read-write
		STATUS			current
		DESCRIPTION
				"TYPE: - Checkbox
				 PAGE: - LoudCustom
					mbagc infthr 4  cmdID= 36302 "
		::= { iqudc12CmdEntry 36302 }


	iqudc12LoudCustomBlock2mbagcatk5 OBJECT-TYPE
		SYNTAX		INTEGER
		MAX-ACCESS		read-write
		STATUS			current
		DESCRIPTION
				"TYPE: - Number
				 PAGE: - LoudCustom
					mbagc atk 5  cmdID= 36245  min= 0  max= 100  step= 1  format= %0.0f  div_scale= 1 
					Min = 0  Max = 100  Step = 1 "
		::= { iqudc12CmdEntry 36245 }


	iqudc12LoudCustomBlock2mbagcrel5 OBJECT-TYPE
		SYNTAX		INTEGER
		MAX-ACCESS		read-write
		STATUS			current
		DESCRIPTION
				"TYPE: - Number
				 PAGE: - LoudCustom
					mbagc rel 5  cmdID= 36235  min= 0  max= 100  step= 1  format= %0.0f  div_scale= 1 
					Min = 0  Max = 100  Step = 1 "
		::= { iqudc12CmdEntry 36235 }


	iqudc12LoudCustomBlock2mbagcthresh5 OBJECT-TYPE
		SYNTAX		INTEGER
		MAX-ACCESS		read-write
		STATUS			current
		DESCRIPTION
				"TYPE: - Number
				 PAGE: - LoudCustom
					mbagc thresh 5  cmdID= 36255  min= -120  max= 120  step= 1  format= %0.1f dB  div_scale= 10 
					Min = -12.0 dB  Max = 12.0 dB  Step = 0.1 dB "
		::= { iqudc12CmdEntry 36255 }


	iqudc12LoudCustomBlock2mbagcoutlev5 OBJECT-TYPE
		SYNTAX		INTEGER
		MAX-ACCESS		read-write
		STATUS			current
		DESCRIPTION
				"TYPE: - Number
				 PAGE: - LoudCustom
					mbagc outlev 5  cmdID= 36275  min= -120  max= 120  step= 1  format= %0.1f dB  div_scale= 10 
					Min = -12.0 dB  Max = 12.0 dB  Step = 0.1 dB "
		::= { iqudc12CmdEntry 36275 }


	iqudc12LoudCustomBlock2mbagclimthresh5 OBJECT-TYPE
		SYNTAX		INTEGER
		MAX-ACCESS		read-write
		STATUS			current
		DESCRIPTION
				"TYPE: - Number
				 PAGE: - LoudCustom
					mbagc limthresh 5  cmdID= 36265  min= 0  max= 180  step= 1  format= %0.1f dB  div_scale= 10 
					Min = 0.0 dB  Max = 18.0 dB  Step = 0.1 dB "
		::= { iqudc12CmdEntry 36265 }


	iqudc12LoudCustomBlock2mbagcinfthr5 OBJECT-TYPE
		SYNTAX		INTEGER { disable(0), enable(1) }
		MAX-ACCESS		read-write
		STATUS			current
		DESCRIPTION
				"TYPE: - Checkbox
				 PAGE: - LoudCustom
					mbagc infthr 5  cmdID= 36303 "
		::= { iqudc12CmdEntry 36303 }


	iqudc12LoudCustomBlock2mbrange OBJECT-TYPE
		SYNTAX		INTEGER
		MAX-ACCESS		read-write
		STATUS			current
		DESCRIPTION
				"TYPE: - Number
				 PAGE: - LoudCustom
					mb range  cmdID= 36217  min= 0  max= 180  step= 1  format= %0.1f dB  div_scale= 5 
					Min = 0.0 dB  Max = 36.0 dB  Step = 0.2 dB "
		::= { iqudc12CmdEntry 36217 }


	iqudc12LoudCustomBlock2mbprogrise OBJECT-TYPE
		SYNTAX		INTEGER
		MAX-ACCESS		read-write
		STATUS			current
		DESCRIPTION
				"TYPE: - Number
				 PAGE: - LoudCustom
					mb progrise  cmdID= 36215  min= 0  max= 100  step= 1  format= %0.0f  div_scale= 1 
					Min = 0  Max = 100  Step = 1 "
		::= { iqudc12CmdEntry 36215 }


	iqudc12LoudCustomBlock2mbsoftclip1 OBJECT-TYPE
		SYNTAX		INTEGER
		MAX-ACCESS		read-write
		STATUS			current
		DESCRIPTION
				"TYPE: - Number
				 PAGE: - LoudCustom
					mb softclip1  cmdID= 36219  min= 0  max= 180  step= 1  format= %0.1f dB  div_scale= 10 
					Min = 0.0 dB  Max = 18.0 dB  Step = 0.1 dB "
		::= { iqudc12CmdEntry 36219 }


	iqudc12LoudCustomBlock2mbsoftclip2 OBJECT-TYPE
		SYNTAX		INTEGER
		MAX-ACCESS		read-write
		STATUS			current
		DESCRIPTION
				"TYPE: - Number
				 PAGE: - LoudCustom
					mb softclip2  cmdID= 36221  min= 0  max= 180  step= 1  format= %0.1f dB  div_scale= 10 
					Min = 0.0 dB  Max = 18.0 dB  Step = 0.1 dB "
		::= { iqudc12CmdEntry 36221 }


	iqudc12LoudCustomBlock2mbratio OBJECT-TYPE
		SYNTAX		INTEGER
		MAX-ACCESS		read-write
		STATUS			current
		DESCRIPTION
				"TYPE: - Number
				 PAGE: - LoudCustom
					mb ratio  cmdID= 36223  min= 0  max= 100  step= 1  format= %0.0f  div_scale= 1 
					Min = 0  Max = 100  Step = 1 "
		::= { iqudc12CmdEntry 36223 }


	iqudc12LoudCustomBlock2mblimdrive OBJECT-TYPE
		SYNTAX		INTEGER
		MAX-ACCESS		read-write
		STATUS			current
		DESCRIPTION
				"TYPE: - Number
				 PAGE: - LoudCustom
					mb lim drive  cmdID= 36225  min= -60  max= 60  step= 1  format= %0.1f dB  div_scale= 10 
					Min = -6.0 dB  Max = 6.0 dB  Step = 0.1 dB "
		::= { iqudc12CmdEntry 36225 }


	iqudc12LoudCustomBlock2CustomPreset OBJECT-TYPE
		SYNTAX		INTEGER {
							val-General(0),
							val-Light(1),
							val-Heavy(2),
							val-Loud(3),
							val-LoudLimit(4),
							val-ProtectionLimit(5),
							val-Defaults(6),
							val-Custom(7)
							}
		MAX-ACCESS		read-write
		STATUS			current
		DESCRIPTION
				"TYPE: - RadiobuttonList
				 PAGE: - LoudCustom
					CustomPreset  cmdID= 36307 
					General  value= 0  
					Light  value= 1  
					Heavy  value= 2  
					Loud  value= 3  
					LoudLimit  value= 4  
					ProtectionLimit  value= 5  
					Defaults  value= 6  
					Custom  value= 7  "
		::= { iqudc12CmdEntry 36307 }


	iqudc12LoudCustomBlock2Copyto1 OBJECT-TYPE
		SYNTAX		INTEGER { noAction(0),val-Copy-to-1(1) }
		MAX-ACCESS		read-write
		STATUS			current
		DESCRIPTION
				"TYPE: - Button
				 PAGE: - LoudCustom
					Copy to 1  cmdID= 36308  value= 1  "
		::= { iqudc12CmdEntry 36308 }


	iqudc12LoudCustomMasterLevelCustom1 OBJECT-TYPE
		SYNTAX		INTEGER
		MAX-ACCESS		read-write
		STATUS			current
		DESCRIPTION
				"TYPE: - Number
				 PAGE: - LoudCustom
					Custom1  cmdID= 36328  min= -310  max= 0  step= 1  format= %0.1f dB  div_scale= 10 
					Min = -31.0 dB  Max = 0.0 dB  Step = 0.1 dB "
		::= { iqudc12CmdEntry 36328 }


	iqudc12LoudCustomMasterLevelCustom2 OBJECT-TYPE
		SYNTAX		INTEGER
		MAX-ACCESS		read-write
		STATUS			current
		DESCRIPTION
				"TYPE: - Number
				 PAGE: - LoudCustom
					Custom2  cmdID= 36329  min= -310  max= 0  step= 1  format= %0.1f dB  div_scale= 10 
					Min = -31.0 dB  Max = 0.0 dB  Step = 0.1 dB "
		::= { iqudc12CmdEntry 36329 }


	iqudc12LoudCustomMasterLevelGen51 OBJECT-TYPE
		SYNTAX		INTEGER
		MAX-ACCESS		read-write
		STATUS			current
		DESCRIPTION
				"TYPE: - Number
				 PAGE: - LoudCustom
					Gen_51  cmdID= 36310  min= -310  max= 0  step= 1  format= %0.1f dB  div_scale= 10 
					Min = -31.0 dB  Max = 0.0 dB  Step = 0.1 dB "
		::= { iqudc12CmdEntry 36310 }


	iqudc12LoudCustomMasterLevelLight51 OBJECT-TYPE
		SYNTAX		INTEGER
		MAX-ACCESS		read-write
		STATUS			current
		DESCRIPTION
				"TYPE: - Number
				 PAGE: - LoudCustom
					Light_51  cmdID= 36311  min= -310  max= 0  step= 1  format= %0.1f dB  div_scale= 10 
					Min = -31.0 dB  Max = 0.0 dB  Step = 0.1 dB "
		::= { iqudc12CmdEntry 36311 }


	iqudc12LoudCustomMasterLevelHeavy51 OBJECT-TYPE
		SYNTAX		INTEGER
		MAX-ACCESS		read-write
		STATUS			current
		DESCRIPTION
				"TYPE: - Number
				 PAGE: - LoudCustom
					Heavy_51  cmdID= 36312  min= -310  max= 0  step= 1  format= %0.1f dB  div_scale= 10 
					Min = -31.0 dB  Max = 0.0 dB  Step = 0.1 dB "
		::= { iqudc12CmdEntry 36312 }


	iqudc12LoudCustomMasterLevelLoud51 OBJECT-TYPE
		SYNTAX		INTEGER
		MAX-ACCESS		read-write
		STATUS			current
		DESCRIPTION
				"TYPE: - Number
				 PAGE: - LoudCustom
					Loud_51  cmdID= 36313  min= -310  max= 0  step= 1  format= %0.1f dB  div_scale= 10 
					Min = -31.0 dB  Max = 0.0 dB  Step = 0.1 dB "
		::= { iqudc12CmdEntry 36313 }


	iqudc12LoudCustomMasterLevelLoudLimit51 OBJECT-TYPE
		SYNTAX		INTEGER
		MAX-ACCESS		read-write
		STATUS			current
		DESCRIPTION
				"TYPE: - Number
				 PAGE: - LoudCustom
					LoudLimit_51  cmdID= 36314  min= -310  max= 0  step= 1  format= %0.1f dB  div_scale= 10 
					Min = -31.0 dB  Max = 0.0 dB  Step = 0.1 dB "
		::= { iqudc12CmdEntry 36314 }


	iqudc12LoudCustomMasterLevelProtect51 OBJECT-TYPE
		SYNTAX		INTEGER
		MAX-ACCESS		read-write
		STATUS			current
		DESCRIPTION
				"TYPE: - Number
				 PAGE: - LoudCustom
					Protect_51  cmdID= 36315  min= -310  max= 0  step= 1  format= %0.1f dB  div_scale= 10 
					Min = -31.0 dB  Max = 0.0 dB  Step = 0.1 dB "
		::= { iqudc12CmdEntry 36315 }


	iqudc12LoudCustomMasterLevelGenSterA OBJECT-TYPE
		SYNTAX		INTEGER
		MAX-ACCESS		read-write
		STATUS			current
		DESCRIPTION
				"TYPE: - Number
				 PAGE: - LoudCustom
					Gen_SterA  cmdID= 36316  min= -310  max= 0  step= 1  format= %0.1f dB  div_scale= 10 
					Min = -31.0 dB  Max = 0.0 dB  Step = 0.1 dB "
		::= { iqudc12CmdEntry 36316 }


	iqudc12LoudCustomMasterLevelLightSterA OBJECT-TYPE
		SYNTAX		INTEGER
		MAX-ACCESS		read-write
		STATUS			current
		DESCRIPTION
				"TYPE: - Number
				 PAGE: - LoudCustom
					Light_SterA  cmdID= 36317  min= -310  max= 0  step= 1  format= %0.1f dB  div_scale= 10 
					Min = -31.0 dB  Max = 0.0 dB  Step = 0.1 dB "
		::= { iqudc12CmdEntry 36317 }


	iqudc12LoudCustomMasterLevelHeavySterA OBJECT-TYPE
		SYNTAX		INTEGER
		MAX-ACCESS		read-write
		STATUS			current
		DESCRIPTION
				"TYPE: - Number
				 PAGE: - LoudCustom
					Heavy_SterA  cmdID= 36318  min= -310  max= 0  step= 1  format= %0.1f dB  div_scale= 10 
					Min = -31.0 dB  Max = 0.0 dB  Step = 0.1 dB "
		::= { iqudc12CmdEntry 36318 }


	iqudc12LoudCustomMasterLevelLoudSterA OBJECT-TYPE
		SYNTAX		INTEGER
		MAX-ACCESS		read-write
		STATUS			current
		DESCRIPTION
				"TYPE: - Number
				 PAGE: - LoudCustom
					Loud_SterA  cmdID= 36319  min= -310  max= 0  step= 1  format= %0.1f dB  div_scale= 10 
					Min = -31.0 dB  Max = 0.0 dB  Step = 0.1 dB "
		::= { iqudc12CmdEntry 36319 }


	iqudc12LoudCustomMasterLevelLoudLimitSterA OBJECT-TYPE
		SYNTAX		INTEGER
		MAX-ACCESS		read-write
		STATUS			current
		DESCRIPTION
				"TYPE: - Number
				 PAGE: - LoudCustom
					LoudLimit_SterA  cmdID= 36320  min= -310  max= 0  step= 1  format= %0.1f dB  div_scale= 10 
					Min = -31.0 dB  Max = 0.0 dB  Step = 0.1 dB "
		::= { iqudc12CmdEntry 36320 }


	iqudc12LoudCustomMasterLevelProtectSterA OBJECT-TYPE
		SYNTAX		INTEGER
		MAX-ACCESS		read-write
		STATUS			current
		DESCRIPTION
				"TYPE: - Number
				 PAGE: - LoudCustom
					Protect_SterA  cmdID= 36321  min= -310  max= 0  step= 1  format= %0.1f dB  div_scale= 10 
					Min = -31.0 dB  Max = 0.0 dB  Step = 0.1 dB "
		::= { iqudc12CmdEntry 36321 }


	iqudc12LoudCustomMasterLevelGenSterB OBJECT-TYPE
		SYNTAX		INTEGER
		MAX-ACCESS		read-write
		STATUS			current
		DESCRIPTION
				"TYPE: - Number
				 PAGE: - LoudCustom
					Gen_SterB  cmdID= 36322  min= -310  max= 0  step= 1  format= %0.1f dB  div_scale= 10 
					Min = -31.0 dB  Max = 0.0 dB  Step = 0.1 dB "
		::= { iqudc12CmdEntry 36322 }


	iqudc12LoudCustomMasterLevelLightSterB OBJECT-TYPE
		SYNTAX		INTEGER
		MAX-ACCESS		read-write
		STATUS			current
		DESCRIPTION
				"TYPE: - Number
				 PAGE: - LoudCustom
					Light_SterB  cmdID= 36323  min= -310  max= 0  step= 1  format= %0.1f dB  div_scale= 10 
					Min = -31.0 dB  Max = 0.0 dB  Step = 0.1 dB "
		::= { iqudc12CmdEntry 36323 }


	iqudc12LoudCustomMasterLevelHeavySterB OBJECT-TYPE
		SYNTAX		INTEGER
		MAX-ACCESS		read-write
		STATUS			current
		DESCRIPTION
				"TYPE: - Number
				 PAGE: - LoudCustom
					Heavy_SterB  cmdID= 36324  min= -310  max= 0  step= 1  format= %0.1f dB  div_scale= 10 
					Min = -31.0 dB  Max = 0.0 dB  Step = 0.1 dB "
		::= { iqudc12CmdEntry 36324 }


	iqudc12LoudCustomMasterLevelLoudSterB OBJECT-TYPE
		SYNTAX		INTEGER
		MAX-ACCESS		read-write
		STATUS			current
		DESCRIPTION
				"TYPE: - Number
				 PAGE: - LoudCustom
					Loud_SterB  cmdID= 36325  min= -310  max= 0  step= 1  format= %0.1f dB  div_scale= 10 
					Min = -31.0 dB  Max = 0.0 dB  Step = 0.1 dB "
		::= { iqudc12CmdEntry 36325 }


	iqudc12LoudCustomMasterLevelLoudLimitSterB OBJECT-TYPE
		SYNTAX		INTEGER
		MAX-ACCESS		read-write
		STATUS			current
		DESCRIPTION
				"TYPE: - Number
				 PAGE: - LoudCustom
					LoudLimit_SterB  cmdID= 36326  min= -310  max= 0  step= 1  format= %0.1f dB  div_scale= 10 
					Min = -31.0 dB  Max = 0.0 dB  Step = 0.1 dB "
		::= { iqudc12CmdEntry 36326 }


	iqudc12LoudCustomMasterLevelProtectSterB OBJECT-TYPE
		SYNTAX		INTEGER
		MAX-ACCESS		read-write
		STATUS			current
		DESCRIPTION
				"TYPE: - Number
				 PAGE: - LoudCustom
					Protect_SterB  cmdID= 36327  min= -310  max= 0  step= 1  format= %0.1f dB  div_scale= 10 
					Min = -31.0 dB  Max = 0.0 dB  Step = 0.1 dB "
		::= { iqudc12CmdEntry 36327 }


	iqudc12MenuMixers13Select OBJECT-TYPE
		SYNTAX		INTEGER {
							val-Mixer1(0),
							val-Mixer2(1),
							val-Mixer3(2),
							val-Mixer4(3),
							val-Downmix1-1(4),
							val-Downmix1-2(5)
							}
		MAX-ACCESS		read-write
		STATUS			current
		DESCRIPTION
				"TYPE: - RadiobuttonList
				 PAGE: - Mixers1_3
					Select  cmdID= 40825 
					Mixer1  value= 0  
					Mixer2  value= 1  
					Mixer3  value= 2  
					Mixer4  value= 3  
					Downmix1-1  value= 4  
					Downmix1-2  value= 5  "
		::= { iqudc12CmdEntry 40825 }


	iqudc12Mixers13Source1ProcGain OBJECT-TYPE
		SYNTAX		INTEGER
		MAX-ACCESS		read-write
		STATUS			current
		DESCRIPTION
				"TYPE: - Number
				 PAGE: - Mixers1_3
					ProcGain  cmdID= 40800  min= -801  max= 120  step= 1  format= %0.1f dB  div_scale= 10 
					Min = -80.1 dB  Max = 12.0 dB  Step = 0.1 dB "
		::= { iqudc12CmdEntry 40800 }


	iqudc12Mixers13Source1Invert OBJECT-TYPE
		SYNTAX		INTEGER { disable(0), enable(1) }
		MAX-ACCESS		read-write
		STATUS			current
		DESCRIPTION
				"TYPE: - Checkbox
				 PAGE: - Mixers1_3
					Invert  cmdID= 40806 "
		::= { iqudc12CmdEntry 40806 }


	iqudc12Mixers13Source1Mute OBJECT-TYPE
		SYNTAX		INTEGER { disable(0), enable(1) }
		MAX-ACCESS		read-write
		STATUS			current
		DESCRIPTION
				"TYPE: - Checkbox
				 PAGE: - Mixers1_3
					Mute  cmdID= 40812 "
		::= { iqudc12CmdEntry 40812 }


	iqudc12Mixers13Source1Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Tone1(16),
							val-Tone2(17),
							val-Tone3(18),
							val-Tone4(19),
							val-Tone5(20),
							val-Tone6(21),
							val-Tone7(22),
							val-Tone8(23),
							val-Silence1(32)
							}
		MAX-ACCESS		read-write
		STATUS			current
		DESCRIPTION
				"TYPE: - RadiobuttonList
				 PAGE: - Mixers1_3
					Src  cmdID= 40818 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Tone1  value= 16  
					Tone2  value= 17  
					Tone3  value= 18  
					Tone4  value= 19  
					Tone5  value= 20  
					Tone6  value= 21  
					Tone7  value= 22  
					Tone8  value= 23  
					Silence  value= 32  "
		::= { iqudc12CmdEntry 40818 }


	iqudc12Mixers13Source1Name OBJECT-TYPE
		SYNTAX		RollCallString
		MAX-ACCESS		read-only
		STATUS			current
		DESCRIPTION
				"TYPE: - Display
				 PAGE: - Mixers1_3
					Name  cmdID= 40826  format=   "
		::= { iqudc12CmdEntry 40826 }


	iqudc12Mixers13Source2ProcGain OBJECT-TYPE
		SYNTAX		INTEGER
		MAX-ACCESS		read-write
		STATUS			current
		DESCRIPTION
				"TYPE: - Number
				 PAGE: - Mixers1_3
					ProcGain  cmdID= 40801  min= -801  max= 120  step= 1  format= %0.1f dB  div_scale= 10 
					Min = -80.1 dB  Max = 12.0 dB  Step = 0.1 dB "
		::= { iqudc12CmdEntry 40801 }


	iqudc12Mixers13Source2Invert OBJECT-TYPE
		SYNTAX		INTEGER { disable(0), enable(1) }
		MAX-ACCESS		read-write
		STATUS			current
		DESCRIPTION
				"TYPE: - Checkbox
				 PAGE: - Mixers1_3
					Invert  cmdID= 40807 "
		::= { iqudc12CmdEntry 40807 }


	iqudc12Mixers13Source2Mute OBJECT-TYPE
		SYNTAX		INTEGER { disable(0), enable(1) }
		MAX-ACCESS		read-write
		STATUS			current
		DESCRIPTION
				"TYPE: - Checkbox
				 PAGE: - Mixers1_3
					Mute  cmdID= 40813 "
		::= { iqudc12CmdEntry 40813 }


	iqudc12Mixers13Source2Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Tone1(16),
							val-Tone2(17),
							val-Tone3(18),
							val-Tone4(19),
							val-Tone5(20),
							val-Tone6(21),
							val-Tone7(22),
							val-Tone8(23),
							val-Silence1(32)
							}
		MAX-ACCESS		read-write
		STATUS			current
		DESCRIPTION
				"TYPE: - RadiobuttonList
				 PAGE: - Mixers1_3
					Src  cmdID= 40819 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Tone1  value= 16  
					Tone2  value= 17  
					Tone3  value= 18  
					Tone4  value= 19  
					Tone5  value= 20  
					Tone6  value= 21  
					Tone7  value= 22  
					Tone8  value= 23  
					Silence  value= 32  "
		::= { iqudc12CmdEntry 40819 }


	iqudc12Mixers13Source2Name OBJECT-TYPE
		SYNTAX		RollCallString
		MAX-ACCESS		read-only
		STATUS			current
		DESCRIPTION
				"TYPE: - Display
				 PAGE: - Mixers1_3
					Name  cmdID= 40827  format=   "
		::= { iqudc12CmdEntry 40827 }


	iqudc12Mixers13Source3ProcGain OBJECT-TYPE
		SYNTAX		INTEGER
		MAX-ACCESS		read-write
		STATUS			current
		DESCRIPTION
				"TYPE: - Number
				 PAGE: - Mixers1_3
					ProcGain  cmdID= 40802  min= -801  max= 120  step= 1  format= %0.1f dB  div_scale= 10 
					Min = -80.1 dB  Max = 12.0 dB  Step = 0.1 dB "
		::= { iqudc12CmdEntry 40802 }


	iqudc12Mixers13Source3Invert OBJECT-TYPE
		SYNTAX		INTEGER { disable(0), enable(1) }
		MAX-ACCESS		read-write
		STATUS			current
		DESCRIPTION
				"TYPE: - Checkbox
				 PAGE: - Mixers1_3
					Invert  cmdID= 40808 "
		::= { iqudc12CmdEntry 40808 }


	iqudc12Mixers13Source3Mute OBJECT-TYPE
		SYNTAX		INTEGER { disable(0), enable(1) }
		MAX-ACCESS		read-write
		STATUS			current
		DESCRIPTION
				"TYPE: - Checkbox
				 PAGE: - Mixers1_3
					Mute  cmdID= 40814 "
		::= { iqudc12CmdEntry 40814 }


	iqudc12Mixers13Source3Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Tone1(16),
							val-Tone2(17),
							val-Tone3(18),
							val-Tone4(19),
							val-Tone5(20),
							val-Tone6(21),
							val-Tone7(22),
							val-Tone8(23),
							val-Silence1(32)
							}
		MAX-ACCESS		read-write
		STATUS			current
		DESCRIPTION
				"TYPE: - RadiobuttonList
				 PAGE: - Mixers1_3
					Src  cmdID= 40820 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Tone1  value= 16  
					Tone2  value= 17  
					Tone3  value= 18  
					Tone4  value= 19  
					Tone5  value= 20  
					Tone6  value= 21  
					Tone7  value= 22  
					Tone8  value= 23  
					Silence  value= 32  "
		::= { iqudc12CmdEntry 40820 }


	iqudc12Mixers13Source3Name OBJECT-TYPE
		SYNTAX		RollCallString
		MAX-ACCESS		read-only
		STATUS			current
		DESCRIPTION
				"TYPE: - Display
				 PAGE: - Mixers1_3
					Name  cmdID= 40828  format=   "
		::= { iqudc12CmdEntry 40828 }


	iqudc12MenuMixers13MixerLoRo OBJECT-TYPE
		SYNTAX		INTEGER {
							val-Custom(0),
							val-3dB-C-Ls-Rs(1),
							val-3dB-C-3dB-Ls-Rs(2),
							val-3dB-C-6dB-Ls-Rs(3),
							val-3dB-C-9dB-Ls-Rs(4)
							}
		MAX-ACCESS		read-write
		STATUS			current
		DESCRIPTION
				"TYPE: - RadiobuttonList
				 PAGE: - Mixers1_3
					MixerLoRo  cmdID= 40832 
					Custom  value= 0  
					-3dB C + Ls/Rs  value= 1  
					-3dB C -3dB Ls/Rs  value= 2  
					-3dB C -6dB Ls/Rs  value= 3  
					-3dB C -9dB Ls/Rs  value= 4  "
		::= { iqudc12CmdEntry 40832 }


	iqudc12Mixers46Source4ProcGain OBJECT-TYPE
		SYNTAX		INTEGER
		MAX-ACCESS		read-write
		STATUS			current
		DESCRIPTION
				"TYPE: - Number
				 PAGE: - Mixers4_6
					ProcGain  cmdID= 40803  min= -801  max= 120  step= 1  format= %0.1f dB  div_scale= 10 
					Min = -80.1 dB  Max = 12.0 dB  Step = 0.1 dB "
		::= { iqudc12CmdEntry 40803 }


	iqudc12Mixers46Source4Invert OBJECT-TYPE
		SYNTAX		INTEGER { disable(0), enable(1) }
		MAX-ACCESS		read-write
		STATUS			current
		DESCRIPTION
				"TYPE: - Checkbox
				 PAGE: - Mixers4_6
					Invert  cmdID= 40809 "
		::= { iqudc12CmdEntry 40809 }


	iqudc12Mixers46Source4Mute OBJECT-TYPE
		SYNTAX		INTEGER { disable(0), enable(1) }
		MAX-ACCESS		read-write
		STATUS			current
		DESCRIPTION
				"TYPE: - Checkbox
				 PAGE: - Mixers4_6
					Mute  cmdID= 40815 "
		::= { iqudc12CmdEntry 40815 }


	iqudc12Mixers46Source4Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Tone1(16),
							val-Tone2(17),
							val-Tone3(18),
							val-Tone4(19),
							val-Tone5(20),
							val-Tone6(21),
							val-Tone7(22),
							val-Tone8(23),
							val-Silence1(32)
							}
		MAX-ACCESS		read-write
		STATUS			current
		DESCRIPTION
				"TYPE: - RadiobuttonList
				 PAGE: - Mixers4_6
					Src  cmdID= 40821 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Tone1  value= 16  
					Tone2  value= 17  
					Tone3  value= 18  
					Tone4  value= 19  
					Tone5  value= 20  
					Tone6  value= 21  
					Tone7  value= 22  
					Tone8  value= 23  
					Silence  value= 32  "
		::= { iqudc12CmdEntry 40821 }


	iqudc12Mixers46Source4Name OBJECT-TYPE
		SYNTAX		RollCallString
		MAX-ACCESS		read-only
		STATUS			current
		DESCRIPTION
				"TYPE: - Display
				 PAGE: - Mixers4_6
					Name  cmdID= 40829  format=   "
		::= { iqudc12CmdEntry 40829 }


	iqudc12Mixers46Source5ProcGain OBJECT-TYPE
		SYNTAX		INTEGER
		MAX-ACCESS		read-write
		STATUS			current
		DESCRIPTION
				"TYPE: - Number
				 PAGE: - Mixers4_6
					ProcGain  cmdID= 40804  min= -801  max= 120  step= 1  format= %0.1f dB  div_scale= 10 
					Min = -80.1 dB  Max = 12.0 dB  Step = 0.1 dB "
		::= { iqudc12CmdEntry 40804 }


	iqudc12Mixers46Source5Invert OBJECT-TYPE
		SYNTAX		INTEGER { disable(0), enable(1) }
		MAX-ACCESS		read-write
		STATUS			current
		DESCRIPTION
				"TYPE: - Checkbox
				 PAGE: - Mixers4_6
					Invert  cmdID= 40810 "
		::= { iqudc12CmdEntry 40810 }


	iqudc12Mixers46Source5Mute OBJECT-TYPE
		SYNTAX		INTEGER { disable(0), enable(1) }
		MAX-ACCESS		read-write
		STATUS			current
		DESCRIPTION
				"TYPE: - Checkbox
				 PAGE: - Mixers4_6
					Mute  cmdID= 40816 "
		::= { iqudc12CmdEntry 40816 }


	iqudc12Mixers46Source5Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Tone1(16),
							val-Tone2(17),
							val-Tone3(18),
							val-Tone4(19),
							val-Tone5(20),
							val-Tone6(21),
							val-Tone7(22),
							val-Tone8(23),
							val-Silence1(32)
							}
		MAX-ACCESS		read-write
		STATUS			current
		DESCRIPTION
				"TYPE: - RadiobuttonList
				 PAGE: - Mixers4_6
					Src  cmdID= 40822 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Tone1  value= 16  
					Tone2  value= 17  
					Tone3  value= 18  
					Tone4  value= 19  
					Tone5  value= 20  
					Tone6  value= 21  
					Tone7  value= 22  
					Tone8  value= 23  
					Silence  value= 32  "
		::= { iqudc12CmdEntry 40822 }


	iqudc12Mixers46Source5Name OBJECT-TYPE
		SYNTAX		RollCallString
		MAX-ACCESS		read-only
		STATUS			current
		DESCRIPTION
				"TYPE: - Display
				 PAGE: - Mixers4_6
					Name  cmdID= 40830  format=   "
		::= { iqudc12CmdEntry 40830 }


	iqudc12Mixers46Source6ProcGain OBJECT-TYPE
		SYNTAX		INTEGER
		MAX-ACCESS		read-write
		STATUS			current
		DESCRIPTION
				"TYPE: - Number
				 PAGE: - Mixers4_6
					ProcGain  cmdID= 40805  min= -801  max= 120  step= 1  format= %0.1f dB  div_scale= 10 
					Min = -80.1 dB  Max = 12.0 dB  Step = 0.1 dB "
		::= { iqudc12CmdEntry 40805 }


	iqudc12Mixers46Source6Invert OBJECT-TYPE
		SYNTAX		INTEGER { disable(0), enable(1) }
		MAX-ACCESS		read-write
		STATUS			current
		DESCRIPTION
				"TYPE: - Checkbox
				 PAGE: - Mixers4_6
					Invert  cmdID= 40811 "
		::= { iqudc12CmdEntry 40811 }


	iqudc12Mixers46Source6Mute OBJECT-TYPE
		SYNTAX		INTEGER { disable(0), enable(1) }
		MAX-ACCESS		read-write
		STATUS			current
		DESCRIPTION
				"TYPE: - Checkbox
				 PAGE: - Mixers4_6
					Mute  cmdID= 40817 "
		::= { iqudc12CmdEntry 40817 }


	iqudc12Mixers46Source6Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Tone1(16),
							val-Tone2(17),
							val-Tone3(18),
							val-Tone4(19),
							val-Tone5(20),
							val-Tone6(21),
							val-Tone7(22),
							val-Tone8(23),
							val-Silence1(32)
							}
		MAX-ACCESS		read-write
		STATUS			current
		DESCRIPTION
				"TYPE: - RadiobuttonList
				 PAGE: - Mixers4_6
					Src  cmdID= 40823 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Tone1  value= 16  
					Tone2  value= 17  
					Tone3  value= 18  
					Tone4  value= 19  
					Tone5  value= 20  
					Tone6  value= 21  
					Tone7  value= 22  
					Tone8  value= 23  
					Silence  value= 32  "
		::= { iqudc12CmdEntry 40823 }


	iqudc12Mixers46Source6Name OBJECT-TYPE
		SYNTAX		RollCallString
		MAX-ACCESS		read-only
		STATUS			current
		DESCRIPTION
				"TYPE: - Display
				 PAGE: - Mixers4_6
					Name  cmdID= 40831  format=   "
		::= { iqudc12CmdEntry 40831 }


	iqudc12DolbyDecodeDolbyDecoderDetectMode OBJECT-TYPE
		SYNTAX		INTEGER {
							val-Auto(0),
							val-Dolby-E-or-Mute(1),
							val-Dolby-Digital-or-Mu(2),
							val-Mute(3)
							}
		MAX-ACCESS		read-write
		STATUS			current
		DESCRIPTION
				"TYPE: - RadiobuttonList
				 PAGE: - DolbyDecode
					Detect Mode  cmdID= 42401 
					Auto  value= 0  
					Dolby E or Mute  value= 1  
					Dolby Digital or Mu  value= 2  
					Mute  value= 3  "
		::= { iqudc12CmdEntry 42401 }


	iqudc12DolbyDecodeDolbyDecoderAESChannelSelect OBJECT-TYPE
		SYNTAX		INTEGER {
							val-Channel-1(0),
							val-Channel-2(1)
							}
		MAX-ACCESS		read-write
		STATUS			current
		DESCRIPTION
				"TYPE: - RadiobuttonList
				 PAGE: - DolbyDecode
					AES Channel Select  cmdID= 42402 
					Channel 1  value= 0  
					Channel 2  value= 1  "
		::= { iqudc12CmdEntry 42402 }


	iqudc12DolbyDecodeDolbyDecoderPCMLatency OBJECT-TYPE
		SYNTAX		INTEGER {
							val-Single-Video-Frame(0),
							val-Minimum(1)
							}
		MAX-ACCESS		read-write
		STATUS			current
		DESCRIPTION
				"TYPE: - RadiobuttonList
				 PAGE: - DolbyDecode
					PCM Latency  cmdID= 42403 
					Single Video Frame  value= 0  
					Minimum  value= 1  "
		::= { iqudc12CmdEntry 42403 }


	iqudc12DolbyDecodeDolbyDecoderListeningModeDolb OBJECT-TYPE
		SYNTAX		INTEGER {
							val-Full(0),
							val-EX(1),
							val-3-Stereo(2),
							val-Phantom(3),
							val-Stereo(4),
							val-Mono(5)
							}
		MAX-ACCESS		read-write
		STATUS			current
		DESCRIPTION
				"TYPE: - RadiobuttonList
				 PAGE: - DolbyDecode
					Listening Mode Dolb  cmdID= 42404 
					Full  value= 0  
					EX  value= 1  
					3 Stereo  value= 2  
					Phantom  value= 3  
					Stereo  value= 4  
					Mono  value= 5  "
		::= { iqudc12CmdEntry 42404 }


	iqudc12DolbyDecodeDolbyDecoderDynamicRange OBJECT-TYPE
		SYNTAX		INTEGER {
							val-Line-Mode(0),
							val-RF-Mode(1),
							val-Bypass-Mode(3)
							}
		MAX-ACCESS		read-write
		STATUS			current
		DESCRIPTION
				"TYPE: - RadiobuttonList
				 PAGE: - DolbyDecode
					Dynamic Range   cmdID= 42405 
					Line Mode  value= 0  
					RF Mode  value= 1  
					Bypass Mode  value= 3  "
		::= { iqudc12CmdEntry 42405 }


	iqudc12DolbyDecoderDownmixChannelProgramSelect OBJECT-TYPE
		SYNTAX		INTEGER {
							val-Program-1(0),
							val-Program-2(1),
							val-Program-3(2),
							val-Program-4(3),
							val-Program-5(4),
							val-Program-6(5),
							val-Program-7(6),
							val-Program-8(7)
							}
		MAX-ACCESS		read-write
		STATUS			current
		DESCRIPTION
				"TYPE: - RadiobuttonList
				 PAGE: - DolbyDecode
					Program Select  cmdID= 42406 
					Program 1  value= 0  
					Program 2  value= 1  
					Program 3  value= 2  
					Program 4  value= 3  
					Program 5  value= 4  
					Program 6  value= 5  
					Program 7  value= 6  
					Program 8  value= 7  "
		::= { iqudc12CmdEntry 42406 }


	iqudc12DolbyDecoderDownmixChannelDynamicRange OBJECT-TYPE
		SYNTAX		INTEGER {
							val-Line-Mode(0),
							val-RF-Mode(1)
							}
		MAX-ACCESS		read-write
		STATUS			current
		DESCRIPTION
				"TYPE: - RadiobuttonList
				 PAGE: - DolbyDecode
					Dynamic Range  cmdID= 42407 
					Line Mode  value= 0  
					RF Mode  value= 1  "
		::= { iqudc12CmdEntry 42407 }


	iqudc12DolbyDecoderDownmixChannelOutputMode OBJECT-TYPE
		SYNTAX		INTEGER {
							val-Lt-Rt(0),
							val-Lo-Ro(1),
							val-Mono(2),
							val-Mute(3)
							}
		MAX-ACCESS		read-write
		STATUS			current
		DESCRIPTION
				"TYPE: - RadiobuttonList
				 PAGE: - DolbyDecode
					Output Mode  cmdID= 42408 
					Lt/Rt  value= 0  
					Lo/Ro  value= 1  
					Mono  value= 2  
					Mute  value= 3  "
		::= { iqudc12CmdEntry 42408 }


	iqudc12DolbyDecoderDecoderStatusBitstreamFormat OBJECT-TYPE
		SYNTAX		RollCallString
		MAX-ACCESS		read-only
		STATUS			current
		DESCRIPTION
				"TYPE: - Display
				 PAGE: - DolbyDecode
					Bitstream Format  cmdID= 42409  format=   "
		::= { iqudc12CmdEntry 42409 }


	iqudc12DolbyDecoderDecoderStatusBitstreamStatus OBJECT-TYPE
		SYNTAX		RollCallString
		MAX-ACCESS		read-only
		STATUS			current
		DESCRIPTION
				"TYPE: - Display
				 PAGE: - DolbyDecode
					Bitstream Status  cmdID= 42410  format=   "
		::= { iqudc12CmdEntry 42410 }


	iqudc12DolbyDecoderDecoderStatusDCRCErrorCount OBJECT-TYPE
		SYNTAX		RollCallString
		MAX-ACCESS		read-only
		STATUS			current
		DESCRIPTION
				"TYPE: - Display
				 PAGE: - DolbyDecode
					D CRC Error Count  cmdID= 42505  format=   "
		::= { iqudc12CmdEntry 42505 }


	iqudc12DolbyDecoderDecoderStatusDCRCErrorTime OBJECT-TYPE
		SYNTAX		RollCallString
		MAX-ACCESS		read-only
		STATUS			current
		DESCRIPTION
				"TYPE: - Display
				 PAGE: - DolbyDecode
					D CRC Error Time  cmdID= 42504  format=   "
		::= { iqudc12CmdEntry 42504 }


	iqudc12DolbyDecoderDecoderStatusECRCErrorCount OBJECT-TYPE
		SYNTAX		RollCallString
		MAX-ACCESS		read-only
		STATUS			current
		DESCRIPTION
				"TYPE: - Display
				 PAGE: - DolbyDecode
					E CRC Error Count  cmdID= 42507  format=   "
		::= { iqudc12CmdEntry 42507 }


	iqudc12DolbyDecoderDecoderStatusECRCErrorTime OBJECT-TYPE
		SYNTAX		RollCallString
		MAX-ACCESS		read-only
		STATUS			current
		DESCRIPTION
				"TYPE: - Display
				 PAGE: - DolbyDecode
					E CRC Error Time  cmdID= 42506  format=   "
		::= { iqudc12CmdEntry 42506 }


	iqudc12DolbyDecoderDecoderStatusResetErrors OBJECT-TYPE
		SYNTAX		INTEGER { noAction(0),val-Reset-Errors(1) }
		MAX-ACCESS		read-write
		STATUS			current
		DESCRIPTION
				"TYPE: - Button
				 PAGE: - DolbyDecode
					Reset Errors  cmdID= 42502  value= 1  "
		::= { iqudc12CmdEntry 42502 }


	iqudc12DolbyDecoderDecoderStatusResetTime OBJECT-TYPE
		SYNTAX		RollCallString
		MAX-ACCESS		read-only
		STATUS			current
		DESCRIPTION
				"TYPE: - Display
				 PAGE: - DolbyDecode
					Reset Time  cmdID= 42503  format=   "
		::= { iqudc12CmdEntry 42503 }


	iqudc12DolbyDecoderOutpuA1A2A1Gain OBJECT-TYPE
		SYNTAX		INTEGER
		MAX-ACCESS		read-write
		STATUS			current
		DESCRIPTION
				"TYPE: - Number
				 PAGE: - DolbyDecode
					A1 Gain  cmdID= 42558  min= -801  max= 120  step= 1  format= %0.1f dB  div_scale= 10 
					Min = -80.1 dB  Max = 12.0 dB  Step = 0.1 dB "
		::= { iqudc12CmdEntry 42558 }


	iqudc12DolbyDecoderOutpuA1A2A2Gain OBJECT-TYPE
		SYNTAX		INTEGER
		MAX-ACCESS		read-write
		STATUS			current
		DESCRIPTION
				"TYPE: - Number
				 PAGE: - DolbyDecode
					A2 Gain  cmdID= 42559  min= -801  max= 120  step= 1  format= %0.1f dB  div_scale= 10 
					Min = -80.1 dB  Max = 12.0 dB  Step = 0.1 dB "
		::= { iqudc12CmdEntry 42559 }


	iqudc12DolbyDecoderOutpuA1A2MuteA1 OBJECT-TYPE
		SYNTAX		INTEGER { disable(0), enable(1) }
		MAX-ACCESS		read-write
		STATUS			current
		DESCRIPTION
				"TYPE: - Checkbox
				 PAGE: - DolbyDecode
					Mute A1  cmdID= 42568 "
		::= { iqudc12CmdEntry 42568 }


	iqudc12DolbyDecoderOutpuA1A2MuteA2 OBJECT-TYPE
		SYNTAX		INTEGER { disable(0), enable(1) }
		MAX-ACCESS		read-write
		STATUS			current
		DESCRIPTION
				"TYPE: - Checkbox
				 PAGE: - DolbyDecode
					Mute A2  cmdID= 42569 "
		::= { iqudc12CmdEntry 42569 }


	iqudc12DolbyDecoderOutpuA1A2StereoA OBJECT-TYPE
		SYNTAX		INTEGER { disable(0), enable(1) }
		MAX-ACCESS		read-write
		STATUS			current
		DESCRIPTION
				"TYPE: - Checkbox
				 PAGE: - DolbyDecode
					Stereo A  cmdID= 42578 "
		::= { iqudc12CmdEntry 42578 }


	iqudc12DolbyDecoderOutpuB3B4B3Gain OBJECT-TYPE
		SYNTAX		INTEGER
		MAX-ACCESS		read-write
		STATUS			current
		DESCRIPTION
				"TYPE: - Number
				 PAGE: - DolbyDecode
					B3 Gain  cmdID= 42560  min= -801  max= 120  step= 1  format= %0.1f dB  div_scale= 10 
					Min = -80.1 dB  Max = 12.0 dB  Step = 0.1 dB "
		::= { iqudc12CmdEntry 42560 }


	iqudc12DolbyDecoderOutpuB3B4B4Gain OBJECT-TYPE
		SYNTAX		INTEGER
		MAX-ACCESS		read-write
		STATUS			current
		DESCRIPTION
				"TYPE: - Number
				 PAGE: - DolbyDecode
					B4 Gain  cmdID= 42561  min= -801  max= 120  step= 1  format= %0.1f dB  div_scale= 10 
					Min = -80.1 dB  Max = 12.0 dB  Step = 0.1 dB "
		::= { iqudc12CmdEntry 42561 }


	iqudc12DolbyDecoderOutpuB3B4MuteB3 OBJECT-TYPE
		SYNTAX		INTEGER { disable(0), enable(1) }
		MAX-ACCESS		read-write
		STATUS			current
		DESCRIPTION
				"TYPE: - Checkbox
				 PAGE: - DolbyDecode
					Mute B3  cmdID= 42570 "
		::= { iqudc12CmdEntry 42570 }


	iqudc12DolbyDecoderOutpuB3B4MuteB4 OBJECT-TYPE
		SYNTAX		INTEGER { disable(0), enable(1) }
		MAX-ACCESS		read-write
		STATUS			current
		DESCRIPTION
				"TYPE: - Checkbox
				 PAGE: - DolbyDecode
					Mute B4  cmdID= 42571 "
		::= { iqudc12CmdEntry 42571 }


	iqudc12DolbyDecoderOutpuB3B4StereoB OBJECT-TYPE
		SYNTAX		INTEGER { disable(0), enable(1) }
		MAX-ACCESS		read-write
		STATUS			current
		DESCRIPTION
				"TYPE: - Checkbox
				 PAGE: - DolbyDecode
					Stereo B  cmdID= 42579 "
		::= { iqudc12CmdEntry 42579 }


	iqudc12DolbyDecoderOutpuC5C6C5Gain OBJECT-TYPE
		SYNTAX		INTEGER
		MAX-ACCESS		read-write
		STATUS			current
		DESCRIPTION
				"TYPE: - Number
				 PAGE: - DolbyDecode
					C5 Gain  cmdID= 42562  min= -801  max= 120  step= 1  format= %0.1f dB  div_scale= 10 
					Min = -80.1 dB  Max = 12.0 dB  Step = 0.1 dB "
		::= { iqudc12CmdEntry 42562 }


	iqudc12DolbyDecoderOutpuC5C6C6Gain OBJECT-TYPE
		SYNTAX		INTEGER
		MAX-ACCESS		read-write
		STATUS			current
		DESCRIPTION
				"TYPE: - Number
				 PAGE: - DolbyDecode
					C6 Gain  cmdID= 42563  min= -801  max= 120  step= 1  format= %0.1f dB  div_scale= 10 
					Min = -80.1 dB  Max = 12.0 dB  Step = 0.1 dB "
		::= { iqudc12CmdEntry 42563 }


	iqudc12DolbyDecoderOutpuC5C6MuteC5 OBJECT-TYPE
		SYNTAX		INTEGER { disable(0), enable(1) }
		MAX-ACCESS		read-write
		STATUS			current
		DESCRIPTION
				"TYPE: - Checkbox
				 PAGE: - DolbyDecode
					Mute C5  cmdID= 42572 "
		::= { iqudc12CmdEntry 42572 }


	iqudc12DolbyDecoderOutpuC5C6MuteC6 OBJECT-TYPE
		SYNTAX		INTEGER { disable(0), enable(1) }
		MAX-ACCESS		read-write
		STATUS			current
		DESCRIPTION
				"TYPE: - Checkbox
				 PAGE: - DolbyDecode
					Mute C6  cmdID= 42573 "
		::= { iqudc12CmdEntry 42573 }


	iqudc12DolbyDecoderOutpuC5C6StereoC OBJECT-TYPE
		SYNTAX		INTEGER { disable(0), enable(1) }
		MAX-ACCESS		read-write
		STATUS			current
		DESCRIPTION
				"TYPE: - Checkbox
				 PAGE: - DolbyDecode
					Stereo C  cmdID= 42580 "
		::= { iqudc12CmdEntry 42580 }


	iqudc12DolbyDecoderOutpuD7D8D7Gain OBJECT-TYPE
		SYNTAX		INTEGER
		MAX-ACCESS		read-write
		STATUS			current
		DESCRIPTION
				"TYPE: - Number
				 PAGE: - DolbyDecode
					D7 Gain  cmdID= 42564  min= -801  max= 120  step= 1  format= %0.1f dB  div_scale= 10 
					Min = -80.1 dB  Max = 12.0 dB  Step = 0.1 dB "
		::= { iqudc12CmdEntry 42564 }


	iqudc12DolbyDecoderOutpuD7D8D8Gain OBJECT-TYPE
		SYNTAX		INTEGER
		MAX-ACCESS		read-write
		STATUS			current
		DESCRIPTION
				"TYPE: - Number
				 PAGE: - DolbyDecode
					D8 Gain  cmdID= 42565  min= -801  max= 120  step= 1  format= %0.1f dB  div_scale= 10 
					Min = -80.1 dB  Max = 12.0 dB  Step = 0.1 dB "
		::= { iqudc12CmdEntry 42565 }


	iqudc12DolbyDecoderOutpuD7D8MuteD7 OBJECT-TYPE
		SYNTAX		INTEGER { disable(0), enable(1) }
		MAX-ACCESS		read-write
		STATUS			current
		DESCRIPTION
				"TYPE: - Checkbox
				 PAGE: - DolbyDecode
					Mute D7  cmdID= 42574 "
		::= { iqudc12CmdEntry 42574 }


	iqudc12DolbyDecoderOutpuD7D8MuteD8 OBJECT-TYPE
		SYNTAX		INTEGER { disable(0), enable(1) }
		MAX-ACCESS		read-write
		STATUS			current
		DESCRIPTION
				"TYPE: - Checkbox
				 PAGE: - DolbyDecode
					Mute D8  cmdID= 42575 "
		::= { iqudc12CmdEntry 42575 }


	iqudc12DolbyDecoderOutpuD7D8StereoD OBJECT-TYPE
		SYNTAX		INTEGER { disable(0), enable(1) }
		MAX-ACCESS		read-write
		STATUS			current
		DESCRIPTION
				"TYPE: - Checkbox
				 PAGE: - DolbyDecode
					Stereo D  cmdID= 42581 "
		::= { iqudc12CmdEntry 42581 }


	iqudc12DolbyDecoderOutpuMLMRMLGain OBJECT-TYPE
		SYNTAX		INTEGER
		MAX-ACCESS		read-write
		STATUS			current
		DESCRIPTION
				"TYPE: - Number
				 PAGE: - DolbyDecode
					ML Gain  cmdID= 42566  min= -801  max= 120  step= 1  format= %0.1f dB  div_scale= 10 
					Min = -80.1 dB  Max = 12.0 dB  Step = 0.1 dB "
		::= { iqudc12CmdEntry 42566 }


	iqudc12DolbyDecoderOutpuMLMRMRGain OBJECT-TYPE
		SYNTAX		INTEGER
		MAX-ACCESS		read-write
		STATUS			current
		DESCRIPTION
				"TYPE: - Number
				 PAGE: - DolbyDecode
					MR Gain  cmdID= 42567  min= -801  max= 120  step= 1  format= %0.1f dB  div_scale= 10 
					Min = -80.1 dB  Max = 12.0 dB  Step = 0.1 dB "
		::= { iqudc12CmdEntry 42567 }


	iqudc12DolbyDecoderOutpuMLMRMuteML OBJECT-TYPE
		SYNTAX		INTEGER { disable(0), enable(1) }
		MAX-ACCESS		read-write
		STATUS			current
		DESCRIPTION
				"TYPE: - Checkbox
				 PAGE: - DolbyDecode
					Mute ML  cmdID= 42576 "
		::= { iqudc12CmdEntry 42576 }


	iqudc12DolbyDecoderOutpuMLMRMuteMR OBJECT-TYPE
		SYNTAX		INTEGER { disable(0), enable(1) }
		MAX-ACCESS		read-write
		STATUS			current
		DESCRIPTION
				"TYPE: - Checkbox
				 PAGE: - DolbyDecode
					Mute MR  cmdID= 42577 "
		::= { iqudc12CmdEntry 42577 }


	iqudc12DolbyDecoderOutpuMLMRStereoM OBJECT-TYPE
		SYNTAX		INTEGER { disable(0), enable(1) }
		MAX-ACCESS		read-write
		STATUS			current
		DESCRIPTION
				"TYPE: - Checkbox
				 PAGE: - DolbyDecode
					Stereo M  cmdID= 42582 "
		::= { iqudc12CmdEntry 42582 }


	iqudc12DolbyDecodeDolbyDecoderOutpuMasterGain OBJECT-TYPE
		SYNTAX		INTEGER
		MAX-ACCESS		read-write
		STATUS			current
		DESCRIPTION
				"TYPE: - Number
				 PAGE: - DolbyDecode
					Master Gain  cmdID= 42556  min= -801  max= 120  step= 1  format= %0.1f dB  div_scale= 10 
					Min = -80.1 dB  Max = 12.0 dB  Step = 0.1 dB "
		::= { iqudc12CmdEntry 42556 }


	iqudc12DolbyDecodeDolbyDecoderOutpuMasterMute OBJECT-TYPE
		SYNTAX		INTEGER { disable(0), enable(1) }
		MAX-ACCESS		read-write
		STATUS			current
		DESCRIPTION
				"TYPE: - Checkbox
				 PAGE: - DolbyDecode
					Master Mute  cmdID= 42557 "
		::= { iqudc12CmdEntry 42557 }


	iqudc12MenuDolbyDecodeHideDecoder OBJECT-TYPE
		SYNTAX		RollCallString
		MAX-ACCESS		read-only
		STATUS			current
		DESCRIPTION
				"TYPE: - Display
				 PAGE: - DolbyDecode
					Hide Decoder  cmdID= 42585  format=   "
		::= { iqudc12CmdEntry 42585 }


	iqudc12DolbyEncInp14Source1ProcGain OBJECT-TYPE
		SYNTAX		INTEGER
		MAX-ACCESS		read-write
		STATUS			current
		DESCRIPTION
				"TYPE: - Number
				 PAGE: - Dolby Enc Inp1_4
					ProcGain  cmdID= 42520  min= -801  max= 120  step= 1  format= %0.1f dB  div_scale= 10 
					Min = -80.1 dB  Max = 12.0 dB  Step = 0.1 dB "
		::= { iqudc12CmdEntry 42520 }


	iqudc12DolbyEncInp14Source1Mute OBJECT-TYPE
		SYNTAX		INTEGER { disable(0), enable(1) }
		MAX-ACCESS		read-write
		STATUS			current
		DESCRIPTION
				"TYPE: - Checkbox
				 PAGE: - Dolby Enc Inp1_4
					Mute  cmdID= 42528 "
		::= { iqudc12CmdEntry 42528 }


	iqudc12DolbyEncInp14Source1Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAcc1-1(24),
							val-LinAcc1-2(25),
							val-LinAcc2-1(26),
							val-LinAcc2-2(27),
							val-LinAcc3-1(28),
							val-LinAcc3-2(29),
							val-LinAcc4-1(30),
							val-LinAcc4-2(31)
							}
		MAX-ACCESS		read-write
		STATUS			current
		DESCRIPTION
				"TYPE: - RadiobuttonList
				 PAGE: - Dolby Enc Inp1_4
					Src  cmdID= 42536 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAcc1_1  value= 24  
					LinAcc1_2  value= 25  
					LinAcc2_1  value= 26  
					LinAcc2_2  value= 27  
					LinAcc3_1  value= 28  
					LinAcc3_2  value= 29  
					LinAcc4_1  value= 30  
					LinAcc4_2  value= 31  "
		::= { iqudc12CmdEntry 42536 }


	iqudc12DolbyEncInp14Source2ProcGain OBJECT-TYPE
		SYNTAX		INTEGER
		MAX-ACCESS		read-write
		STATUS			current
		DESCRIPTION
				"TYPE: - Number
				 PAGE: - Dolby Enc Inp1_4
					ProcGain  cmdID= 42521  min= -801  max= 120  step= 1  format= %0.1f dB  div_scale= 10 
					Min = -80.1 dB  Max = 12.0 dB  Step = 0.1 dB "
		::= { iqudc12CmdEntry 42521 }


	iqudc12DolbyEncInp14Source2Mute OBJECT-TYPE
		SYNTAX		INTEGER { disable(0), enable(1) }
		MAX-ACCESS		read-write
		STATUS			current
		DESCRIPTION
				"TYPE: - Checkbox
				 PAGE: - Dolby Enc Inp1_4
					Mute  cmdID= 42529 "
		::= { iqudc12CmdEntry 42529 }


	iqudc12DolbyEncInp14Source2Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAcc1-1(24),
							val-LinAcc1-2(25),
							val-LinAcc2-1(26),
							val-LinAcc2-2(27),
							val-LinAcc3-1(28),
							val-LinAcc3-2(29),
							val-LinAcc4-1(30),
							val-LinAcc4-2(31)
							}
		MAX-ACCESS		read-write
		STATUS			current
		DESCRIPTION
				"TYPE: - RadiobuttonList
				 PAGE: - Dolby Enc Inp1_4
					Src  cmdID= 42537 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAcc1_1  value= 24  
					LinAcc1_2  value= 25  
					LinAcc2_1  value= 26  
					LinAcc2_2  value= 27  
					LinAcc3_1  value= 28  
					LinAcc3_2  value= 29  
					LinAcc4_1  value= 30  
					LinAcc4_2  value= 31  "
		::= { iqudc12CmdEntry 42537 }


	iqudc12DolbyEncInp14Source3ProcGain OBJECT-TYPE
		SYNTAX		INTEGER
		MAX-ACCESS		read-write
		STATUS			current
		DESCRIPTION
				"TYPE: - Number
				 PAGE: - Dolby Enc Inp1_4
					ProcGain  cmdID= 42522  min= -801  max= 120  step= 1  format= %0.1f dB  div_scale= 10 
					Min = -80.1 dB  Max = 12.0 dB  Step = 0.1 dB "
		::= { iqudc12CmdEntry 42522 }


	iqudc12DolbyEncInp14Source3Mute OBJECT-TYPE
		SYNTAX		INTEGER { disable(0), enable(1) }
		MAX-ACCESS		read-write
		STATUS			current
		DESCRIPTION
				"TYPE: - Checkbox
				 PAGE: - Dolby Enc Inp1_4
					Mute  cmdID= 42530 "
		::= { iqudc12CmdEntry 42530 }


	iqudc12DolbyEncInp14Source3Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAcc1-1(24),
							val-LinAcc1-2(25),
							val-LinAcc2-1(26),
							val-LinAcc2-2(27),
							val-LinAcc3-1(28),
							val-LinAcc3-2(29),
							val-LinAcc4-1(30),
							val-LinAcc4-2(31)
							}
		MAX-ACCESS		read-write
		STATUS			current
		DESCRIPTION
				"TYPE: - RadiobuttonList
				 PAGE: - Dolby Enc Inp1_4
					Src  cmdID= 42538 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAcc1_1  value= 24  
					LinAcc1_2  value= 25  
					LinAcc2_1  value= 26  
					LinAcc2_2  value= 27  
					LinAcc3_1  value= 28  
					LinAcc3_2  value= 29  
					LinAcc4_1  value= 30  
					LinAcc4_2  value= 31  "
		::= { iqudc12CmdEntry 42538 }


	iqudc12DolbyEncInp14Source4ProcGain OBJECT-TYPE
		SYNTAX		INTEGER
		MAX-ACCESS		read-write
		STATUS			current
		DESCRIPTION
				"TYPE: - Number
				 PAGE: - Dolby Enc Inp1_4
					ProcGain  cmdID= 42523  min= -801  max= 120  step= 1  format= %0.1f dB  div_scale= 10 
					Min = -80.1 dB  Max = 12.0 dB  Step = 0.1 dB "
		::= { iqudc12CmdEntry 42523 }


	iqudc12DolbyEncInp14Source4Mute OBJECT-TYPE
		SYNTAX		INTEGER { disable(0), enable(1) }
		MAX-ACCESS		read-write
		STATUS			current
		DESCRIPTION
				"TYPE: - Checkbox
				 PAGE: - Dolby Enc Inp1_4
					Mute  cmdID= 42531 "
		::= { iqudc12CmdEntry 42531 }


	iqudc12DolbyEncInp14Source4Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAcc1-1(24),
							val-LinAcc1-2(25),
							val-LinAcc2-1(26),
							val-LinAcc2-2(27),
							val-LinAcc3-1(28),
							val-LinAcc3-2(29),
							val-LinAcc4-1(30),
							val-LinAcc4-2(31)
							}
		MAX-ACCESS		read-write
		STATUS			current
		DESCRIPTION
				"TYPE: - RadiobuttonList
				 PAGE: - Dolby Enc Inp1_4
					Src  cmdID= 42539 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAcc1_1  value= 24  
					LinAcc1_2  value= 25  
					LinAcc2_1  value= 26  
					LinAcc2_2  value= 27  
					LinAcc3_1  value= 28  
					LinAcc3_2  value= 29  
					LinAcc4_1  value= 30  
					LinAcc4_2  value= 31  "
		::= { iqudc12CmdEntry 42539 }


	iqudc12DolbyEncInp58Source5ProcGain OBJECT-TYPE
		SYNTAX		INTEGER
		MAX-ACCESS		read-write
		STATUS			current
		DESCRIPTION
				"TYPE: - Number
				 PAGE: - Dolby Enc Inp5_8
					ProcGain  cmdID= 42524  min= -801  max= 120  step= 1  format= %0.1f dB  div_scale= 10 
					Min = -80.1 dB  Max = 12.0 dB  Step = 0.1 dB "
		::= { iqudc12CmdEntry 42524 }


	iqudc12DolbyEncInp58Source5Mute OBJECT-TYPE
		SYNTAX		INTEGER { disable(0), enable(1) }
		MAX-ACCESS		read-write
		STATUS			current
		DESCRIPTION
				"TYPE: - Checkbox
				 PAGE: - Dolby Enc Inp5_8
					Mute  cmdID= 42532 "
		::= { iqudc12CmdEntry 42532 }


	iqudc12DolbyEncInp58Source5Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAcc1-1(24),
							val-LinAcc1-2(25),
							val-LinAcc2-1(26),
							val-LinAcc2-2(27),
							val-LinAcc3-1(28),
							val-LinAcc3-2(29),
							val-LinAcc4-1(30),
							val-LinAcc4-2(31)
							}
		MAX-ACCESS		read-write
		STATUS			current
		DESCRIPTION
				"TYPE: - RadiobuttonList
				 PAGE: - Dolby Enc Inp5_8
					Src  cmdID= 42540 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAcc1_1  value= 24  
					LinAcc1_2  value= 25  
					LinAcc2_1  value= 26  
					LinAcc2_2  value= 27  
					LinAcc3_1  value= 28  
					LinAcc3_2  value= 29  
					LinAcc4_1  value= 30  
					LinAcc4_2  value= 31  "
		::= { iqudc12CmdEntry 42540 }


	iqudc12DolbyEncInp58Source6ProcGain OBJECT-TYPE
		SYNTAX		INTEGER
		MAX-ACCESS		read-write
		STATUS			current
		DESCRIPTION
				"TYPE: - Number
				 PAGE: - Dolby Enc Inp5_8
					ProcGain  cmdID= 42525  min= -801  max= 120  step= 1  format= %0.1f dB  div_scale= 10 
					Min = -80.1 dB  Max = 12.0 dB  Step = 0.1 dB "
		::= { iqudc12CmdEntry 42525 }


	iqudc12DolbyEncInp58Source6Mute OBJECT-TYPE
		SYNTAX		INTEGER { disable(0), enable(1) }
		MAX-ACCESS		read-write
		STATUS			current
		DESCRIPTION
				"TYPE: - Checkbox
				 PAGE: - Dolby Enc Inp5_8
					Mute  cmdID= 42533 "
		::= { iqudc12CmdEntry 42533 }


	iqudc12DolbyEncInp58Source6Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAcc1-1(24),
							val-LinAcc1-2(25),
							val-LinAcc2-1(26),
							val-LinAcc2-2(27),
							val-LinAcc3-1(28),
							val-LinAcc3-2(29),
							val-LinAcc4-1(30),
							val-LinAcc4-2(31)
							}
		MAX-ACCESS		read-write
		STATUS			current
		DESCRIPTION
				"TYPE: - RadiobuttonList
				 PAGE: - Dolby Enc Inp5_8
					Src  cmdID= 42541 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAcc1_1  value= 24  
					LinAcc1_2  value= 25  
					LinAcc2_1  value= 26  
					LinAcc2_2  value= 27  
					LinAcc3_1  value= 28  
					LinAcc3_2  value= 29  
					LinAcc4_1  value= 30  
					LinAcc4_2  value= 31  "
		::= { iqudc12CmdEntry 42541 }


	iqudc12DolbyEncInp58Source7ProcGain OBJECT-TYPE
		SYNTAX		INTEGER
		MAX-ACCESS		read-write
		STATUS			current
		DESCRIPTION
				"TYPE: - Number
				 PAGE: - Dolby Enc Inp5_8
					ProcGain  cmdID= 42526  min= -801  max= 120  step= 1  format= %0.1f dB  div_scale= 10 
					Min = -80.1 dB  Max = 12.0 dB  Step = 0.1 dB "
		::= { iqudc12CmdEntry 42526 }


	iqudc12DolbyEncInp58Source7Mute OBJECT-TYPE
		SYNTAX		INTEGER { disable(0), enable(1) }
		MAX-ACCESS		read-write
		STATUS			current
		DESCRIPTION
				"TYPE: - Checkbox
				 PAGE: - Dolby Enc Inp5_8
					Mute  cmdID= 42534 "
		::= { iqudc12CmdEntry 42534 }


	iqudc12DolbyEncInp58Source7Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAcc1-1(24),
							val-LinAcc1-2(25),
							val-LinAcc2-1(26),
							val-LinAcc2-2(27),
							val-LinAcc3-1(28),
							val-LinAcc3-2(29),
							val-LinAcc4-1(30),
							val-LinAcc4-2(31)
							}
		MAX-ACCESS		read-write
		STATUS			current
		DESCRIPTION
				"TYPE: - RadiobuttonList
				 PAGE: - Dolby Enc Inp5_8
					Src  cmdID= 42542 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAcc1_1  value= 24  
					LinAcc1_2  value= 25  
					LinAcc2_1  value= 26  
					LinAcc2_2  value= 27  
					LinAcc3_1  value= 28  
					LinAcc3_2  value= 29  
					LinAcc4_1  value= 30  
					LinAcc4_2  value= 31  "
		::= { iqudc12CmdEntry 42542 }


	iqudc12DolbyEncInp58Source8ProcGain OBJECT-TYPE
		SYNTAX		INTEGER
		MAX-ACCESS		read-write
		STATUS			current
		DESCRIPTION
				"TYPE: - Number
				 PAGE: - Dolby Enc Inp5_8
					ProcGain  cmdID= 42527  min= -801  max= 120  step= 1  format= %0.1f dB  div_scale= 10 
					Min = -80.1 dB  Max = 12.0 dB  Step = 0.1 dB "
		::= { iqudc12CmdEntry 42527 }


	iqudc12DolbyEncInp58Source8Mute OBJECT-TYPE
		SYNTAX		INTEGER { disable(0), enable(1) }
		MAX-ACCESS		read-write
		STATUS			current
		DESCRIPTION
				"TYPE: - Checkbox
				 PAGE: - Dolby Enc Inp5_8
					Mute  cmdID= 42535 "
		::= { iqudc12CmdEntry 42535 }


	iqudc12DolbyEncInp58Source8Src OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAcc1-1(24),
							val-LinAcc1-2(25),
							val-LinAcc2-1(26),
							val-LinAcc2-2(27),
							val-LinAcc3-1(28),
							val-LinAcc3-2(29),
							val-LinAcc4-1(30),
							val-LinAcc4-2(31)
							}
		MAX-ACCESS		read-write
		STATUS			current
		DESCRIPTION
				"TYPE: - RadiobuttonList
				 PAGE: - Dolby Enc Inp5_8
					Src  cmdID= 42543 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAcc1_1  value= 24  
					LinAcc1_2  value= 25  
					LinAcc2_1  value= 26  
					LinAcc2_2  value= 27  
					LinAcc3_1  value= 28  
					LinAcc3_2  value= 29  
					LinAcc4_1  value= 30  
					LinAcc4_2  value= 31  "
		::= { iqudc12CmdEntry 42543 }


	iqudc12DolbyControlDolbyEncoderContrSampleRateConvers OBJECT-TYPE
		SYNTAX		INTEGER {
							val-Enabled(0),
							val-Disabled(1)
							}
		MAX-ACCESS		read-write
		STATUS			current
		DESCRIPTION
				"TYPE: - RadiobuttonList
				 PAGE: - DolbyControl
					Sample Rate Convers  cmdID= 42451 
					Enabled  value= 0  
					Disabled  value= 1  "
		::= { iqudc12CmdEntry 42451 }


	iqudc12DolbyControlDolbyEncoderContrMetaRevertMode OBJECT-TYPE
		SYNTAX		INTEGER {
							val-Last-used(0),
							val-Internal(1)
							}
		MAX-ACCESS		read-write
		STATUS			current
		DESCRIPTION
				"TYPE: - RadiobuttonList
				 PAGE: - DolbyControl
					Meta Revert Mode  cmdID= 42452 
					Last used  value= 0  
					Internal  value= 1  "
		::= { iqudc12CmdEntry 42452 }


	iqudc12DolbyControlDolbyEncoderContrEncodingMode OBJECT-TYPE
		SYNTAX		INTEGER {
							val-Encode(0),
							val-Pass-Through(1)
							}
		MAX-ACCESS		read-write
		STATUS			current
		DESCRIPTION
				"TYPE: - RadiobuttonList
				 PAGE: - DolbyControl
					Encoding Mode  cmdID= 42450 
					Encode  value= 0  
					Pass Through  value= 1  "
		::= { iqudc12CmdEntry 42450 }


	iqudc12DolbyControlDolbyEEncoderCntBitDepth OBJECT-TYPE
		SYNTAX		INTEGER {
							val-20-bit(0),
							val-16-bit(1)
							}
		MAX-ACCESS		read-write
		STATUS			current
		DESCRIPTION
				"TYPE: - RadiobuttonList
				 PAGE: - DolbyControl
					Bit Depth  cmdID= 42453 
					20 bit  value= 0  
					16 bit  value= 1  "
		::= { iqudc12CmdEntry 42453 }


	iqudc12DolbyControlDolbyEEncoderCntMetadataSource OBJECT-TYPE
		SYNTAX		INTEGER {
							val-External(0),
							val-Internal(1)
							}
		MAX-ACCESS		read-write
		STATUS			current
		DESCRIPTION
				"TYPE: - RadiobuttonList
				 PAGE: - DolbyControl
					Metadata Source  cmdID= 42456 
					External  value= 0  
					Internal  value= 1  "
		::= { iqudc12CmdEntry 42456 }


	iqudc12DolbyControlDolbyEEncoderCntInternalConfig OBJECT-TYPE
		SYNTAX		INTEGER {
							val-5-1-2(0),
							val-5-1-2x1(1),
							val-4-4(2),
							val-4-2x2(3),
							val-4-2-2x1(4),
							val-4-4x1(5),
							val-4x2(6),
							val-3x2-2x1(7),
							val-2x2-4x1(8),
							val-2-6x1(9),
							val-8x1(10),
							val-5-1(11),
							val-4-2(12),
							val-4-2x1(13),
							val-3x2(14),
							val-2x2-2x1(15),
							val-2-4x1(16),
							val-6x1(17),
							val-4(18),
							val-2-2(19),
							val-2-2x1(20),
							val-4x1(21),
							val-7-1(22),
							val-7-1-Screen(23)
							}
		MAX-ACCESS		read-write
		STATUS			current
		DESCRIPTION
				"TYPE: - RadiobuttonList
				 PAGE: - DolbyControl
					Internal Config  cmdID= 42455 
					5.1+2  value= 0  
					5.1+2x1  value= 1  
					4+4  value= 2  
					4+2x2  value= 3  
					4+2+2x1  value= 4  
					4+4x1  value= 5  
					4x2  value= 6  
					3x2+2x1  value= 7  
					2x2+4x1  value= 8  
					2+6x1  value= 9  
					8x1  value= 10  
					5.1  value= 11  
					4+2  value= 12  
					4+2x1  value= 13  
					3x2  value= 14  
					2x2+2x1  value= 15  
					2+4x1  value= 16  
					6x1  value= 17  
					4  value= 18  
					2+2  value= 19  
					2+2x1  value= 20  
					4x1  value= 21  
					7.1  value= 22  
					7.1 Screen  value= 23  "
		::= { iqudc12CmdEntry 42455 }


	iqudc12DolbyControlDolbyEEncoderCntDefaultAllMeta OBJECT-TYPE
		SYNTAX		INTEGER { noAction(0),val-Default-All-Meta(3) }
		MAX-ACCESS		read-write
		STATUS			current
		DESCRIPTION
				"TYPE: - Button
				 PAGE: - DolbyControl
					Default All Meta  cmdID= 42514  value= 3  "
		::= { iqudc12CmdEntry 42514 }


	iqudc12DolbyControlDolbyIntMetaCntrCopyExtMetadata OBJECT-TYPE
		SYNTAX		INTEGER { noAction(0),val-Copy-Ext-Metadata(1) }
		MAX-ACCESS		read-write
		STATUS			current
		DESCRIPTION
				"TYPE: - Button
				 PAGE: - DolbyControl
					Copy Ext Metadata  cmdID= 42512  value= 1  "
		::= { iqudc12CmdEntry 42512 }


	iqudc12DolbyControlDolbyIntMetaCntrDefaultProgramMet OBJECT-TYPE
		SYNTAX		INTEGER { noAction(0),val-Default-Program-Met(2) }
		MAX-ACCESS		read-write
		STATUS			current
		DESCRIPTION
				"TYPE: - Button
				 PAGE: - DolbyControl
					Default Program Met  cmdID= 42513  value= 2  "
		::= { iqudc12CmdEntry 42513 }


	iqudc12DolbyControlDolbyIntMetaCntrDialogueNorm OBJECT-TYPE
		SYNTAX		INTEGER
		MAX-ACCESS		read-write
		STATUS			current
		DESCRIPTION
				"TYPE: - Number
				 PAGE: - DolbyControl
					Dialogue Norm  cmdID= 42468  min= -31  max= -1  step= 1  format= %0.0f dBFS  div_scale= 1 
					Min = -31 dBFS  Max = -1 dBFS  Step = 1 dBFS "
		::= { iqudc12CmdEntry 42468 }


	iqudc12DolbyControlDolbyIntMetaCntrChannelMode OBJECT-TYPE
		SYNTAX		INTEGER {
							val-1-0-C(1),
							val-2-0-L-R(2),
							val-3-0-L-C-R(3),
							val-2-1-L-R-S(4),
							val-3-1-L-C-R-S(5),
							val-2-2-L-R-SL-SR(6),
							val-3-2-L-C-R-SL-SR(7)
							}
		MAX-ACCESS		read-write
		STATUS			current
		DESCRIPTION
				"TYPE: - RadiobuttonList
				 PAGE: - DolbyControl
					Channel Mode  cmdID= 42461 
					1/0 (C)  value= 1  
					2/0 (L R)  value= 2  
					3/0 (L C R)  value= 3  
					2/1 (L R S)  value= 4  
					3/1 (L C R S)  value= 5  
					2/2 (L R SL SR)  value= 6  
					3/2 (L C R SL SR)  value= 7  "
		::= { iqudc12CmdEntry 42461 }


	iqudc12DolbyControlDolbyIntMetaCntrLFEChannel OBJECT-TYPE
		SYNTAX		INTEGER { disable(0), enable(1) }
		MAX-ACCESS		read-write
		STATUS			current
		DESCRIPTION
				"TYPE: - Checkbox
				 PAGE: - DolbyControl
					LFE Channel  cmdID= 42467 "
		::= { iqudc12CmdEntry 42467 }


	iqudc12DolbyControlDolbyIntMetaCntrBitstreamMode OBJECT-TYPE
		SYNTAX		INTEGER {
							val-Complete-Main(0),
							val-Music-Effects(1),
							val-Visually-Impaired(2),
							val-Hearing-Impaired(3),
							val-Dialogue(4),
							val-Commentary(5),
							val-Emergency(6),
							val-Voice-Over-Karaoke(7)
							}
		MAX-ACCESS		read-write
		STATUS			current
		DESCRIPTION
				"TYPE: - RadiobuttonList
				 PAGE: - DolbyControl
					Bitstream Mode  cmdID= 42460 
					Complete Main  value= 0  
					Music & Effects  value= 1  
					Visually Impaired  value= 2  
					Hearing Impaired  value= 3  
					Dialogue  value= 4  
					Commentary  value= 5  
					Emergency  value= 6  
					Voice Over/Karaoke  value= 7  "
		::= { iqudc12CmdEntry 42460 }


	iqudc12DolbyControlDolbyIntMetaCntrRFMode OBJECT-TYPE
		SYNTAX		INTEGER {
							val-None(0),
							val-Film-Standard(1),
							val-Film-Light(2),
							val-Music-Standard(3),
							val-Music-Light(4),
							val-Speech(5)
							}
		MAX-ACCESS		read-write
		STATUS			current
		DESCRIPTION
				"TYPE: - RadiobuttonList
				 PAGE: - DolbyControl
					RF Mode  cmdID= 42463 
					None  value= 0  
					Film Standard  value= 1  
					Film Light  value= 2  
					Music Standard  value= 3  
					Music Light  value= 4  
					Speech  value= 5  "
		::= { iqudc12CmdEntry 42463 }


	iqudc12DolbyControlDolbyIntMetaCntrLineMode OBJECT-TYPE
		SYNTAX		INTEGER {
							val-None(0),
							val-Film-Standard(1),
							val-Film-Light(2),
							val-Music-Standard(3),
							val-Music-Light(4),
							val-Speech(5)
							}
		MAX-ACCESS		read-write
		STATUS			current
		DESCRIPTION
				"TYPE: - RadiobuttonList
				 PAGE: - DolbyControl
					Line Mode  cmdID= 42462 
					None  value= 0  
					Film Standard  value= 1  
					Film Light  value= 2  
					Music Standard  value= 3  
					Music Light  value= 4  
					Speech  value= 5  "
		::= { iqudc12CmdEntry 42462 }


	iqudc12DolbyIntMetaCntrAudioProductionInExists OBJECT-TYPE
		SYNTAX		INTEGER { disable(0), enable(1) }
		MAX-ACCESS		read-write
		STATUS			current
		DESCRIPTION
				"TYPE: - Checkbox
				 PAGE: - DolbyControl
					Exists  cmdID= 42469 "
		::= { iqudc12CmdEntry 42469 }


	iqudc12DolbyIntMetaCntrAudioProductionInMixLevel OBJECT-TYPE
		SYNTAX		INTEGER
		MAX-ACCESS		read-write
		STATUS			current
		DESCRIPTION
				"TYPE: - Number
				 PAGE: - DolbyControl
					Mix Level  cmdID= 42470  min= 80  max= 111  step= 1  format= %0.0f dB SPL  div_scale= 1 
					Min = 80 dB SPL  Max = 111 dB SPL  Step = 1 dB SPL "
		::= { iqudc12CmdEntry 42470 }


	iqudc12DolbyIntMetaCntrAudioProductionInRoomType OBJECT-TYPE
		SYNTAX		INTEGER {
							val-Not-indicated(0),
							val-Large(1),
							val-Small(2)
							}
		MAX-ACCESS		read-write
		STATUS			current
		DESCRIPTION
				"TYPE: - RadiobuttonList
				 PAGE: - DolbyControl
					Room Type  cmdID= 42471 
					Not indicated  value= 0  
					Large  value= 1  
					Small  value= 2  "
		::= { iqudc12CmdEntry 42471 }


	iqudc12DolbyControlDolbyIntMetaCntrCentreMixLevel OBJECT-TYPE
		SYNTAX		INTEGER {
							val-3-0dB(0),
							val-4-5dB(1),
							val-6-0dB(2)
							}
		MAX-ACCESS		read-write
		STATUS			current
		DESCRIPTION
				"TYPE: - RadiobuttonList
				 PAGE: - DolbyControl
					Centre Mix Level  cmdID= 42464 
					-3.0dB  value= 0  
					-4.5dB  value= 1  
					-6.0dB  value= 2  "
		::= { iqudc12CmdEntry 42464 }


	iqudc12DolbyControlDolbyIntMetaCntrSurroundMixLevel OBJECT-TYPE
		SYNTAX		INTEGER {
							val-3-0dB(0),
							val-6-0dB(1),
							val-Off(2)
							}
		MAX-ACCESS		read-write
		STATUS			current
		DESCRIPTION
				"TYPE: - RadiobuttonList
				 PAGE: - DolbyControl
					Surround Mix Level  cmdID= 42465 
					-3.0dB  value= 0  
					-6.0dB  value= 1  
					Off  value= 2  "
		::= { iqudc12CmdEntry 42465 }


	iqudc12DolbyControlDolbyIntMetaCntrSurroundMode OBJECT-TYPE
		SYNTAX		INTEGER {
							val-Not-indicated(0),
							val-Off(1),
							val-On(2)
							}
		MAX-ACCESS		read-write
		STATUS			current
		DESCRIPTION
				"TYPE: - RadiobuttonList
				 PAGE: - DolbyControl
					Surround Mode  cmdID= 42466 
					Not indicated  value= 0  
					Off  value= 1  
					On  value= 2  "
		::= { iqudc12CmdEntry 42466 }


	iqudc12DolbyControlDolbyIntMetaCntrCopyright OBJECT-TYPE
		SYNTAX		INTEGER { disable(0), enable(1) }
		MAX-ACCESS		read-write
		STATUS			current
		DESCRIPTION
				"TYPE: - Checkbox
				 PAGE: - DolbyControl
					Copyright  cmdID= 42384 "
		::= { iqudc12CmdEntry 42384 }


	iqudc12DolbyIntMetaCntrExtendedBSI1Exists OBJECT-TYPE
		SYNTAX		INTEGER { disable(0), enable(1) }
		MAX-ACCESS		read-write
		STATUS			current
		DESCRIPTION
				"TYPE: - Checkbox
				 PAGE: - DolbyControl
					Exists  cmdID= 42472 "
		::= { iqudc12CmdEntry 42472 }


	iqudc12DolbyIntMetaCntrExtendedBSI1StereoDownmixMode OBJECT-TYPE
		SYNTAX		INTEGER {
							val-Not-indicated(0),
							val-LtRt-Preferred(1),
							val-LoRo-Preferred(2)
							}
		MAX-ACCESS		read-write
		STATUS			current
		DESCRIPTION
				"TYPE: - RadiobuttonList
				 PAGE: - DolbyControl
					Stereo Downmix Mode  cmdID= 42473 
					Not indicated  value= 0  
					LtRt Preferred  value= 1  
					LoRo Preferred  value= 2  "
		::= { iqudc12CmdEntry 42473 }


	iqudc12DolbyIntMetaCntrExtendedBSI1LtRtCentreMixLe OBJECT-TYPE
		SYNTAX		INTEGER {
							val-3-0dB(0),
							val-1-5dB(1),
							val-0-0dB(2),
							val-1-5dB1(3),
							val-3-0dB1(4),
							val-4-5dB(5),
							val-6-0dB(6),
							val-Off(7)
							}
		MAX-ACCESS		read-write
		STATUS			current
		DESCRIPTION
				"TYPE: - RadiobuttonList
				 PAGE: - DolbyControl
					Lt/Rt Centre Mix Le  cmdID= 42474 
					+3.0dB  value= 0  
					+1.5dB  value= 1  
					+0.0dB  value= 2  
					-1.5dB  value= 3  
					-3.0dB  value= 4  
					-4.5dB  value= 5  
					-6.0dB  value= 6  
					Off  value= 7  "
		::= { iqudc12CmdEntry 42474 }


	iqudc12DolbyIntMetaCntrExtendedBSI1LtRtSurrMixLeve OBJECT-TYPE
		SYNTAX		INTEGER {
							val-1-5dB1(3),
							val-3-0dB1(4),
							val-4-5dB(5),
							val-6-0dB(6),
							val-Off(7)
							}
		MAX-ACCESS		read-write
		STATUS			current
		DESCRIPTION
				"TYPE: - RadiobuttonList
				 PAGE: - DolbyControl
					Lt/Rt Surr Mix Leve  cmdID= 42475 
					-1.5dB  value= 3  
					-3.0dB  value= 4  
					-4.5dB  value= 5  
					-6.0dB  value= 6  
					Off  value= 7  "
		::= { iqudc12CmdEntry 42475 }


	iqudc12DolbyIntMetaCntrExtendedBSI1LoRoCentreMixLe OBJECT-TYPE
		SYNTAX		INTEGER {
							val-3-0dB(0),
							val-1-5dB(1),
							val-0-0dB(2),
							val-1-5dB1(3),
							val-3-0dB1(4),
							val-4-5dB(5),
							val-6-0dB(6),
							val-Off(7)
							}
		MAX-ACCESS		read-write
		STATUS			current
		DESCRIPTION
				"TYPE: - RadiobuttonList
				 PAGE: - DolbyControl
					Lo/Ro Centre Mix Le  cmdID= 42476 
					+3.0dB  value= 0  
					+1.5dB  value= 1  
					+0.0dB  value= 2  
					-1.5dB  value= 3  
					-3.0dB  value= 4  
					-4.5dB  value= 5  
					-6.0dB  value= 6  
					Off  value= 7  "
		::= { iqudc12CmdEntry 42476 }


	iqudc12DolbyIntMetaCntrExtendedBSI1LoRoSurrMixLeve OBJECT-TYPE
		SYNTAX		INTEGER {
							val-1-5dB1(3),
							val-3-0dB1(4),
							val-4-5dB(5),
							val-6-0dB(6),
							val-Off(7)
							}
		MAX-ACCESS		read-write
		STATUS			current
		DESCRIPTION
				"TYPE: - RadiobuttonList
				 PAGE: - DolbyControl
					Lo/Ro Surr Mix Leve  cmdID= 42477 
					-1.5dB  value= 3  
					-3.0dB  value= 4  
					-4.5dB  value= 5  
					-6.0dB  value= 6  
					Off  value= 7  "
		::= { iqudc12CmdEntry 42477 }


	iqudc12DolbyIntMetaCntrExtendedBSI2Exists OBJECT-TYPE
		SYNTAX		INTEGER { disable(0), enable(1) }
		MAX-ACCESS		read-write
		STATUS			current
		DESCRIPTION
				"TYPE: - Checkbox
				 PAGE: - DolbyControl
					Exists  cmdID= 42478 "
		::= { iqudc12CmdEntry 42478 }


	iqudc12DolbyIntMetaCntrExtendedBSI2SurroundEXMode OBJECT-TYPE
		SYNTAX		INTEGER {
							val-Not-indicated(0),
							val-Off(1),
							val-On(2)
							}
		MAX-ACCESS		read-write
		STATUS			current
		DESCRIPTION
				"TYPE: - RadiobuttonList
				 PAGE: - DolbyControl
					Surround EX Mode  cmdID= 42479 
					Not indicated  value= 0  
					Off  value= 1  
					On  value= 2  "
		::= { iqudc12CmdEntry 42479 }


	iqudc12DolbyIntMetaCntrExtendedBSI2LowpassFilter OBJECT-TYPE
		SYNTAX		INTEGER { disable(0), enable(1) }
		MAX-ACCESS		read-write
		STATUS			current
		DESCRIPTION
				"TYPE: - Checkbox
				 PAGE: - DolbyControl
					Lowpass Filter  cmdID= 42480 "
		::= { iqudc12CmdEntry 42480 }


	iqudc12DolbyIntMetaCntrExtendedBSI2LFEFIlter OBJECT-TYPE
		SYNTAX		INTEGER { disable(0), enable(1) }
		MAX-ACCESS		read-write
		STATUS			current
		DESCRIPTION
				"TYPE: - Checkbox
				 PAGE: - DolbyControl
					LFE FIlter  cmdID= 42481 "
		::= { iqudc12CmdEntry 42481 }


	iqudc12DolbyIntMetaCntrExtendedBSI2SurrPhaseShiftFl OBJECT-TYPE
		SYNTAX		INTEGER { disable(0), enable(1) }
		MAX-ACCESS		read-write
		STATUS			current
		DESCRIPTION
				"TYPE: - Checkbox
				 PAGE: - DolbyControl
					Surr Phase Shift Fl  cmdID= 42482 "
		::= { iqudc12CmdEntry 42482 }


	iqudc12DolbyIntMetaCntrExtendedBSI2Surr3dBAttenuator OBJECT-TYPE
		SYNTAX		INTEGER { disable(0), enable(1) }
		MAX-ACCESS		read-write
		STATUS			current
		DESCRIPTION
				"TYPE: - Checkbox
				 PAGE: - DolbyControl
					Surr 3dB Attenuator  cmdID= 42483 "
		::= { iqudc12CmdEntry 42483 }


	iqudc12DolbyControlDolbyIntMetaCntrProgramDescription42510 OBJECT-TYPE
		SYNTAX		RollCallString
		MAX-ACCESS		read-write
		STATUS			current
		DESCRIPTION
				"TYPE: - Editstring
				 PAGE: - DolbyControl
					Program Description  cmdID= 42510  "
		::= { iqudc12CmdEntry 42510 }


	iqudc12DolbyControlDolbyIntMetaCntrProgramDescription42511 OBJECT-TYPE
		SYNTAX		RollCallString
		MAX-ACCESS		read-write
		STATUS			current
		DESCRIPTION
				"TYPE: - Editstring
				 PAGE: - DolbyControl
					Program Description  cmdID= 42511  "
		::= { iqudc12CmdEntry 42511 }


	iqudc12DolbyControlDolbyIntMetaCntrIntMetaSaveset OBJECT-TYPE
		SYNTAX		INTEGER
		MAX-ACCESS		read-write
		STATUS			current
		DESCRIPTION
				"TYPE: - Number
				 PAGE: - DolbyControl
					Int Meta Saveset  cmdID= 42590  min= 0  max= 17  step= 1  format= %0.0f  div_scale= 1 
					Min = 0  Max = 17  Step = 1 "
		::= { iqudc12CmdEntry 42590 }


	iqudc12DolbyControlDolbyDEncoderCntInternalMode OBJECT-TYPE
		SYNTAX		INTEGER {
							val-Film-Surround(0),
							val-Film-Stereo(1),
							val-Music-Surround(2),
							val-Music-Stereo(3),
							val-Defaults(4),
							val-Custom(5)
							}
		MAX-ACCESS		read-write
		STATUS			current
		DESCRIPTION
				"TYPE: - RadiobuttonList
				 PAGE: - DolbyControl- Dolby D Encoder Cnt
					Internal Mode  cmdID= 42485 
					Film Surround  value= 0  
					Film Stereo  value= 1  
					Music Surround  value= 2  
					Music Stereo  value= 3  
					Defaults  value= 4  
					Custom  value= 5  "
		::= { iqudc12CmdEntry 42485 }


	iqudc12DolbyControlDolbyDEncoderCntBitstreamFormat OBJECT-TYPE
		SYNTAX		INTEGER {
							val-32-bit(0),
							val-16-bit-Chl1(1),
							val-16-bit-Chl2(2)
							}
		MAX-ACCESS		read-write
		STATUS			current
		DESCRIPTION
				"TYPE: - RadiobuttonList
				 PAGE: - DolbyControl- Dolby D Encoder Cnt
					Bitstream Format  cmdID= 42454 
					32 bit  value= 0  
					16 bit Chl1  value= 1  
					16 bit Chl2  value= 2  "
		::= { iqudc12CmdEntry 42454 }


	iqudc12DolbyControlDolbyDEncoderCntMetadataSource OBJECT-TYPE
		SYNTAX		INTEGER {
							val-Program-1(0),
							val-Program-2(1),
							val-Program-3(2),
							val-Program-4(3),
							val-Program-5(4),
							val-Program-6(5),
							val-Program-7(6),
							val-Program-8(7),
							val-Internal(8)
							}
		MAX-ACCESS		read-write
		STATUS			current
		DESCRIPTION
				"TYPE: - RadiobuttonList
				 PAGE: - DolbyControl- Dolby D Encoder Cnt
					Metadata Source  cmdID= 42498 
					Program 1  value= 0  
					Program 2  value= 1  
					Program 3  value= 2  
					Program 4  value= 3  
					Program 5  value= 4  
					Program 6  value= 5  
					Program 7  value= 6  
					Program 8  value= 7  
					Internal  value= 8  "
		::= { iqudc12CmdEntry 42498 }


	iqudc12DolbyControlDolbyDEncoderCntIntMetaDataRate OBJECT-TYPE
		SYNTAX		INTEGER {
							val-Auto-384(0),
							val-Auto-448(1),
							val-640-kbps(17),
							val-576-kbps(16),
							val-512-kbps(15),
							val-448-kbps(14),
							val-384-kbps(13),
							val-320-kbps(12),
							val-256-kbps(11),
							val-224-kbps(10),
							val-192-kbps(9),
							val-160-kbps(8),
							val-128-kbps(7),
							val-112-kbps(6),
							val-96-kbps(5),
							val-80-kbps(4),
							val-64-kbps(3),
							val-56-kbps(2)
							}
		MAX-ACCESS		read-write
		STATUS			current
		DESCRIPTION
				"TYPE: - RadiobuttonList
				 PAGE: - DolbyControl- Dolby D Encoder Cnt
					Int Meta Data Rate  cmdID= 42499 
					Auto 384  value= 0  
					Auto 448  value= 1  
					640 kbps  value= 17  
					576 kbps  value= 16  
					512 kbps  value= 15  
					448 kbps  value= 14  
					384 kbps  value= 13  
					320 kbps  value= 12  
					256 kbps  value= 11  
					224 kbps  value= 10  
					192 kbps  value= 9  
					160 kbps  value= 8  
					128 kbps  value= 7  
					112 kbps  value= 6  
					96 kbps  value= 5  
					80 kbps  value= 4  
					64 kbps  value= 3  
					56 kbps  value= 2  "
		::= { iqudc12CmdEntry 42499 }


	iqudc12DolbyControlDolbyDEncoderCntStreamNumber OBJECT-TYPE
		SYNTAX		INTEGER {
							val-Stream-0(0),
							val-Stream-1(1),
							val-Stream-2(2),
							val-Stream-3(3),
							val-Stream-4(4),
							val-Stream-5(5),
							val-Stream-6(6)
							}
		MAX-ACCESS		read-write
		STATUS			current
		DESCRIPTION
				"TYPE: - RadiobuttonList
				 PAGE: - DolbyControl- Dolby D Encoder Cnt
					Stream Number  cmdID= 42357 
					Stream 0  value= 0  
					Stream 1  value= 1  
					Stream 2  value= 2  
					Stream 3  value= 3  
					Stream 4  value= 4  
					Stream 5  value= 5  
					Stream 6  value= 6  "
		::= { iqudc12CmdEntry 42357 }


	iqudc12DolbyControlDolbyMetaProgSelMetaProgramSelect42413 OBJECT-TYPE
		SYNTAX		INTEGER {
							val-Program-1(0),
							val-Program-2(1),
							val-Program-3(2),
							val-Program-4(3),
							val-Program-5(4),
							val-Program-6(5),
							val-Program-7(6),
							val-Program-8(7)
							}
		MAX-ACCESS		read-write
		STATUS			current
		DESCRIPTION
				"TYPE: - RadiobuttonList
				 PAGE: - DolbyControl
					Meta Program Select  cmdID= 42413 
					Program 1  value= 0  
					Program 2  value= 1  
					Program 3  value= 2  
					Program 4  value= 3  
					Program 5  value= 4  
					Program 6  value= 5  
					Program 7  value= 6  
					Program 8  value= 7  "
		::= { iqudc12CmdEntry 42413 }


	iqudc12DolbyControlDolbyMetaProgSelMetaProgramSelect42440 OBJECT-TYPE
		SYNTAX		INTEGER {
							val-Program-1(0),
							val-Program-2(1),
							val-Program-3(2),
							val-Program-4(3),
							val-Program-5(4),
							val-Program-6(5),
							val-Program-7(6),
							val-Program-8(7)
							}
		MAX-ACCESS		read-write
		STATUS			current
		DESCRIPTION
				"TYPE: - RadiobuttonList
				 PAGE: - DolbyControl
					Meta Program Select  cmdID= 42440 
					Program 1  value= 0  
					Program 2  value= 1  
					Program 3  value= 2  
					Program 4  value= 3  
					Program 5  value= 4  
					Program 6  value= 5  
					Program 7  value= 6  
					Program 8  value= 7  "
		::= { iqudc12CmdEntry 42440 }


	iqudc12MenuDolbyControlHideEEncoder OBJECT-TYPE
		SYNTAX		RollCallString
		MAX-ACCESS		read-only
		STATUS			current
		DESCRIPTION
				"TYPE: - Display
				 PAGE: - DolbyControl
					Hide E Encoder  cmdID= 42586  format=   "
		::= { iqudc12CmdEntry 42586 }


	iqudc12MenuDolbyControlHideDEncoder OBJECT-TYPE
		SYNTAX		RollCallString
		MAX-ACCESS		read-only
		STATUS			current
		DESCRIPTION
				"TYPE: - Display
				 PAGE: - DolbyControl
					Hide D Encoder  cmdID= 42587  format=   "
		::= { iqudc12CmdEntry 42587 }


	iqudc12MenuDolbyControlResetModule OBJECT-TYPE
		SYNTAX		INTEGER { noAction(0),val-ResetModule(1) }
		MAX-ACCESS		read-write
		STATUS			current
		DESCRIPTION
				"TYPE: - Button
				 PAGE: - DolbyControl
					ResetModule  cmdID= 40243  value= 1  "
		::= { iqudc12CmdEntry 40243 }


	iqudc12DolbyStatusMetaDolbyMetadataRS485PortConfig OBJECT-TYPE
		SYNTAX		INTEGER {
							val-Out-Dolby-552-Decod(0),
							val-Out-S2020-Deembedde(3),
							val-Input(5)
							}
		MAX-ACCESS		read-write
		STATUS			current
		DESCRIPTION
				"TYPE: - RadiobuttonList
				 PAGE: - DolbyStatus/Meta
					RS485 Port Config  cmdID= 42591 
					Out:Dolby 552 Decod  value= 0  
					Out:S2020 Deembedde  value= 3  
					Input  value= 5  "
		::= { iqudc12CmdEntry 42591 }


	iqudc12DolbyStatusMetaDolbyMetadataInputMetadataSour OBJECT-TYPE
		SYNTAX		INTEGER {
							val-RS485-Port(1),
							val-SMPTE2020-Deembedde(3)
							}
		MAX-ACCESS		read-write
		STATUS			current
		DESCRIPTION
				"TYPE: - RadiobuttonList
				 PAGE: - DolbyStatus/Meta
					Input Metadata Sour  cmdID= 42592 
					RS485 Port  value= 1  
					SMPTE2020 Deembedde  value= 3  "
		::= { iqudc12CmdEntry 42592 }


	iqudc12DolbyStatusMetaDolbyMetadataSMPTE2020Embedder OBJECT-TYPE
		SYNTAX		INTEGER {
							val-Dolby-552-Decoder(0),
							val-RS485-Port(1),
							val-SMPTE2020-Deembedde(3)
							}
		MAX-ACCESS		read-write
		STATUS			current
		DESCRIPTION
				"TYPE: - RadiobuttonList
				 PAGE: - DolbyStatus/Meta
					SMPTE2020 Embedder   cmdID= 42593 
					Dolby 552 Decoder  value= 0  
					RS485 Port  value= 1  
					SMPTE2020 Deembedde  value= 3  "
		::= { iqudc12CmdEntry 42593 }


	iqudc12DolbyMetadataSMPTE2020SMPTE2020OPLine OBJECT-TYPE
		SYNTAX		INTEGER
		MAX-ACCESS		read-write
		STATUS			current
		DESCRIPTION
				"TYPE: - Number
				 PAGE: - DolbyStatus/Meta
					SMPTE2020 O/P Line  cmdID= 42594  min= 2  max= 33  step= 1  format= Line %0.0f  div_scale= 1 
					Min = Line 2  Max = Line 33  Step = Line 1 "
		::= { iqudc12CmdEntry 42594 }


	iqudc12DolbyMetadataSMPTE2020SMPTE2020IPLine OBJECT-TYPE
		SYNTAX		RollCallString
		MAX-ACCESS		read-only
		STATUS			current
		DESCRIPTION
				"TYPE: - Display
				 PAGE: - DolbyStatus/Meta
					SMPTE2020 I/P Line  cmdID= 42595  format=   "
		::= { iqudc12CmdEntry 42595 }


	iqudc12DolbyMetadataSMPTE2020OPEnable OBJECT-TYPE
		SYNTAX		INTEGER { disable(0), enable(1) }
		MAX-ACCESS		read-write
		STATUS			current
		DESCRIPTION
				"TYPE: - Checkbox
				 PAGE: - DolbyStatus/Meta
					O/P Enable  cmdID= 42596 "
		::= { iqudc12CmdEntry 42596 }


	iqudc12DolbyMetadataSMPTE2020FollowIPLine OBJECT-TYPE
		SYNTAX		INTEGER { disable(0), enable(1) }
		MAX-ACCESS		read-write
		STATUS			current
		DESCRIPTION
				"TYPE: - Checkbox
				 PAGE: - DolbyStatus/Meta
					Follow I/P Line  cmdID= 42597 "
		::= { iqudc12CmdEntry 42597 }


	iqudc12DolbyStatusMetaDolbyCommonStatusVideoSync OBJECT-TYPE
		SYNTAX		RollCallString
		MAX-ACCESS		read-only
		STATUS			current
		DESCRIPTION
				"TYPE: - Display
				 PAGE: - DolbyStatus/Meta
					Video Sync  cmdID= 42381  format=   "
		::= { iqudc12CmdEntry 42381 }


	iqudc12DolbyStatusMetaDolbyCommonStatusFrameRate OBJECT-TYPE
		SYNTAX		RollCallString
		MAX-ACCESS		read-only
		STATUS			current
		DESCRIPTION
				"TYPE: - Display
				 PAGE: - DolbyStatus/Meta
					Frame Rate  cmdID= 42412  format=   "
		::= { iqudc12CmdEntry 42412 }


	iqudc12DolbyStatusMetaDolbyCommonStatusProgramConfig OBJECT-TYPE
		SYNTAX		RollCallString
		MAX-ACCESS		read-only
		STATUS			current
		DESCRIPTION
				"TYPE: - Display
				 PAGE: - DolbyStatus/Meta
					Program Config  cmdID= 42439  format=   "
		::= { iqudc12CmdEntry 42439 }


	iqudc12DolbyStatusMetaDolbyCommonStatusFWVersion OBJECT-TYPE
		SYNTAX		RollCallString
		MAX-ACCESS		read-only
		STATUS			current
		DESCRIPTION
				"TYPE: - Display
				 PAGE: - DolbyStatus/Meta
					F/W Version  cmdID= 42493  format=   "
		::= { iqudc12CmdEntry 42493 }


	iqudc12DolbyStatusMetaDolbyCommonStatusDeviceName OBJECT-TYPE
		SYNTAX		RollCallString
		MAX-ACCESS		read-only
		STATUS			current
		DESCRIPTION
				"TYPE: - Display
				 PAGE: - DolbyStatus/Meta
					Device Name  cmdID= 42495  format=   "
		::= { iqudc12CmdEntry 42495 }


	iqudc12DolbyCommonStatusChannelAssignmentDolbyA1 OBJECT-TYPE
		SYNTAX		RollCallString
		MAX-ACCESS		read-only
		STATUS			current
		DESCRIPTION
				"TYPE: - Display
				 PAGE: - DolbyStatus/Meta
					Dolby A1  cmdID= 42548  format=   "
		::= { iqudc12CmdEntry 42548 }


	iqudc12DolbyCommonStatusChannelAssignmentDolbyA2 OBJECT-TYPE
		SYNTAX		RollCallString
		MAX-ACCESS		read-only
		STATUS			current
		DESCRIPTION
				"TYPE: - Display
				 PAGE: - DolbyStatus/Meta
					Dolby A2  cmdID= 42549  format=   "
		::= { iqudc12CmdEntry 42549 }


	iqudc12DolbyCommonStatusChannelAssignmentDolbyB3 OBJECT-TYPE
		SYNTAX		RollCallString
		MAX-ACCESS		read-only
		STATUS			current
		DESCRIPTION
				"TYPE: - Display
				 PAGE: - DolbyStatus/Meta
					Dolby B3  cmdID= 42550  format=   "
		::= { iqudc12CmdEntry 42550 }


	iqudc12DolbyCommonStatusChannelAssignmentDolbyB4 OBJECT-TYPE
		SYNTAX		RollCallString
		MAX-ACCESS		read-only
		STATUS			current
		DESCRIPTION
				"TYPE: - Display
				 PAGE: - DolbyStatus/Meta
					Dolby B4  cmdID= 42551  format=   "
		::= { iqudc12CmdEntry 42551 }


	iqudc12DolbyCommonStatusChannelAssignmentDolbyC5 OBJECT-TYPE
		SYNTAX		RollCallString
		MAX-ACCESS		read-only
		STATUS			current
		DESCRIPTION
				"TYPE: - Display
				 PAGE: - DolbyStatus/Meta
					Dolby C5  cmdID= 42552  format=   "
		::= { iqudc12CmdEntry 42552 }


	iqudc12DolbyCommonStatusChannelAssignmentDolbyC6 OBJECT-TYPE
		SYNTAX		RollCallString
		MAX-ACCESS		read-only
		STATUS			current
		DESCRIPTION
				"TYPE: - Display
				 PAGE: - DolbyStatus/Meta
					Dolby C6  cmdID= 42553  format=   "
		::= { iqudc12CmdEntry 42553 }


	iqudc12DolbyCommonStatusChannelAssignmentDolbyD7 OBJECT-TYPE
		SYNTAX		RollCallString
		MAX-ACCESS		read-only
		STATUS			current
		DESCRIPTION
				"TYPE: - Display
				 PAGE: - DolbyStatus/Meta
					Dolby D7  cmdID= 42554  format=   "
		::= { iqudc12CmdEntry 42554 }


	iqudc12DolbyCommonStatusChannelAssignmentDolbyD8 OBJECT-TYPE
		SYNTAX		RollCallString
		MAX-ACCESS		read-only
		STATUS			current
		DESCRIPTION
				"TYPE: - Display
				 PAGE: - DolbyStatus/Meta
					Dolby D8  cmdID= 42555  format=   "
		::= { iqudc12CmdEntry 42555 }


	iqudc12DolbyCommonStatusChnlPairAssignmenDolby12 OBJECT-TYPE
		SYNTAX		RollCallString
		MAX-ACCESS		read-only
		STATUS			current
		DESCRIPTION
				"TYPE: - Display
				 PAGE: - DolbyStatus/Meta
					Dolby 1/2  cmdID= 42544  format=   "
		::= { iqudc12CmdEntry 42544 }


	iqudc12DolbyCommonStatusChnlPairAssignmenDolby34 OBJECT-TYPE
		SYNTAX		RollCallString
		MAX-ACCESS		read-only
		STATUS			current
		DESCRIPTION
				"TYPE: - Display
				 PAGE: - DolbyStatus/Meta
					Dolby 3/4  cmdID= 42545  format=   "
		::= { iqudc12CmdEntry 42545 }


	iqudc12DolbyCommonStatusChnlPairAssignmenDolby56 OBJECT-TYPE
		SYNTAX		RollCallString
		MAX-ACCESS		read-only
		STATUS			current
		DESCRIPTION
				"TYPE: - Display
				 PAGE: - DolbyStatus/Meta
					Dolby 5/6  cmdID= 42546  format=   "
		::= { iqudc12CmdEntry 42546 }


	iqudc12DolbyCommonStatusChnlPairAssignmenDolby78 OBJECT-TYPE
		SYNTAX		RollCallString
		MAX-ACCESS		read-only
		STATUS			current
		DESCRIPTION
				"TYPE: - Display
				 PAGE: - DolbyStatus/Meta
					Dolby 7/8  cmdID= 42547  format=   "
		::= { iqudc12CmdEntry 42547 }


	iqudc12DolbyStatusMetaDolbyExtProgStatP1Status OBJECT-TYPE
		SYNTAX		RollCallString
		MAX-ACCESS		read-only
		STATUS			current
		DESCRIPTION
				"TYPE: - Display
				 PAGE: - DolbyStatus/Meta
					P1 Status  cmdID= 42441  format=   "
		::= { iqudc12CmdEntry 42441 }


	iqudc12DolbyStatusMetaDolbyExtProgStatP2Status OBJECT-TYPE
		SYNTAX		RollCallString
		MAX-ACCESS		read-only
		STATUS			current
		DESCRIPTION
				"TYPE: - Display
				 PAGE: - DolbyStatus/Meta
					P2 Status  cmdID= 42442  format=   "
		::= { iqudc12CmdEntry 42442 }


	iqudc12DolbyStatusMetaDolbyExtProgStatP3Status OBJECT-TYPE
		SYNTAX		RollCallString
		MAX-ACCESS		read-only
		STATUS			current
		DESCRIPTION
				"TYPE: - Display
				 PAGE: - DolbyStatus/Meta
					P3 Status  cmdID= 42443  format=   "
		::= { iqudc12CmdEntry 42443 }


	iqudc12DolbyStatusMetaDolbyExtProgStatP4Status OBJECT-TYPE
		SYNTAX		RollCallString
		MAX-ACCESS		read-only
		STATUS			current
		DESCRIPTION
				"TYPE: - Display
				 PAGE: - DolbyStatus/Meta
					P4 Status  cmdID= 42444  format=   "
		::= { iqudc12CmdEntry 42444 }


	iqudc12DolbyStatusMetaDolbyExtProgStatP5Status OBJECT-TYPE
		SYNTAX		RollCallString
		MAX-ACCESS		read-only
		STATUS			current
		DESCRIPTION
				"TYPE: - Display
				 PAGE: - DolbyStatus/Meta
					P5 Status  cmdID= 42445  format=   "
		::= { iqudc12CmdEntry 42445 }


	iqudc12DolbyStatusMetaDolbyExtProgStatP6Status OBJECT-TYPE
		SYNTAX		RollCallString
		MAX-ACCESS		read-only
		STATUS			current
		DESCRIPTION
				"TYPE: - Display
				 PAGE: - DolbyStatus/Meta
					P6 Status  cmdID= 42446  format=   "
		::= { iqudc12CmdEntry 42446 }


	iqudc12DolbyStatusMetaDolbyExtProgStatP7Status OBJECT-TYPE
		SYNTAX		RollCallString
		MAX-ACCESS		read-only
		STATUS			current
		DESCRIPTION
				"TYPE: - Display
				 PAGE: - DolbyStatus/Meta
					P7 Status  cmdID= 42447  format=   "
		::= { iqudc12CmdEntry 42447 }


	iqudc12DolbyStatusMetaDolbyExtProgStatP8Status OBJECT-TYPE
		SYNTAX		RollCallString
		MAX-ACCESS		read-only
		STATUS			current
		DESCRIPTION
				"TYPE: - Display
				 PAGE: - DolbyStatus/Meta
					P8 Status  cmdID= 42448  format=   "
		::= { iqudc12CmdEntry 42448 }


	iqudc12DolbyStatusMetaDolbyMetadataStatProgramDescription42508 OBJECT-TYPE
		SYNTAX		RollCallString
		MAX-ACCESS		read-only
		STATUS			current
		DESCRIPTION
				"TYPE: - Display
				 PAGE: - DolbyStatus/Meta
					Program Description  cmdID= 42508  format=   "
		::= { iqudc12CmdEntry 42508 }


	iqudc12DolbyStatusMetaDolbyMetadataStatProgramDescription42509 OBJECT-TYPE
		SYNTAX		RollCallString
		MAX-ACCESS		read-only
		STATUS			current
		DESCRIPTION
				"TYPE: - Display
				 PAGE: - DolbyStatus/Meta
					Program Description  cmdID= 42509  format=   "
		::= { iqudc12CmdEntry 42509 }


	iqudc12DolbyStatusMetaDolbyMetadataStatDialogueNorm OBJECT-TYPE
		SYNTAX		RollCallString
		MAX-ACCESS		read-only
		STATUS			current
		DESCRIPTION
				"TYPE: - Display
				 PAGE: - DolbyStatus/Meta
					Dialogue Norm  cmdID= 42422  format=   "
		::= { iqudc12CmdEntry 42422 }


	iqudc12DolbyStatusMetaDolbyMetadataStatChannelMode OBJECT-TYPE
		SYNTAX		RollCallString
		MAX-ACCESS		read-only
		STATUS			current
		DESCRIPTION
				"TYPE: - Display
				 PAGE: - DolbyStatus/Meta
					Channel Mode  cmdID= 42415  format=   "
		::= { iqudc12CmdEntry 42415 }


	iqudc12DolbyStatusMetaDolbyMetadataStatLFE OBJECT-TYPE
		SYNTAX		RollCallString
		MAX-ACCESS		read-only
		STATUS			current
		DESCRIPTION
				"TYPE: - Display
				 PAGE: - DolbyStatus/Meta
					LFE  cmdID= 42421  format=   "
		::= { iqudc12CmdEntry 42421 }


	iqudc12DolbyStatusMetaDolbyMetadataStatBitstreamMode OBJECT-TYPE
		SYNTAX		RollCallString
		MAX-ACCESS		read-only
		STATUS			current
		DESCRIPTION
				"TYPE: - Display
				 PAGE: - DolbyStatus/Meta
					Bitstream Mode  cmdID= 42414  format=   "
		::= { iqudc12CmdEntry 42414 }


	iqudc12DolbyStatusMetaDolbyMetadataStatRFMode OBJECT-TYPE
		SYNTAX		RollCallString
		MAX-ACCESS		read-only
		STATUS			current
		DESCRIPTION
				"TYPE: - Display
				 PAGE: - DolbyStatus/Meta
					RF Mode  cmdID= 42417  format=   "
		::= { iqudc12CmdEntry 42417 }


	iqudc12DolbyStatusMetaDolbyMetadataStatLineMode OBJECT-TYPE
		SYNTAX		RollCallString
		MAX-ACCESS		read-only
		STATUS			current
		DESCRIPTION
				"TYPE: - Display
				 PAGE: - DolbyStatus/Meta
					Line Mode  cmdID= 42416  format=   "
		::= { iqudc12CmdEntry 42416 }


	iqudc12DolbyStatusMetaDolbyMetadataStatCentreMixLevel OBJECT-TYPE
		SYNTAX		RollCallString
		MAX-ACCESS		read-only
		STATUS			current
		DESCRIPTION
				"TYPE: - Display
				 PAGE: - DolbyStatus/Meta
					Centre Mix Level  cmdID= 42418  format=   "
		::= { iqudc12CmdEntry 42418 }


	iqudc12DolbyStatusMetaDolbyMetadataStatSurroundMixLevel OBJECT-TYPE
		SYNTAX		RollCallString
		MAX-ACCESS		read-only
		STATUS			current
		DESCRIPTION
				"TYPE: - Display
				 PAGE: - DolbyStatus/Meta
					Surround Mix Level  cmdID= 42419  format=   "
		::= { iqudc12CmdEntry 42419 }


	iqudc12DolbyStatusMetaDolbyMetadataStatSurroundMode OBJECT-TYPE
		SYNTAX		RollCallString
		MAX-ACCESS		read-only
		STATUS			current
		DESCRIPTION
				"TYPE: - Display
				 PAGE: - DolbyStatus/Meta
					Surround Mode  cmdID= 42420  format=   "
		::= { iqudc12CmdEntry 42420 }


	iqudc12DolbyStatusMetaDolbyMetadataStatCopyright OBJECT-TYPE
		SYNTAX		RollCallString
		MAX-ACCESS		read-only
		STATUS			current
		DESCRIPTION
				"TYPE: - Display
				 PAGE: - DolbyStatus/Meta
					Copyright  cmdID= 42438  format=   "
		::= { iqudc12CmdEntry 42438 }


	iqudc12DolbyMetadataStatAudioProductionInAudioProdInfoExi OBJECT-TYPE
		SYNTAX		RollCallString
		MAX-ACCESS		read-only
		STATUS			current
		DESCRIPTION
				"TYPE: - Display
				 PAGE: - DolbyStatus/Meta
					Audio Prod Info Exi  cmdID= 42423  format=   "
		::= { iqudc12CmdEntry 42423 }


	iqudc12DolbyMetadataStatAudioProductionInMixLevel OBJECT-TYPE
		SYNTAX		RollCallString
		MAX-ACCESS		read-only
		STATUS			current
		DESCRIPTION
				"TYPE: - Display
				 PAGE: - DolbyStatus/Meta
					Mix Level  cmdID= 42424  format=   "
		::= { iqudc12CmdEntry 42424 }


	iqudc12DolbyMetadataStatAudioProductionInRoomType OBJECT-TYPE
		SYNTAX		RollCallString
		MAX-ACCESS		read-only
		STATUS			current
		DESCRIPTION
				"TYPE: - Display
				 PAGE: - DolbyStatus/Meta
					Room Type  cmdID= 42425  format=   "
		::= { iqudc12CmdEntry 42425 }


	iqudc12DolbyMetadataStatExtendedBSI1ExtendedBSI1Exist OBJECT-TYPE
		SYNTAX		RollCallString
		MAX-ACCESS		read-only
		STATUS			current
		DESCRIPTION
				"TYPE: - Display
				 PAGE: - DolbyStatus/Meta
					Extended BSI1 Exist  cmdID= 42426  format=   "
		::= { iqudc12CmdEntry 42426 }


	iqudc12DolbyMetadataStatExtendedBSI1StereoDownmixMode OBJECT-TYPE
		SYNTAX		RollCallString
		MAX-ACCESS		read-only
		STATUS			current
		DESCRIPTION
				"TYPE: - Display
				 PAGE: - DolbyStatus/Meta
					Stereo Downmix Mode  cmdID= 42427  format=   "
		::= { iqudc12CmdEntry 42427 }


	iqudc12DolbyMetadataStatExtendedBSI1LtRtCentreMixLe OBJECT-TYPE
		SYNTAX		RollCallString
		MAX-ACCESS		read-only
		STATUS			current
		DESCRIPTION
				"TYPE: - Display
				 PAGE: - DolbyStatus/Meta
					Lt/Rt Centre Mix Le  cmdID= 42428  format=   "
		::= { iqudc12CmdEntry 42428 }


	iqudc12DolbyMetadataStatExtendedBSI1LtRtSurrMixLeve OBJECT-TYPE
		SYNTAX		RollCallString
		MAX-ACCESS		read-only
		STATUS			current
		DESCRIPTION
				"TYPE: - Display
				 PAGE: - DolbyStatus/Meta
					Lt/Rt Surr Mix Leve  cmdID= 42429  format=   "
		::= { iqudc12CmdEntry 42429 }


	iqudc12DolbyMetadataStatExtendedBSI1LoRoCentreMixLe OBJECT-TYPE
		SYNTAX		RollCallString
		MAX-ACCESS		read-only
		STATUS			current
		DESCRIPTION
				"TYPE: - Display
				 PAGE: - DolbyStatus/Meta
					Lo/Ro Centre Mix Le  cmdID= 42430  format=   "
		::= { iqudc12CmdEntry 42430 }


	iqudc12DolbyMetadataStatExtendedBSI1LoRoSurrMixLeve OBJECT-TYPE
		SYNTAX		RollCallString
		MAX-ACCESS		read-only
		STATUS			current
		DESCRIPTION
				"TYPE: - Display
				 PAGE: - DolbyStatus/Meta
					Lo/Ro Surr Mix Leve  cmdID= 42431  format=   "
		::= { iqudc12CmdEntry 42431 }


	iqudc12DolbyMetadataStatExtendedBSI2ExtendedBSI2Exist OBJECT-TYPE
		SYNTAX		RollCallString
		MAX-ACCESS		read-only
		STATUS			current
		DESCRIPTION
				"TYPE: - Display
				 PAGE: - DolbyStatus/Meta
					Extended BSI2 Exist  cmdID= 42432  format=   "
		::= { iqudc12CmdEntry 42432 }


	iqudc12DolbyMetadataStatExtendedBSI2SurroundEXMode OBJECT-TYPE
		SYNTAX		RollCallString
		MAX-ACCESS		read-only
		STATUS			current
		DESCRIPTION
				"TYPE: - Display
				 PAGE: - DolbyStatus/Meta
					Surround EX Mode  cmdID= 42433  format=   "
		::= { iqudc12CmdEntry 42433 }


	iqudc12DolbyMetadataStatExtendedBSI2LowpassFilter OBJECT-TYPE
		SYNTAX		RollCallString
		MAX-ACCESS		read-only
		STATUS			current
		DESCRIPTION
				"TYPE: - Display
				 PAGE: - DolbyStatus/Meta
					Lowpass Filter  cmdID= 42434  format=   "
		::= { iqudc12CmdEntry 42434 }


	iqudc12DolbyMetadataStatExtendedBSI2LFEFilter OBJECT-TYPE
		SYNTAX		RollCallString
		MAX-ACCESS		read-only
		STATUS			current
		DESCRIPTION
				"TYPE: - Display
				 PAGE: - DolbyStatus/Meta
					LFE Filter  cmdID= 42435  format=   "
		::= { iqudc12CmdEntry 42435 }


	iqudc12DolbyMetadataStatExtendedBSI2SurrPhaseShiftFl OBJECT-TYPE
		SYNTAX		RollCallString
		MAX-ACCESS		read-only
		STATUS			current
		DESCRIPTION
				"TYPE: - Display
				 PAGE: - DolbyStatus/Meta
					Surr Phase Shift Fl  cmdID= 42436  format=   "
		::= { iqudc12CmdEntry 42436 }


	iqudc12DolbyMetadataStatExtendedBSI2Surr3dBAtten OBJECT-TYPE
		SYNTAX		RollCallString
		MAX-ACCESS		read-only
		STATUS			current
		DESCRIPTION
				"TYPE: - Display
				 PAGE: - DolbyStatus/Meta
					Surr 3dB Atten  cmdID= 42437  format=   "
		::= { iqudc12CmdEntry 42437 }


	iqudc12DolbyStatusMetaDolbyEncoderStatuStatus OBJECT-TYPE
		SYNTAX		RollCallString
		MAX-ACCESS		read-only
		STATUS			current
		DESCRIPTION
				"TYPE: - Display
				 PAGE: - DolbyStatus/Meta
					Status  cmdID= 42491  format=   "
		::= { iqudc12CmdEntry 42491 }


	iqudc12DolbyStatusMetaDolbyEncoderStatuBitstreamStatus OBJECT-TYPE
		SYNTAX		RollCallString
		MAX-ACCESS		read-only
		STATUS			current
		DESCRIPTION
				"TYPE: - Display
				 PAGE: - DolbyStatus/Meta
					Bitstream Status  cmdID= 42496  format=   "
		::= { iqudc12CmdEntry 42496 }


	iqudc12DolbyStatusMetaDolbyEncoderStatuReversionStatus OBJECT-TYPE
		SYNTAX		RollCallString
		MAX-ACCESS		read-only
		STATUS			current
		DESCRIPTION
				"TYPE: - Display
				 PAGE: - DolbyStatus/Meta
					Reversion Status  cmdID= 42497  format=   "
		::= { iqudc12CmdEntry 42497 }


	iqudc12DolbyStatusMetaDolbyEncoderStatuHWVersion OBJECT-TYPE
		SYNTAX		RollCallString
		MAX-ACCESS		read-only
		STATUS			current
		DESCRIPTION
				"TYPE: - Display
				 PAGE: - DolbyStatus/Meta
					H/W Version  cmdID= 42494  format=   "
		::= { iqudc12CmdEntry 42494 }


	iqudc12DolbyStatusMetaDolbyEncoderStatuOPProgramConfig OBJECT-TYPE
		SYNTAX		RollCallString
		MAX-ACCESS		read-only
		STATUS			current
		DESCRIPTION
				"TYPE: - Display
				 PAGE: - DolbyStatus/Meta
					O/P Program Config  cmdID= 42392  format=   "
		::= { iqudc12CmdEntry 42392 }


	iqudc12RollCallMemoriesMemoriesABCRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - RollCall/Memories
					Recall Memory  cmdID= 37100 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqudc12CmdEntry 37100 }


	iqudc12RollCallMemoriesMemoriesABCSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - RollCall/Memories
					Sel Memory  cmdID= 37101 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqudc12CmdEntry 37101 }


	iqudc12RollCallMemoriesMemoriesABCSaveMemory OBJECT-TYPE
		SYNTAX		INTEGER { noAction(0),val-Save-Memory(1) }
		MAX-ACCESS		read-write
		STATUS			current
		DESCRIPTION
				"TYPE: - Button
				 PAGE: - RollCall/Memories
					Save Memory  cmdID= 37102  value= 1  "
		::= { iqudc12CmdEntry 37102 }


	iqudc12RollCallMemoriesMemoriesABCClearMemory OBJECT-TYPE
		SYNTAX		INTEGER { noAction(0),val-Clear-Memory(1) }
		MAX-ACCESS		read-write
		STATUS			current
		DESCRIPTION
				"TYPE: - Button
				 PAGE: - RollCall/Memories
					Clear Memory  cmdID= 37105  value= 1  "
		::= { iqudc12CmdEntry 37105 }


	iqudc12MemoriesABCMemoryNameChangeName OBJECT-TYPE
		SYNTAX		RollCallString
		MAX-ACCESS		read-write
		STATUS			current
		DESCRIPTION
				"TYPE: - Editstring
				 PAGE: - RollCall/Memories
					Change Name  cmdID= 37103  "
		::= { iqudc12CmdEntry 37103 }


	iqudc12MemoriesABCMemoryNameLastUserMemory OBJECT-TYPE
		SYNTAX		RollCallString
		MAX-ACCESS		read-only
		STATUS			current
		DESCRIPTION
				"TYPE: - Display
				 PAGE: - RollCall/Memories
					Last User Memory  cmdID= 37104  format=   "
		::= { iqudc12CmdEntry 37104 }


	iqudc12RollCallMemoriesMemoriesABCMemoryName1 OBJECT-TYPE
		SYNTAX		RollCallString
		MAX-ACCESS		read-only
		STATUS			current
		DESCRIPTION
				"TYPE: - Display
				 PAGE: - RollCall/Memories
					Memory Name1  cmdID= 37106  format=   "
		::= { iqudc12CmdEntry 37106 }


	iqudc12RollCallMemoriesMemoriesABCMemoryName2 OBJECT-TYPE
		SYNTAX		RollCallString
		MAX-ACCESS		read-only
		STATUS			current
		DESCRIPTION
				"TYPE: - Display
				 PAGE: - RollCall/Memories
					Memory Name2  cmdID= 37107  format=   "
		::= { iqudc12CmdEntry 37107 }


	iqudc12RollCallMemoriesMemoriesABCMemoryName3 OBJECT-TYPE
		SYNTAX		RollCallString
		MAX-ACCESS		read-only
		STATUS			current
		DESCRIPTION
				"TYPE: - Display
				 PAGE: - RollCall/Memories
					Memory Name3  cmdID= 37108  format=   "
		::= { iqudc12CmdEntry 37108 }


	iqudc12RollCallMemoriesMemoriesABCMemoryName4 OBJECT-TYPE
		SYNTAX		RollCallString
		MAX-ACCESS		read-only
		STATUS			current
		DESCRIPTION
				"TYPE: - Display
				 PAGE: - RollCall/Memories
					Memory Name4  cmdID= 37109  format=   "
		::= { iqudc12CmdEntry 37109 }


	iqudc12RollCallMemoriesMemoriesABCMemoryName5 OBJECT-TYPE
		SYNTAX		RollCallString
		MAX-ACCESS		read-only
		STATUS			current
		DESCRIPTION
				"TYPE: - Display
				 PAGE: - RollCall/Memories
					Memory Name5  cmdID= 37110  format=   "
		::= { iqudc12CmdEntry 37110 }


	iqudc12RollCallMemoriesMemoriesABCMemoryName6 OBJECT-TYPE
		SYNTAX		RollCallString
		MAX-ACCESS		read-only
		STATUS			current
		DESCRIPTION
				"TYPE: - Display
				 PAGE: - RollCall/Memories
					Memory Name6  cmdID= 37111  format=   "
		::= { iqudc12CmdEntry 37111 }


	iqudc12RollCallMemoriesMemoriesABCMemoryName7 OBJECT-TYPE
		SYNTAX		RollCallString
		MAX-ACCESS		read-only
		STATUS			current
		DESCRIPTION
				"TYPE: - Display
				 PAGE: - RollCall/Memories
					Memory Name7  cmdID= 37112  format=   "
		::= { iqudc12CmdEntry 37112 }


	iqudc12RollCallMemoriesMemoriesABCMemoryName8 OBJECT-TYPE
		SYNTAX		RollCallString
		MAX-ACCESS		read-only
		STATUS			current
		DESCRIPTION
				"TYPE: - Display
				 PAGE: - RollCall/Memories
					Memory Name8  cmdID= 37113  format=   "
		::= { iqudc12CmdEntry 37113 }


	iqudc12RollCallMemoriesMemoriesABCMemoryName9 OBJECT-TYPE
		SYNTAX		RollCallString
		MAX-ACCESS		read-only
		STATUS			current
		DESCRIPTION
				"TYPE: - Display
				 PAGE: - RollCall/Memories
					Memory Name9  cmdID= 37114  format=   "
		::= { iqudc12CmdEntry 37114 }


	iqudc12RollCallMemoriesMemoriesABCMemoryName10 OBJECT-TYPE
		SYNTAX		RollCallString
		MAX-ACCESS		read-only
		STATUS			current
		DESCRIPTION
				"TYPE: - Display
				 PAGE: - RollCall/Memories
					Memory Name10  cmdID= 37115  format=   "
		::= { iqudc12CmdEntry 37115 }


	iqudc12RollCallMemoriesMemoriesABCMemoryName11 OBJECT-TYPE
		SYNTAX		RollCallString
		MAX-ACCESS		read-only
		STATUS			current
		DESCRIPTION
				"TYPE: - Display
				 PAGE: - RollCall/Memories
					Memory Name11  cmdID= 37116  format=   "
		::= { iqudc12CmdEntry 37116 }


	iqudc12RollCallMemoriesMemoriesABCMemoryName12 OBJECT-TYPE
		SYNTAX		RollCallString
		MAX-ACCESS		read-only
		STATUS			current
		DESCRIPTION
				"TYPE: - Display
				 PAGE: - RollCall/Memories
					Memory Name12  cmdID= 37117  format=   "
		::= { iqudc12CmdEntry 37117 }


	iqudc12RollCallMemoriesMemoriesABCMemoryName13 OBJECT-TYPE
		SYNTAX		RollCallString
		MAX-ACCESS		read-only
		STATUS			current
		DESCRIPTION
				"TYPE: - Display
				 PAGE: - RollCall/Memories
					Memory Name13  cmdID= 37118  format=   "
		::= { iqudc12CmdEntry 37118 }


	iqudc12RollCallMemoriesMemoriesABCMemoryName14 OBJECT-TYPE
		SYNTAX		RollCallString
		MAX-ACCESS		read-only
		STATUS			current
		DESCRIPTION
				"TYPE: - Display
				 PAGE: - RollCall/Memories
					Memory Name14  cmdID= 37119  format=   "
		::= { iqudc12CmdEntry 37119 }


	iqudc12RollCallMemoriesMemoriesABCMemoryName15 OBJECT-TYPE
		SYNTAX		RollCallString
		MAX-ACCESS		read-only
		STATUS			current
		DESCRIPTION
				"TYPE: - Display
				 PAGE: - RollCall/Memories
					Memory Name15  cmdID= 37120  format=   "
		::= { iqudc12CmdEntry 37120 }


	iqudc12RollCallMemoriesMemoriesABCMemoryName16 OBJECT-TYPE
		SYNTAX		RollCallString
		MAX-ACCESS		read-only
		STATUS			current
		DESCRIPTION
				"TYPE: - Display
				 PAGE: - RollCall/Memories
					Memory Name16  cmdID= 37121  format=   "
		::= { iqudc12CmdEntry 37121 }


	iqudc12Logging1AESInputAudLoggiLogAESInput1stat OBJECT-TYPE
		SYNTAX		INTEGER { disable(0), enable(1) }
		MAX-ACCESS		read-write
		STATUS			current
		DESCRIPTION
				"TYPE: - Checkbox
				 PAGE: - RollCall/Memories- Logging1
					Log AES Input1 stat  cmdID= 42016 "
		::= { iqudc12CmdEntry 42016 }


	iqudc12Logging1AESInputAudLoggiAESInput1state OBJECT-TYPE
		SYNTAX		RollCallString
		MAX-ACCESS		read-only
		STATUS			current
		DESCRIPTION
				"TYPE: - Display
				 PAGE: - RollCall/Memories- Logging1
					AES Input1 state=  cmdID= 42216  format=   "
		::= { iqudc12CmdEntry 42216 }


	iqudc12Logging1AESInputAudLoggiLogAESInput2stat OBJECT-TYPE
		SYNTAX		INTEGER { disable(0), enable(1) }
		MAX-ACCESS		read-write
		STATUS			current
		DESCRIPTION
				"TYPE: - Checkbox
				 PAGE: - RollCall/Memories- Logging1
					Log AES Input2 stat  cmdID= 42017 "
		::= { iqudc12CmdEntry 42017 }


	iqudc12Logging1AESInputAudLoggiAESInput2state OBJECT-TYPE
		SYNTAX		RollCallString
		MAX-ACCESS		read-only
		STATUS			current
		DESCRIPTION
				"TYPE: - Display
				 PAGE: - RollCall/Memories- Logging1
					AES Input2 state=  cmdID= 42217  format=   "
		::= { iqudc12CmdEntry 42217 }


	iqudc12Logging1AESInputAudLoggiLogAESInput3stat OBJECT-TYPE
		SYNTAX		INTEGER { disable(0), enable(1) }
		MAX-ACCESS		read-write
		STATUS			current
		DESCRIPTION
				"TYPE: - Checkbox
				 PAGE: - RollCall/Memories- Logging1
					Log AES Input3 stat  cmdID= 42018 "
		::= { iqudc12CmdEntry 42018 }


	iqudc12Logging1AESInputAudLoggiAESInput3state OBJECT-TYPE
		SYNTAX		RollCallString
		MAX-ACCESS		read-only
		STATUS			current
		DESCRIPTION
				"TYPE: - Display
				 PAGE: - RollCall/Memories- Logging1
					AES Input3 state=  cmdID= 42218  format=   "
		::= { iqudc12CmdEntry 42218 }


	iqudc12Logging1AESInputAudLoggiLogAESInput4stat OBJECT-TYPE
		SYNTAX		INTEGER { disable(0), enable(1) }
		MAX-ACCESS		read-write
		STATUS			current
		DESCRIPTION
				"TYPE: - Checkbox
				 PAGE: - RollCall/Memories- Logging1
					Log AES Input4 stat  cmdID= 42019 "
		::= { iqudc12CmdEntry 42019 }


	iqudc12Logging1AESInputAudLoggiAESInput4state OBJECT-TYPE
		SYNTAX		RollCallString
		MAX-ACCESS		read-only
		STATUS			current
		DESCRIPTION
				"TYPE: - Display
				 PAGE: - RollCall/Memories- Logging1
					AES Input4 state=  cmdID= 42219  format=   "
		::= { iqudc12CmdEntry 42219 }


	iqudc12Logging1AESInputAudLoggiLogAESInput5stat OBJECT-TYPE
		SYNTAX		INTEGER { disable(0), enable(1) }
		MAX-ACCESS		read-write
		STATUS			current
		DESCRIPTION
				"TYPE: - Checkbox
				 PAGE: - RollCall/Memories- Logging1
					Log AES Input5 stat  cmdID= 42020 "
		::= { iqudc12CmdEntry 42020 }


	iqudc12Logging1AESInputAudLoggiAESInput5state OBJECT-TYPE
		SYNTAX		RollCallString
		MAX-ACCESS		read-only
		STATUS			current
		DESCRIPTION
				"TYPE: - Display
				 PAGE: - RollCall/Memories- Logging1
					AES Input5 state=  cmdID= 42220  format=   "
		::= { iqudc12CmdEntry 42220 }


	iqudc12Logging1AESInputAudLoggiLogAESInput6stat OBJECT-TYPE
		SYNTAX		INTEGER { disable(0), enable(1) }
		MAX-ACCESS		read-write
		STATUS			current
		DESCRIPTION
				"TYPE: - Checkbox
				 PAGE: - RollCall/Memories- Logging1
					Log AES Input6 stat  cmdID= 42021 "
		::= { iqudc12CmdEntry 42021 }


	iqudc12Logging1AESInputAudLoggiAESInput6state OBJECT-TYPE
		SYNTAX		RollCallString
		MAX-ACCESS		read-only
		STATUS			current
		DESCRIPTION
				"TYPE: - Display
				 PAGE: - RollCall/Memories- Logging1
					AES Input6 state=  cmdID= 42221  format=   "
		::= { iqudc12CmdEntry 42221 }


	iqudc12Logging1AESInputAudLoggiLogAESInput7stat OBJECT-TYPE
		SYNTAX		INTEGER { disable(0), enable(1) }
		MAX-ACCESS		read-write
		STATUS			current
		DESCRIPTION
				"TYPE: - Checkbox
				 PAGE: - RollCall/Memories- Logging1
					Log AES Input7 stat  cmdID= 42022 "
		::= { iqudc12CmdEntry 42022 }


	iqudc12Logging1AESInputAudLoggiAESInput7state OBJECT-TYPE
		SYNTAX		RollCallString
		MAX-ACCESS		read-only
		STATUS			current
		DESCRIPTION
				"TYPE: - Display
				 PAGE: - RollCall/Memories- Logging1
					AES Input7 state=  cmdID= 42222  format=   "
		::= { iqudc12CmdEntry 42222 }


	iqudc12Logging1AESInputAudLoggiLogAESInput8stat OBJECT-TYPE
		SYNTAX		INTEGER { disable(0), enable(1) }
		MAX-ACCESS		read-write
		STATUS			current
		DESCRIPTION
				"TYPE: - Checkbox
				 PAGE: - RollCall/Memories- Logging1
					Log AES Input8 stat  cmdID= 42023 "
		::= { iqudc12CmdEntry 42023 }


	iqudc12Logging1AESInputAudLoggiAESInput8state OBJECT-TYPE
		SYNTAX		RollCallString
		MAX-ACCESS		read-only
		STATUS			current
		DESCRIPTION
				"TYPE: - Display
				 PAGE: - RollCall/Memories- Logging1
					AES Input8 state=  cmdID= 42223  format=   "
		::= { iqudc12CmdEntry 42223 }


	iqudc12Logging1OutEmbAudLoggingLogOutEmb11stat OBJECT-TYPE
		SYNTAX		INTEGER { disable(0), enable(1) }
		MAX-ACCESS		read-write
		STATUS			current
		DESCRIPTION
				"TYPE: - Checkbox
				 PAGE: - RollCall/Memories- Logging1
					Log Out Emb.11 stat  cmdID= 42024 "
		::= { iqudc12CmdEntry 42024 }


	iqudc12Logging1OutEmbAudLoggingOutEmb11state OBJECT-TYPE
		SYNTAX		RollCallString
		MAX-ACCESS		read-only
		STATUS			current
		DESCRIPTION
				"TYPE: - Display
				 PAGE: - RollCall/Memories- Logging1
					Out Emb.11 state=  cmdID= 42224  format=   "
		::= { iqudc12CmdEntry 42224 }


	iqudc12Logging1OutEmbAudLoggingLogOutEmb12stat OBJECT-TYPE
		SYNTAX		INTEGER { disable(0), enable(1) }
		MAX-ACCESS		read-write
		STATUS			current
		DESCRIPTION
				"TYPE: - Checkbox
				 PAGE: - RollCall/Memories- Logging1
					Log Out Emb.12 stat  cmdID= 42025 "
		::= { iqudc12CmdEntry 42025 }


	iqudc12Logging1OutEmbAudLoggingOutEmb12state OBJECT-TYPE
		SYNTAX		RollCallString
		MAX-ACCESS		read-only
		STATUS			current
		DESCRIPTION
				"TYPE: - Display
				 PAGE: - RollCall/Memories- Logging1
					Out Emb.12 state=  cmdID= 42225  format=   "
		::= { iqudc12CmdEntry 42225 }


	iqudc12Logging1OutEmbAudLoggingLogOutEmb21stat OBJECT-TYPE
		SYNTAX		INTEGER { disable(0), enable(1) }
		MAX-ACCESS		read-write
		STATUS			current
		DESCRIPTION
				"TYPE: - Checkbox
				 PAGE: - RollCall/Memories- Logging1
					Log Out Emb.21 stat  cmdID= 42026 "
		::= { iqudc12CmdEntry 42026 }


	iqudc12Logging1OutEmbAudLoggingOutEmb21state OBJECT-TYPE
		SYNTAX		RollCallString
		MAX-ACCESS		read-only
		STATUS			current
		DESCRIPTION
				"TYPE: - Display
				 PAGE: - RollCall/Memories- Logging1
					Out Emb.21 state=  cmdID= 42226  format=   "
		::= { iqudc12CmdEntry 42226 }


	iqudc12Logging1OutEmbAudLoggingLogOutEmb22stat OBJECT-TYPE
		SYNTAX		INTEGER { disable(0), enable(1) }
		MAX-ACCESS		read-write
		STATUS			current
		DESCRIPTION
				"TYPE: - Checkbox
				 PAGE: - RollCall/Memories- Logging1
					Log Out Emb.22 stat  cmdID= 42027 "
		::= { iqudc12CmdEntry 42027 }


	iqudc12Logging1OutEmbAudLoggingOutEmb22state OBJECT-TYPE
		SYNTAX		RollCallString
		MAX-ACCESS		read-only
		STATUS			current
		DESCRIPTION
				"TYPE: - Display
				 PAGE: - RollCall/Memories- Logging1
					Out Emb.22 state=  cmdID= 42227  format=   "
		::= { iqudc12CmdEntry 42227 }


	iqudc12Logging1OutEmbAudLoggingLogOutEmb31stat OBJECT-TYPE
		SYNTAX		INTEGER { disable(0), enable(1) }
		MAX-ACCESS		read-write
		STATUS			current
		DESCRIPTION
				"TYPE: - Checkbox
				 PAGE: - RollCall/Memories- Logging1
					Log Out Emb.31 stat  cmdID= 42028 "
		::= { iqudc12CmdEntry 42028 }


	iqudc12Logging1OutEmbAudLoggingOutEmb31state OBJECT-TYPE
		SYNTAX		RollCallString
		MAX-ACCESS		read-only
		STATUS			current
		DESCRIPTION
				"TYPE: - Display
				 PAGE: - RollCall/Memories- Logging1
					Out Emb.31 state=  cmdID= 42228  format=   "
		::= { iqudc12CmdEntry 42228 }


	iqudc12Logging1OutEmbAudLoggingLogOutEmb32stat OBJECT-TYPE
		SYNTAX		INTEGER { disable(0), enable(1) }
		MAX-ACCESS		read-write
		STATUS			current
		DESCRIPTION
				"TYPE: - Checkbox
				 PAGE: - RollCall/Memories- Logging1
					Log Out Emb.32 stat  cmdID= 42029 "
		::= { iqudc12CmdEntry 42029 }


	iqudc12Logging1OutEmbAudLoggingOutEmb32state OBJECT-TYPE
		SYNTAX		RollCallString
		MAX-ACCESS		read-only
		STATUS			current
		DESCRIPTION
				"TYPE: - Display
				 PAGE: - RollCall/Memories- Logging1
					Out Emb.32 state=  cmdID= 42229  format=   "
		::= { iqudc12CmdEntry 42229 }


	iqudc12Logging1OutEmbAudLoggingLogOutEmb41stat OBJECT-TYPE
		SYNTAX		INTEGER { disable(0), enable(1) }
		MAX-ACCESS		read-write
		STATUS			current
		DESCRIPTION
				"TYPE: - Checkbox
				 PAGE: - RollCall/Memories- Logging1
					Log Out Emb.41 stat  cmdID= 42030 "
		::= { iqudc12CmdEntry 42030 }


	iqudc12Logging1OutEmbAudLoggingOutEmb41state OBJECT-TYPE
		SYNTAX		RollCallString
		MAX-ACCESS		read-only
		STATUS			current
		DESCRIPTION
				"TYPE: - Display
				 PAGE: - RollCall/Memories- Logging1
					Out Emb.41 state=  cmdID= 42230  format=   "
		::= { iqudc12CmdEntry 42230 }


	iqudc12Logging1OutEmbAudLoggingLogOutEmb42stat OBJECT-TYPE
		SYNTAX		INTEGER { disable(0), enable(1) }
		MAX-ACCESS		read-write
		STATUS			current
		DESCRIPTION
				"TYPE: - Checkbox
				 PAGE: - RollCall/Memories- Logging1
					Log Out Emb.42 stat  cmdID= 42031 "
		::= { iqudc12CmdEntry 42031 }


	iqudc12Logging1OutEmbAudLoggingOutEmb42state OBJECT-TYPE
		SYNTAX		RollCallString
		MAX-ACCESS		read-only
		STATUS			current
		DESCRIPTION
				"TYPE: - Display
				 PAGE: - RollCall/Memories- Logging1
					Out Emb.42 state=  cmdID= 42231  format=   "
		::= { iqudc12CmdEntry 42231 }


	iqudc12Logging1OutEmbAudLoggingLogOutEmb51stat OBJECT-TYPE
		SYNTAX		INTEGER { disable(0), enable(1) }
		MAX-ACCESS		read-write
		STATUS			current
		DESCRIPTION
				"TYPE: - Checkbox
				 PAGE: - RollCall/Memories- Logging1
					Log Out Emb.51 stat  cmdID= 42032 "
		::= { iqudc12CmdEntry 42032 }


	iqudc12Logging1OutEmbAudLoggingOutEmb51state OBJECT-TYPE
		SYNTAX		RollCallString
		MAX-ACCESS		read-only
		STATUS			current
		DESCRIPTION
				"TYPE: - Display
				 PAGE: - RollCall/Memories- Logging1
					Out Emb.51 state=  cmdID= 42232  format=   "
		::= { iqudc12CmdEntry 42232 }


	iqudc12Logging1OutEmbAudLoggingLogOutEmb52stat OBJECT-TYPE
		SYNTAX		INTEGER { disable(0), enable(1) }
		MAX-ACCESS		read-write
		STATUS			current
		DESCRIPTION
				"TYPE: - Checkbox
				 PAGE: - RollCall/Memories- Logging1
					Log Out Emb.52 stat  cmdID= 42033 "
		::= { iqudc12CmdEntry 42033 }


	iqudc12Logging1OutEmbAudLoggingOutEmb52state OBJECT-TYPE
		SYNTAX		RollCallString
		MAX-ACCESS		read-only
		STATUS			current
		DESCRIPTION
				"TYPE: - Display
				 PAGE: - RollCall/Memories- Logging1
					Out Emb.52 state=  cmdID= 42233  format=   "
		::= { iqudc12CmdEntry 42233 }


	iqudc12Logging1OutEmbAudLoggingLogOutEmb61stat OBJECT-TYPE
		SYNTAX		INTEGER { disable(0), enable(1) }
		MAX-ACCESS		read-write
		STATUS			current
		DESCRIPTION
				"TYPE: - Checkbox
				 PAGE: - RollCall/Memories- Logging1
					Log Out Emb.61 stat  cmdID= 42034 "
		::= { iqudc12CmdEntry 42034 }


	iqudc12Logging1OutEmbAudLoggingOutEmb61state OBJECT-TYPE
		SYNTAX		RollCallString
		MAX-ACCESS		read-only
		STATUS			current
		DESCRIPTION
				"TYPE: - Display
				 PAGE: - RollCall/Memories- Logging1
					Out Emb.61 state=  cmdID= 42234  format=   "
		::= { iqudc12CmdEntry 42234 }


	iqudc12Logging1OutEmbAudLoggingLogOutEmb62stat OBJECT-TYPE
		SYNTAX		INTEGER { disable(0), enable(1) }
		MAX-ACCESS		read-write
		STATUS			current
		DESCRIPTION
				"TYPE: - Checkbox
				 PAGE: - RollCall/Memories- Logging1
					Log Out Emb.62 stat  cmdID= 42035 "
		::= { iqudc12CmdEntry 42035 }


	iqudc12Logging1OutEmbAudLoggingOutEmb62state OBJECT-TYPE
		SYNTAX		RollCallString
		MAX-ACCESS		read-only
		STATUS			current
		DESCRIPTION
				"TYPE: - Display
				 PAGE: - RollCall/Memories- Logging1
					Out Emb.62 state=  cmdID= 42235  format=   "
		::= { iqudc12CmdEntry 42235 }


	iqudc12Logging1OutEmbAudLoggingLogOutEmb71stat OBJECT-TYPE
		SYNTAX		INTEGER { disable(0), enable(1) }
		MAX-ACCESS		read-write
		STATUS			current
		DESCRIPTION
				"TYPE: - Checkbox
				 PAGE: - RollCall/Memories- Logging1
					Log Out Emb.71 stat  cmdID= 42036 "
		::= { iqudc12CmdEntry 42036 }


	iqudc12Logging1OutEmbAudLoggingOutEmb71state OBJECT-TYPE
		SYNTAX		RollCallString
		MAX-ACCESS		read-only
		STATUS			current
		DESCRIPTION
				"TYPE: - Display
				 PAGE: - RollCall/Memories- Logging1
					Out Emb.71 state=  cmdID= 42236  format=   "
		::= { iqudc12CmdEntry 42236 }


	iqudc12Logging1OutEmbAudLoggingLogOutEmb72stat OBJECT-TYPE
		SYNTAX		INTEGER { disable(0), enable(1) }
		MAX-ACCESS		read-write
		STATUS			current
		DESCRIPTION
				"TYPE: - Checkbox
				 PAGE: - RollCall/Memories- Logging1
					Log Out Emb.72 stat  cmdID= 42037 "
		::= { iqudc12CmdEntry 42037 }


	iqudc12Logging1OutEmbAudLoggingOutEmb72state OBJECT-TYPE
		SYNTAX		RollCallString
		MAX-ACCESS		read-only
		STATUS			current
		DESCRIPTION
				"TYPE: - Display
				 PAGE: - RollCall/Memories- Logging1
					Out Emb.72 state=  cmdID= 42237  format=   "
		::= { iqudc12CmdEntry 42237 }


	iqudc12Logging1OutEmbAudLoggingLogOutEmb81stat OBJECT-TYPE
		SYNTAX		INTEGER { disable(0), enable(1) }
		MAX-ACCESS		read-write
		STATUS			current
		DESCRIPTION
				"TYPE: - Checkbox
				 PAGE: - RollCall/Memories- Logging1
					Log Out Emb.81 stat  cmdID= 42038 "
		::= { iqudc12CmdEntry 42038 }


	iqudc12Logging1OutEmbAudLoggingOutEmb81state OBJECT-TYPE
		SYNTAX		RollCallString
		MAX-ACCESS		read-only
		STATUS			current
		DESCRIPTION
				"TYPE: - Display
				 PAGE: - RollCall/Memories- Logging1
					Out Emb.81 state=  cmdID= 42238  format=   "
		::= { iqudc12CmdEntry 42238 }


	iqudc12Logging1OutEmbAudLoggingLogOutEmb82stat OBJECT-TYPE
		SYNTAX		INTEGER { disable(0), enable(1) }
		MAX-ACCESS		read-write
		STATUS			current
		DESCRIPTION
				"TYPE: - Checkbox
				 PAGE: - RollCall/Memories- Logging1
					Log Out Emb.82 stat  cmdID= 42039 "
		::= { iqudc12CmdEntry 42039 }


	iqudc12Logging1OutEmbAudLoggingOutEmb82state OBJECT-TYPE
		SYNTAX		RollCallString
		MAX-ACCESS		read-only
		STATUS			current
		DESCRIPTION
				"TYPE: - Display
				 PAGE: - RollCall/Memories- Logging1
					Out Emb.82 state=  cmdID= 42239  format=   "
		::= { iqudc12CmdEntry 42239 }


	iqudc12Logging1AESOutputAudLoggLogAESOutput11st OBJECT-TYPE
		SYNTAX		INTEGER { disable(0), enable(1) }
		MAX-ACCESS		read-write
		STATUS			current
		DESCRIPTION
				"TYPE: - Checkbox
				 PAGE: - RollCall/Memories- Logging1
					Log AES Output11 st  cmdID= 42040 "
		::= { iqudc12CmdEntry 42040 }


	iqudc12Logging1AESOutputAudLoggAESOutput11state OBJECT-TYPE
		SYNTAX		RollCallString
		MAX-ACCESS		read-only
		STATUS			current
		DESCRIPTION
				"TYPE: - Display
				 PAGE: - RollCall/Memories- Logging1
					AES Output11 state=  cmdID= 42240  format=   "
		::= { iqudc12CmdEntry 42240 }


	iqudc12Logging1AESOutputAudLoggLogAESOutput12st OBJECT-TYPE
		SYNTAX		INTEGER { disable(0), enable(1) }
		MAX-ACCESS		read-write
		STATUS			current
		DESCRIPTION
				"TYPE: - Checkbox
				 PAGE: - RollCall/Memories- Logging1
					Log AES Output12 st  cmdID= 42041 "
		::= { iqudc12CmdEntry 42041 }


	iqudc12Logging1AESOutputAudLoggAESOutput12state OBJECT-TYPE
		SYNTAX		RollCallString
		MAX-ACCESS		read-only
		STATUS			current
		DESCRIPTION
				"TYPE: - Display
				 PAGE: - RollCall/Memories- Logging1
					AES Output12 state=  cmdID= 42241  format=   "
		::= { iqudc12CmdEntry 42241 }


	iqudc12Logging1AESOutputAudLoggLogAESOutput21st OBJECT-TYPE
		SYNTAX		INTEGER { disable(0), enable(1) }
		MAX-ACCESS		read-write
		STATUS			current
		DESCRIPTION
				"TYPE: - Checkbox
				 PAGE: - RollCall/Memories- Logging1
					Log AES Output21 st  cmdID= 42042 "
		::= { iqudc12CmdEntry 42042 }


	iqudc12Logging1AESOutputAudLoggAESOutput21state OBJECT-TYPE
		SYNTAX		RollCallString
		MAX-ACCESS		read-only
		STATUS			current
		DESCRIPTION
				"TYPE: - Display
				 PAGE: - RollCall/Memories- Logging1
					AES Output21 state=  cmdID= 42242  format=   "
		::= { iqudc12CmdEntry 42242 }


	iqudc12Logging1AESOutputAudLoggLogAESOutput22st OBJECT-TYPE
		SYNTAX		INTEGER { disable(0), enable(1) }
		MAX-ACCESS		read-write
		STATUS			current
		DESCRIPTION
				"TYPE: - Checkbox
				 PAGE: - RollCall/Memories- Logging1
					Log AES Output22 st  cmdID= 42043 "
		::= { iqudc12CmdEntry 42043 }


	iqudc12Logging1AESOutputAudLoggAESOutput22state OBJECT-TYPE
		SYNTAX		RollCallString
		MAX-ACCESS		read-only
		STATUS			current
		DESCRIPTION
				"TYPE: - Display
				 PAGE: - RollCall/Memories- Logging1
					AES Output22 state=  cmdID= 42243  format=   "
		::= { iqudc12CmdEntry 42243 }


	iqudc12Logging1AESOutputAudLoggLogAESOutput31st OBJECT-TYPE
		SYNTAX		INTEGER { disable(0), enable(1) }
		MAX-ACCESS		read-write
		STATUS			current
		DESCRIPTION
				"TYPE: - Checkbox
				 PAGE: - RollCall/Memories- Logging1
					Log AES Output31 st  cmdID= 42044 "
		::= { iqudc12CmdEntry 42044 }


	iqudc12Logging1AESOutputAudLoggAESOutput31state OBJECT-TYPE
		SYNTAX		RollCallString
		MAX-ACCESS		read-only
		STATUS			current
		DESCRIPTION
				"TYPE: - Display
				 PAGE: - RollCall/Memories- Logging1
					AES Output31 state=  cmdID= 42244  format=   "
		::= { iqudc12CmdEntry 42244 }


	iqudc12Logging1AESOutputAudLoggLogAESOutput32st OBJECT-TYPE
		SYNTAX		INTEGER { disable(0), enable(1) }
		MAX-ACCESS		read-write
		STATUS			current
		DESCRIPTION
				"TYPE: - Checkbox
				 PAGE: - RollCall/Memories- Logging1
					Log AES Output32 st  cmdID= 42045 "
		::= { iqudc12CmdEntry 42045 }


	iqudc12Logging1AESOutputAudLoggAESOutput32state OBJECT-TYPE
		SYNTAX		RollCallString
		MAX-ACCESS		read-only
		STATUS			current
		DESCRIPTION
				"TYPE: - Display
				 PAGE: - RollCall/Memories- Logging1
					AES Output32 state=  cmdID= 42245  format=   "
		::= { iqudc12CmdEntry 42245 }


	iqudc12Logging1AESOutputAudLoggLogAESOutput41st OBJECT-TYPE
		SYNTAX		INTEGER { disable(0), enable(1) }
		MAX-ACCESS		read-write
		STATUS			current
		DESCRIPTION
				"TYPE: - Checkbox
				 PAGE: - RollCall/Memories- Logging1
					Log AES Output41 st  cmdID= 42046 "
		::= { iqudc12CmdEntry 42046 }


	iqudc12Logging1AESOutputAudLoggAESOutput41state OBJECT-TYPE
		SYNTAX		RollCallString
		MAX-ACCESS		read-only
		STATUS			current
		DESCRIPTION
				"TYPE: - Display
				 PAGE: - RollCall/Memories- Logging1
					AES Output41 state=  cmdID= 42246  format=   "
		::= { iqudc12CmdEntry 42246 }


	iqudc12Logging1AESOutputAudLoggLogAESOutput42st OBJECT-TYPE
		SYNTAX		INTEGER { disable(0), enable(1) }
		MAX-ACCESS		read-write
		STATUS			current
		DESCRIPTION
				"TYPE: - Checkbox
				 PAGE: - RollCall/Memories- Logging1
					Log AES Output42 st  cmdID= 42047 "
		::= { iqudc12CmdEntry 42047 }


	iqudc12Logging1AESOutputAudLoggAESOutput42state OBJECT-TYPE
		SYNTAX		RollCallString
		MAX-ACCESS		read-only
		STATUS			current
		DESCRIPTION
				"TYPE: - Display
				 PAGE: - RollCall/Memories- Logging1
					AES Output42 state=  cmdID= 42247  format=   "
		::= { iqudc12CmdEntry 42247 }


	iqudc12Logging1AESOutputAudLoggLogAESOutput51st OBJECT-TYPE
		SYNTAX		INTEGER { disable(0), enable(1) }
		MAX-ACCESS		read-write
		STATUS			current
		DESCRIPTION
				"TYPE: - Checkbox
				 PAGE: - RollCall/Memories- Logging1
					Log AES Output51 st  cmdID= 42048 "
		::= { iqudc12CmdEntry 42048 }


	iqudc12Logging1AESOutputAudLoggAESOutput51state OBJECT-TYPE
		SYNTAX		RollCallString
		MAX-ACCESS		read-only
		STATUS			current
		DESCRIPTION
				"TYPE: - Display
				 PAGE: - RollCall/Memories- Logging1
					AES Output51 state=  cmdID= 42248  format=   "
		::= { iqudc12CmdEntry 42248 }


	iqudc12Logging1AESOutputAudLoggLogAESOutput52st OBJECT-TYPE
		SYNTAX		INTEGER { disable(0), enable(1) }
		MAX-ACCESS		read-write
		STATUS			current
		DESCRIPTION
				"TYPE: - Checkbox
				 PAGE: - RollCall/Memories- Logging1
					Log AES Output52 st  cmdID= 42049 "
		::= { iqudc12CmdEntry 42049 }


	iqudc12Logging1AESOutputAudLoggAESOutput52state OBJECT-TYPE
		SYNTAX		RollCallString
		MAX-ACCESS		read-only
		STATUS			current
		DESCRIPTION
				"TYPE: - Display
				 PAGE: - RollCall/Memories- Logging1
					AES Output52 state=  cmdID= 42249  format=   "
		::= { iqudc12CmdEntry 42249 }


	iqudc12Logging1AESOutputAudLoggLogAESOutput61st OBJECT-TYPE
		SYNTAX		INTEGER { disable(0), enable(1) }
		MAX-ACCESS		read-write
		STATUS			current
		DESCRIPTION
				"TYPE: - Checkbox
				 PAGE: - RollCall/Memories- Logging1
					Log AES Output61 st  cmdID= 42050 "
		::= { iqudc12CmdEntry 42050 }


	iqudc12Logging1AESOutputAudLoggAESOutput61state OBJECT-TYPE
		SYNTAX		RollCallString
		MAX-ACCESS		read-only
		STATUS			current
		DESCRIPTION
				"TYPE: - Display
				 PAGE: - RollCall/Memories- Logging1
					AES Output61 state=  cmdID= 42250  format=   "
		::= { iqudc12CmdEntry 42250 }


	iqudc12Logging1AESOutputAudLoggLogAESOutput62st OBJECT-TYPE
		SYNTAX		INTEGER { disable(0), enable(1) }
		MAX-ACCESS		read-write
		STATUS			current
		DESCRIPTION
				"TYPE: - Checkbox
				 PAGE: - RollCall/Memories- Logging1
					Log AES Output62 st  cmdID= 42051 "
		::= { iqudc12CmdEntry 42051 }


	iqudc12Logging1AESOutputAudLoggAESOutput62state OBJECT-TYPE
		SYNTAX		RollCallString
		MAX-ACCESS		read-only
		STATUS			current
		DESCRIPTION
				"TYPE: - Display
				 PAGE: - RollCall/Memories- Logging1
					AES Output62 state=  cmdID= 42251  format=   "
		::= { iqudc12CmdEntry 42251 }


	iqudc12Logging1AESOutputAudLoggLogAESOutput71st OBJECT-TYPE
		SYNTAX		INTEGER { disable(0), enable(1) }
		MAX-ACCESS		read-write
		STATUS			current
		DESCRIPTION
				"TYPE: - Checkbox
				 PAGE: - RollCall/Memories- Logging1
					Log AES Output71 st  cmdID= 42052 "
		::= { iqudc12CmdEntry 42052 }


	iqudc12Logging1AESOutputAudLoggAESOutput71state OBJECT-TYPE
		SYNTAX		RollCallString
		MAX-ACCESS		read-only
		STATUS			current
		DESCRIPTION
				"TYPE: - Display
				 PAGE: - RollCall/Memories- Logging1
					AES Output71 state=  cmdID= 42252  format=   "
		::= { iqudc12CmdEntry 42252 }


	iqudc12Logging1AESOutputAudLoggLogAESOutput72st OBJECT-TYPE
		SYNTAX		INTEGER { disable(0), enable(1) }
		MAX-ACCESS		read-write
		STATUS			current
		DESCRIPTION
				"TYPE: - Checkbox
				 PAGE: - RollCall/Memories- Logging1
					Log AES Output72 st  cmdID= 42053 "
		::= { iqudc12CmdEntry 42053 }


	iqudc12Logging1AESOutputAudLoggAESOutput72state OBJECT-TYPE
		SYNTAX		RollCallString
		MAX-ACCESS		read-only
		STATUS			current
		DESCRIPTION
				"TYPE: - Display
				 PAGE: - RollCall/Memories- Logging1
					AES Output72 state=  cmdID= 42253  format=   "
		::= { iqudc12CmdEntry 42253 }


	iqudc12Logging1AESOutputAudLoggLogAESOutput81st OBJECT-TYPE
		SYNTAX		INTEGER { disable(0), enable(1) }
		MAX-ACCESS		read-write
		STATUS			current
		DESCRIPTION
				"TYPE: - Checkbox
				 PAGE: - RollCall/Memories- Logging1
					Log AES Output81 st  cmdID= 42054 "
		::= { iqudc12CmdEntry 42054 }


	iqudc12Logging1AESOutputAudLoggAESOutput81state OBJECT-TYPE
		SYNTAX		RollCallString
		MAX-ACCESS		read-only
		STATUS			current
		DESCRIPTION
				"TYPE: - Display
				 PAGE: - RollCall/Memories- Logging1
					AES Output81 state=  cmdID= 42254  format=   "
		::= { iqudc12CmdEntry 42254 }


	iqudc12Logging1AESOutputAudLoggLogAESOutput82st OBJECT-TYPE
		SYNTAX		INTEGER { disable(0), enable(1) }
		MAX-ACCESS		read-write
		STATUS			current
		DESCRIPTION
				"TYPE: - Checkbox
				 PAGE: - RollCall/Memories- Logging1
					Log AES Output82 st  cmdID= 42055 "
		::= { iqudc12CmdEntry 42055 }


	iqudc12Logging1AESOutputAudLoggAESOutput82state OBJECT-TYPE
		SYNTAX		RollCallString
		MAX-ACCESS		read-only
		STATUS			current
		DESCRIPTION
				"TYPE: - Display
				 PAGE: - RollCall/Memories- Logging1
					AES Output82 state=  cmdID= 42255  format=   "
		::= { iqudc12CmdEntry 42255 }


	iqudc12Logging1AnlgOutAudLogginLogAnlgOut11stat OBJECT-TYPE
		SYNTAX		INTEGER { disable(0), enable(1) }
		MAX-ACCESS		read-write
		STATUS			current
		DESCRIPTION
				"TYPE: - Checkbox
				 PAGE: - RollCall/Memories- Logging1
					Log Anlg Out11 stat  cmdID= 42056 "
		::= { iqudc12CmdEntry 42056 }


	iqudc12Logging1AnlgOutAudLogginAnlgOutput11state OBJECT-TYPE
		SYNTAX		RollCallString
		MAX-ACCESS		read-only
		STATUS			current
		DESCRIPTION
				"TYPE: - Display
				 PAGE: - RollCall/Memories- Logging1
					Anlg Output11 state  cmdID= 42256  format=   "
		::= { iqudc12CmdEntry 42256 }


	iqudc12Logging1AnlgOutAudLogginLogAnlgOut12stat OBJECT-TYPE
		SYNTAX		INTEGER { disable(0), enable(1) }
		MAX-ACCESS		read-write
		STATUS			current
		DESCRIPTION
				"TYPE: - Checkbox
				 PAGE: - RollCall/Memories- Logging1
					Log Anlg Out12 stat  cmdID= 42057 "
		::= { iqudc12CmdEntry 42057 }


	iqudc12Logging1AnlgOutAudLogginAnlgOutput12state OBJECT-TYPE
		SYNTAX		RollCallString
		MAX-ACCESS		read-only
		STATUS			current
		DESCRIPTION
				"TYPE: - Display
				 PAGE: - RollCall/Memories- Logging1
					Anlg Output12 state  cmdID= 42257  format=   "
		::= { iqudc12CmdEntry 42257 }


	iqudc12Logging1AnlgOutAudLogginLogAnlgOut21stat OBJECT-TYPE
		SYNTAX		INTEGER { disable(0), enable(1) }
		MAX-ACCESS		read-write
		STATUS			current
		DESCRIPTION
				"TYPE: - Checkbox
				 PAGE: - RollCall/Memories- Logging1
					Log Anlg Out21 stat  cmdID= 42058 "
		::= { iqudc12CmdEntry 42058 }


	iqudc12Logging1AnlgOutAudLogginAnlgOutput21state OBJECT-TYPE
		SYNTAX		RollCallString
		MAX-ACCESS		read-only
		STATUS			current
		DESCRIPTION
				"TYPE: - Display
				 PAGE: - RollCall/Memories- Logging1
					Anlg Output21 state  cmdID= 42258  format=   "
		::= { iqudc12CmdEntry 42258 }


	iqudc12Logging1AnlgOutAudLogginLogAnlgOut22stat OBJECT-TYPE
		SYNTAX		INTEGER { disable(0), enable(1) }
		MAX-ACCESS		read-write
		STATUS			current
		DESCRIPTION
				"TYPE: - Checkbox
				 PAGE: - RollCall/Memories- Logging1
					Log Anlg Out22 stat  cmdID= 42059 "
		::= { iqudc12CmdEntry 42059 }


	iqudc12Logging1AnlgOutAudLogginAnlgOutput22state OBJECT-TYPE
		SYNTAX		RollCallString
		MAX-ACCESS		read-only
		STATUS			current
		DESCRIPTION
				"TYPE: - Display
				 PAGE: - RollCall/Memories- Logging1
					Anlg Output22 state  cmdID= 42259  format=   "
		::= { iqudc12CmdEntry 42259 }


	iqudc12Logging1DolbyDecoderLoggiLogBitstreamForma OBJECT-TYPE
		SYNTAX		INTEGER { disable(0), enable(1) }
		MAX-ACCESS		read-write
		STATUS			current
		DESCRIPTION
				"TYPE: - Checkbox
				 PAGE: - RollCall/Memories- Logging1
					Log Bitstream Forma  cmdID= 42100 "
		::= { iqudc12CmdEntry 42100 }


	iqudc12Logging1DolbyDecoderLoggiBitstreamFormat OBJECT-TYPE
		SYNTAX		RollCallString
		MAX-ACCESS		read-only
		STATUS			current
		DESCRIPTION
				"TYPE: - Display
				 PAGE: - RollCall/Memories- Logging1
					Bitstream Format=  cmdID= 42300  format=   "
		::= { iqudc12CmdEntry 42300 }


	iqudc12Logging1DolbyDecoderLoggiLogBitstreamStatu OBJECT-TYPE
		SYNTAX		INTEGER { disable(0), enable(1) }
		MAX-ACCESS		read-write
		STATUS			current
		DESCRIPTION
				"TYPE: - Checkbox
				 PAGE: - RollCall/Memories- Logging1
					Log Bitstream Statu  cmdID= 42101 "
		::= { iqudc12CmdEntry 42101 }


	iqudc12Logging1DolbyDecoderLoggiBitstreamStatus OBJECT-TYPE
		SYNTAX		RollCallString
		MAX-ACCESS		read-only
		STATUS			current
		DESCRIPTION
				"TYPE: - Display
				 PAGE: - RollCall/Memories- Logging1
					Bitstream Status=  cmdID= 42301  format=   "
		::= { iqudc12CmdEntry 42301 }


	iqudc12Logging1DolbyDecoderLoggiLogDCRCErrors OBJECT-TYPE
		SYNTAX		INTEGER { disable(0), enable(1) }
		MAX-ACCESS		read-write
		STATUS			current
		DESCRIPTION
				"TYPE: - Checkbox
				 PAGE: - RollCall/Memories- Logging1
					Log D CRC Errors  cmdID= 42102 "
		::= { iqudc12CmdEntry 42102 }


	iqudc12Logging1DolbyDecoderLoggiDCRCErrorCount OBJECT-TYPE
		SYNTAX		RollCallString
		MAX-ACCESS		read-only
		STATUS			current
		DESCRIPTION
				"TYPE: - Display
				 PAGE: - RollCall/Memories- Logging1
					D CRC Error Count=  cmdID= 42302  format=   "
		::= { iqudc12CmdEntry 42302 }


	iqudc12Logging1DolbyDecoderLoggiLogECRCErrors OBJECT-TYPE
		SYNTAX		INTEGER { disable(0), enable(1) }
		MAX-ACCESS		read-write
		STATUS			current
		DESCRIPTION
				"TYPE: - Checkbox
				 PAGE: - RollCall/Memories- Logging1
					Log E CRC Errors  cmdID= 42103 "
		::= { iqudc12CmdEntry 42103 }


	iqudc12Logging1DolbyDecoderLoggiECRCErrorCount OBJECT-TYPE
		SYNTAX		RollCallString
		MAX-ACCESS		read-only
		STATUS			current
		DESCRIPTION
				"TYPE: - Display
				 PAGE: - RollCall/Memories- Logging1
					E CRC Error Count=  cmdID= 42303  format=   "
		::= { iqudc12CmdEntry 42303 }


	iqudc12Logging1DolbyEncoderLoggiLogEncoderStatus OBJECT-TYPE
		SYNTAX		INTEGER { disable(0), enable(1) }
		MAX-ACCESS		read-write
		STATUS			current
		DESCRIPTION
				"TYPE: - Checkbox
				 PAGE: - RollCall/Memories- Logging1
					Log Encoder Status  cmdID= 42112 "
		::= { iqudc12CmdEntry 42112 }


	iqudc12Logging1DolbyEncoderLoggiEncoderStatus OBJECT-TYPE
		SYNTAX		RollCallString
		MAX-ACCESS		read-only
		STATUS			current
		DESCRIPTION
				"TYPE: - Display
				 PAGE: - RollCall/Memories- Logging1
					Encoder Status=  cmdID= 42312  format=   "
		::= { iqudc12CmdEntry 42312 }


	iqudc12Logging1DolbyEncoderLoggiLogBitstreamStatu OBJECT-TYPE
		SYNTAX		INTEGER { disable(0), enable(1) }
		MAX-ACCESS		read-write
		STATUS			current
		DESCRIPTION
				"TYPE: - Checkbox
				 PAGE: - RollCall/Memories- Logging1
					Log Bitstream Statu  cmdID= 42113 "
		::= { iqudc12CmdEntry 42113 }


	iqudc12Logging1DolbyEncoderLoggiBitstreamStatus OBJECT-TYPE
		SYNTAX		RollCallString
		MAX-ACCESS		read-only
		STATUS			current
		DESCRIPTION
				"TYPE: - Display
				 PAGE: - RollCall/Memories- Logging1
					Bitstream Status=  cmdID= 42313  format=   "
		::= { iqudc12CmdEntry 42313 }


	iqudc12Logging1DolbyEncoderLoggiLogReversionStatu OBJECT-TYPE
		SYNTAX		INTEGER { disable(0), enable(1) }
		MAX-ACCESS		read-write
		STATUS			current
		DESCRIPTION
				"TYPE: - Checkbox
				 PAGE: - RollCall/Memories- Logging1
					Log Reversion Statu  cmdID= 42114 "
		::= { iqudc12CmdEntry 42114 }


	iqudc12Logging1DolbyEncoderLoggiReversionStatus OBJECT-TYPE
		SYNTAX		RollCallString
		MAX-ACCESS		read-only
		STATUS			current
		DESCRIPTION
				"TYPE: - Display
				 PAGE: - RollCall/Memories- Logging1
					Reversion Status=  cmdID= 42314  format=   "
		::= { iqudc12CmdEntry 42314 }


	iqudc12Logging1DolbyLoggingLogVideoSync OBJECT-TYPE
		SYNTAX		INTEGER { disable(0), enable(1) }
		MAX-ACCESS		read-write
		STATUS			current
		DESCRIPTION
				"TYPE: - Checkbox
				 PAGE: - RollCall/Memories- Logging1
					Log Video Sync  cmdID= 42104 "
		::= { iqudc12CmdEntry 42104 }


	iqudc12Logging1DolbyLoggingVideoSync OBJECT-TYPE
		SYNTAX		RollCallString
		MAX-ACCESS		read-only
		STATUS			current
		DESCRIPTION
				"TYPE: - Display
				 PAGE: - RollCall/Memories- Logging1
					Video Sync=  cmdID= 42304  format=   "
		::= { iqudc12CmdEntry 42304 }


	iqudc12Logging1DolbyLoggingLogFrameRate OBJECT-TYPE
		SYNTAX		INTEGER { disable(0), enable(1) }
		MAX-ACCESS		read-write
		STATUS			current
		DESCRIPTION
				"TYPE: - Checkbox
				 PAGE: - RollCall/Memories- Logging1
					Log Frame Rate  cmdID= 42105 "
		::= { iqudc12CmdEntry 42105 }


	iqudc12Logging1DolbyLoggingFrameRate OBJECT-TYPE
		SYNTAX		RollCallString
		MAX-ACCESS		read-only
		STATUS			current
		DESCRIPTION
				"TYPE: - Display
				 PAGE: - RollCall/Memories- Logging1
					Frame Rate=  cmdID= 42305  format=   "
		::= { iqudc12CmdEntry 42305 }


	iqudc12Logging1DolbyLoggingLogProgramConfig OBJECT-TYPE
		SYNTAX		INTEGER { disable(0), enable(1) }
		MAX-ACCESS		read-write
		STATUS			current
		DESCRIPTION
				"TYPE: - Checkbox
				 PAGE: - RollCall/Memories- Logging1
					Log Program Config  cmdID= 42106 "
		::= { iqudc12CmdEntry 42106 }


	iqudc12Logging1DolbyLoggingProgramConfig OBJECT-TYPE
		SYNTAX		RollCallString
		MAX-ACCESS		read-only
		STATUS			current
		DESCRIPTION
				"TYPE: - Display
				 PAGE: - RollCall/Memories- Logging1
					Program Config=  cmdID= 42306  format=   "
		::= { iqudc12CmdEntry 42306 }


	iqudc12Logging1DolbyMetadataLoggLogSelectedProgra OBJECT-TYPE
		SYNTAX		INTEGER { disable(0), enable(1) }
		MAX-ACCESS		read-write
		STATUS			current
		DESCRIPTION
				"TYPE: - Checkbox
				 PAGE: - RollCall/Memories- Logging1
					Log Selected Progra  cmdID= 42107 "
		::= { iqudc12CmdEntry 42107 }


	iqudc12Logging1DolbyMetadataLoggSelectedProgram OBJECT-TYPE
		SYNTAX		RollCallString
		MAX-ACCESS		read-only
		STATUS			current
		DESCRIPTION
				"TYPE: - Display
				 PAGE: - RollCall/Memories- Logging1
					Selected Program=  cmdID= 42307  format=   "
		::= { iqudc12CmdEntry 42307 }


	iqudc12Logging1DolbyMetadataLoggLogProgramDescrip OBJECT-TYPE
		SYNTAX		INTEGER { disable(0), enable(1) }
		MAX-ACCESS		read-write
		STATUS			current
		DESCRIPTION
				"TYPE: - Checkbox
				 PAGE: - RollCall/Memories- Logging1
					Log Program Descrip  cmdID= 42108 "
		::= { iqudc12CmdEntry 42108 }


	iqudc12Logging1DolbyMetadataLoggProgramDescriptor OBJECT-TYPE
		SYNTAX		RollCallString
		MAX-ACCESS		read-only
		STATUS			current
		DESCRIPTION
				"TYPE: - Display
				 PAGE: - RollCall/Memories- Logging1
					Program Descriptor=  cmdID= 42308  format=   "
		::= { iqudc12CmdEntry 42308 }


	iqudc12Logging1DolbyMetadataLoggProgramDescPt2 OBJECT-TYPE
		SYNTAX		RollCallString
		MAX-ACCESS		read-only
		STATUS			current
		DESCRIPTION
				"TYPE: - Display
				 PAGE: - RollCall/Memories- Logging1
					Program Desc Pt2  cmdID= 42400  format=   "
		::= { iqudc12CmdEntry 42400 }


	iqudc12Logging1DolbyMetadataLoggLogChannelMode OBJECT-TYPE
		SYNTAX		INTEGER { disable(0), enable(1) }
		MAX-ACCESS		read-write
		STATUS			current
		DESCRIPTION
				"TYPE: - Checkbox
				 PAGE: - RollCall/Memories- Logging1
					Log Channel Mode  cmdID= 42109 "
		::= { iqudc12CmdEntry 42109 }


	iqudc12Logging1DolbyMetadataLoggChannelMode OBJECT-TYPE
		SYNTAX		RollCallString
		MAX-ACCESS		read-only
		STATUS			current
		DESCRIPTION
				"TYPE: - Display
				 PAGE: - RollCall/Memories- Logging1
					Channel Mode=  cmdID= 42309  format=   "
		::= { iqudc12CmdEntry 42309 }


	iqudc12Logging1DolbyMetadataLoggLogLFEChannel OBJECT-TYPE
		SYNTAX		INTEGER { disable(0), enable(1) }
		MAX-ACCESS		read-write
		STATUS			current
		DESCRIPTION
				"TYPE: - Checkbox
				 PAGE: - RollCall/Memories- Logging1
					Log LFE Channel  cmdID= 42110 "
		::= { iqudc12CmdEntry 42110 }


	iqudc12Logging1DolbyMetadataLoggLFEChannel OBJECT-TYPE
		SYNTAX		RollCallString
		MAX-ACCESS		read-only
		STATUS			current
		DESCRIPTION
				"TYPE: - Display
				 PAGE: - RollCall/Memories- Logging1
					LFE Channel=  cmdID= 42310  format=   "
		::= { iqudc12CmdEntry 42310 }


	iqudc12Logging1DolbyMetadataLoggLogDialogueNorm OBJECT-TYPE
		SYNTAX		INTEGER { disable(0), enable(1) }
		MAX-ACCESS		read-write
		STATUS			current
		DESCRIPTION
				"TYPE: - Checkbox
				 PAGE: - RollCall/Memories- Logging1
					Log Dialogue Norm  cmdID= 42111 "
		::= { iqudc12CmdEntry 42111 }


	iqudc12Logging1DolbyMetadataLoggDialogueNorm OBJECT-TYPE
		SYNTAX		RollCallString
		MAX-ACCESS		read-only
		STATUS			current
		DESCRIPTION
				"TYPE: - Display
				 PAGE: - RollCall/Memories- Logging1
					Dialogue Norm=  cmdID= 42311  format=   "
		::= { iqudc12CmdEntry 42311 }


	iqudc12Logging1VBIANCLoggingLogInputRefVITC OBJECT-TYPE
		SYNTAX		INTEGER { disable(0), enable(1) }
		MAX-ACCESS		read-write
		STATUS			current
		DESCRIPTION
				"TYPE: - Checkbox
				 PAGE: - RollCall/Memories- Logging1- VBI/ANC Logging
					Log Input Ref VITC  cmdID= 41217 "
		::= { iqudc12CmdEntry 41217 }


	iqudc12Logging1VBIANCLoggingInputRefVITC OBJECT-TYPE
		SYNTAX		RollCallString
		MAX-ACCESS		read-only
		STATUS			current
		DESCRIPTION
				"TYPE: - Display
				 PAGE: - RollCall/Memories- Logging1- VBI/ANC Logging
					Input Ref VITC=  cmdID= 41017  format=   "
		::= { iqudc12CmdEntry 41017 }


	iqudc12Logging1VBIANCLoggingLogInputVITC OBJECT-TYPE
		SYNTAX		INTEGER { disable(0), enable(1) }
		MAX-ACCESS		read-write
		STATUS			current
		DESCRIPTION
				"TYPE: - Checkbox
				 PAGE: - RollCall/Memories- Logging1- VBI/ANC Logging
					Log Input VITC  cmdID= 41218 "
		::= { iqudc12CmdEntry 41218 }


	iqudc12Logging1VBIANCLoggingInputVITC OBJECT-TYPE
		SYNTAX		RollCallString
		MAX-ACCESS		read-only
		STATUS			current
		DESCRIPTION
				"TYPE: - Display
				 PAGE: - RollCall/Memories- Logging1- VBI/ANC Logging
					Input VITC=  cmdID= 41018  format=   "
		::= { iqudc12CmdEntry 41018 }


	iqudc12Logging1VBIANCLoggingLogInputANCLine7 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line7  cmdID= 41200 "
		::= { iqudc12CmdEntry 41200 }


	iqudc12Logging1VBIANCLoggingInputANCLn7 OBJECT-TYPE
		SYNTAX		RollCallString
		MAX-ACCESS		read-only
		STATUS			current
		DESCRIPTION
				"TYPE: - Display
				 PAGE: - RollCall/Memories- Logging1- VBI/ANC Logging
					Input ANC Ln7=  cmdID= 41000  format=   "
		::= { iqudc12CmdEntry 41000 }


	iqudc12Logging1VBIANCLoggingLogInputANCLine8 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line8  cmdID= 41201 "
		::= { iqudc12CmdEntry 41201 }


	iqudc12Logging1VBIANCLoggingInputANCLn8 OBJECT-TYPE
		SYNTAX		RollCallString
		MAX-ACCESS		read-only
		STATUS			current
		DESCRIPTION
				"TYPE: - Display
				 PAGE: - RollCall/Memories- Logging1- VBI/ANC Logging
					Input ANC Ln8=  cmdID= 41001  format=   "
		::= { iqudc12CmdEntry 41001 }


	iqudc12Logging1VBIANCLoggingLogInputANCLine9 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line9  cmdID= 41202 "
		::= { iqudc12CmdEntry 41202 }


	iqudc12Logging1VBIANCLoggingInputANCLn9 OBJECT-TYPE
		SYNTAX		RollCallString
		MAX-ACCESS		read-only
		STATUS			current
		DESCRIPTION
				"TYPE: - Display
				 PAGE: - RollCall/Memories- Logging1- VBI/ANC Logging
					Input ANC Ln9=  cmdID= 41002  format=   "
		::= { iqudc12CmdEntry 41002 }


	iqudc12Logging1VBIANCLoggingLogInputANCLine141203 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41203 "
		::= { iqudc12CmdEntry 41203 }


	iqudc12Logging1VBIANCLoggingInputANCLn10 OBJECT-TYPE
		SYNTAX		RollCallString
		MAX-ACCESS		read-only
		STATUS			current
		DESCRIPTION
				"TYPE: - Display
				 PAGE: - RollCall/Memories- Logging1- VBI/ANC Logging
					Input ANC Ln10=  cmdID= 41003  format=   "
		::= { iqudc12CmdEntry 41003 }


	iqudc12Logging1VBIANCLoggingLogInputANCLine141204 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41204 "
		::= { iqudc12CmdEntry 41204 }


	iqudc12Logging1VBIANCLoggingInputANCLn11 OBJECT-TYPE
		SYNTAX		RollCallString
		MAX-ACCESS		read-only
		STATUS			current
		DESCRIPTION
				"TYPE: - Display
				 PAGE: - RollCall/Memories- Logging1- VBI/ANC Logging
					Input ANC Ln11=  cmdID= 41004  format=   "
		::= { iqudc12CmdEntry 41004 }


	iqudc12Logging1VBIANCLoggingLogInputANCLine141205 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41205 "
		::= { iqudc12CmdEntry 41205 }


	iqudc12Logging1VBIANCLoggingInputANCLn12 OBJECT-TYPE
		SYNTAX		RollCallString
		MAX-ACCESS		read-only
		STATUS			current
		DESCRIPTION
				"TYPE: - Display
				 PAGE: - RollCall/Memories- Logging1- VBI/ANC Logging
					Input ANC Ln12=  cmdID= 41005  format=   "
		::= { iqudc12CmdEntry 41005 }


	iqudc12Logging1VBIANCLoggingLogInputANCLine141206 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41206 "
		::= { iqudc12CmdEntry 41206 }


	iqudc12Logging1VBIANCLoggingInputANCLn13 OBJECT-TYPE
		SYNTAX		RollCallString
		MAX-ACCESS		read-only
		STATUS			current
		DESCRIPTION
				"TYPE: - Display
				 PAGE: - RollCall/Memories- Logging1- VBI/ANC Logging
					Input ANC Ln13=  cmdID= 41006  format=   "
		::= { iqudc12CmdEntry 41006 }


	iqudc12Logging1VBIANCLoggingLogInputANCLine141207 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41207 "
		::= { iqudc12CmdEntry 41207 }


	iqudc12Logging1VBIANCLoggingInputANCLn14 OBJECT-TYPE
		SYNTAX		RollCallString
		MAX-ACCESS		read-only
		STATUS			current
		DESCRIPTION
				"TYPE: - Display
				 PAGE: - RollCall/Memories- Logging1- VBI/ANC Logging
					Input ANC Ln14=  cmdID= 41007  format=   "
		::= { iqudc12CmdEntry 41007 }


	iqudc12Logging1VBIANCLoggingLogInputANCLine141208 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41208 "
		::= { iqudc12CmdEntry 41208 }


	iqudc12Logging1VBIANCLoggingInputANCLn15 OBJECT-TYPE
		SYNTAX		RollCallString
		MAX-ACCESS		read-only
		STATUS			current
		DESCRIPTION
				"TYPE: - Display
				 PAGE: - RollCall/Memories- Logging1- VBI/ANC Logging
					Input ANC Ln15=  cmdID= 41008  format=   "
		::= { iqudc12CmdEntry 41008 }


	iqudc12Logging1VBIANCLoggingLogInputANCLine141209 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41209 "
		::= { iqudc12CmdEntry 41209 }


	iqudc12Logging1VBIANCLoggingInputANCLn16 OBJECT-TYPE
		SYNTAX		RollCallString
		MAX-ACCESS		read-only
		STATUS			current
		DESCRIPTION
				"TYPE: - Display
				 PAGE: - RollCall/Memories- Logging1- VBI/ANC Logging
					Input ANC Ln16=  cmdID= 41009  format=   "
		::= { iqudc12CmdEntry 41009 }


	iqudc12Logging1VBIANCLoggingLogInputANCLine141210 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41210 "
		::= { iqudc12CmdEntry 41210 }


	iqudc12Logging1VBIANCLoggingInputANCLn17 OBJECT-TYPE
		SYNTAX		RollCallString
		MAX-ACCESS		read-only
		STATUS			current
		DESCRIPTION
				"TYPE: - Display
				 PAGE: - RollCall/Memories- Logging1- VBI/ANC Logging
					Input ANC Ln17=  cmdID= 41010  format=   "
		::= { iqudc12CmdEntry 41010 }


	iqudc12Logging1VBIANCLoggingLogInputANCLine141211 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41211 "
		::= { iqudc12CmdEntry 41211 }


	iqudc12Logging1VBIANCLoggingInputANCLn18 OBJECT-TYPE
		SYNTAX		RollCallString
		MAX-ACCESS		read-only
		STATUS			current
		DESCRIPTION
				"TYPE: - Display
				 PAGE: - RollCall/Memories- Logging1- VBI/ANC Logging
					Input ANC Ln18=  cmdID= 41011  format=   "
		::= { iqudc12CmdEntry 41011 }


	iqudc12Logging1VBIANCLoggingLogInputANCLine141212 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line1  cmdID= 41212 "
		::= { iqudc12CmdEntry 41212 }


	iqudc12Logging1VBIANCLoggingInputANCLn19 OBJECT-TYPE
		SYNTAX		RollCallString
		MAX-ACCESS		read-only
		STATUS			current
		DESCRIPTION
				"TYPE: - Display
				 PAGE: - RollCall/Memories- Logging1- VBI/ANC Logging
					Input ANC Ln19=  cmdID= 41012  format=   "
		::= { iqudc12CmdEntry 41012 }


	iqudc12Logging1VBIANCLoggingLogInputANCLine241213 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line2  cmdID= 41213 "
		::= { iqudc12CmdEntry 41213 }


	iqudc12Logging1VBIANCLoggingInputANCLn20 OBJECT-TYPE
		SYNTAX		RollCallString
		MAX-ACCESS		read-only
		STATUS			current
		DESCRIPTION
				"TYPE: - Display
				 PAGE: - RollCall/Memories- Logging1- VBI/ANC Logging
					Input ANC Ln20=  cmdID= 41013  format=   "
		::= { iqudc12CmdEntry 41013 }


	iqudc12Logging1VBIANCLoggingLogInputANCLine241214 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line2  cmdID= 41214 "
		::= { iqudc12CmdEntry 41214 }


	iqudc12Logging1VBIANCLoggingInputANCLn21 OBJECT-TYPE
		SYNTAX		RollCallString
		MAX-ACCESS		read-only
		STATUS			current
		DESCRIPTION
				"TYPE: - Display
				 PAGE: - RollCall/Memories- Logging1- VBI/ANC Logging
					Input ANC Ln21=  cmdID= 41014  format=   "
		::= { iqudc12CmdEntry 41014 }


	iqudc12Logging1VBIANCLoggingLogInputANCLine241215 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line2  cmdID= 41215 "
		::= { iqudc12CmdEntry 41215 }


	iqudc12Logging1VBIANCLoggingInputANCLn22 OBJECT-TYPE
		SYNTAX		RollCallString
		MAX-ACCESS		read-only
		STATUS			current
		DESCRIPTION
				"TYPE: - Display
				 PAGE: - RollCall/Memories- Logging1- VBI/ANC Logging
					Input ANC Ln22=  cmdID= 41015  format=   "
		::= { iqudc12CmdEntry 41015 }


	iqudc12Logging1VBIANCLoggingLogInputANCLine241216 OBJECT-TYPE
		SYNTAX		INTEGER { disable(0), enable(1) }
		MAX-ACCESS		read-write
		STATUS			current
		DESCRIPTION
				"TYPE: - Checkbox
				 PAGE: - RollCall/Memories- Logging1- VBI/ANC Logging
					Log Input ANC Line2  cmdID= 41216 "
		::= { iqudc12CmdEntry 41216 }


	iqudc12Logging1VBIANCLoggingInputANCLn23 OBJECT-TYPE
		SYNTAX		RollCallString
		MAX-ACCESS		read-only
		STATUS			current
		DESCRIPTION
				"TYPE: - Display
				 PAGE: - RollCall/Memories- Logging1- VBI/ANC Logging
					Input ANC Ln23=  cmdID= 41016  format=   "
		::= { iqudc12CmdEntry 41016 }


	iqudc12Logging1VBIANCLoggingLogOutput1Timecod OBJECT-TYPE
		SYNTAX		INTEGER { disable(0), enable(1) }
		MAX-ACCESS		read-write
		STATUS			current
		DESCRIPTION
				"TYPE: - Checkbox
				 PAGE: - RollCall/Memories- Logging1- VBI/ANC Logging
					Log Output1 Timecod  cmdID= 41219 "
		::= { iqudc12CmdEntry 41219 }


	iqudc12Logging1VBIANCLoggingOutput1Timecode OBJECT-TYPE
		SYNTAX		RollCallString
		MAX-ACCESS		read-only
		STATUS			current
		DESCRIPTION
				"TYPE: - Display
				 PAGE: - RollCall/Memories- Logging1- VBI/ANC Logging
					Output1 Timecode=  cmdID= 41019  format=   "
		::= { iqudc12CmdEntry 41019 }


	iqudc12Logging1VBIANCLoggingLogOutput1ANCLin41220 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41220 "
		::= { iqudc12CmdEntry 41220 }


	iqudc12Logging1VBIANCLoggingOutput1ANCLn7 OBJECT-TYPE
		SYNTAX		RollCallString
		MAX-ACCESS		read-only
		STATUS			current
		DESCRIPTION
				"TYPE: - Display
				 PAGE: - RollCall/Memories- Logging1- VBI/ANC Logging
					Output1 ANC Ln7=  cmdID= 41034  format=   "
		::= { iqudc12CmdEntry 41034 }


	iqudc12Logging1VBIANCLoggingLogOutput1ANCLin41221 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41221 "
		::= { iqudc12CmdEntry 41221 }


	iqudc12Logging1VBIANCLoggingOutput1ANCLn8 OBJECT-TYPE
		SYNTAX		RollCallString
		MAX-ACCESS		read-only
		STATUS			current
		DESCRIPTION
				"TYPE: - Display
				 PAGE: - RollCall/Memories- Logging1- VBI/ANC Logging
					Output1 ANC Ln8=  cmdID= 41035  format=   "
		::= { iqudc12CmdEntry 41035 }


	iqudc12Logging1VBIANCLoggingLogOutput1ANCLin41222 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41222 "
		::= { iqudc12CmdEntry 41222 }


	iqudc12Logging1VBIANCLoggingOutput1ANCLn9 OBJECT-TYPE
		SYNTAX		RollCallString
		MAX-ACCESS		read-only
		STATUS			current
		DESCRIPTION
				"TYPE: - Display
				 PAGE: - RollCall/Memories- Logging1- VBI/ANC Logging
					Output1 ANC Ln9=  cmdID= 41036  format=   "
		::= { iqudc12CmdEntry 41036 }


	iqudc12Logging1VBIANCLoggingLogOutput1ANCLin41223 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41223 "
		::= { iqudc12CmdEntry 41223 }


	iqudc12Logging1VBIANCLoggingOutput1ANCLn10 OBJECT-TYPE
		SYNTAX		RollCallString
		MAX-ACCESS		read-only
		STATUS			current
		DESCRIPTION
				"TYPE: - Display
				 PAGE: - RollCall/Memories- Logging1- VBI/ANC Logging
					Output1 ANC Ln10=  cmdID= 41020  format=   "
		::= { iqudc12CmdEntry 41020 }


	iqudc12Logging1VBIANCLoggingLogOutput1ANCLin41224 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41224 "
		::= { iqudc12CmdEntry 41224 }


	iqudc12Logging1VBIANCLoggingOutput1ANCLn11 OBJECT-TYPE
		SYNTAX		RollCallString
		MAX-ACCESS		read-only
		STATUS			current
		DESCRIPTION
				"TYPE: - Display
				 PAGE: - RollCall/Memories- Logging1- VBI/ANC Logging
					Output1 ANC Ln11=  cmdID= 41021  format=   "
		::= { iqudc12CmdEntry 41021 }


	iqudc12Logging1VBIANCLoggingLogOutput1ANCLin41225 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41225 "
		::= { iqudc12CmdEntry 41225 }


	iqudc12Logging1VBIANCLoggingOutput1ANCLn12 OBJECT-TYPE
		SYNTAX		RollCallString
		MAX-ACCESS		read-only
		STATUS			current
		DESCRIPTION
				"TYPE: - Display
				 PAGE: - RollCall/Memories- Logging1- VBI/ANC Logging
					Output1 ANC Ln12=  cmdID= 41022  format=   "
		::= { iqudc12CmdEntry 41022 }


	iqudc12Logging1VBIANCLoggingLogOutput1ANCLin41226 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41226 "
		::= { iqudc12CmdEntry 41226 }


	iqudc12Logging1VBIANCLoggingOutput1ANCLn13 OBJECT-TYPE
		SYNTAX		RollCallString
		MAX-ACCESS		read-only
		STATUS			current
		DESCRIPTION
				"TYPE: - Display
				 PAGE: - RollCall/Memories- Logging1- VBI/ANC Logging
					Output1 ANC Ln13=  cmdID= 41023  format=   "
		::= { iqudc12CmdEntry 41023 }


	iqudc12Logging1VBIANCLoggingLogOutput1ANCLin41227 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41227 "
		::= { iqudc12CmdEntry 41227 }


	iqudc12Logging1VBIANCLoggingOutput1ANCLn14 OBJECT-TYPE
		SYNTAX		RollCallString
		MAX-ACCESS		read-only
		STATUS			current
		DESCRIPTION
				"TYPE: - Display
				 PAGE: - RollCall/Memories- Logging1- VBI/ANC Logging
					Output1 ANC Ln14=  cmdID= 41024  format=   "
		::= { iqudc12CmdEntry 41024 }


	iqudc12Logging1VBIANCLoggingLogOutput1ANCLin41228 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41228 "
		::= { iqudc12CmdEntry 41228 }


	iqudc12Logging1VBIANCLoggingOutput1ANCLn15 OBJECT-TYPE
		SYNTAX		RollCallString
		MAX-ACCESS		read-only
		STATUS			current
		DESCRIPTION
				"TYPE: - Display
				 PAGE: - RollCall/Memories- Logging1- VBI/ANC Logging
					Output1 ANC Ln15=  cmdID= 41025  format=   "
		::= { iqudc12CmdEntry 41025 }


	iqudc12Logging1VBIANCLoggingLogOutput1ANCLin41229 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41229 "
		::= { iqudc12CmdEntry 41229 }


	iqudc12Logging1VBIANCLoggingOutput1ANCLn16 OBJECT-TYPE
		SYNTAX		RollCallString
		MAX-ACCESS		read-only
		STATUS			current
		DESCRIPTION
				"TYPE: - Display
				 PAGE: - RollCall/Memories- Logging1- VBI/ANC Logging
					Output1 ANC Ln16=  cmdID= 41026  format=   "
		::= { iqudc12CmdEntry 41026 }


	iqudc12Logging1VBIANCLoggingLogOutput1ANCLin41230 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41230 "
		::= { iqudc12CmdEntry 41230 }


	iqudc12Logging1VBIANCLoggingOutput1ANCLn17 OBJECT-TYPE
		SYNTAX		RollCallString
		MAX-ACCESS		read-only
		STATUS			current
		DESCRIPTION
				"TYPE: - Display
				 PAGE: - RollCall/Memories- Logging1- VBI/ANC Logging
					Output1 ANC Ln17=  cmdID= 41027  format=   "
		::= { iqudc12CmdEntry 41027 }


	iqudc12Logging1VBIANCLoggingLogOutput1ANCLin41231 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41231 "
		::= { iqudc12CmdEntry 41231 }


	iqudc12Logging1VBIANCLoggingOutput1ANCLn18 OBJECT-TYPE
		SYNTAX		RollCallString
		MAX-ACCESS		read-only
		STATUS			current
		DESCRIPTION
				"TYPE: - Display
				 PAGE: - RollCall/Memories- Logging1- VBI/ANC Logging
					Output1 ANC Ln18=  cmdID= 41028  format=   "
		::= { iqudc12CmdEntry 41028 }


	iqudc12Logging1VBIANCLoggingLogOutput1ANCLin41232 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41232 "
		::= { iqudc12CmdEntry 41232 }


	iqudc12Logging1VBIANCLoggingOutput1ANCLn19 OBJECT-TYPE
		SYNTAX		RollCallString
		MAX-ACCESS		read-only
		STATUS			current
		DESCRIPTION
				"TYPE: - Display
				 PAGE: - RollCall/Memories- Logging1- VBI/ANC Logging
					Output1 ANC Ln19=  cmdID= 41029  format=   "
		::= { iqudc12CmdEntry 41029 }


	iqudc12Logging1VBIANCLoggingLogOutput1ANCLin41233 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41233 "
		::= { iqudc12CmdEntry 41233 }


	iqudc12Logging1VBIANCLoggingOutput1ANCLn20 OBJECT-TYPE
		SYNTAX		RollCallString
		MAX-ACCESS		read-only
		STATUS			current
		DESCRIPTION
				"TYPE: - Display
				 PAGE: - RollCall/Memories- Logging1- VBI/ANC Logging
					Output1 ANC Ln20=  cmdID= 41030  format=   "
		::= { iqudc12CmdEntry 41030 }


	iqudc12Logging1VBIANCLoggingLogOutput1ANCLin41234 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41234 "
		::= { iqudc12CmdEntry 41234 }


	iqudc12Logging1VBIANCLoggingOutput1ANCLn21 OBJECT-TYPE
		SYNTAX		RollCallString
		MAX-ACCESS		read-only
		STATUS			current
		DESCRIPTION
				"TYPE: - Display
				 PAGE: - RollCall/Memories- Logging1- VBI/ANC Logging
					Output1 ANC Ln21=  cmdID= 41031  format=   "
		::= { iqudc12CmdEntry 41031 }


	iqudc12Logging1VBIANCLoggingLogOutput1ANCLin41235 OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41235 "
		::= { iqudc12CmdEntry 41235 }


	iqudc12Logging1VBIANCLoggingOutput1ANCLn22 OBJECT-TYPE
		SYNTAX		RollCallString
		MAX-ACCESS		read-only
		STATUS			current
		DESCRIPTION
				"TYPE: - Display
				 PAGE: - RollCall/Memories- Logging1- VBI/ANC Logging
					Output1 ANC Ln22=  cmdID= 41032  format=   "
		::= { iqudc12CmdEntry 41032 }


	iqudc12Logging1VBIANCLoggingLogOutput1ANCLin OBJECT-TYPE
		SYNTAX		INTEGER { disable(0), enable(1) }
		MAX-ACCESS		read-write
		STATUS			current
		DESCRIPTION
				"TYPE: - Checkbox
				 PAGE: - RollCall/Memories- Logging1- VBI/ANC Logging
					Log Output1 ANC Lin  cmdID= 41236 "
		::= { iqudc12CmdEntry 41236 }


	iqudc12Logging1VBIANCLoggingOutput1ANCLn23 OBJECT-TYPE
		SYNTAX		RollCallString
		MAX-ACCESS		read-only
		STATUS			current
		DESCRIPTION
				"TYPE: - Display
				 PAGE: - RollCall/Memories- Logging1- VBI/ANC Logging
					Output1 ANC Ln23=  cmdID= 41033  format=   "
		::= { iqudc12CmdEntry 41033 }


	iqudc12Logging1WideScreenLoggingLogInput1AFD OBJECT-TYPE
		SYNTAX		INTEGER { disable(0), enable(1) }
		MAX-ACCESS		read-write
		STATUS			current
		DESCRIPTION
				"TYPE: - Checkbox
				 PAGE: - RollCall/Memories- Logging1
					Log Input 1 AFD  cmdID= 35027 "
		::= { iqudc12CmdEntry 35027 }


	iqudc12Logging1WideScreenLoggingInput1AFD OBJECT-TYPE
		SYNTAX		RollCallString
		MAX-ACCESS		read-only
		STATUS			current
		DESCRIPTION
				"TYPE: - Display
				 PAGE: - RollCall/Memories- Logging1
					Input 1 AFD=  cmdID= 36027  format=   "
		::= { iqudc12CmdEntry 36027 }


	iqudc12Logging1WideScreenLoggingLogInput1Aspect OBJECT-TYPE
		SYNTAX		INTEGER { disable(0), enable(1) }
		MAX-ACCESS		read-write
		STATUS			current
		DESCRIPTION
				"TYPE: - Checkbox
				 PAGE: - RollCall/Memories- Logging1
					Log Input 1 Aspect  cmdID= 35026 "
		::= { iqudc12CmdEntry 35026 }


	iqudc12Logging1WideScreenLoggingInput1Aspect OBJECT-TYPE
		SYNTAX		RollCallString
		MAX-ACCESS		read-only
		STATUS			current
		DESCRIPTION
				"TYPE: - Display
				 PAGE: - RollCall/Memories- Logging1
					Input 1 Aspect=  cmdID= 36026  format=   "
		::= { iqudc12CmdEntry 36026 }


	iqudc12Logging1WideScreenLoggingLogInput12016St OBJECT-TYPE
		SYNTAX		INTEGER { disable(0), enable(1) }
		MAX-ACCESS		read-write
		STATUS			current
		DESCRIPTION
				"TYPE: - Checkbox
				 PAGE: - RollCall/Memories- Logging1
					Log Input 1 2016 St  cmdID= 39221 "
		::= { iqudc12CmdEntry 39221 }


	iqudc12Logging1WideScreenLoggingInput12016STATE OBJECT-TYPE
		SYNTAX		RollCallString
		MAX-ACCESS		read-only
		STATUS			current
		DESCRIPTION
				"TYPE: - Display
				 PAGE: - RollCall/Memories- Logging1
					Input 1 2016 STATE=  cmdID= 39321  format=   "
		::= { iqudc12CmdEntry 39321 }


	iqudc12Logging1WideScreenLoggingLogInput12016AS OBJECT-TYPE
		SYNTAX		INTEGER { disable(0), enable(1) }
		MAX-ACCESS		read-write
		STATUS			current
		DESCRIPTION
				"TYPE: - Checkbox
				 PAGE: - RollCall/Memories- Logging1
					Log Input 1 2016 AS  cmdID= 39222 "
		::= { iqudc12CmdEntry 39222 }


	iqudc12Logging1WideScreenLoggingInput12016ASPECT OBJECT-TYPE
		SYNTAX		RollCallString
		MAX-ACCESS		read-only
		STATUS			current
		DESCRIPTION
				"TYPE: - Display
				 PAGE: - RollCall/Memories- Logging1
					Input 1 2016 ASPECT  cmdID= 39322  format=   "
		::= { iqudc12CmdEntry 39322 }


	iqudc12Logging1WideScreenLoggingLogInput12016 OBJECT-TYPE
		SYNTAX		INTEGER { disable(0), enable(1) }
		MAX-ACCESS		read-write
		STATUS			current
		DESCRIPTION
				"TYPE: - Checkbox
				 PAGE: - RollCall/Memories- Logging1
					Log Input 1 2016   cmdID= 39223 "
		::= { iqudc12CmdEntry 39223 }


	iqudc12Logging1WideScreenLoggingInput12016 OBJECT-TYPE
		SYNTAX		RollCallString
		MAX-ACCESS		read-only
		STATUS			current
		DESCRIPTION
				"TYPE: - Display
				 PAGE: - RollCall/Memories- Logging1
					Input 1 2016 =  cmdID= 39323  format=   "
		::= { iqudc12CmdEntry 39323 }


	iqudc12Logging1WideScreenLoggingLogInput1WSSSta OBJECT-TYPE
		SYNTAX		INTEGER { disable(0), enable(1) }
		MAX-ACCESS		read-write
		STATUS			current
		DESCRIPTION
				"TYPE: - Checkbox
				 PAGE: - RollCall/Memories- Logging1
					Log Input 1 WSS Sta  cmdID= 39224 "
		::= { iqudc12CmdEntry 39224 }


	iqudc12Logging1WideScreenLoggingInput1WSSSTATE OBJECT-TYPE
		SYNTAX		RollCallString
		MAX-ACCESS		read-only
		STATUS			current
		DESCRIPTION
				"TYPE: - Display
				 PAGE: - RollCall/Memories- Logging1
					Input 1 WSS STATE=  cmdID= 39324  format=   "
		::= { iqudc12CmdEntry 39324 }


	iqudc12Logging1WideScreenLoggingLogInput1WSSASP OBJECT-TYPE
		SYNTAX		INTEGER { disable(0), enable(1) }
		MAX-ACCESS		read-write
		STATUS			current
		DESCRIPTION
				"TYPE: - Checkbox
				 PAGE: - RollCall/Memories- Logging1
					Log Input 1 WSS ASP  cmdID= 39225 "
		::= { iqudc12CmdEntry 39225 }


	iqudc12Logging1WideScreenLoggingInput1WSSASPECT OBJECT-TYPE
		SYNTAX		RollCallString
		MAX-ACCESS		read-only
		STATUS			current
		DESCRIPTION
				"TYPE: - Display
				 PAGE: - RollCall/Memories- Logging1
					Input 1 WSS ASPECT=  cmdID= 39325  format=   "
		::= { iqudc12CmdEntry 39325 }


	iqudc12Logging1WideScreenLoggingLogInput1WSS OBJECT-TYPE
		SYNTAX		INTEGER { disable(0), enable(1) }
		MAX-ACCESS		read-write
		STATUS			current
		DESCRIPTION
				"TYPE: - Checkbox
				 PAGE: - RollCall/Memories- Logging1
					Log Input 1 WSS   cmdID= 35059 "
		::= { iqudc12CmdEntry 35059 }


	iqudc12Logging1WideScreenLoggingInput1WSS OBJECT-TYPE
		SYNTAX		RollCallString
		MAX-ACCESS		read-only
		STATUS			current
		DESCRIPTION
				"TYPE: - Display
				 PAGE: - RollCall/Memories- Logging1
					Input 1 WSS =  cmdID= 36029  format=   "
		::= { iqudc12CmdEntry 36029 }


	iqudc12Logging1WideScreenLoggingLogInput1VIStat OBJECT-TYPE
		SYNTAX		INTEGER { disable(0), enable(1) }
		MAX-ACCESS		read-write
		STATUS			current
		DESCRIPTION
				"TYPE: - Checkbox
				 PAGE: - RollCall/Memories- Logging1
					Log Input 1 VI Stat  cmdID= 39226 "
		::= { iqudc12CmdEntry 39226 }


	iqudc12Logging1WideScreenLoggingInput1VISTATE OBJECT-TYPE
		SYNTAX		RollCallString
		MAX-ACCESS		read-only
		STATUS			current
		DESCRIPTION
				"TYPE: - Display
				 PAGE: - RollCall/Memories- Logging1
					Input 1 VI STATE=  cmdID= 39326  format=   "
		::= { iqudc12CmdEntry 39326 }


	iqudc12Logging1WideScreenLoggingLogInput1VIASPE OBJECT-TYPE
		SYNTAX		INTEGER { disable(0), enable(1) }
		MAX-ACCESS		read-write
		STATUS			current
		DESCRIPTION
				"TYPE: - Checkbox
				 PAGE: - RollCall/Memories- Logging1
					Log Input 1 VI ASPE  cmdID= 39227 "
		::= { iqudc12CmdEntry 39227 }


	iqudc12Logging1WideScreenLoggingInput1VIASPECT OBJECT-TYPE
		SYNTAX		RollCallString
		MAX-ACCESS		read-only
		STATUS			current
		DESCRIPTION
				"TYPE: - Display
				 PAGE: - RollCall/Memories- Logging1
					Input 1 VI ASPECT=  cmdID= 39327  format=   "
		::= { iqudc12CmdEntry 39327 }


	iqudc12Logging1WideScreenLoggingLogInput1VI OBJECT-TYPE
		SYNTAX		INTEGER { disable(0), enable(1) }
		MAX-ACCESS		read-write
		STATUS			current
		DESCRIPTION
				"TYPE: - Checkbox
				 PAGE: - RollCall/Memories- Logging1
					Log Input 1 VI   cmdID= 35058 "
		::= { iqudc12CmdEntry 35058 }


	iqudc12Logging1WideScreenLoggingInput1VI OBJECT-TYPE
		SYNTAX		RollCallString
		MAX-ACCESS		read-only
		STATUS			current
		DESCRIPTION
				"TYPE: - Display
				 PAGE: - RollCall/Memories- Logging1
					Input 1 VI =  cmdID= 36028  format=   "
		::= { iqudc12CmdEntry 36028 }


	iqudc12Logging1WideScreenLoggingLogOutputAFD35944 OBJECT-TYPE
		SYNTAX		INTEGER { disable(0), enable(1) }
		MAX-ACCESS		read-write
		STATUS			current
		DESCRIPTION
				"TYPE: - Checkbox
				 PAGE: - RollCall/Memories- Logging1
					Log Output AFD  cmdID= 35944 "
		::= { iqudc12CmdEntry 35944 }


	iqudc12Logging1WideScreenLoggingOutputAFD36944 OBJECT-TYPE
		SYNTAX		RollCallString
		MAX-ACCESS		read-only
		STATUS			current
		DESCRIPTION
				"TYPE: - Display
				 PAGE: - RollCall/Memories- Logging1
					Output AFD=  cmdID= 36944  format=   "
		::= { iqudc12CmdEntry 36944 }


	iqudc12Logging1WideScreenLoggingLogOutputAFD35945 OBJECT-TYPE
		SYNTAX		INTEGER { disable(0), enable(1) }
		MAX-ACCESS		read-write
		STATUS			current
		DESCRIPTION
				"TYPE: - Checkbox
				 PAGE: - RollCall/Memories- Logging1
					Log Output AFD  cmdID= 35945 "
		::= { iqudc12CmdEntry 35945 }


	iqudc12Logging1WideScreenLoggingOutputAFD36945 OBJECT-TYPE
		SYNTAX		RollCallString
		MAX-ACCESS		read-only
		STATUS			current
		DESCRIPTION
				"TYPE: - Display
				 PAGE: - RollCall/Memories- Logging1
					Output AFD=  cmdID= 36945  format=   "
		::= { iqudc12CmdEntry 36945 }


	iqudc12Logging2VideoRefLogInp1Type OBJECT-TYPE
		SYNTAX		INTEGER { disable(0), enable(1) }
		MAX-ACCESS		read-write
		STATUS			current
		DESCRIPTION
				"TYPE: - Checkbox
				 PAGE: - RollCall/Memories- Logging2
					Log Inp1 Type  cmdID= 42060 "
		::= { iqudc12CmdEntry 42060 }


	iqudc12Logging2VideoRefInp1Type OBJECT-TYPE
		SYNTAX		RollCallString
		MAX-ACCESS		read-only
		STATUS			current
		DESCRIPTION
				"TYPE: - Display
				 PAGE: - RollCall/Memories- Logging2
					Inp1 Type=  cmdID= 42260  format=   "
		::= { iqudc12CmdEntry 42260 }


	iqudc12Logging2VideoRefLogInp1State OBJECT-TYPE
		SYNTAX		INTEGER { disable(0), enable(1) }
		MAX-ACCESS		read-write
		STATUS			current
		DESCRIPTION
				"TYPE: - Checkbox
				 PAGE: - RollCall/Memories- Logging2
					Log Inp1 State  cmdID= 42063 "
		::= { iqudc12CmdEntry 42063 }


	iqudc12Logging2VideoRefInp1State OBJECT-TYPE
		SYNTAX		RollCallString
		MAX-ACCESS		read-only
		STATUS			current
		DESCRIPTION
				"TYPE: - Display
				 PAGE: - RollCall/Memories- Logging2
					Inp1 State=  cmdID= 42263  format=   "
		::= { iqudc12CmdEntry 42263 }


	iqudc12Logging2VideoRefLogInp1Std OBJECT-TYPE
		SYNTAX		INTEGER { disable(0), enable(1) }
		MAX-ACCESS		read-write
		STATUS			current
		DESCRIPTION
				"TYPE: - Checkbox
				 PAGE: - RollCall/Memories- Logging2
					Log Inp1 Std  cmdID= 42066 "
		::= { iqudc12CmdEntry 42066 }


	iqudc12Logging2VideoRefInp1Std OBJECT-TYPE
		SYNTAX		RollCallString
		MAX-ACCESS		read-only
		STATUS			current
		DESCRIPTION
				"TYPE: - Display
				 PAGE: - RollCall/Memories- Logging2
					Inp1 Std=  cmdID= 42266  format=   "
		::= { iqudc12CmdEntry 42266 }


	iqudc12Logging2VideoRefLogInp1SDIErrs OBJECT-TYPE
		SYNTAX		INTEGER { disable(0), enable(1) }
		MAX-ACCESS		read-write
		STATUS			current
		DESCRIPTION
				"TYPE: - Checkbox
				 PAGE: - RollCall/Memories- Logging2
					Log Inp1 SDIErrs  cmdID= 42069 "
		::= { iqudc12CmdEntry 42069 }


	iqudc12Logging2VideoRefInp1SDIErrs OBJECT-TYPE
		SYNTAX		RollCallString
		MAX-ACCESS		read-only
		STATUS			current
		DESCRIPTION
				"TYPE: - Display
				 PAGE: - RollCall/Memories- Logging2
					Inp1 SDIErrs=  cmdID= 42269  format=   "
		::= { iqudc12CmdEntry 42269 }


	iqudc12Logging2VideoRefLogInp1SDIErrSec OBJECT-TYPE
		SYNTAX		INTEGER { disable(0), enable(1) }
		MAX-ACCESS		read-write
		STATUS			current
		DESCRIPTION
				"TYPE: - Checkbox
				 PAGE: - RollCall/Memories- Logging2
					Log Inp1 SDIErrSec  cmdID= 42071 "
		::= { iqudc12CmdEntry 42071 }


	iqudc12Logging2VideoRefInp1SDIErrSec OBJECT-TYPE
		SYNTAX		RollCallString
		MAX-ACCESS		read-only
		STATUS			current
		DESCRIPTION
				"TYPE: - Display
				 PAGE: - RollCall/Memories- Logging2
					Inp1 SDIErrSec=  cmdID= 42271  format=   "
		::= { iqudc12CmdEntry 42271 }


	iqudc12Logging2VideoRefLogInp1ANCerrs OBJECT-TYPE
		SYNTAX		INTEGER { disable(0), enable(1) }
		MAX-ACCESS		read-write
		STATUS			current
		DESCRIPTION
				"TYPE: - Checkbox
				 PAGE: - RollCall/Memories- Logging2
					Log Inp1 ANCerrs  cmdID= 42073 "
		::= { iqudc12CmdEntry 42073 }


	iqudc12Logging2VideoRefInp1ANCerrs OBJECT-TYPE
		SYNTAX		RollCallString
		MAX-ACCESS		read-only
		STATUS			current
		DESCRIPTION
				"TYPE: - Display
				 PAGE: - RollCall/Memories- Logging2
					Inp1 ANCerrs=  cmdID= 42273  format=   "
		::= { iqudc12CmdEntry 42273 }


	iqudc12Logging2VideoRefLogInp1ANCerrSec OBJECT-TYPE
		SYNTAX		INTEGER { disable(0), enable(1) }
		MAX-ACCESS		read-write
		STATUS			current
		DESCRIPTION
				"TYPE: - Checkbox
				 PAGE: - RollCall/Memories- Logging2
					Log Inp1 ANCerrSec  cmdID= 42075 "
		::= { iqudc12CmdEntry 42075 }


	iqudc12Logging2VideoRefInp1ANCerrSec OBJECT-TYPE
		SYNTAX		RollCallString
		MAX-ACCESS		read-only
		STATUS			current
		DESCRIPTION
				"TYPE: - Display
				 PAGE: - RollCall/Memories- Logging2
					Inp1 ANCerrSec=  cmdID= 42275  format=   "
		::= { iqudc12CmdEntry 42275 }


	iqudc12Logging2VideoRefLogInp2Type OBJECT-TYPE
		SYNTAX		INTEGER { disable(0), enable(1) }
		MAX-ACCESS		read-write
		STATUS			current
		DESCRIPTION
				"TYPE: - Checkbox
				 PAGE: - RollCall/Memories- Logging2
					Log Inp2 Type  cmdID= 42061 "
		::= { iqudc12CmdEntry 42061 }


	iqudc12Logging2VideoRefInp2Type OBJECT-TYPE
		SYNTAX		RollCallString
		MAX-ACCESS		read-only
		STATUS			current
		DESCRIPTION
				"TYPE: - Display
				 PAGE: - RollCall/Memories- Logging2
					Inp2 Type=  cmdID= 42261  format=   "
		::= { iqudc12CmdEntry 42261 }


	iqudc12Logging2VideoRefLogInp2State OBJECT-TYPE
		SYNTAX		INTEGER { disable(0), enable(1) }
		MAX-ACCESS		read-write
		STATUS			current
		DESCRIPTION
				"TYPE: - Checkbox
				 PAGE: - RollCall/Memories- Logging2
					Log Inp2 State  cmdID= 42064 "
		::= { iqudc12CmdEntry 42064 }


	iqudc12Logging2VideoRefInp2State OBJECT-TYPE
		SYNTAX		RollCallString
		MAX-ACCESS		read-only
		STATUS			current
		DESCRIPTION
				"TYPE: - Display
				 PAGE: - RollCall/Memories- Logging2
					Inp2 State=  cmdID= 42264  format=   "
		::= { iqudc12CmdEntry 42264 }


	iqudc12Logging2VideoRefLogInp2Std OBJECT-TYPE
		SYNTAX		INTEGER { disable(0), enable(1) }
		MAX-ACCESS		read-write
		STATUS			current
		DESCRIPTION
				"TYPE: - Checkbox
				 PAGE: - RollCall/Memories- Logging2
					Log Inp2 Std  cmdID= 42067 "
		::= { iqudc12CmdEntry 42067 }


	iqudc12Logging2VideoRefInp2Std OBJECT-TYPE
		SYNTAX		RollCallString
		MAX-ACCESS		read-only
		STATUS			current
		DESCRIPTION
				"TYPE: - Display
				 PAGE: - RollCall/Memories- Logging2
					Inp2 Std=  cmdID= 42267  format=   "
		::= { iqudc12CmdEntry 42267 }


	iqudc12Logging2VideoRefLogInp2SDIErrs OBJECT-TYPE
		SYNTAX		INTEGER { disable(0), enable(1) }
		MAX-ACCESS		read-write
		STATUS			current
		DESCRIPTION
				"TYPE: - Checkbox
				 PAGE: - RollCall/Memories- Logging2
					Log Inp2 SDIErrs  cmdID= 42070 "
		::= { iqudc12CmdEntry 42070 }


	iqudc12Logging2VideoRefInp2SDIErrs OBJECT-TYPE
		SYNTAX		RollCallString
		MAX-ACCESS		read-only
		STATUS			current
		DESCRIPTION
				"TYPE: - Display
				 PAGE: - RollCall/Memories- Logging2
					Inp2 SDIErrs=  cmdID= 42270  format=   "
		::= { iqudc12CmdEntry 42270 }


	iqudc12Logging2VideoRefLogInp2SDIErrSec OBJECT-TYPE
		SYNTAX		INTEGER { disable(0), enable(1) }
		MAX-ACCESS		read-write
		STATUS			current
		DESCRIPTION
				"TYPE: - Checkbox
				 PAGE: - RollCall/Memories- Logging2
					Log Inp2 SDIErrSec  cmdID= 42072 "
		::= { iqudc12CmdEntry 42072 }


	iqudc12Logging2VideoRefInp2SDIErrSec OBJECT-TYPE
		SYNTAX		RollCallString
		MAX-ACCESS		read-only
		STATUS			current
		DESCRIPTION
				"TYPE: - Display
				 PAGE: - RollCall/Memories- Logging2
					Inp2 SDIErrSec=  cmdID= 42272  format=   "
		::= { iqudc12CmdEntry 42272 }


	iqudc12Logging2VideoRefLogInp2ANCerrs OBJECT-TYPE
		SYNTAX		INTEGER { disable(0), enable(1) }
		MAX-ACCESS		read-write
		STATUS			current
		DESCRIPTION
				"TYPE: - Checkbox
				 PAGE: - RollCall/Memories- Logging2
					Log Inp2 ANCerrs  cmdID= 42074 "
		::= { iqudc12CmdEntry 42074 }


	iqudc12Logging2VideoRefInp2ANCerrs OBJECT-TYPE
		SYNTAX		RollCallString
		MAX-ACCESS		read-only
		STATUS			current
		DESCRIPTION
				"TYPE: - Display
				 PAGE: - RollCall/Memories- Logging2
					Inp2 ANCerrs=  cmdID= 42274  format=   "
		::= { iqudc12CmdEntry 42274 }


	iqudc12Logging2VideoRefLogInp2ANCerrSec OBJECT-TYPE
		SYNTAX		INTEGER { disable(0), enable(1) }
		MAX-ACCESS		read-write
		STATUS			current
		DESCRIPTION
				"TYPE: - Checkbox
				 PAGE: - RollCall/Memories- Logging2
					Log Inp2 ANCerrSec  cmdID= 42076 "
		::= { iqudc12CmdEntry 42076 }


	iqudc12Logging2VideoRefInp2ANCerrSec OBJECT-TYPE
		SYNTAX		RollCallString
		MAX-ACCESS		read-only
		STATUS			current
		DESCRIPTION
				"TYPE: - Display
				 PAGE: - RollCall/Memories- Logging2
					Inp2 ANCerrSec=  cmdID= 42276  format=   "
		::= { iqudc12CmdEntry 42276 }


	iqudc12Logging2VideoRefLogInp3Type OBJECT-TYPE
		SYNTAX		INTEGER { disable(0), enable(1) }
		MAX-ACCESS		read-write
		STATUS			current
		DESCRIPTION
				"TYPE: - Checkbox
				 PAGE: - RollCall/Memories- Logging2
					Log Inp3 Type  cmdID= 42062 "
		::= { iqudc12CmdEntry 42062 }


	iqudc12Logging2VideoRefInp3Type OBJECT-TYPE
		SYNTAX		RollCallString
		MAX-ACCESS		read-only
		STATUS			current
		DESCRIPTION
				"TYPE: - Display
				 PAGE: - RollCall/Memories- Logging2
					Inp3 Type=  cmdID= 42262  format=   "
		::= { iqudc12CmdEntry 42262 }


	iqudc12Logging2VideoRefLogInp3State OBJECT-TYPE
		SYNTAX		INTEGER { disable(0), enable(1) }
		MAX-ACCESS		read-write
		STATUS			current
		DESCRIPTION
				"TYPE: - Checkbox
				 PAGE: - RollCall/Memories- Logging2
					Log Inp3 State  cmdID= 42065 "
		::= { iqudc12CmdEntry 42065 }


	iqudc12Logging2VideoRefInp3State OBJECT-TYPE
		SYNTAX		RollCallString
		MAX-ACCESS		read-only
		STATUS			current
		DESCRIPTION
				"TYPE: - Display
				 PAGE: - RollCall/Memories- Logging2
					Inp3 State=  cmdID= 42265  format=   "
		::= { iqudc12CmdEntry 42265 }


	iqudc12Logging2VideoRefLogInp3Std OBJECT-TYPE
		SYNTAX		INTEGER { disable(0), enable(1) }
		MAX-ACCESS		read-write
		STATUS			current
		DESCRIPTION
				"TYPE: - Checkbox
				 PAGE: - RollCall/Memories- Logging2
					Log Inp3 Std  cmdID= 42068 "
		::= { iqudc12CmdEntry 42068 }


	iqudc12Logging2VideoRefInp3Std OBJECT-TYPE
		SYNTAX		RollCallString
		MAX-ACCESS		read-only
		STATUS			current
		DESCRIPTION
				"TYPE: - Display
				 PAGE: - RollCall/Memories- Logging2
					Inp3 Std=  cmdID= 42268  format=   "
		::= { iqudc12CmdEntry 42268 }


	iqudc12Logging2VideoRefLogOutp1Type OBJECT-TYPE
		SYNTAX		INTEGER { disable(0), enable(1) }
		MAX-ACCESS		read-write
		STATUS			current
		DESCRIPTION
				"TYPE: - Checkbox
				 PAGE: - RollCall/Memories- Logging2
					Log Outp1 Type  cmdID= 42077 "
		::= { iqudc12CmdEntry 42077 }


	iqudc12Logging2VideoRefOutp1Type OBJECT-TYPE
		SYNTAX		RollCallString
		MAX-ACCESS		read-only
		STATUS			current
		DESCRIPTION
				"TYPE: - Display
				 PAGE: - RollCall/Memories- Logging2
					Outp1 Type=  cmdID= 42277  format=   "
		::= { iqudc12CmdEntry 42277 }


	iqudc12Logging2VideoRefLogOutp1State OBJECT-TYPE
		SYNTAX		INTEGER { disable(0), enable(1) }
		MAX-ACCESS		read-write
		STATUS			current
		DESCRIPTION
				"TYPE: - Checkbox
				 PAGE: - RollCall/Memories- Logging2
					Log Outp1 State  cmdID= 42078 "
		::= { iqudc12CmdEntry 42078 }


	iqudc12Logging2VideoRefOutp1State OBJECT-TYPE
		SYNTAX		RollCallString
		MAX-ACCESS		read-only
		STATUS			current
		DESCRIPTION
				"TYPE: - Display
				 PAGE: - RollCall/Memories- Logging2
					Outp1 State=  cmdID= 42278  format=   "
		::= { iqudc12CmdEntry 42278 }


	iqudc12Logging2VideoRefLogOutp1Std OBJECT-TYPE
		SYNTAX		INTEGER { disable(0), enable(1) }
		MAX-ACCESS		read-write
		STATUS			current
		DESCRIPTION
				"TYPE: - Checkbox
				 PAGE: - RollCall/Memories- Logging2
					Log Outp1 Std  cmdID= 42079 "
		::= { iqudc12CmdEntry 42079 }


	iqudc12Logging2VideoRefOutp1Std OBJECT-TYPE
		SYNTAX		RollCallString
		MAX-ACCESS		read-only
		STATUS			current
		DESCRIPTION
				"TYPE: - Display
				 PAGE: - RollCall/Memories- Logging2
					Outp1 Std=  cmdID= 42279  format=   "
		::= { iqudc12CmdEntry 42279 }


	iqudc12Logging2VideoRefLogOutp2State OBJECT-TYPE
		SYNTAX		INTEGER { disable(0), enable(1) }
		MAX-ACCESS		read-write
		STATUS			current
		DESCRIPTION
				"TYPE: - Checkbox
				 PAGE: - RollCall/Memories- Logging2
					Log Outp2 State  cmdID= 42086 "
		::= { iqudc12CmdEntry 42086 }


	iqudc12Logging2VideoRefOutp2State OBJECT-TYPE
		SYNTAX		RollCallString
		MAX-ACCESS		read-only
		STATUS			current
		DESCRIPTION
				"TYPE: - Display
				 PAGE: - RollCall/Memories- Logging2
					Outp2 State=  cmdID= 42286  format=   "
		::= { iqudc12CmdEntry 42286 }


	iqudc12Logging2VideoRefLogOutp2Std OBJECT-TYPE
		SYNTAX		INTEGER { disable(0), enable(1) }
		MAX-ACCESS		read-write
		STATUS			current
		DESCRIPTION
				"TYPE: - Checkbox
				 PAGE: - RollCall/Memories- Logging2
					Log Outp2 Std  cmdID= 42087 "
		::= { iqudc12CmdEntry 42087 }


	iqudc12Logging2VideoRefOutp2Std OBJECT-TYPE
		SYNTAX		RollCallString
		MAX-ACCESS		read-only
		STATUS			current
		DESCRIPTION
				"TYPE: - Display
				 PAGE: - RollCall/Memories- Logging2
					Outp2 Std=  cmdID= 42287  format=   "
		::= { iqudc12CmdEntry 42287 }


	iqudc12Logging2VideoRefLogOutp1 OBJECT-TYPE
		SYNTAX		INTEGER { disable(0), enable(1) }
		MAX-ACCESS		read-write
		STATUS			current
		DESCRIPTION
				"TYPE: - Checkbox
				 PAGE: - RollCall/Memories- Logging2
					Log Outp1  cmdID= 42080 "
		::= { iqudc12CmdEntry 42080 }


	iqudc12Logging2VideoRefOutp1 OBJECT-TYPE
		SYNTAX		RollCallString
		MAX-ACCESS		read-only
		STATUS			current
		DESCRIPTION
				"TYPE: - Display
				 PAGE: - RollCall/Memories- Logging2
					Outp1=  cmdID= 42280  format=   "
		::= { iqudc12CmdEntry 42280 }


	iqudc12Logging2VideoRefLogOutp1Capt OBJECT-TYPE
		SYNTAX		INTEGER { disable(0), enable(1) }
		MAX-ACCESS		read-write
		STATUS			current
		DESCRIPTION
				"TYPE: - Checkbox
				 PAGE: - RollCall/Memories- Logging2
					Log Outp1 Capt  cmdID= 42081 "
		::= { iqudc12CmdEntry 42081 }


	iqudc12Logging2VideoRefOutp1Capt OBJECT-TYPE
		SYNTAX		RollCallString
		MAX-ACCESS		read-only
		STATUS			current
		DESCRIPTION
				"TYPE: - Display
				 PAGE: - RollCall/Memories- Logging2
					Outp1 Capt=  cmdID= 42281  format=   "
		::= { iqudc12CmdEntry 42281 }


	iqudc12Logging2VideoRefLogRefType OBJECT-TYPE
		SYNTAX		INTEGER { disable(0), enable(1) }
		MAX-ACCESS		read-write
		STATUS			current
		DESCRIPTION
				"TYPE: - Checkbox
				 PAGE: - RollCall/Memories- Logging2
					Log Ref Type  cmdID= 42083 "
		::= { iqudc12CmdEntry 42083 }


	iqudc12Logging2VideoRefRefType OBJECT-TYPE
		SYNTAX		RollCallString
		MAX-ACCESS		read-only
		STATUS			current
		DESCRIPTION
				"TYPE: - Display
				 PAGE: - RollCall/Memories- Logging2
					Ref Type=  cmdID= 42283  format=   "
		::= { iqudc12CmdEntry 42283 }


	iqudc12Logging2VideoRefLogRefState OBJECT-TYPE
		SYNTAX		INTEGER { disable(0), enable(1) }
		MAX-ACCESS		read-write
		STATUS			current
		DESCRIPTION
				"TYPE: - Checkbox
				 PAGE: - RollCall/Memories- Logging2
					Log Ref State  cmdID= 42084 "
		::= { iqudc12CmdEntry 42084 }


	iqudc12Logging2VideoRefRefState OBJECT-TYPE
		SYNTAX		RollCallString
		MAX-ACCESS		read-only
		STATUS			current
		DESCRIPTION
				"TYPE: - Display
				 PAGE: - RollCall/Memories- Logging2
					Ref State=  cmdID= 42284  format=   "
		::= { iqudc12CmdEntry 42284 }


	iqudc12Logging2VideoRefLogRefStd OBJECT-TYPE
		SYNTAX		INTEGER { disable(0), enable(1) }
		MAX-ACCESS		read-write
		STATUS			current
		DESCRIPTION
				"TYPE: - Checkbox
				 PAGE: - RollCall/Memories- Logging2
					Log Ref Std  cmdID= 42085 "
		::= { iqudc12CmdEntry 42085 }


	iqudc12Logging2VideoRefRefStd OBJECT-TYPE
		SYNTAX		RollCallString
		MAX-ACCESS		read-only
		STATUS			current
		DESCRIPTION
				"TYPE: - Display
				 PAGE: - RollCall/Memories- Logging2
					Ref Std=  cmdID= 42285  format=   "
		::= { iqudc12CmdEntry 42285 }


	iqudc12Logging2VideoRefLogGenlockState OBJECT-TYPE
		SYNTAX		INTEGER { disable(0), enable(1) }
		MAX-ACCESS		read-write
		STATUS			current
		DESCRIPTION
				"TYPE: - Checkbox
				 PAGE: - RollCall/Memories- Logging2
					Log Genlock State  cmdID= 42082 "
		::= { iqudc12CmdEntry 42082 }


	iqudc12Logging2VideoRefGenlocState OBJECT-TYPE
		SYNTAX		RollCallString
		MAX-ACCESS		read-only
		STATUS			current
		DESCRIPTION
				"TYPE: - Display
				 PAGE: - RollCall/Memories- Logging2
					Genloc State=  cmdID= 42282  format=   "
		::= { iqudc12CmdEntry 42282 }


	iqudc12Logging2VideoRefLogInp1Ident OBJECT-TYPE
		SYNTAX		INTEGER { disable(0), enable(1) }
		MAX-ACCESS		read-write
		STATUS			current
		DESCRIPTION
				"TYPE: - Checkbox
				 PAGE: - RollCall/Memories- Logging2
					Log Inp1 Ident  cmdID= 42130 "
		::= { iqudc12CmdEntry 42130 }


	iqudc12Logging2VideoRefInp1Ident OBJECT-TYPE
		SYNTAX		RollCallString
		MAX-ACCESS		read-only
		STATUS			current
		DESCRIPTION
				"TYPE: - Display
				 PAGE: - RollCall/Memories- Logging2
					Inp1 Ident=  cmdID= 42330  format=   "
		::= { iqudc12CmdEntry 42330 }


	iqudc12Logging2VideoRefLogInp1Name OBJECT-TYPE
		SYNTAX		INTEGER { disable(0), enable(1) }
		MAX-ACCESS		read-write
		STATUS			current
		DESCRIPTION
				"TYPE: - Checkbox
				 PAGE: - RollCall/Memories- Logging2
					Log Inp1 Name  cmdID= 42133 "
		::= { iqudc12CmdEntry 42133 }


	iqudc12Logging2VideoRefInp1Name OBJECT-TYPE
		SYNTAX		RollCallString
		MAX-ACCESS		read-only
		STATUS			current
		DESCRIPTION
				"TYPE: - Display
				 PAGE: - RollCall/Memories- Logging2
					Inp1 Name=  cmdID= 42333  format=   "
		::= { iqudc12CmdEntry 42333 }


	iqudc12Logging2VideoRefLogInp2Ident OBJECT-TYPE
		SYNTAX		INTEGER { disable(0), enable(1) }
		MAX-ACCESS		read-write
		STATUS			current
		DESCRIPTION
				"TYPE: - Checkbox
				 PAGE: - RollCall/Memories- Logging2
					Log Inp2 Ident  cmdID= 42131 "
		::= { iqudc12CmdEntry 42131 }


	iqudc12Logging2VideoRefInp2Ident OBJECT-TYPE
		SYNTAX		RollCallString
		MAX-ACCESS		read-only
		STATUS			current
		DESCRIPTION
				"TYPE: - Display
				 PAGE: - RollCall/Memories- Logging2
					Inp2 Ident=  cmdID= 42331  format=   "
		::= { iqudc12CmdEntry 42331 }


	iqudc12Logging2VideoRefLogInp2Name OBJECT-TYPE
		SYNTAX		INTEGER { disable(0), enable(1) }
		MAX-ACCESS		read-write
		STATUS			current
		DESCRIPTION
				"TYPE: - Checkbox
				 PAGE: - RollCall/Memories- Logging2
					Log Inp2 Name  cmdID= 42134 "
		::= { iqudc12CmdEntry 42134 }


	iqudc12Logging2VideoRefInp2Name OBJECT-TYPE
		SYNTAX		RollCallString
		MAX-ACCESS		read-only
		STATUS			current
		DESCRIPTION
				"TYPE: - Display
				 PAGE: - RollCall/Memories- Logging2
					Inp2 Name=  cmdID= 42334  format=   "
		::= { iqudc12CmdEntry 42334 }


	iqudc12Logging2VideoRefLogInp3Ident OBJECT-TYPE
		SYNTAX		INTEGER { disable(0), enable(1) }
		MAX-ACCESS		read-write
		STATUS			current
		DESCRIPTION
				"TYPE: - Checkbox
				 PAGE: - RollCall/Memories- Logging2
					Log Inp3 Ident  cmdID= 42132 "
		::= { iqudc12CmdEntry 42132 }


	iqudc12Logging2VideoRefInp3Ident OBJECT-TYPE
		SYNTAX		RollCallString
		MAX-ACCESS		read-only
		STATUS			current
		DESCRIPTION
				"TYPE: - Display
				 PAGE: - RollCall/Memories- Logging2
					Inp3 Ident=  cmdID= 42332  format=   "
		::= { iqudc12CmdEntry 42332 }


	iqudc12Logging2VideoRefLogInp3Name OBJECT-TYPE
		SYNTAX		INTEGER { disable(0), enable(1) }
		MAX-ACCESS		read-write
		STATUS			current
		DESCRIPTION
				"TYPE: - Checkbox
				 PAGE: - RollCall/Memories- Logging2
					Log Inp3 Name  cmdID= 42135 "
		::= { iqudc12CmdEntry 42135 }


	iqudc12Logging2VideoRefInp3Name OBJECT-TYPE
		SYNTAX		RollCallString
		MAX-ACCESS		read-only
		STATUS			current
		DESCRIPTION
				"TYPE: - Display
				 PAGE: - RollCall/Memories- Logging2
					Inp3 Name=  cmdID= 42335  format=   "
		::= { iqudc12CmdEntry 42335 }


	iqudc12Logging2VideoRefLogOutp2Type OBJECT-TYPE
		SYNTAX		INTEGER { disable(0), enable(1) }
		MAX-ACCESS		read-write
		STATUS			current
		DESCRIPTION
				"TYPE: - Checkbox
				 PAGE: - RollCall/Memories- Logging2
					Log Outp2 Type  cmdID= 42620 "
		::= { iqudc12CmdEntry 42620 }


	iqudc12Logging2VideoRefOutp2Type OBJECT-TYPE
		SYNTAX		RollCallString
		MAX-ACCESS		read-only
		STATUS			current
		DESCRIPTION
				"TYPE: - Display
				 PAGE: - RollCall/Memories- Logging2
					Outp2 Type=  cmdID= 42820  format=   "
		::= { iqudc12CmdEntry 42820 }


	iqudc12Logging2VideoRefLogOutp2 OBJECT-TYPE
		SYNTAX		INTEGER { disable(0), enable(1) }
		MAX-ACCESS		read-write
		STATUS			current
		DESCRIPTION
				"TYPE: - Checkbox
				 PAGE: - RollCall/Memories- Logging2
					Log Outp2  cmdID= 42622 "
		::= { iqudc12CmdEntry 42622 }


	iqudc12Logging2VideoRefOutp2 OBJECT-TYPE
		SYNTAX		RollCallString
		MAX-ACCESS		read-only
		STATUS			current
		DESCRIPTION
				"TYPE: - Display
				 PAGE: - RollCall/Memories- Logging2
					Outp2=  cmdID= 42822  format=   "
		::= { iqudc12CmdEntry 42822 }


	iqudc12Logging2VideoRefLogOutp2Capt OBJECT-TYPE
		SYNTAX		INTEGER { disable(0), enable(1) }
		MAX-ACCESS		read-write
		STATUS			current
		DESCRIPTION
				"TYPE: - Checkbox
				 PAGE: - RollCall/Memories- Logging2
					Log Outp2 Capt  cmdID= 42624 "
		::= { iqudc12CmdEntry 42624 }


	iqudc12Logging2VideoRefOutp2Capt OBJECT-TYPE
		SYNTAX		RollCallString
		MAX-ACCESS		read-only
		STATUS			current
		DESCRIPTION
				"TYPE: - Display
				 PAGE: - RollCall/Memories- Logging2
					Outp2 Capt=  cmdID= 42824  format=   "
		::= { iqudc12CmdEntry 42824 }


	iqudc12Logging2VideoRefLogOutp3Type OBJECT-TYPE
		SYNTAX		INTEGER { disable(0), enable(1) }
		MAX-ACCESS		read-write
		STATUS			current
		DESCRIPTION
				"TYPE: - Checkbox
				 PAGE: - RollCall/Memories- Logging2
					Log Outp3 Type  cmdID= 42621 "
		::= { iqudc12CmdEntry 42621 }


	iqudc12Logging2VideoRefOutp3Type OBJECT-TYPE
		SYNTAX		RollCallString
		MAX-ACCESS		read-only
		STATUS			current
		DESCRIPTION
				"TYPE: - Display
				 PAGE: - RollCall/Memories- Logging2
					Outp3 Type=  cmdID= 42821  format=   "
		::= { iqudc12CmdEntry 42821 }


	iqudc12Logging2VideoRefLogOutp3State OBJECT-TYPE
		SYNTAX		INTEGER { disable(0), enable(1) }
		MAX-ACCESS		read-write
		STATUS			current
		DESCRIPTION
				"TYPE: - Checkbox
				 PAGE: - RollCall/Memories- Logging2
					Log Outp3 State  cmdID= 42626 "
		::= { iqudc12CmdEntry 42626 }


	iqudc12Logging2VideoRefOutp3State OBJECT-TYPE
		SYNTAX		RollCallString
		MAX-ACCESS		read-only
		STATUS			current
		DESCRIPTION
				"TYPE: - Display
				 PAGE: - RollCall/Memories- Logging2
					Outp3 State=  cmdID= 42826  format=   "
		::= { iqudc12CmdEntry 42826 }


	iqudc12Logging2VideoRefLogOutp3Std OBJECT-TYPE
		SYNTAX		INTEGER { disable(0), enable(1) }
		MAX-ACCESS		read-write
		STATUS			current
		DESCRIPTION
				"TYPE: - Checkbox
				 PAGE: - RollCall/Memories- Logging2
					Log Outp3 Std  cmdID= 42627 "
		::= { iqudc12CmdEntry 42627 }


	iqudc12Logging2VideoRefOutp3Std OBJECT-TYPE
		SYNTAX		RollCallString
		MAX-ACCESS		read-only
		STATUS			current
		DESCRIPTION
				"TYPE: - Display
				 PAGE: - RollCall/Memories- Logging2
					Outp3 Std=  cmdID= 42827  format=   "
		::= { iqudc12CmdEntry 42827 }


	iqudc12Logging2VideoRefLogOutp3 OBJECT-TYPE
		SYNTAX		INTEGER { disable(0), enable(1) }
		MAX-ACCESS		read-write
		STATUS			current
		DESCRIPTION
				"TYPE: - Checkbox
				 PAGE: - RollCall/Memories- Logging2
					Log Outp3  cmdID= 42623 "
		::= { iqudc12CmdEntry 42623 }


	iqudc12Logging2VideoRefOutp3 OBJECT-TYPE
		SYNTAX		RollCallString
		MAX-ACCESS		read-only
		STATUS			current
		DESCRIPTION
				"TYPE: - Display
				 PAGE: - RollCall/Memories- Logging2
					Outp3=  cmdID= 42823  format=   "
		::= { iqudc12CmdEntry 42823 }


	iqudc12Logging2VideoRefLogOutp3Capt OBJECT-TYPE
		SYNTAX		INTEGER { disable(0), enable(1) }
		MAX-ACCESS		read-write
		STATUS			current
		DESCRIPTION
				"TYPE: - Checkbox
				 PAGE: - RollCall/Memories- Logging2
					Log Outp3 Capt  cmdID= 42625 "
		::= { iqudc12CmdEntry 42625 }


	iqudc12Logging2VideoRefOutp3Capt OBJECT-TYPE
		SYNTAX		RollCallString
		MAX-ACCESS		read-only
		STATUS			current
		DESCRIPTION
				"TYPE: - Display
				 PAGE: - RollCall/Memories- Logging2
					Outp3 Capt=  cmdID= 42825  format=   "
		::= { iqudc12CmdEntry 42825 }


	iqudc12Logging2InEmbAudLoggingInpEmb1state OBJECT-TYPE
		SYNTAX		RollCallString
		MAX-ACCESS		read-only
		STATUS			current
		DESCRIPTION
				"TYPE: - Display
				 PAGE: - RollCall/Memories- Logging2
					Inp Emb.1 state=  cmdID= 42200  format=   "
		::= { iqudc12CmdEntry 42200 }


	iqudc12Logging2InEmbAudLoggingInpEmb2state OBJECT-TYPE
		SYNTAX		RollCallString
		MAX-ACCESS		read-only
		STATUS			current
		DESCRIPTION
				"TYPE: - Display
				 PAGE: - RollCall/Memories- Logging2
					Inp Emb.2 state=  cmdID= 42201  format=   "
		::= { iqudc12CmdEntry 42201 }


	iqudc12Logging2InEmbAudLoggingInpEmb3state OBJECT-TYPE
		SYNTAX		RollCallString
		MAX-ACCESS		read-only
		STATUS			current
		DESCRIPTION
				"TYPE: - Display
				 PAGE: - RollCall/Memories- Logging2
					Inp Emb.3 state=  cmdID= 42202  format=   "
		::= { iqudc12CmdEntry 42202 }


	iqudc12Logging2InEmbAudLoggingInpEmb4state OBJECT-TYPE
		SYNTAX		RollCallString
		MAX-ACCESS		read-only
		STATUS			current
		DESCRIPTION
				"TYPE: - Display
				 PAGE: - RollCall/Memories- Logging2
					Inp Emb.4 state=  cmdID= 42203  format=   "
		::= { iqudc12CmdEntry 42203 }


	iqudc12Logging2InEmbAudLoggingInpEmb5state OBJECT-TYPE
		SYNTAX		RollCallString
		MAX-ACCESS		read-only
		STATUS			current
		DESCRIPTION
				"TYPE: - Display
				 PAGE: - RollCall/Memories- Logging2
					Inp Emb.5 state=  cmdID= 42204  format=   "
		::= { iqudc12CmdEntry 42204 }


	iqudc12Logging2InEmbAudLoggingInpEmb6state OBJECT-TYPE
		SYNTAX		RollCallString
		MAX-ACCESS		read-only
		STATUS			current
		DESCRIPTION
				"TYPE: - Display
				 PAGE: - RollCall/Memories- Logging2
					Inp Emb.6 state=  cmdID= 42205  format=   "
		::= { iqudc12CmdEntry 42205 }


	iqudc12Logging2InEmbAudLoggingInpEmb7state OBJECT-TYPE
		SYNTAX		RollCallString
		MAX-ACCESS		read-only
		STATUS			current
		DESCRIPTION
				"TYPE: - Display
				 PAGE: - RollCall/Memories- Logging2
					Inp Emb.7 state=  cmdID= 42206  format=   "
		::= { iqudc12CmdEntry 42206 }


	iqudc12Logging2InEmbAudLoggingInpEmb8state OBJECT-TYPE
		SYNTAX		RollCallString
		MAX-ACCESS		read-only
		STATUS			current
		DESCRIPTION
				"TYPE: - Display
				 PAGE: - RollCall/Memories- Logging2
					Inp Emb.8 state=  cmdID= 42207  format=   "
		::= { iqudc12CmdEntry 42207 }


	iqudc12Logging2In1EmbAudLoggingLogInp1Emb1stat OBJECT-TYPE
		SYNTAX		INTEGER { disable(0), enable(1) }
		MAX-ACCESS		read-write
		STATUS			current
		DESCRIPTION
				"TYPE: - Checkbox
				 PAGE: - RollCall/Memories- Logging2
					Log Inp1 Emb.1 stat  cmdID= 42139 "
		::= { iqudc12CmdEntry 42139 }


	iqudc12Logging2In1EmbAudLoggingInp1Emb1state OBJECT-TYPE
		SYNTAX		RollCallString
		MAX-ACCESS		read-only
		STATUS			current
		DESCRIPTION
				"TYPE: - Display
				 PAGE: - RollCall/Memories- Logging2
					Inp1 Emb.1 state=  cmdID= 42339  format=   "
		::= { iqudc12CmdEntry 42339 }


	iqudc12Logging2In1EmbAudLoggingLogInp1Emb2stat OBJECT-TYPE
		SYNTAX		INTEGER { disable(0), enable(1) }
		MAX-ACCESS		read-write
		STATUS			current
		DESCRIPTION
				"TYPE: - Checkbox
				 PAGE: - RollCall/Memories- Logging2
					Log Inp1 Emb.2 stat  cmdID= 42140 "
		::= { iqudc12CmdEntry 42140 }


	iqudc12Logging2In1EmbAudLoggingInp1Emb2state OBJECT-TYPE
		SYNTAX		RollCallString
		MAX-ACCESS		read-only
		STATUS			current
		DESCRIPTION
				"TYPE: - Display
				 PAGE: - RollCall/Memories- Logging2
					Inp1 Emb.2 state=  cmdID= 42340  format=   "
		::= { iqudc12CmdEntry 42340 }


	iqudc12Logging2In1EmbAudLoggingLogInp1Emb3stat OBJECT-TYPE
		SYNTAX		INTEGER { disable(0), enable(1) }
		MAX-ACCESS		read-write
		STATUS			current
		DESCRIPTION
				"TYPE: - Checkbox
				 PAGE: - RollCall/Memories- Logging2
					Log Inp1 Emb.3 stat  cmdID= 42141 "
		::= { iqudc12CmdEntry 42141 }


	iqudc12Logging2In1EmbAudLoggingInp1Emb3state OBJECT-TYPE
		SYNTAX		RollCallString
		MAX-ACCESS		read-only
		STATUS			current
		DESCRIPTION
				"TYPE: - Display
				 PAGE: - RollCall/Memories- Logging2
					Inp1 Emb.3 state=  cmdID= 42341  format=   "
		::= { iqudc12CmdEntry 42341 }


	iqudc12Logging2In1EmbAudLoggingLogInp1Emb4stat OBJECT-TYPE
		SYNTAX		INTEGER { disable(0), enable(1) }
		MAX-ACCESS		read-write
		STATUS			current
		DESCRIPTION
				"TYPE: - Checkbox
				 PAGE: - RollCall/Memories- Logging2
					Log Inp1 Emb.4 stat  cmdID= 42142 "
		::= { iqudc12CmdEntry 42142 }


	iqudc12Logging2In1EmbAudLoggingInp1Emb4state OBJECT-TYPE
		SYNTAX		RollCallString
		MAX-ACCESS		read-only
		STATUS			current
		DESCRIPTION
				"TYPE: - Display
				 PAGE: - RollCall/Memories- Logging2
					Inp1 Emb.4 state=  cmdID= 42342  format=   "
		::= { iqudc12CmdEntry 42342 }


	iqudc12Logging2In1EmbAudLoggingLogInp1Emb5stat OBJECT-TYPE
		SYNTAX		INTEGER { disable(0), enable(1) }
		MAX-ACCESS		read-write
		STATUS			current
		DESCRIPTION
				"TYPE: - Checkbox
				 PAGE: - RollCall/Memories- Logging2
					Log Inp1 Emb.5 stat  cmdID= 42143 "
		::= { iqudc12CmdEntry 42143 }


	iqudc12Logging2In1EmbAudLoggingInp1Emb5state OBJECT-TYPE
		SYNTAX		RollCallString
		MAX-ACCESS		read-only
		STATUS			current
		DESCRIPTION
				"TYPE: - Display
				 PAGE: - RollCall/Memories- Logging2
					Inp1 Emb.5 state=  cmdID= 42343  format=   "
		::= { iqudc12CmdEntry 42343 }


	iqudc12Logging2In1EmbAudLoggingLogInp1Emb6stat OBJECT-TYPE
		SYNTAX		INTEGER { disable(0), enable(1) }
		MAX-ACCESS		read-write
		STATUS			current
		DESCRIPTION
				"TYPE: - Checkbox
				 PAGE: - RollCall/Memories- Logging2
					Log Inp1 Emb.6 stat  cmdID= 42144 "
		::= { iqudc12CmdEntry 42144 }


	iqudc12Logging2In1EmbAudLoggingInp1Emb6state OBJECT-TYPE
		SYNTAX		RollCallString
		MAX-ACCESS		read-only
		STATUS			current
		DESCRIPTION
				"TYPE: - Display
				 PAGE: - RollCall/Memories- Logging2
					Inp1 Emb.6 state=  cmdID= 42344  format=   "
		::= { iqudc12CmdEntry 42344 }


	iqudc12Logging2In1EmbAudLoggingLogInp1Emb7stat OBJECT-TYPE
		SYNTAX		INTEGER { disable(0), enable(1) }
		MAX-ACCESS		read-write
		STATUS			current
		DESCRIPTION
				"TYPE: - Checkbox
				 PAGE: - RollCall/Memories- Logging2
					Log Inp1 Emb.7 stat  cmdID= 42145 "
		::= { iqudc12CmdEntry 42145 }


	iqudc12Logging2In1EmbAudLoggingInp1Emb7state OBJECT-TYPE
		SYNTAX		RollCallString
		MAX-ACCESS		read-only
		STATUS			current
		DESCRIPTION
				"TYPE: - Display
				 PAGE: - RollCall/Memories- Logging2
					Inp1 Emb.7 state=  cmdID= 42345  format=   "
		::= { iqudc12CmdEntry 42345 }


	iqudc12Logging2In1EmbAudLoggingLogInp1Emb8stat OBJECT-TYPE
		SYNTAX		INTEGER { disable(0), enable(1) }
		MAX-ACCESS		read-write
		STATUS			current
		DESCRIPTION
				"TYPE: - Checkbox
				 PAGE: - RollCall/Memories- Logging2
					Log Inp1 Emb.8 stat  cmdID= 42146 "
		::= { iqudc12CmdEntry 42146 }


	iqudc12Logging2In1EmbAudLoggingInp1Emb8state OBJECT-TYPE
		SYNTAX		RollCallString
		MAX-ACCESS		read-only
		STATUS			current
		DESCRIPTION
				"TYPE: - Display
				 PAGE: - RollCall/Memories- Logging2
					Inp1 Emb.8 state=  cmdID= 42346  format=   "
		::= { iqudc12CmdEntry 42346 }


	iqudc12Logging2In2EmbAudLoggingLogInp2Emb1stat OBJECT-TYPE
		SYNTAX		INTEGER { disable(0), enable(1) }
		MAX-ACCESS		read-write
		STATUS			current
		DESCRIPTION
				"TYPE: - Checkbox
				 PAGE: - RollCall/Memories- Logging2
					Log Inp2 Emb.1 stat  cmdID= 42147 "
		::= { iqudc12CmdEntry 42147 }


	iqudc12Logging2In2EmbAudLoggingInp2Emb1state OBJECT-TYPE
		SYNTAX		RollCallString
		MAX-ACCESS		read-only
		STATUS			current
		DESCRIPTION
				"TYPE: - Display
				 PAGE: - RollCall/Memories- Logging2
					Inp2 Emb.1 state=  cmdID= 42347  format=   "
		::= { iqudc12CmdEntry 42347 }


	iqudc12Logging2In2EmbAudLoggingLogInp2Emb2stat OBJECT-TYPE
		SYNTAX		INTEGER { disable(0), enable(1) }
		MAX-ACCESS		read-write
		STATUS			current
		DESCRIPTION
				"TYPE: - Checkbox
				 PAGE: - RollCall/Memories- Logging2
					Log Inp2 Emb.2 stat  cmdID= 42148 "
		::= { iqudc12CmdEntry 42148 }


	iqudc12Logging2In2EmbAudLoggingInp2Emb2state OBJECT-TYPE
		SYNTAX		RollCallString
		MAX-ACCESS		read-only
		STATUS			current
		DESCRIPTION
				"TYPE: - Display
				 PAGE: - RollCall/Memories- Logging2
					Inp2 Emb.2 state=  cmdID= 42348  format=   "
		::= { iqudc12CmdEntry 42348 }


	iqudc12Logging2In2EmbAudLoggingLogInp2Emb3stat OBJECT-TYPE
		SYNTAX		INTEGER { disable(0), enable(1) }
		MAX-ACCESS		read-write
		STATUS			current
		DESCRIPTION
				"TYPE: - Checkbox
				 PAGE: - RollCall/Memories- Logging2
					Log Inp2 Emb.3 stat  cmdID= 42149 "
		::= { iqudc12CmdEntry 42149 }


	iqudc12Logging2In2EmbAudLoggingInp2Emb3state OBJECT-TYPE
		SYNTAX		RollCallString
		MAX-ACCESS		read-only
		STATUS			current
		DESCRIPTION
				"TYPE: - Display
				 PAGE: - RollCall/Memories- Logging2
					Inp2 Emb.3 state=  cmdID= 42349  format=   "
		::= { iqudc12CmdEntry 42349 }


	iqudc12Logging2In2EmbAudLoggingLogInp2Emb4stat OBJECT-TYPE
		SYNTAX		INTEGER { disable(0), enable(1) }
		MAX-ACCESS		read-write
		STATUS			current
		DESCRIPTION
				"TYPE: - Checkbox
				 PAGE: - RollCall/Memories- Logging2
					Log Inp2 Emb.4 stat  cmdID= 42150 "
		::= { iqudc12CmdEntry 42150 }


	iqudc12Logging2In2EmbAudLoggingInp2Emb4state OBJECT-TYPE
		SYNTAX		RollCallString
		MAX-ACCESS		read-only
		STATUS			current
		DESCRIPTION
				"TYPE: - Display
				 PAGE: - RollCall/Memories- Logging2
					Inp2 Emb.4 state=  cmdID= 42350  format=   "
		::= { iqudc12CmdEntry 42350 }


	iqudc12Logging2In2EmbAudLoggingLogInp2Emb5stat OBJECT-TYPE
		SYNTAX		INTEGER { disable(0), enable(1) }
		MAX-ACCESS		read-write
		STATUS			current
		DESCRIPTION
				"TYPE: - Checkbox
				 PAGE: - RollCall/Memories- Logging2
					Log Inp2 Emb.5 stat  cmdID= 42151 "
		::= { iqudc12CmdEntry 42151 }


	iqudc12Logging2In2EmbAudLoggingInp2Emb5state OBJECT-TYPE
		SYNTAX		RollCallString
		MAX-ACCESS		read-only
		STATUS			current
		DESCRIPTION
				"TYPE: - Display
				 PAGE: - RollCall/Memories- Logging2
					Inp2 Emb.5 state=  cmdID= 42351  format=   "
		::= { iqudc12CmdEntry 42351 }


	iqudc12Logging2In2EmbAudLoggingLogInp2Emb6stat OBJECT-TYPE
		SYNTAX		INTEGER { disable(0), enable(1) }
		MAX-ACCESS		read-write
		STATUS			current
		DESCRIPTION
				"TYPE: - Checkbox
				 PAGE: - RollCall/Memories- Logging2
					Log Inp2 Emb.6 stat  cmdID= 42152 "
		::= { iqudc12CmdEntry 42152 }


	iqudc12Logging2In2EmbAudLoggingInp2Emb6state OBJECT-TYPE
		SYNTAX		RollCallString
		MAX-ACCESS		read-only
		STATUS			current
		DESCRIPTION
				"TYPE: - Display
				 PAGE: - RollCall/Memories- Logging2
					Inp2 Emb.6 state=  cmdID= 42352  format=   "
		::= { iqudc12CmdEntry 42352 }


	iqudc12Logging2In2EmbAudLoggingLogInp2Emb7stat OBJECT-TYPE
		SYNTAX		INTEGER { disable(0), enable(1) }
		MAX-ACCESS		read-write
		STATUS			current
		DESCRIPTION
				"TYPE: - Checkbox
				 PAGE: - RollCall/Memories- Logging2
					Log Inp2 Emb.7 stat  cmdID= 42153 "
		::= { iqudc12CmdEntry 42153 }


	iqudc12Logging2In2EmbAudLoggingInp2Emb7state OBJECT-TYPE
		SYNTAX		RollCallString
		MAX-ACCESS		read-only
		STATUS			current
		DESCRIPTION
				"TYPE: - Display
				 PAGE: - RollCall/Memories- Logging2
					Inp2 Emb.7 state=  cmdID= 42353  format=   "
		::= { iqudc12CmdEntry 42353 }


	iqudc12Logging2In2EmbAudLoggingLogInp2Emb8stat OBJECT-TYPE
		SYNTAX		INTEGER { disable(0), enable(1) }
		MAX-ACCESS		read-write
		STATUS			current
		DESCRIPTION
				"TYPE: - Checkbox
				 PAGE: - RollCall/Memories- Logging2
					Log Inp2 Emb.8 stat  cmdID= 42154 "
		::= { iqudc12CmdEntry 42154 }


	iqudc12Logging2In2EmbAudLoggingInp2Emb8state OBJECT-TYPE
		SYNTAX		RollCallString
		MAX-ACCESS		read-only
		STATUS			current
		DESCRIPTION
				"TYPE: - Display
				 PAGE: - RollCall/Memories- Logging2
					Inp2 Emb.8 state=  cmdID= 42354  format=   "
		::= { iqudc12CmdEntry 42354 }


	iqudc12Logging2DolbyEAlignLogOutEmb1dolby OBJECT-TYPE
		SYNTAX		INTEGER { disable(0), enable(1) }
		MAX-ACCESS		read-write
		STATUS			current
		DESCRIPTION
				"TYPE: - Checkbox
				 PAGE: - RollCall/Memories- Logging2
					Log Out Emb.1 dolby  cmdID= 42160 "
		::= { iqudc12CmdEntry 42160 }


	iqudc12Logging2DolbyEAlignOutEmb1Dolby OBJECT-TYPE
		SYNTAX		RollCallString
		MAX-ACCESS		read-only
		STATUS			current
		DESCRIPTION
				"TYPE: - Display
				 PAGE: - RollCall/Memories- Logging2
					Out Emb.1 Dolby=  cmdID= 42360  format=   "
		::= { iqudc12CmdEntry 42360 }


	iqudc12Logging2DolbyEAlignLogOutEmb2dolby OBJECT-TYPE
		SYNTAX		INTEGER { disable(0), enable(1) }
		MAX-ACCESS		read-write
		STATUS			current
		DESCRIPTION
				"TYPE: - Checkbox
				 PAGE: - RollCall/Memories- Logging2
					Log Out Emb.2 dolby  cmdID= 42161 "
		::= { iqudc12CmdEntry 42161 }


	iqudc12Logging2DolbyEAlignOutEmb2Dolby OBJECT-TYPE
		SYNTAX		RollCallString
		MAX-ACCESS		read-only
		STATUS			current
		DESCRIPTION
				"TYPE: - Display
				 PAGE: - RollCall/Memories- Logging2
					Out Emb.2 Dolby=  cmdID= 42361  format=   "
		::= { iqudc12CmdEntry 42361 }


	iqudc12Logging2DolbyEAlignLogOutEmb3dolby OBJECT-TYPE
		SYNTAX		INTEGER { disable(0), enable(1) }
		MAX-ACCESS		read-write
		STATUS			current
		DESCRIPTION
				"TYPE: - Checkbox
				 PAGE: - RollCall/Memories- Logging2
					Log Out Emb.3 dolby  cmdID= 42162 "
		::= { iqudc12CmdEntry 42162 }


	iqudc12Logging2DolbyEAlignOutEmb3Dolby OBJECT-TYPE
		SYNTAX		RollCallString
		MAX-ACCESS		read-only
		STATUS			current
		DESCRIPTION
				"TYPE: - Display
				 PAGE: - RollCall/Memories- Logging2
					Out Emb.3 Dolby=  cmdID= 42362  format=   "
		::= { iqudc12CmdEntry 42362 }


	iqudc12Logging2DolbyEAlignLogOutEmb4dolby OBJECT-TYPE
		SYNTAX		INTEGER { disable(0), enable(1) }
		MAX-ACCESS		read-write
		STATUS			current
		DESCRIPTION
				"TYPE: - Checkbox
				 PAGE: - RollCall/Memories- Logging2
					Log Out Emb.4 dolby  cmdID= 42163 "
		::= { iqudc12CmdEntry 42163 }


	iqudc12Logging2DolbyEAlignOutEmb4Dolby OBJECT-TYPE
		SYNTAX		RollCallString
		MAX-ACCESS		read-only
		STATUS			current
		DESCRIPTION
				"TYPE: - Display
				 PAGE: - RollCall/Memories- Logging2
					Out Emb.4 Dolby=  cmdID= 42363  format=   "
		::= { iqudc12CmdEntry 42363 }


	iqudc12Logging2DolbyEAlignLogOutEmb5dolby OBJECT-TYPE
		SYNTAX		INTEGER { disable(0), enable(1) }
		MAX-ACCESS		read-write
		STATUS			current
		DESCRIPTION
				"TYPE: - Checkbox
				 PAGE: - RollCall/Memories- Logging2
					Log Out Emb.5 dolby  cmdID= 42164 "
		::= { iqudc12CmdEntry 42164 }


	iqudc12Logging2DolbyEAlignOutEmb5Dolby OBJECT-TYPE
		SYNTAX		RollCallString
		MAX-ACCESS		read-only
		STATUS			current
		DESCRIPTION
				"TYPE: - Display
				 PAGE: - RollCall/Memories- Logging2
					Out Emb.5 Dolby=  cmdID= 42364  format=   "
		::= { iqudc12CmdEntry 42364 }


	iqudc12Logging2DolbyEAlignLogOutEmb6dolby OBJECT-TYPE
		SYNTAX		INTEGER { disable(0), enable(1) }
		MAX-ACCESS		read-write
		STATUS			current
		DESCRIPTION
				"TYPE: - Checkbox
				 PAGE: - RollCall/Memories- Logging2
					Log Out Emb.6 dolby  cmdID= 42165 "
		::= { iqudc12CmdEntry 42165 }


	iqudc12Logging2DolbyEAlignOutEmb6Dolby OBJECT-TYPE
		SYNTAX		RollCallString
		MAX-ACCESS		read-only
		STATUS			current
		DESCRIPTION
				"TYPE: - Display
				 PAGE: - RollCall/Memories- Logging2
					Out Emb.6 Dolby=  cmdID= 42365  format=   "
		::= { iqudc12CmdEntry 42365 }


	iqudc12Logging2DolbyEAlignLogOutEmb7dolby OBJECT-TYPE
		SYNTAX		INTEGER { disable(0), enable(1) }
		MAX-ACCESS		read-write
		STATUS			current
		DESCRIPTION
				"TYPE: - Checkbox
				 PAGE: - RollCall/Memories- Logging2
					Log Out Emb.7 dolby  cmdID= 42166 "
		::= { iqudc12CmdEntry 42166 }


	iqudc12Logging2DolbyEAlignOutEmb7Dolby OBJECT-TYPE
		SYNTAX		RollCallString
		MAX-ACCESS		read-only
		STATUS			current
		DESCRIPTION
				"TYPE: - Display
				 PAGE: - RollCall/Memories- Logging2
					Out Emb.7 Dolby=  cmdID= 42366  format=   "
		::= { iqudc12CmdEntry 42366 }


	iqudc12Logging2DolbyEAlignLogOutEmb8dolby OBJECT-TYPE
		SYNTAX		INTEGER { disable(0), enable(1) }
		MAX-ACCESS		read-write
		STATUS			current
		DESCRIPTION
				"TYPE: - Checkbox
				 PAGE: - RollCall/Memories- Logging2
					Log Out Emb.8 dolby  cmdID= 42167 "
		::= { iqudc12CmdEntry 42167 }


	iqudc12Logging2DolbyEAlignOutEmb8Dolby OBJECT-TYPE
		SYNTAX		RollCallString
		MAX-ACCESS		read-only
		STATUS			current
		DESCRIPTION
				"TYPE: - Display
				 PAGE: - RollCall/Memories- Logging2
					Out Emb.8 Dolby=  cmdID= 42367  format=   "
		::= { iqudc12CmdEntry 42367 }


	iqudc12Logging2MiscLoggingLogSerialNo OBJECT-TYPE
		SYNTAX		INTEGER { disable(0), enable(1) }
		MAX-ACCESS		read-write
		STATUS			current
		DESCRIPTION
				"TYPE: - Checkbox
				 PAGE: - RollCall/Memories- Logging2
					Log Serial No.  cmdID= 35015 "
		::= { iqudc12CmdEntry 35015 }


	iqudc12Logging2MiscLoggingSerialNo OBJECT-TYPE
		SYNTAX		RollCallString
		MAX-ACCESS		read-only
		STATUS			current
		DESCRIPTION
				"TYPE: - Display
				 PAGE: - RollCall/Memories- Logging2
					Serial No.=  cmdID= 36015  format=   "
		::= { iqudc12CmdEntry 36015 }


	iqudc12Logging2MiscLoggingLogOSVersion OBJECT-TYPE
		SYNTAX		INTEGER { disable(0), enable(1) }
		MAX-ACCESS		read-write
		STATUS			current
		DESCRIPTION
				"TYPE: - Checkbox
				 PAGE: - RollCall/Memories- Logging2
					Log OS Version  cmdID= 35993 "
		::= { iqudc12CmdEntry 35993 }


	iqudc12Logging2MiscLoggingOSVersion OBJECT-TYPE
		SYNTAX		RollCallString
		MAX-ACCESS		read-only
		STATUS			current
		DESCRIPTION
				"TYPE: - Display
				 PAGE: - RollCall/Memories- Logging2
					OS Version=  cmdID= 36993  format=   "
		::= { iqudc12CmdEntry 36993 }


	iqudc12Logging2MiscLoggingLogBuildNo OBJECT-TYPE
		SYNTAX		INTEGER { disable(0), enable(1) }
		MAX-ACCESS		read-write
		STATUS			current
		DESCRIPTION
				"TYPE: - Checkbox
				 PAGE: - RollCall/Memories- Logging2
					Log Build No.  cmdID= 35990 "
		::= { iqudc12CmdEntry 35990 }


	iqudc12Logging2MiscLoggingBuildNo OBJECT-TYPE
		SYNTAX		RollCallString
		MAX-ACCESS		read-only
		STATUS			current
		DESCRIPTION
				"TYPE: - Display
				 PAGE: - RollCall/Memories- Logging2
					Build No.=  cmdID= 36990  format=   "
		::= { iqudc12CmdEntry 36990 }


	iqudc12Logging2MiscLoggingLogHardwareVer OBJECT-TYPE
		SYNTAX		INTEGER { disable(0), enable(1) }
		MAX-ACCESS		read-write
		STATUS			current
		DESCRIPTION
				"TYPE: - Checkbox
				 PAGE: - RollCall/Memories- Logging2
					Log Hardware Ver.  cmdID= 35992 "
		::= { iqudc12CmdEntry 35992 }


	iqudc12Logging2MiscLoggingHardwareVer OBJECT-TYPE
		SYNTAX		RollCallString
		MAX-ACCESS		read-only
		STATUS			current
		DESCRIPTION
				"TYPE: - Display
				 PAGE: - RollCall/Memories- Logging2
					Hardware Ver.=  cmdID= 36992  format=   "
		::= { iqudc12CmdEntry 36992 }


	iqudc12Logging2MiscLoggingLogFirmwareVer OBJECT-TYPE
		SYNTAX		INTEGER { disable(0), enable(1) }
		MAX-ACCESS		read-write
		STATUS			current
		DESCRIPTION
				"TYPE: - Checkbox
				 PAGE: - RollCall/Memories- Logging2
					Log Firmware Ver.  cmdID= 35991 "
		::= { iqudc12CmdEntry 35991 }


	iqudc12Logging2MiscLoggingFirmwareVer OBJECT-TYPE
		SYNTAX		RollCallString
		MAX-ACCESS		read-only
		STATUS			current
		DESCRIPTION
				"TYPE: - Display
				 PAGE: - RollCall/Memories- Logging2
					Firmware Ver.=  cmdID= 36991  format=   "
		::= { iqudc12CmdEntry 36991 }


	iqudc12Logging2MiscLoggingLogUpTime OBJECT-TYPE
		SYNTAX		INTEGER { disable(0), enable(1) }
		MAX-ACCESS		read-write
		STATUS			current
		DESCRIPTION
				"TYPE: - Checkbox
				 PAGE: - RollCall/Memories- Logging2
					Log Up Time  cmdID= 35994 "
		::= { iqudc12CmdEntry 35994 }


	iqudc12Logging2MiscLoggingUpTime OBJECT-TYPE
		SYNTAX		RollCallString
		MAX-ACCESS		read-only
		STATUS			current
		DESCRIPTION
				"TYPE: - Display
				 PAGE: - RollCall/Memories- Logging2
					Up Time=  cmdID= 36994  format=   "
		::= { iqudc12CmdEntry 36994 }


	iqudc12Logging2MiscLoggingLogLicensedOpt OBJECT-TYPE
		SYNTAX		INTEGER { disable(0), enable(1) }
		MAX-ACCESS		read-write
		STATUS			current
		DESCRIPTION
				"TYPE: - Checkbox
				 PAGE: - RollCall/Memories- Logging2
					Log Licensed Opt.  cmdID= 35995 "
		::= { iqudc12CmdEntry 35995 }


	iqudc12Logging2MiscLoggingLicensedOptions OBJECT-TYPE
		SYNTAX		RollCallString
		MAX-ACCESS		read-only
		STATUS			current
		DESCRIPTION
				"TYPE: - Display
				 PAGE: - RollCall/Memories- Logging2
					Licensed Options   cmdID= 36995  format=   "
		::= { iqudc12CmdEntry 36995 }


	iqudc12Logging2MiscLoggingLogLicensedOpt2 OBJECT-TYPE
		SYNTAX		INTEGER { disable(0), enable(1) }
		MAX-ACCESS		read-write
		STATUS			current
		DESCRIPTION
				"TYPE: - Checkbox
				 PAGE: - RollCall/Memories- Logging2
					Log Licensed Opt2.  cmdID= 35996 "
		::= { iqudc12CmdEntry 35996 }


	iqudc12Logging2MiscLoggingLicensedOptions2 OBJECT-TYPE
		SYNTAX		RollCallString
		MAX-ACCESS		read-only
		STATUS			current
		DESCRIPTION
				"TYPE: - Display
				 PAGE: - RollCall/Memories- Logging2
					Licensed Options 2  cmdID= 36996  format=   "
		::= { iqudc12CmdEntry 36996 }


	iqudc12Logging2MiscLoggingLogTemp1State OBJECT-TYPE
		SYNTAX		INTEGER { disable(0), enable(1) }
		MAX-ACCESS		read-write
		STATUS			current
		DESCRIPTION
				"TYPE: - Checkbox
				 PAGE: - RollCall/Memories- Logging2
					Log Temp1State  cmdID= 42137 "
		::= { iqudc12CmdEntry 42137 }


	iqudc12Logging2MiscLoggingTemp1State OBJECT-TYPE
		SYNTAX		RollCallString
		MAX-ACCESS		read-only
		STATUS			current
		DESCRIPTION
				"TYPE: - Display
				 PAGE: - RollCall/Memories- Logging2
					Temp1State=  cmdID= 42337  format=   "
		::= { iqudc12CmdEntry 42337 }


	iqudc12Logging2MiscLoggingLogTemp1Name OBJECT-TYPE
		SYNTAX		INTEGER { disable(0), enable(1) }
		MAX-ACCESS		read-write
		STATUS			current
		DESCRIPTION
				"TYPE: - Checkbox
				 PAGE: - RollCall/Memories- Logging2
					Log Temp1Name  cmdID= 42138 "
		::= { iqudc12CmdEntry 42138 }


	iqudc12Logging2MiscLoggingTemp1Name OBJECT-TYPE
		SYNTAX		RollCallString
		MAX-ACCESS		read-only
		STATUS			current
		DESCRIPTION
				"TYPE: - Display
				 PAGE: - RollCall/Memories- Logging2
					Temp1Name=  cmdID= 42338  format=   "
		::= { iqudc12CmdEntry 42338 }


	iqudc12Logging2MiscLoggingLogRearId OBJECT-TYPE
		SYNTAX		INTEGER { disable(0), enable(1) }
		MAX-ACCESS		read-write
		STATUS			current
		DESCRIPTION
				"TYPE: - Checkbox
				 PAGE: - RollCall/Memories- Logging2
					Log RearId  cmdID= 35997 "
		::= { iqudc12CmdEntry 35997 }


	iqudc12Logging2MiscLoggingRearID OBJECT-TYPE
		SYNTAX		RollCallString
		MAX-ACCESS		read-only
		STATUS			current
		DESCRIPTION
				"TYPE: - Display
				 PAGE: - RollCall/Memories- Logging2
					RearID=  cmdID= 36997  format=   "
		::= { iqudc12CmdEntry 36997 }


	iqudc12Logging2MiscLoggingLogSlotWidth OBJECT-TYPE
		SYNTAX		INTEGER { disable(0), enable(1) }
		MAX-ACCESS		read-write
		STATUS			current
		DESCRIPTION
				"TYPE: - Checkbox
				 PAGE: - RollCall/Memories- Logging2
					Log Slot Width  cmdID= 35998 "
		::= { iqudc12CmdEntry 35998 }


	iqudc12Logging2MiscLoggingSlotWidth OBJECT-TYPE
		SYNTAX		RollCallString
		MAX-ACCESS		read-only
		STATUS			current
		DESCRIPTION
				"TYPE: - Display
				 PAGE: - RollCall/Memories- Logging2
					SlotWidth=  cmdID= 36998  format=   "
		::= { iqudc12CmdEntry 36998 }


	iqudc12Logging2MiscLoggingLogSlotStart OBJECT-TYPE
		SYNTAX		INTEGER { disable(0), enable(1) }
		MAX-ACCESS		read-write
		STATUS			current
		DESCRIPTION
				"TYPE: - Checkbox
				 PAGE: - RollCall/Memories- Logging2
					Log Slot Start  cmdID= 35999 "
		::= { iqudc12CmdEntry 35999 }


	iqudc12Logging2MiscLoggingSlotStart OBJECT-TYPE
		SYNTAX		RollCallString
		MAX-ACCESS		read-only
		STATUS			current
		DESCRIPTION
				"TYPE: - Display
				 PAGE: - RollCall/Memories- Logging2
					SlotStart=  cmdID= 36999  format=   "
		::= { iqudc12CmdEntry 36999 }


	iqudc12Logging2MiscLoggingLogRearStatus OBJECT-TYPE
		SYNTAX		INTEGER { disable(0), enable(1) }
		MAX-ACCESS		read-write
		STATUS			current
		DESCRIPTION
				"TYPE: - Checkbox
				 PAGE: - RollCall/Memories- Logging2
					Log RearStatus  cmdID= 36000 "
		::= { iqudc12CmdEntry 36000 }


	iqudc12Logging2MiscLoggingRearSTATUS OBJECT-TYPE
		SYNTAX		RollCallString
		MAX-ACCESS		read-only
		STATUS			current
		DESCRIPTION
				"TYPE: - Display
				 PAGE: - RollCall/Memories- Logging2
					RearSTATUS=  cmdID= 37000  format=   "
		::= { iqudc12CmdEntry 37000 }


	iqudc12Logging2MiscLoggingLogPowerUsage OBJECT-TYPE
		SYNTAX		INTEGER { disable(0), enable(1) }
		MAX-ACCESS		read-write
		STATUS			current
		DESCRIPTION
				"TYPE: - Checkbox
				 PAGE: - RollCall/Memories- Logging2
					Log Power Usage  cmdID= 36001 "
		::= { iqudc12CmdEntry 36001 }


	iqudc12Logging2MiscLoggingPowerUsage OBJECT-TYPE
		SYNTAX		RollCallString
		MAX-ACCESS		read-only
		STATUS			current
		DESCRIPTION
				"TYPE: - Display
				 PAGE: - RollCall/Memories- Logging2
					PowerUsage=  cmdID= 37003  format=   "
		::= { iqudc12CmdEntry 37003 }


	iqudc12RollCallMemoriesRollTrackDisableAll OBJECT-TYPE
		SYNTAX		INTEGER { disable(0), enable(1) }
		MAX-ACCESS		read-write
		STATUS			current
		DESCRIPTION
				"TYPE: - Checkbox
				 PAGE: - RollCall/Memories
					Disable All  cmdID= 36104 "
		::= { iqudc12CmdEntry 36104 }


	iqudc12RollCallMemoriesRollTrackIndex OBJECT-TYPE
		SYNTAX		INTEGER
		MAX-ACCESS		read-write
		STATUS			current
		DESCRIPTION
				"TYPE: - BarGraph
				 PAGE: - RollCall/Memories
					Index  cmdID= 36100  min= 1  max= 32   step= 1  format= %0.0f  div_scale= 1 
					Min = 1  Max = 32  Step = 1 "
		::= { iqudc12CmdEntry 36100 }


	iqudc12RollCallMemoriesRollTrackSource OBJECT-TYPE
		SYNTAX		INTEGER {
							val-Unused(-1),
							val-Video-Delay(0),
							val-Input-Present(2),
							val-Input-1-Present(3),
							val-Input-2-Present(4),
							val-Analog-Present(5),
							val-Input-Loss(6),
							val-Input-1-Loss(7),
							val-Input-2-Loss(8),
							val-Analog-Loss(9),
							val-Input-1-Select(10),
							val-Input-2-Select(11),
							val-Analog-Select(12),
							val-Input-1080-59p(13),
							val-Input-1080-50p(14),
							val-Input-1080-29i(15),
							val-Input-1080-25i(16),
							val-Input-1080-23sF(102),
							val-Input-1080-29p(103),
							val-Input-1080-25sF(105),
							val-Input-1080-25p(104),
							val-Input-720-59p(17),
							val-Input-720-50p(18),
							val-Input-525-29i(19),
							val-Input-625-25i(20),
							val-Output-Black-On(21),
							val-Output-Black-Off(22),
							val-Output-Freeze(23),
							val-Output-UnFreeze(24),
							val-Output-Pattern-On(25),
							val-Output-Pattern-Off(26),
							val-Output-Caption-On(27),
							val-Output-Caption-Off(28),
							val-Reference-OK(29),
							val-Reference-Loss(30),
							val-AES-1-PCM(31),
							val-AES-1-Data(32),
							val-AES-1-DolbyE(33),
							val-AES-1-Loss(34),
							val-AES-2-PCM(35),
							val-AES-2-Data(36),
							val-AES-2-DolbyE(37),
							val-AES-2-Loss(38),
							val-AES-3-PCM(39),
							val-AES-3-Data(40),
							val-AES-3-DolbyE(41),
							val-AES-3-Loss(42),
							val-AES-4-PCM(43),
							val-AES-4-Data(44),
							val-AES-4-DolbyE(45),
							val-AES-4-Loss(46),
							val-AES-5-PCM(47),
							val-AES-5-Data(48),
							val-AES-5-DolbyE(49),
							val-AES-5-Loss(50),
							val-AES-6-PCM(51),
							val-AES-6-Data(52),
							val-AES-6-DolbyE(53),
							val-AES-6-Loss(54),
							val-AES-7-PCM(55),
							val-AES-7-Data(56),
							val-AES-7-DolbyE(57),
							val-AES-7-Loss(58),
							val-AES-8-PCM(59),
							val-AES-8-Data(60),
							val-AES-8-DolbyE(61),
							val-AES-8-Loss(62),
							val-Disemb-1-PCM(63),
							val-Disemb-1-Data(64),
							val-Disemb-1-DolbyE(65),
							val-Disemb-1-Loss(66),
							val-Disemb-2-PCM(67),
							val-Disemb-2-Data(68),
							val-Disemb-2-DolbyE(69),
							val-Disemb-2-Loss(70),
							val-Disemb-3-PCM(71),
							val-Disemb-3-Data(72),
							val-Disemb-3-DolbyE(73),
							val-Disemb-3-Loss(74),
							val-Disemb-4-PCM(75),
							val-Disemb-4-Data(76),
							val-Disemb-4-DolbyE(77),
							val-Disemb-4-Loss(78),
							val-Disemb-5-PCM(79),
							val-Disemb-5-Data(80),
							val-Disemb-5-DolbyE(81),
							val-Disemb-5-Loss(82),
							val-Disemb-6-PCM(83),
							val-Disemb-6-Data(84),
							val-Disemb-6-DolbyE(85),
							val-Disemb-6-Loss(86),
							val-Disemb-7-PCM(87),
							val-Disemb-7-Data(88),
							val-Disemb-7-DolbyE(89),
							val-Disemb-7-Loss(90),
							val-Disemb-8-PCM(91),
							val-Disemb-8-Data(92),
							val-Disemb-8-DolbyE(93),
							val-Disemb-8-Loss(94),
							val-Decoder-I-P-Dolby-D(95),
							val-Decoder-I-P-Dolby-E(96),
							val-Decoder-I-P-PCM(97),
							val-Ext-Meta-Absent(98),
							val-Ext-Meta-Valid(99),
							val-Encoder-Active(100),
							val-Encoder-Stopped(101)
							}
		MAX-ACCESS		read-write
		STATUS			current
		DESCRIPTION
				"TYPE: - RadiobuttonList
				 PAGE: - RollCall/Memories
					Source  cmdID= 36101 
					Unused  value= -1  
					Video Delay  value= 0  
					Input Present  value= 2  
					Input 1 Present  value= 3  
					Input 2 Present  value= 4  
					Analog Present  value= 5  
					Input Loss  value= 6  
					Input 1 Loss  value= 7  
					Input 2 Loss  value= 8  
					Analog Loss  value= 9  
					Input 1 Select  value= 10  
					Input 2 Select  value= 11  
					Analog Select  value= 12  
					Input 1080/59p  value= 13  
					Input 1080/50p  value= 14  
					Input 1080/29i  value= 15  
					Input 1080/25i  value= 16  
					Input 1080/23sF  value= 102  
					Input 1080/29p  value= 103  
					Input 1080/25sF  value= 105  
					Input 1080/25p  value= 104  
					Input 720/59p  value= 17  
					Input 720/50p  value= 18  
					Input 525/29i  value= 19  
					Input 625/25i  value= 20  
					Output Black On  value= 21  
					Output Black Off  value= 22  
					Output Freeze  value= 23  
					Output UnFreeze  value= 24  
					Output Pattern On  value= 25  
					Output Pattern Off  value= 26  
					Output Caption On  value= 27  
					Output Caption Off  value= 28  
					Reference OK  value= 29  
					Reference Loss  value= 30  
					AES 1 PCM  value= 31  
					AES 1 Data  value= 32  
					AES 1 DolbyE  value= 33  
					AES 1 Loss  value= 34  
					AES 2 PCM  value= 35  
					AES 2 Data  value= 36  
					AES 2 DolbyE  value= 37  
					AES 2 Loss  value= 38  
					AES 3 PCM  value= 39  
					AES 3 Data  value= 40  
					AES 3 DolbyE  value= 41  
					AES 3 Loss  value= 42  
					AES 4 PCM  value= 43  
					AES 4 Data  value= 44  
					AES 4 DolbyE  value= 45  
					AES 4 Loss  value= 46  
					AES 5 PCM  value= 47  
					AES 5 Data  value= 48  
					AES 5 DolbyE  value= 49  
					AES 5 Loss  value= 50  
					AES 6 PCM  value= 51  
					AES 6 Data  value= 52  
					AES 6 DolbyE  value= 53  
					AES 6 Loss  value= 54  
					AES 7 PCM  value= 55  
					AES 7 Data  value= 56  
					AES 7 DolbyE  value= 57  
					AES 7 Loss  value= 58  
					AES 8 PCM  value= 59  
					AES 8 Data  value= 60  
					AES 8 DolbyE  value= 61  
					AES 8 Loss  value= 62  
					Disemb 1 PCM  value= 63  
					Disemb 1 Data  value= 64  
					Disemb 1 DolbyE  value= 65  
					Disemb 1 Loss  value= 66  
					Disemb 2 PCM  value= 67  
					Disemb 2 Data  value= 68  
					Disemb 2 DolbyE  value= 69  
					Disemb 2 Loss  value= 70  
					Disemb 3 PCM  value= 71  
					Disemb 3 Data  value= 72  
					Disemb 3 DolbyE  value= 73  
					Disemb 3 Loss  value= 74  
					Disemb 4 PCM  value= 75  
					Disemb 4 Data  value= 76  
					Disemb 4 DolbyE  value= 77  
					Disemb 4 Loss  value= 78  
					Disemb 5 PCM  value= 79  
					Disemb 5 Data  value= 80  
					Disemb 5 DolbyE  value= 81  
					Disemb 5 Loss  value= 82  
					Disemb 6 PCM  value= 83  
					Disemb 6 Data  value= 84  
					Disemb 6 DolbyE  value= 85  
					Disemb 6 Loss  value= 86  
					Disemb 7 PCM  value= 87  
					Disemb 7 Data  value= 88  
					Disemb 7 DolbyE  value= 89  
					Disemb 7 Loss  value= 90  
					Disemb 8 PCM  value= 91  
					Disemb 8 Data  value= 92  
					Disemb 8 DolbyE  value= 93  
					Disemb 8 Loss  value= 94  
					Decoder I/P Dolby D  value= 95  
					Decoder I/P Dolby E  value= 96  
					Decoder I/P PCM  value= 97  
					Ext Meta Absent  value= 98  
					Ext Meta Valid  value= 99  
					Encoder Active  value= 100  
					Encoder Stopped  value= 101  "
		::= { iqudc12CmdEntry 36101 }


	iqudc12RollCallMemoriesRollTrackAddress OBJECT-TYPE
		SYNTAX		RollCallString
		MAX-ACCESS		read-write
		STATUS			current
		DESCRIPTION
				"TYPE: - Editstring
				 PAGE: - RollCall/Memories
					Address  cmdID= 36102  "
		::= { iqudc12CmdEntry 36102 }


	iqudc12RollCallMemoriesRollTrackCommand OBJECT-TYPE
		SYNTAX		RollCallString
		MAX-ACCESS		read-write
		STATUS			current
		DESCRIPTION
				"TYPE: - Editstring
				 PAGE: - RollCall/Memories
					Command  cmdID= 36103  "
		::= { iqudc12CmdEntry 36103 }


	iqudc12RollCallMemoriesRollTrackStatus OBJECT-TYPE
		SYNTAX		RollCallString
		MAX-ACCESS		read-only
		STATUS			current
		DESCRIPTION
				"TYPE: - Display
				 PAGE: - RollCall/Memories
					Status  cmdID= 36105  format=   "
		::= { iqudc12CmdEntry 36105 }


	iqudc12RollCallMemoriesRollTrackSending OBJECT-TYPE
		SYNTAX		RollCallString
		MAX-ACCESS		read-only
		STATUS			current
		DESCRIPTION
				"TYPE: - Display
				 PAGE: - RollCall/Memories
					Sending  cmdID= 36106  format=   "
		::= { iqudc12CmdEntry 36106 }


	iqudc12RollCallMemoriesHideHideGpio OBJECT-TYPE
		SYNTAX		INTEGER
		MAX-ACCESS		read-write
		STATUS			current
		DESCRIPTION
				"TYPE: - Number
				 PAGE: - RollCall/Memories
					HideGpio  cmdID= 54  min= 0  max= 1  step= 1  format= %d  div_scale= 1 
					Min = 0  Max = 1  Step = 1 "
		::= { iqudc12CmdEntry 54 }


	iqudc12GPIOGPI1GPIO1Mode OBJECT-TYPE
		SYNTAX		INTEGER {
							val-Unused(0),
							val-Input-GPI1(1),
							val-Output-GPO1(2)
							}
		MAX-ACCESS		read-write
		STATUS			current
		DESCRIPTION
				"TYPE: - RadiobuttonList
				 PAGE: - GPI-1
					GPI/O 1 Mode  cmdID= 36120 
					Unused  value= 0  
					Input (GPI1)  value= 1  
					Output (GPO1)  value= 2  "
		::= { iqudc12CmdEntry 36120 }


	iqudc12GPIOGPI1GPI1IPHighSele OBJECT-TYPE
		SYNTAX		INTEGER {
							val-Unused(-1),
							val-Select-Input-1(50),
							val-Select-Input-2(51),
							val-Select-Analog-Input(52),
							val-Black(56),
							val-Freeze(57),
							val-Pattern(58),
							val-Video-Input(59),
							val-User-Memory-1(100),
							val-User-Memory-2(101),
							val-User-Memory-3(102),
							val-User-Memory-4(103),
							val-User-Memory-5(104),
							val-User-Memory-6(105),
							val-User-Memory-7(106),
							val-User-Memory-8(107),
							val-User-Memory-9(108),
							val-User-Memory-10(109),
							val-User-Memory-11(110),
							val-User-Memory-12(111),
							val-User-Memory-13(112),
							val-User-Memory-14(113),
							val-User-Memory-15(114),
							val-User-Memory-16(115),
							val-Display-Memory-1(61),
							val-Display-Memory-2(62),
							val-Display-Memory-3(63),
							val-Display-Memory-4(64),
							val-Display-Memory-5(65),
							val-Display-Memory-6(66),
							val-Display-Memory-7(67),
							val-Display-Memory-8(68),
							val-Display-Memory-9(69),
							val-Display-Memory-10(70),
							val-Display-Memory-11(71),
							val-Display-Memory-12(72),
							val-Display-Memory-13(73),
							val-Display-Memory-14(74),
							val-Display-Memory-15(75),
							val-Display-Memory-16(76),
							val-Display-Memory-17(77),
							val-Display-Memory-18(78),
							val-Display-Memory-19(79),
							val-Display-Memory-20(80),
							val-Display-Memory-21(81),
							val-Display-Memory-22(82),
							val-Display-Memory-23(83),
							val-Display-Memory-24(84),
							val-Display-Memory-25(85),
							val-Display-Memory-26(86),
							val-Display-Memory-27(87),
							val-Display-Memory-28(88),
							val-Display-Memory-29(89),
							val-Display-Memory-30(90),
							val-Display-Memory-31(91),
							val-Display-Memory-32(92),
							val-Force-ARC-AFD-1(93),
							val-Force-ARC-AFD-2(94),
							val-Force-ARC-AFD-3(95),
							val-Force-ARC-AFD-4(96)
							}
		MAX-ACCESS		read-write
		STATUS			current
		DESCRIPTION
				"TYPE: - RadiobuttonList
				 PAGE: - GPI-1
					GPI 1 I/P High Sele  cmdID= 36121 
					Unused  value= -1  
					Select Input 1  value= 50  
					Select Input 2  value= 51  
					Select Analog Input  value= 52  
					Black  value= 56  
					Freeze  value= 57  
					Pattern  value= 58  
					Video Input  value= 59  
					User Memory 1  value= 100  
					User Memory 2  value= 101  
					User Memory 3  value= 102  
					User Memory 4  value= 103  
					User Memory 5  value= 104  
					User Memory 6  value= 105  
					User Memory 7  value= 106  
					User Memory 8  value= 107  
					User Memory 9  value= 108  
					User Memory 10  value= 109  
					User Memory 11  value= 110  
					User Memory 12  value= 111  
					User Memory 13  value= 112  
					User Memory 14  value= 113  
					User Memory 15  value= 114  
					User Memory 16  value= 115  
					Display Memory 1  value= 61  
					Display Memory 2  value= 62  
					Display Memory 3  value= 63  
					Display Memory 4  value= 64  
					Display Memory 5  value= 65  
					Display Memory 6  value= 66  
					Display Memory 7  value= 67  
					Display Memory 8  value= 68  
					Display Memory 9  value= 69  
					Display Memory 10  value= 70  
					Display Memory 11  value= 71  
					Display Memory 12  value= 72  
					Display Memory 13  value= 73  
					Display Memory 14  value= 74  
					Display Memory 15  value= 75  
					Display Memory 16  value= 76  
					Display Memory 17  value= 77  
					Display Memory 18  value= 78  
					Display Memory 19  value= 79  
					Display Memory 20  value= 80  
					Display Memory 21  value= 81  
					Display Memory 22  value= 82  
					Display Memory 23  value= 83  
					Display Memory 24  value= 84  
					Display Memory 25  value= 85  
					Display Memory 26  value= 86  
					Display Memory 27  value= 87  
					Display Memory 28  value= 88  
					Display Memory 29  value= 89  
					Display Memory 30  value= 90  
					Display Memory 31  value= 91  
					Display Memory 32  value= 92  
					Force ARC/AFD 1  value= 93  
					Force ARC/AFD 2  value= 94  
					Force ARC/AFD 3  value= 95  
					Force ARC/AFD 4  value= 96  "
		::= { iqudc12CmdEntry 36121 }


	iqudc12GPIOGPI1GPI1IPLowSelec OBJECT-TYPE
		SYNTAX		INTEGER {
							val-Unused(-1),
							val-Select-Input-1(50),
							val-Select-Input-2(51),
							val-Select-Analog-Input(52),
							val-Black(56),
							val-Freeze(57),
							val-Pattern(58),
							val-Video-Input(59),
							val-User-Memory-1(100),
							val-User-Memory-2(101),
							val-User-Memory-3(102),
							val-User-Memory-4(103),
							val-User-Memory-5(104),
							val-User-Memory-6(105),
							val-User-Memory-7(106),
							val-User-Memory-8(107),
							val-User-Memory-9(108),
							val-User-Memory-10(109),
							val-User-Memory-11(110),
							val-User-Memory-12(111),
							val-User-Memory-13(112),
							val-User-Memory-14(113),
							val-User-Memory-15(114),
							val-User-Memory-16(115),
							val-Display-Memory-1(61),
							val-Display-Memory-2(62),
							val-Display-Memory-3(63),
							val-Display-Memory-4(64),
							val-Display-Memory-5(65),
							val-Display-Memory-6(66),
							val-Display-Memory-7(67),
							val-Display-Memory-8(68),
							val-Display-Memory-9(69),
							val-Display-Memory-10(70),
							val-Display-Memory-11(71),
							val-Display-Memory-12(72),
							val-Display-Memory-13(73),
							val-Display-Memory-14(74),
							val-Display-Memory-15(75),
							val-Display-Memory-16(76),
							val-Display-Memory-17(77),
							val-Display-Memory-18(78),
							val-Display-Memory-19(79),
							val-Display-Memory-20(80),
							val-Display-Memory-21(81),
							val-Display-Memory-22(82),
							val-Display-Memory-23(83),
							val-Display-Memory-24(84),
							val-Display-Memory-25(85),
							val-Display-Memory-26(86),
							val-Display-Memory-27(87),
							val-Display-Memory-28(88),
							val-Display-Memory-29(89),
							val-Display-Memory-30(90),
							val-Display-Memory-31(91),
							val-Display-Memory-32(92),
							val-Force-ARC-AFD-1(93),
							val-Force-ARC-AFD-2(94),
							val-Force-ARC-AFD-3(95),
							val-Force-ARC-AFD-4(96)
							}
		MAX-ACCESS		read-write
		STATUS			current
		DESCRIPTION
				"TYPE: - RadiobuttonList
				 PAGE: - GPI-1
					GPI 1 I/P Low Selec  cmdID= 36125 
					Unused  value= -1  
					Select Input 1  value= 50  
					Select Input 2  value= 51  
					Select Analog Input  value= 52  
					Black  value= 56  
					Freeze  value= 57  
					Pattern  value= 58  
					Video Input  value= 59  
					User Memory 1  value= 100  
					User Memory 2  value= 101  
					User Memory 3  value= 102  
					User Memory 4  value= 103  
					User Memory 5  value= 104  
					User Memory 6  value= 105  
					User Memory 7  value= 106  
					User Memory 8  value= 107  
					User Memory 9  value= 108  
					User Memory 10  value= 109  
					User Memory 11  value= 110  
					User Memory 12  value= 111  
					User Memory 13  value= 112  
					User Memory 14  value= 113  
					User Memory 15  value= 114  
					User Memory 16  value= 115  
					Display Memory 1  value= 61  
					Display Memory 2  value= 62  
					Display Memory 3  value= 63  
					Display Memory 4  value= 64  
					Display Memory 5  value= 65  
					Display Memory 6  value= 66  
					Display Memory 7  value= 67  
					Display Memory 8  value= 68  
					Display Memory 9  value= 69  
					Display Memory 10  value= 70  
					Display Memory 11  value= 71  
					Display Memory 12  value= 72  
					Display Memory 13  value= 73  
					Display Memory 14  value= 74  
					Display Memory 15  value= 75  
					Display Memory 16  value= 76  
					Display Memory 17  value= 77  
					Display Memory 18  value= 78  
					Display Memory 19  value= 79  
					Display Memory 20  value= 80  
					Display Memory 21  value= 81  
					Display Memory 22  value= 82  
					Display Memory 23  value= 83  
					Display Memory 24  value= 84  
					Display Memory 25  value= 85  
					Display Memory 26  value= 86  
					Display Memory 27  value= 87  
					Display Memory 28  value= 88  
					Display Memory 29  value= 89  
					Display Memory 30  value= 90  
					Display Memory 31  value= 91  
					Display Memory 32  value= 92  
					Force ARC/AFD 1  value= 93  
					Force ARC/AFD 2  value= 94  
					Force ARC/AFD 3  value= 95  
					Force ARC/AFD 4  value= 96  "
		::= { iqudc12CmdEntry 36125 }


	iqudc12GPIOGPI1GPO1OPSelect OBJECT-TYPE
		SYNTAX		INTEGER {
							val-Unused(-1),
							val-Input-OK(0),
							val-Input-1-OK(50),
							val-Input-2-OK(51),
							val-Analog-Input-OK(52),
							val-Input-1-Selected(53),
							val-Input-2-Selected(54),
							val-Analog-I-P-Selected(55),
							val-Black(56),
							val-Freeze(57),
							val-Pattern(58),
							val-No-User-Mem-Sel-d(99),
							val-User-Memory-1(100),
							val-User-Memory-2(101),
							val-User-Memory-3(102),
							val-User-Memory-4(103),
							val-User-Memory-5(104),
							val-User-Memory-6(105),
							val-User-Memory-7(106),
							val-User-Memory-8(107),
							val-User-Memory-9(108),
							val-User-Memory-10(109),
							val-User-Memory-11(110),
							val-User-Memory-12(111),
							val-User-Memory-13(112),
							val-User-Memory-14(113),
							val-User-Memory-15(114),
							val-User-Memory-16(115),
							val-No-Disp-Mem-Sel-d(60),
							val-Display-Memory-1(61),
							val-Display-Memory-2(62),
							val-Display-Memory-3(63),
							val-Display-Memory-4(64),
							val-Display-Memory-5(65),
							val-Display-Memory-6(66),
							val-Display-Memory-7(67),
							val-Display-Memory-8(68),
							val-Display-Memory-9(69),
							val-Display-Memory-10(70),
							val-Display-Memory-11(71),
							val-Display-Memory-12(72),
							val-Display-Memory-13(73),
							val-Display-Memory-14(74),
							val-Display-Memory-15(75),
							val-Display-Memory-16(76),
							val-Display-Memory-17(77),
							val-Display-Memory-18(78),
							val-Display-Memory-19(79),
							val-Display-Memory-20(80),
							val-Display-Memory-21(81),
							val-Display-Memory-22(82),
							val-Display-Memory-23(83),
							val-Display-Memory-24(84),
							val-Display-Memory-25(85),
							val-Display-Memory-26(86),
							val-Display-Memory-27(87),
							val-Display-Memory-28(88),
							val-Display-Memory-29(89),
							val-Display-Memory-30(90),
							val-Display-Memory-31(91),
							val-Display-Memory-32(92)
							}
		MAX-ACCESS		read-write
		STATUS			current
		DESCRIPTION
				"TYPE: - RadiobuttonList
				 PAGE: - GPI-1
					GPO 1 O/P Select  cmdID= 36122 
					Unused  value= -1  
					Input OK  value= 0  
					Input 1 OK  value= 50  
					Input 2 OK  value= 51  
					Analog Input OK  value= 52  
					Input 1 Selected  value= 53  
					Input 2 Selected  value= 54  
					Analog I/P Selected  value= 55  
					Black  value= 56  
					Freeze  value= 57  
					Pattern  value= 58  
					No User Mem Sel'd  value= 99  
					User Memory 1  value= 100  
					User Memory 2  value= 101  
					User Memory 3  value= 102  
					User Memory 4  value= 103  
					User Memory 5  value= 104  
					User Memory 6  value= 105  
					User Memory 7  value= 106  
					User Memory 8  value= 107  
					User Memory 9  value= 108  
					User Memory 10  value= 109  
					User Memory 11  value= 110  
					User Memory 12  value= 111  
					User Memory 13  value= 112  
					User Memory 14  value= 113  
					User Memory 15  value= 114  
					User Memory 16  value= 115  
					No Disp Mem Sel'd  value= 60  
					Display Memory 1  value= 61  
					Display Memory 2  value= 62  
					Display Memory 3  value= 63  
					Display Memory 4  value= 64  
					Display Memory 5  value= 65  
					Display Memory 6  value= 66  
					Display Memory 7  value= 67  
					Display Memory 8  value= 68  
					Display Memory 9  value= 69  
					Display Memory 10  value= 70  
					Display Memory 11  value= 71  
					Display Memory 12  value= 72  
					Display Memory 13  value= 73  
					Display Memory 14  value= 74  
					Display Memory 15  value= 75  
					Display Memory 16  value= 76  
					Display Memory 17  value= 77  
					Display Memory 18  value= 78  
					Display Memory 19  value= 79  
					Display Memory 20  value= 80  
					Display Memory 21  value= 81  
					Display Memory 22  value= 82  
					Display Memory 23  value= 83  
					Display Memory 24  value= 84  
					Display Memory 25  value= 85  
					Display Memory 26  value= 86  
					Display Memory 27  value= 87  
					Display Memory 28  value= 88  
					Display Memory 29  value= 89  
					Display Memory 30  value= 90  
					Display Memory 31  value= 91  
					Display Memory 32  value= 92  "
		::= { iqudc12CmdEntry 36122 }


	iqudc12GPIOGPI1InvertGPIO1 OBJECT-TYPE
		SYNTAX		INTEGER { disable(0), enable(1) }
		MAX-ACCESS		read-write
		STATUS			current
		DESCRIPTION
				"TYPE: - Checkbox
				 PAGE: - GPI-1
					Invert GPIO 1  cmdID= 36123 "
		::= { iqudc12CmdEntry 36123 }


	iqudc12GPIOGPI1Status OBJECT-TYPE
		SYNTAX		RollCallString
		MAX-ACCESS		read-only
		STATUS			current
		DESCRIPTION
				"TYPE: - Display
				 PAGE: - GPI-1
					Status  cmdID= 36134  format=   "
		::= { iqudc12CmdEntry 36134 }


	iqudc12GPIOGPI2GPIO2Mode OBJECT-TYPE
		SYNTAX		INTEGER {
							val-Unused(0),
							val-Input-GPI2(1),
							val-Output-GPO2(2)
							}
		MAX-ACCESS		read-write
		STATUS			current
		DESCRIPTION
				"TYPE: - RadiobuttonList
				 PAGE: - GPI-2
					GPI/O 2 Mode  cmdID= 36130 
					Unused  value= 0  
					Input (GPI2)  value= 1  
					Output (GPO2)  value= 2  "
		::= { iqudc12CmdEntry 36130 }


	iqudc12GPIOGPI2GPI2IPHighSele OBJECT-TYPE
		SYNTAX		INTEGER {
							val-Unused(-1),
							val-Select-Input-1(50),
							val-Select-Input-2(51),
							val-Select-Analog-Input(52),
							val-Black(56),
							val-Freeze(57),
							val-Pattern(58),
							val-Video-Input(59),
							val-User-Memory-1(100),
							val-User-Memory-2(101),
							val-User-Memory-3(102),
							val-User-Memory-4(103),
							val-User-Memory-5(104),
							val-User-Memory-6(105),
							val-User-Memory-7(106),
							val-User-Memory-8(107),
							val-User-Memory-9(108),
							val-User-Memory-10(109),
							val-User-Memory-11(110),
							val-User-Memory-12(111),
							val-User-Memory-13(112),
							val-User-Memory-14(113),
							val-User-Memory-15(114),
							val-User-Memory-16(115),
							val-Display-Memory-1(61),
							val-Display-Memory-2(62),
							val-Display-Memory-3(63),
							val-Display-Memory-4(64),
							val-Display-Memory-5(65),
							val-Display-Memory-6(66),
							val-Display-Memory-7(67),
							val-Display-Memory-8(68),
							val-Display-Memory-9(69),
							val-Display-Memory-10(70),
							val-Display-Memory-11(71),
							val-Display-Memory-12(72),
							val-Display-Memory-13(73),
							val-Display-Memory-14(74),
							val-Display-Memory-15(75),
							val-Display-Memory-16(76),
							val-Display-Memory-17(77),
							val-Display-Memory-18(78),
							val-Display-Memory-19(79),
							val-Display-Memory-20(80),
							val-Display-Memory-21(81),
							val-Display-Memory-22(82),
							val-Display-Memory-23(83),
							val-Display-Memory-24(84),
							val-Display-Memory-25(85),
							val-Display-Memory-26(86),
							val-Display-Memory-27(87),
							val-Display-Memory-28(88),
							val-Display-Memory-29(89),
							val-Display-Memory-30(90),
							val-Display-Memory-31(91),
							val-Display-Memory-32(92),
							val-Force-ARC-AFD-1(93),
							val-Force-ARC-AFD-2(94),
							val-Force-ARC-AFD-3(95),
							val-Force-ARC-AFD-4(96)
							}
		MAX-ACCESS		read-write
		STATUS			current
		DESCRIPTION
				"TYPE: - RadiobuttonList
				 PAGE: - GPI-2
					GPI 2 I/P High Sele  cmdID= 36131 
					Unused  value= -1  
					Select Input 1  value= 50  
					Select Input 2  value= 51  
					Select Analog Input  value= 52  
					Black  value= 56  
					Freeze  value= 57  
					Pattern  value= 58  
					Video Input  value= 59  
					User Memory 1  value= 100  
					User Memory 2  value= 101  
					User Memory 3  value= 102  
					User Memory 4  value= 103  
					User Memory 5  value= 104  
					User Memory 6  value= 105  
					User Memory 7  value= 106  
					User Memory 8  value= 107  
					User Memory 9  value= 108  
					User Memory 10  value= 109  
					User Memory 11  value= 110  
					User Memory 12  value= 111  
					User Memory 13  value= 112  
					User Memory 14  value= 113  
					User Memory 15  value= 114  
					User Memory 16  value= 115  
					Display Memory 1  value= 61  
					Display Memory 2  value= 62  
					Display Memory 3  value= 63  
					Display Memory 4  value= 64  
					Display Memory 5  value= 65  
					Display Memory 6  value= 66  
					Display Memory 7  value= 67  
					Display Memory 8  value= 68  
					Display Memory 9  value= 69  
					Display Memory 10  value= 70  
					Display Memory 11  value= 71  
					Display Memory 12  value= 72  
					Display Memory 13  value= 73  
					Display Memory 14  value= 74  
					Display Memory 15  value= 75  
					Display Memory 16  value= 76  
					Display Memory 17  value= 77  
					Display Memory 18  value= 78  
					Display Memory 19  value= 79  
					Display Memory 20  value= 80  
					Display Memory 21  value= 81  
					Display Memory 22  value= 82  
					Display Memory 23  value= 83  
					Display Memory 24  value= 84  
					Display Memory 25  value= 85  
					Display Memory 26  value= 86  
					Display Memory 27  value= 87  
					Display Memory 28  value= 88  
					Display Memory 29  value= 89  
					Display Memory 30  value= 90  
					Display Memory 31  value= 91  
					Display Memory 32  value= 92  
					Force ARC/AFD 1  value= 93  
					Force ARC/AFD 2  value= 94  
					Force ARC/AFD 3  value= 95  
					Force ARC/AFD 4  value= 96  "
		::= { iqudc12CmdEntry 36131 }


	iqudc12GPIOGPI2GPI2IPLowSelec OBJECT-TYPE
		SYNTAX		INTEGER {
							val-Unused(-1),
							val-Select-Input-1(50),
							val-Select-Input-2(51),
							val-Select-Analog-Input(52),
							val-Black(56),
							val-Freeze(57),
							val-Pattern(58),
							val-Video-Input(59),
							val-User-Memory-1(100),
							val-User-Memory-2(101),
							val-User-Memory-3(102),
							val-User-Memory-4(103),
							val-User-Memory-5(104),
							val-User-Memory-6(105),
							val-User-Memory-7(106),
							val-User-Memory-8(107),
							val-User-Memory-9(108),
							val-User-Memory-10(109),
							val-User-Memory-11(110),
							val-User-Memory-12(111),
							val-User-Memory-13(112),
							val-User-Memory-14(113),
							val-User-Memory-15(114),
							val-User-Memory-16(115),
							val-Display-Memory-1(61),
							val-Display-Memory-2(62),
							val-Display-Memory-3(63),
							val-Display-Memory-4(64),
							val-Display-Memory-5(65),
							val-Display-Memory-6(66),
							val-Display-Memory-7(67),
							val-Display-Memory-8(68),
							val-Display-Memory-9(69),
							val-Display-Memory-10(70),
							val-Display-Memory-11(71),
							val-Display-Memory-12(72),
							val-Display-Memory-13(73),
							val-Display-Memory-14(74),
							val-Display-Memory-15(75),
							val-Display-Memory-16(76),
							val-Display-Memory-17(77),
							val-Display-Memory-18(78),
							val-Display-Memory-19(79),
							val-Display-Memory-20(80),
							val-Display-Memory-21(81),
							val-Display-Memory-22(82),
							val-Display-Memory-23(83),
							val-Display-Memory-24(84),
							val-Display-Memory-25(85),
							val-Display-Memory-26(86),
							val-Display-Memory-27(87),
							val-Display-Memory-28(88),
							val-Display-Memory-29(89),
							val-Display-Memory-30(90),
							val-Display-Memory-31(91),
							val-Display-Memory-32(92),
							val-Force-ARC-AFD-1(93),
							val-Force-ARC-AFD-2(94),
							val-Force-ARC-AFD-3(95),
							val-Force-ARC-AFD-4(96)
							}
		MAX-ACCESS		read-write
		STATUS			current
		DESCRIPTION
				"TYPE: - RadiobuttonList
				 PAGE: - GPI-2
					GPI 2 I/P Low Selec  cmdID= 36137 
					Unused  value= -1  
					Select Input 1  value= 50  
					Select Input 2  value= 51  
					Select Analog Input  value= 52  
					Black  value= 56  
					Freeze  value= 57  
					Pattern  value= 58  
					Video Input  value= 59  
					User Memory 1  value= 100  
					User Memory 2  value= 101  
					User Memory 3  value= 102  
					User Memory 4  value= 103  
					User Memory 5  value= 104  
					User Memory 6  value= 105  
					User Memory 7  value= 106  
					User Memory 8  value= 107  
					User Memory 9  value= 108  
					User Memory 10  value= 109  
					User Memory 11  value= 110  
					User Memory 12  value= 111  
					User Memory 13  value= 112  
					User Memory 14  value= 113  
					User Memory 15  value= 114  
					User Memory 16  value= 115  
					Display Memory 1  value= 61  
					Display Memory 2  value= 62  
					Display Memory 3  value= 63  
					Display Memory 4  value= 64  
					Display Memory 5  value= 65  
					Display Memory 6  value= 66  
					Display Memory 7  value= 67  
					Display Memory 8  value= 68  
					Display Memory 9  value= 69  
					Display Memory 10  value= 70  
					Display Memory 11  value= 71  
					Display Memory 12  value= 72  
					Display Memory 13  value= 73  
					Display Memory 14  value= 74  
					Display Memory 15  value= 75  
					Display Memory 16  value= 76  
					Display Memory 17  value= 77  
					Display Memory 18  value= 78  
					Display Memory 19  value= 79  
					Display Memory 20  value= 80  
					Display Memory 21  value= 81  
					Display Memory 22  value= 82  
					Display Memory 23  value= 83  
					Display Memory 24  value= 84  
					Display Memory 25  value= 85  
					Display Memory 26  value= 86  
					Display Memory 27  value= 87  
					Display Memory 28  value= 88  
					Display Memory 29  value= 89  
					Display Memory 30  value= 90  
					Display Memory 31  value= 91  
					Display Memory 32  value= 92  
					Force ARC/AFD 1  value= 93  
					Force ARC/AFD 2  value= 94  
					Force ARC/AFD 3  value= 95  
					Force ARC/AFD 4  value= 96  "
		::= { iqudc12CmdEntry 36137 }


	iqudc12GPIOGPI2GPO2OPSelect OBJECT-TYPE
		SYNTAX		INTEGER {
							val-Unused(-1),
							val-Input-OK(0),
							val-Input-1-OK(50),
							val-Input-2-OK(51),
							val-Analog-Input-OK(52),
							val-Input-1-Selected(53),
							val-Input-2-Selected(54),
							val-Analog-I-P-Selected(55),
							val-Black(56),
							val-Freeze(57),
							val-Pattern(58),
							val-No-User-Mem-Sel-d(99),
							val-User-Memory-1(100),
							val-User-Memory-2(101),
							val-User-Memory-3(102),
							val-User-Memory-4(103),
							val-User-Memory-5(104),
							val-User-Memory-6(105),
							val-User-Memory-7(106),
							val-User-Memory-8(107),
							val-User-Memory-9(108),
							val-User-Memory-10(109),
							val-User-Memory-11(110),
							val-User-Memory-12(111),
							val-User-Memory-13(112),
							val-User-Memory-14(113),
							val-User-Memory-15(114),
							val-User-Memory-16(115),
							val-No-Disp-Mem-Sel-d(60),
							val-Display-Memory-1(61),
							val-Display-Memory-2(62),
							val-Display-Memory-3(63),
							val-Display-Memory-4(64),
							val-Display-Memory-5(65),
							val-Display-Memory-6(66),
							val-Display-Memory-7(67),
							val-Display-Memory-8(68),
							val-Display-Memory-9(69),
							val-Display-Memory-10(70),
							val-Display-Memory-11(71),
							val-Display-Memory-12(72),
							val-Display-Memory-13(73),
							val-Display-Memory-14(74),
							val-Display-Memory-15(75),
							val-Display-Memory-16(76),
							val-Display-Memory-17(77),
							val-Display-Memory-18(78),
							val-Display-Memory-19(79),
							val-Display-Memory-20(80),
							val-Display-Memory-21(81),
							val-Display-Memory-22(82),
							val-Display-Memory-23(83),
							val-Display-Memory-24(84),
							val-Display-Memory-25(85),
							val-Display-Memory-26(86),
							val-Display-Memory-27(87),
							val-Display-Memory-28(88),
							val-Display-Memory-29(89),
							val-Display-Memory-30(90),
							val-Display-Memory-31(91),
							val-Display-Memory-32(92)
							}
		MAX-ACCESS		read-write
		STATUS			current
		DESCRIPTION
				"TYPE: - RadiobuttonList
				 PAGE: - GPI-2
					GPO 2 O/P Select  cmdID= 36132 
					Unused  value= -1  
					Input OK  value= 0  
					Input 1 OK  value= 50  
					Input 2 OK  value= 51  
					Analog Input OK  value= 52  
					Input 1 Selected  value= 53  
					Input 2 Selected  value= 54  
					Analog I/P Selected  value= 55  
					Black  value= 56  
					Freeze  value= 57  
					Pattern  value= 58  
					No User Mem Sel'd  value= 99  
					User Memory 1  value= 100  
					User Memory 2  value= 101  
					User Memory 3  value= 102  
					User Memory 4  value= 103  
					User Memory 5  value= 104  
					User Memory 6  value= 105  
					User Memory 7  value= 106  
					User Memory 8  value= 107  
					User Memory 9  value= 108  
					User Memory 10  value= 109  
					User Memory 11  value= 110  
					User Memory 12  value= 111  
					User Memory 13  value= 112  
					User Memory 14  value= 113  
					User Memory 15  value= 114  
					User Memory 16  value= 115  
					No Disp Mem Sel'd  value= 60  
					Display Memory 1  value= 61  
					Display Memory 2  value= 62  
					Display Memory 3  value= 63  
					Display Memory 4  value= 64  
					Display Memory 5  value= 65  
					Display Memory 6  value= 66  
					Display Memory 7  value= 67  
					Display Memory 8  value= 68  
					Display Memory 9  value= 69  
					Display Memory 10  value= 70  
					Display Memory 11  value= 71  
					Display Memory 12  value= 72  
					Display Memory 13  value= 73  
					Display Memory 14  value= 74  
					Display Memory 15  value= 75  
					Display Memory 16  value= 76  
					Display Memory 17  value= 77  
					Display Memory 18  value= 78  
					Display Memory 19  value= 79  
					Display Memory 20  value= 80  
					Display Memory 21  value= 81  
					Display Memory 22  value= 82  
					Display Memory 23  value= 83  
					Display Memory 24  value= 84  
					Display Memory 25  value= 85  
					Display Memory 26  value= 86  
					Display Memory 27  value= 87  
					Display Memory 28  value= 88  
					Display Memory 29  value= 89  
					Display Memory 30  value= 90  
					Display Memory 31  value= 91  
					Display Memory 32  value= 92  "
		::= { iqudc12CmdEntry 36132 }


	iqudc12GPIOGPI2InvertGPIO2 OBJECT-TYPE
		SYNTAX		INTEGER { disable(0), enable(1) }
		MAX-ACCESS		read-write
		STATUS			current
		DESCRIPTION
				"TYPE: - Checkbox
				 PAGE: - GPI-2
					Invert GPIO 2  cmdID= 36133 "
		::= { iqudc12CmdEntry 36133 }


	iqudc12GPIOGPI2Status OBJECT-TYPE
		SYNTAX		RollCallString
		MAX-ACCESS		read-only
		STATUS			current
		DESCRIPTION
				"TYPE: - Display
				 PAGE: - GPI-2
					Status  cmdID= 36135  format=   "
		::= { iqudc12CmdEntry 36135 }


	iqudc12MenuSetupDisplay OBJECT-TYPE
		SYNTAX		INTEGER {
							val-VideoStatus(0),
							val-AudioStatus(1),
							val-DolbyStatus(2),
							val-RefStatus(3),
							val-LedStatus(4),
							val-AfdStatus(6),
							val-TcStatus(7)
							}
		MAX-ACCESS		read-write
		STATUS			current
		DESCRIPTION
				"TYPE: - RadiobuttonList
					Display  cmdID= 32773 
					VideoStatus  value= 0  
					AudioStatus  value= 1  
					DolbyStatus  value= 2  
					RefStatus  value= 3  
					LedStatus  value= 4  
					AfdStatus  value= 6  
					TcStatus  value= 7  "
		::= { iqudc12CmdEntry 32773 }


	iqudc12MenuSetupProduct OBJECT-TYPE
		SYNTAX		RollCallString
		MAX-ACCESS		read-only
		STATUS			current
		DESCRIPTION
				"TYPE: - Display
					Product  cmdID= 32771  format=   "
		::= { iqudc12CmdEntry 32771 }


	iqudc12MenuSetupRelease OBJECT-TYPE
		SYNTAX		RollCallString
		MAX-ACCESS		read-only
		STATUS			current
		DESCRIPTION
				"TYPE: - Display
					Release  cmdID= 2  format=   "
		::= { iqudc12CmdEntry 2 }


	iqudc12MenuSetupBuild OBJECT-TYPE
		SYNTAX		RollCallString
		MAX-ACCESS		read-only
		STATUS			current
		DESCRIPTION
				"TYPE: - Display
					Build  cmdID= 5  format=   "
		::= { iqudc12CmdEntry 5 }


	iqudc12MenuSetupKOS OBJECT-TYPE
		SYNTAX		RollCallString
		MAX-ACCESS		read-only
		STATUS			current
		DESCRIPTION
				"TYPE: - Display
					KOS  cmdID= 32772  format=   "
		::= { iqudc12CmdEntry 32772 }


	iqudc12MenuSetupSerialNo OBJECT-TYPE
		SYNTAX		RollCallString
		MAX-ACCESS		read-only
		STATUS			current
		DESCRIPTION
				"TYPE: - Display
					Serial No.  cmdID= 1  format=   "
		::= { iqudc12CmdEntry 1 }


	iqudc12MenuSetupFactoryDefault OBJECT-TYPE
		SYNTAX		INTEGER { noAction(0),val-Factory-Default(1) }
		MAX-ACCESS		read-write
		STATUS			current
		DESCRIPTION
				"TYPE: - Button
					Factory Default  cmdID= 37002  value= 1  "
		::= { iqudc12CmdEntry 37002 }


	iqudc12MenuSetupRestart OBJECT-TYPE
		SYNTAX		INTEGER { noAction(0),val-Restart(1) }
		MAX-ACCESS		read-write
		STATUS			current
		DESCRIPTION
				"TYPE: - Button
					Restart  cmdID= 4  value= 1  "
		::= { iqudc12CmdEntry 4 }


	iqudc12MenuSetupDefaultSettings OBJECT-TYPE
		SYNTAX		INTEGER { noAction(0),val-Default-Settings(1) }
		MAX-ACCESS		read-write
		STATUS			current
		DESCRIPTION
				"TYPE: - Button
					Default Settings  cmdID= 37001  value= 1  "
		::= { iqudc12CmdEntry 37001 }


	iqudc12MenuSetupSerialNumber OBJECT-TYPE
		SYNTAX		RollCallString
		MAX-ACCESS		read-write
		STATUS			current
		DESCRIPTION
				"TYPE: - Editstring
					Serial Number  cmdID= 32774  "
		::= { iqudc12CmdEntry 32774 }


	iqudc12MenuSetupBoardID OBJECT-TYPE
		SYNTAX		INTEGER {
							val-IQUPC00(539),
							val-IQUPC01(540),
							val-IQDNC00(541),
							val-IQDNC01(549),
							val-IQDCC00(542),
							val-IQUDC10(543),
							val-IQUDC11(544),
							val-IQUCC00(548),
							val-IQUAV10(545),
							val-IQMUX33(546),
							val-IQDMX33(547),
							val-IQSYN33(551)
							}
		MAX-ACCESS		read-write
		STATUS			current
		DESCRIPTION
				"TYPE: - RadiobuttonList
					BoardID  cmdID= 32776 
					IQUPC00  value= 539  
					IQUPC01  value= 540  
					IQDNC00  value= 541  
					IQDNC01  value= 549  
					IQDCC00  value= 542  
					IQUDC10  value= 543  
					IQUDC11  value= 544  
					IQUCC00  value= 548  
					IQUAV10  value= 545  
					IQMUX33  value= 546  
					IQDMX33  value= 547  
					IQSYN33  value= 551  "
		::= { iqudc12CmdEntry 32776 }


	iqudc12MenuSetupSaveID OBJECT-TYPE
		SYNTAX		INTEGER { noAction(0),val-Save-ID(1) }
		MAX-ACCESS		read-write
		STATUS			current
		DESCRIPTION
				"TYPE: - Button
					Save ID  cmdID= 32775  value= 1  "
		::= { iqudc12CmdEntry 32775 }


	iqudc12SetupFpgaBoardType OBJECT-TYPE
		SYNTAX		RollCallString
		MAX-ACCESS		read-only
		STATUS			current
		DESCRIPTION
				"TYPE: - Display
					Board Type  cmdID= 33152  format=   "
		::= { iqudc12CmdEntry 33152 }


	iqudc12SetupFpgaFpgaSerialNo OBJECT-TYPE
		SYNTAX		RollCallString
		MAX-ACCESS		read-only
		STATUS			current
		DESCRIPTION
				"TYPE: - Display
					Fpga SerialNo  cmdID= 33156  format=   "
		::= { iqudc12CmdEntry 33156 }


	iqudc12SetupFpgaSoftVer OBJECT-TYPE
		SYNTAX		RollCallString
		MAX-ACCESS		read-only
		STATUS			current
		DESCRIPTION
				"TYPE: - Display
					Soft Ver  cmdID= 33150  format=   "
		::= { iqudc12CmdEntry 33150 }


	iqudc12SetupFpgaFpgaVer OBJECT-TYPE
		SYNTAX		RollCallString
		MAX-ACCESS		read-only
		STATUS			current
		DESCRIPTION
				"TYPE: - Display
					Fpga Ver  cmdID= 33157  format=   "
		::= { iqudc12CmdEntry 33157 }


	iqudc12SetupFpgaTIVer OBJECT-TYPE
		SYNTAX		RollCallString
		MAX-ACCESS		read-only
		STATUS			current
		DESCRIPTION
				"TYPE: - Display
					TI Ver  cmdID= 33160  format=   "
		::= { iqudc12CmdEntry 33160 }


	iqudc12SetupFpgaDolbyModId OBJECT-TYPE
		SYNTAX		RollCallString
		MAX-ACCESS		read-only
		STATUS			current
		DESCRIPTION
				"TYPE: - Display
					Dolby Mod Id  cmdID= 33162  format=   "
		::= { iqudc12CmdEntry 33162 }


	iqudc12SetupFpgaProtVer OBJECT-TYPE
		SYNTAX		RollCallString
		MAX-ACCESS		read-only
		STATUS			current
		DESCRIPTION
				"TYPE: - Display
					Prot Ver  cmdID= 33151  format=   "
		::= { iqudc12CmdEntry 33151 }


	iqudc12SetupFpgaProgCRC OBJECT-TYPE
		SYNTAX		RollCallString
		MAX-ACCESS		read-only
		STATUS			current
		DESCRIPTION
				"TYPE: - Display
					Prog CRC  cmdID= 33155  format=   "
		::= { iqudc12CmdEntry 33155 }


	iqudc12SetupFpgaUptime OBJECT-TYPE
		SYNTAX		RollCallString
		MAX-ACCESS		read-only
		STATUS			current
		DESCRIPTION
				"TYPE: - Display
					Uptime  cmdID= 33163  format=   "
		::= { iqudc12CmdEntry 33163 }


	iqudc12SetupFpgaENGVXPVer OBJECT-TYPE
		SYNTAX		RollCallString
		MAX-ACCESS		read-only
		STATUS			current
		DESCRIPTION
				"TYPE: - Display
					VXP Ver  cmdID= 33158  format=   "
		::= { iqudc12CmdEntry 33158 }


	iqudc12SetupFpgaENGSharcVer OBJECT-TYPE
		SYNTAX		RollCallString
		MAX-ACCESS		read-only
		STATUS			current
		DESCRIPTION
				"TYPE: - Display
					Sharc Ver  cmdID= 33159  format=   "
		::= { iqudc12CmdEntry 33159 }


	iqudc12SetupFpgaENGAlteraVer OBJECT-TYPE
		SYNTAX		RollCallString
		MAX-ACCESS		read-only
		STATUS			current
		DESCRIPTION
				"TYPE: - Display
					Altera Ver  cmdID= 33161  format=   "
		::= { iqudc12CmdEntry 33161 }


	iqudc12SetupFpgaENGVCCint OBJECT-TYPE
		SYNTAX		RollCallString
		MAX-ACCESS		read-only
		STATUS			current
		DESCRIPTION
				"TYPE: - Display
					VCCint  cmdID= 33164  format=   "
		::= { iqudc12CmdEntry 33164 }


	iqudc12SetupFpgaENGVCCaux OBJECT-TYPE
		SYNTAX		RollCallString
		MAX-ACCESS		read-only
		STATUS			current
		DESCRIPTION
				"TYPE: - Display
					VCCaux  cmdID= 33165  format=   "
		::= { iqudc12CmdEntry 33165 }


	iqudc12SetupOptionsOption1 OBJECT-TYPE
		SYNTAX		RollCallString
		MAX-ACCESS		read-only
		STATUS			current
		DESCRIPTION
				"TYPE: - Display
					Option1  cmdID= 33166  format=   "
		::= { iqudc12CmdEntry 33166 }


	iqudc12SetupOptionsOption2 OBJECT-TYPE
		SYNTAX		RollCallString
		MAX-ACCESS		read-only
		STATUS			current
		DESCRIPTION
				"TYPE: - Display
					Option2  cmdID= 33167  format=   "
		::= { iqudc12CmdEntry 33167 }


	iqudc12SetupOptionsOption3 OBJECT-TYPE
		SYNTAX		RollCallString
		MAX-ACCESS		read-only
		STATUS			current
		DESCRIPTION
				"TYPE: - Display
					Option3  cmdID= 33168  format=   "
		::= { iqudc12CmdEntry 33168 }


	iqudc12SetupOptionsOption4 OBJECT-TYPE
		SYNTAX		RollCallString
		MAX-ACCESS		read-only
		STATUS			current
		DESCRIPTION
				"TYPE: - Display
					Option4  cmdID= 33169  format=   "
		::= { iqudc12CmdEntry 33169 }


	iqudc12SetupOptionsOption5 OBJECT-TYPE
		SYNTAX		RollCallString
		MAX-ACCESS		read-only
		STATUS			current
		DESCRIPTION
				"TYPE: - Display
					Option5  cmdID= 33170  format=   "
		::= { iqudc12CmdEntry 33170 }


	iqudc12SetupOptionsOption6 OBJECT-TYPE
		SYNTAX		RollCallString
		MAX-ACCESS		read-only
		STATUS			current
		DESCRIPTION
				"TYPE: - Display
					Option6  cmdID= 33171  format=   "
		::= { iqudc12CmdEntry 33171 }


	iqudc12SetupOptionsOption7 OBJECT-TYPE
		SYNTAX		RollCallString
		MAX-ACCESS		read-only
		STATUS			current
		DESCRIPTION
				"TYPE: - Display
					Option7  cmdID= 33172  format=   "
		::= { iqudc12CmdEntry 33172 }


	iqudc12SetupOptionsOption8 OBJECT-TYPE
		SYNTAX		RollCallString
		MAX-ACCESS		read-only
		STATUS			current
		DESCRIPTION
				"TYPE: - Display
					Option8  cmdID= 33173  format=   "
		::= { iqudc12CmdEntry 33173 }


	iqudc12SetupOptionsOption9 OBJECT-TYPE
		SYNTAX		RollCallString
		MAX-ACCESS		read-only
		STATUS			current
		DESCRIPTION
				"TYPE: - Display
					Option9  cmdID= 33174  format=   "
		::= { iqudc12CmdEntry 33174 }


	iqudc12SetupOptionsOptionsMask OBJECT-TYPE
		SYNTAX		INTEGER
		MAX-ACCESS		read-write
		STATUS			current
		DESCRIPTION
				"TYPE: - Number
					OptionsMask  cmdID= 36147  min= 0  max= 65535  step= 1  format= %d  div_scale= 1 
					Min = 0  Max = -1  Step = 1 "
		::= { iqudc12CmdEntry 36147 }


	iqudc12SetupDemoNonDemoRestart OBJECT-TYPE
		SYNTAX		INTEGER { noAction(0),val-NonDemoRestart(1) }
		MAX-ACCESS		read-write
		STATUS			current
		DESCRIPTION
				"TYPE: - Button
					NonDemoRestart  cmdID= 43092  value= 1  "
		::= { iqudc12CmdEntry 43092 }


	iqudc12SetupDemoRestartMode OBJECT-TYPE
		SYNTAX		INTEGER { disable(0), enable(1) }
		MAX-ACCESS		read-write
		STATUS			current
		DESCRIPTION
				"TYPE: - Checkbox
					RestartMode  cmdID= 43093 "
		::= { iqudc12CmdEntry 43093 }


	iqudc12SetupDemoRemainingDemo OBJECT-TYPE
		SYNTAX		INTEGER
		MAX-ACCESS		read-write
		STATUS			current
		DESCRIPTION
				"TYPE: - Number
					RemainingDemo  cmdID= 43091  min= 0  max= 50000  step= 1  format= %d  div_scale= 1 
					Min = 0  Max = -15536  Step = 1 "
		::= { iqudc12CmdEntry 43091 }


	iqudc12SetupDemoRemaining24h OBJECT-TYPE
		SYNTAX		INTEGER
		MAX-ACCESS		read-write
		STATUS			current
		DESCRIPTION
				"TYPE: - Number
					Remaining24h  cmdID= 43094  min= 0  max= 1440  step= 1  format= %d  div_scale= 1 
					Min = 0  Max = 1440  Step = 1 "
		::= { iqudc12CmdEntry 43094 }


	iqudc12SetupDemoDolbyType OBJECT-TYPE
		SYNTAX		INTEGER {
							val-None(0),
							val-Decode(1),
							val-E-Encode(2),
							val-D-Encode(3)
							}
		MAX-ACCESS		read-write
		STATUS			current
		DESCRIPTION
				"TYPE: - RadiobuttonList
					Dolby Type  cmdID= 43108 
					None  value= 0  
					Decode  value= 1  
					E Encode  value= 2  
					D Encode  value= 3  "
		::= { iqudc12CmdEntry 43108 }


	iqudc12MenuSetupRestartHard OBJECT-TYPE
		SYNTAX		INTEGER { noAction(0),val-Restart-Hard(1) }
		MAX-ACCESS		read-write
		STATUS			current
		DESCRIPTION
				"TYPE: - Button
					Restart Hard  cmdID= 36138  value= 1  "
		::= { iqudc12CmdEntry 36138 }


	iqudc12MenuSetupInput1Name OBJECT-TYPE
		SYNTAX		RollCallString
		MAX-ACCESS		read-write
		STATUS			current
		DESCRIPTION
				"TYPE: - Editstring
					Input 1 Name  cmdID= 9000  "
		::= { iqudc12CmdEntry 9000 }


	iqudc12MenuSetupInput2Name OBJECT-TYPE
		SYNTAX		RollCallString
		MAX-ACCESS		read-write
		STATUS			current
		DESCRIPTION
				"TYPE: - Editstring
					Input 2 Name  cmdID= 9001  "
		::= { iqudc12CmdEntry 9001 }


	iqudc12MenuSetupInput3Name OBJECT-TYPE
		SYNTAX		RollCallString
		MAX-ACCESS		read-write
		STATUS			current
		DESCRIPTION
				"TYPE: - Editstring
					Input 3 Name  cmdID= 9002  "
		::= { iqudc12CmdEntry 9002 }


	iqudc12LoudMonBlk1SourceLSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk1
					Src  cmdID= 43200 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43200 }


	iqudc12LoudMonBlk1SourceRSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk1
					Src  cmdID= 43201 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43201 }


	iqudc12LoudMonBlk1SourceLSSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk1
					Src  cmdID= 43202 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43202 }


	iqudc12LoudMonBlk1SourceRSSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk1
					Src  cmdID= 43203 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43203 }


	iqudc12LoudMonBlk1SourceCSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk1
					Src  cmdID= 43204 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43204 }


	iqudc12LoudMonBlk2SourceLSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk2
					Src  cmdID= 43206 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43206 }


	iqudc12LoudMonBlk2SourceRSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk2
					Src  cmdID= 43207 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43207 }


	iqudc12LoudMonBlk2SourceLSSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk2
					Src  cmdID= 43208 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43208 }


	iqudc12LoudMonBlk2SourceRSSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk2
					Src  cmdID= 43209 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43209 }


	iqudc12LoudMonBlk2SourceCSrc OBJECT-TYPE
		SYNTAX		INTEGER {
							val-Silence(34),
							val-Bus1-1(0),
							val-Bus1-2(1),
							val-Bus2-1(2),
							val-Bus2-2(3),
							val-Bus3-1(4),
							val-Bus3-2(5),
							val-Bus4-1(6),
							val-Bus4-2(7),
							val-Bus5-1(8),
							val-Bus5-2(9),
							val-Bus6-1(10),
							val-Bus6-2(11),
							val-Bus7-1(12),
							val-Bus7-2(13),
							val-Bus8-1(14),
							val-Bus8-2(15),
							val-LinAc1-1(24),
							val-LinAc1-2(25),
							val-LinAc2-1(26),
							val-LinAc2-2(27),
							val-LinAc3-1(28),
							val-LinAc3-2(29),
							val-LinAc4-1(30),
							val-LinAc4-2(31),
							val-Mix1(35),
							val-Mix2(36),
							val-Mix3(37),
							val-Mix4(38),
							val-DownMix1-1(39),
							val-DownMix1-2(40),
							val-DownMix2-1(41),
							val-DownMix2-2(42)
							}
		MAX-ACCESS		read-write
		STATUS			current
		DESCRIPTION
				"TYPE: - RadiobuttonList
				 PAGE: - LoudMonBlk2
					Src  cmdID= 43210 
					Silence  value= 34  
					Bus1_1  value= 0  
					Bus1_2  value= 1  
					Bus2_1  value= 2  
					Bus2_2  value= 3  
					Bus3_1  value= 4  
					Bus3_2  value= 5  
					Bus4_1  value= 6  
					Bus4_2  value= 7  
					Bus5_1  value= 8  
					Bus5_2  value= 9  
					Bus6_1  value= 10  
					Bus6_2  value= 11  
					Bus7_1  value= 12  
					Bus7_2  value= 13  
					Bus8_1  value= 14  
					Bus8_2  value= 15  
					LinAc1_1  value= 24  
					LinAc1_2  value= 25  
					LinAc2_1  value= 26  
					LinAc2_2  value= 27  
					LinAc3_1  value= 28  
					LinAc3_2  value= 29  
					LinAc4_1  value= 30  
					LinAc4_2  value= 31  
					Mix1  value= 35  
					Mix2  value= 36  
					Mix3  value= 37  
					Mix4  value= 38  
					DownMix1-1  value= 39  
					DownMix1-2  value= 40  
					DownMix2-1  value= 41  
					DownMix2-2  value= 42  "
		::= { iqudc12CmdEntry 43210 }


	iqudc12LoudMonitorBlock1ResetSession OBJECT-TYPE
		SYNTAX		INTEGER { noAction(0),val-ResetSession(1) }
		MAX-ACCESS		read-write
		STATUS			current
		DESCRIPTION
				"TYPE: - Button
				 PAGE: - LoudMonitor
					ResetSession  cmdID= 50091  value= 1  "
		::= { iqudc12CmdEntry 50091 }


	iqudc12LoudMonitorBlock1StartSession OBJECT-TYPE
		SYNTAX		INTEGER { noAction(0),val-StartSession(1) }
		MAX-ACCESS		read-write
		STATUS			current
		DESCRIPTION
				"TYPE: - Button
				 PAGE: - LoudMonitor
					StartSession  cmdID= 50051  value= 1  "
		::= { iqudc12CmdEntry 50051 }


	iqudc12LoudMonitorBlock1PauseSession OBJECT-TYPE
		SYNTAX		INTEGER { noAction(0),val-PauseSession(1) }
		MAX-ACCESS		read-write
		STATUS			current
		DESCRIPTION
				"TYPE: - Button
				 PAGE: - LoudMonitor
					PauseSession  cmdID= 50071  value= 1  "
		::= { iqudc12CmdEntry 50071 }


	iqudc12LoudMonitorBlock1StopSession OBJECT-TYPE
		SYNTAX		INTEGER { noAction(0),val-StopSession(1) }
		MAX-ACCESS		read-write
		STATUS			current
		DESCRIPTION
				"TYPE: - Button
				 PAGE: - LoudMonitor
					StopSession  cmdID= 50131  value= 1  "
		::= { iqudc12CmdEntry 50131 }


	iqudc12LoudMonitorBlock1IntegratedLevel OBJECT-TYPE
		SYNTAX		RollCallString
		MAX-ACCESS		read-only
		STATUS			current
		DESCRIPTION
				"TYPE: - Display
				 PAGE: - LoudMonitor
					IntegratedLevel  cmdID= 43217  format=   "
		::= { iqudc12CmdEntry 43217 }


	iqudc12LoudMonitorBlock1ShortTermLevel OBJECT-TYPE
		SYNTAX		RollCallString
		MAX-ACCESS		read-only
		STATUS			current
		DESCRIPTION
				"TYPE: - Display
				 PAGE: - LoudMonitor
					ShortTermLevel  cmdID= 43219  format=   "
		::= { iqudc12CmdEntry 43219 }


	iqudc12LoudMonitorBlock1MomentaryLevel OBJECT-TYPE
		SYNTAX		RollCallString
		MAX-ACCESS		read-only
		STATUS			current
		DESCRIPTION
				"TYPE: - Display
				 PAGE: - LoudMonitor
					MomentaryLevel  cmdID= 43215  format=   "
		::= { iqudc12CmdEntry 43215 }


	iqudc12LoudMonitorBlock1LRA OBJECT-TYPE
		SYNTAX		RollCallString
		MAX-ACCESS		read-only
		STATUS			current
		DESCRIPTION
				"TYPE: - Display
				 PAGE: - LoudMonitor
					LRA  cmdID= 43221  format=   "
		::= { iqudc12CmdEntry 43221 }


	iqudc12LoudMonitorBlock1MTPL OBJECT-TYPE
		SYNTAX		RollCallString
		MAX-ACCESS		read-only
		STATUS			current
		DESCRIPTION
				"TYPE: - Display
				 PAGE: - LoudMonitor
					MTPL  cmdID= 43223  format=   "
		::= { iqudc12CmdEntry 43223 }


	iqudc12LoudMonitorBlock1SessTime OBJECT-TYPE
		SYNTAX		RollCallString
		MAX-ACCESS		read-only
		STATUS			current
		DESCRIPTION
				"TYPE: - Display
				 PAGE: - LoudMonitor
					SessTime  cmdID= 43225  format=   "
		::= { iqudc12CmdEntry 43225 }


	iqudc12LoudMonitorBlock1LiveLevel OBJECT-TYPE
		SYNTAX		RollCallString
		MAX-ACCESS		read-only
		STATUS			current
		DESCRIPTION
				"TYPE: - Display
				 PAGE: - LoudMonitor
					LiveLevel  cmdID= 43226  format=   "
		::= { iqudc12CmdEntry 43226 }


	iqudc12LoudMonitorBlock1Units OBJECT-TYPE
		SYNTAX		RollCallString
		MAX-ACCESS		read-only
		STATUS			current
		DESCRIPTION
				"TYPE: - Display
				 PAGE: - LoudMonitor
					Units  cmdID= 43236  format=   "
		::= { iqudc12CmdEntry 43236 }


	iqudc12LoudMonitorBlock1Proc1State OBJECT-TYPE
		SYNTAX		INTEGER {
							val-Started(1),
							val-Stopped(3),
							val-Paused(0),
							val-Reset(2)
							}
		MAX-ACCESS		read-write
		STATUS			current
		DESCRIPTION
				"TYPE: - RadiobuttonList
				 PAGE: - LoudMonitor
					Proc1 State  cmdID= 43239 
					Started  value= 1  
					Stopped  value= 3  
					Paused  value= 0  
					Reset  value= 2  "
		::= { iqudc12CmdEntry 43239 }


	iqudc12LoudMonitorBlock1Proc1Status OBJECT-TYPE
		SYNTAX		RollCallString
		MAX-ACCESS		read-only
		STATUS			current
		DESCRIPTION
				"TYPE: - Display
				 PAGE: - LoudMonitor
					Proc1 Status  cmdID= 50111  format=   "
		::= { iqudc12CmdEntry 50111 }


	iqudc12LoudMonitorBlock1Proc1UpdRate OBJECT-TYPE
		SYNTAX		INTEGER {
							val-Rate-1Hz(0),
							val-Rate-10Hz(1)
							}
		MAX-ACCESS		read-write
		STATUS			current
		DESCRIPTION
				"TYPE: - RadiobuttonList
				 PAGE: - LoudMonitor
					Proc1 UpdRate  cmdID= 50031 
					Rate 1Hz  value= 0  
					Rate 10Hz  value= 1  "
		::= { iqudc12CmdEntry 50031 }


	iqudc12LoudMonitorBlock1MSUpdate OBJECT-TYPE
		SYNTAX		RollCallString
		MAX-ACCESS		read-only
		STATUS			current
		DESCRIPTION
				"TYPE: - Display
				 PAGE: - LoudMonitor
					MSUpdate  cmdID= 50001  format=   "
		::= { iqudc12CmdEntry 50001 }


	iqudc12LoudMonitorBlock1ILRAUpdate OBJECT-TYPE
		SYNTAX		RollCallString
		MAX-ACCESS		read-only
		STATUS			current
		DESCRIPTION
				"TYPE: - Display
				 PAGE: - LoudMonitor
					I LRA Update  cmdID= 50002  format=   "
		::= { iqudc12CmdEntry 50002 }


	iqudc12LoudMonitorBlock1Proc1MinMax OBJECT-TYPE
		SYNTAX		RollCallString
		MAX-ACCESS		read-only
		STATUS			current
		DESCRIPTION
				"TYPE: - Display
				 PAGE: - LoudMonitor
					Proc1MinMax  cmdID= 50011  format=   "
		::= { iqudc12CmdEntry 50011 }


	iqudc12LoudMonitorBlock2ResetSession OBJECT-TYPE
		SYNTAX		INTEGER { noAction(0),val-ResetSession(1) }
		MAX-ACCESS		read-write
		STATUS			current
		DESCRIPTION
				"TYPE: - Button
				 PAGE: - LoudMonitor
					ResetSession  cmdID= 50092  value= 1  "
		::= { iqudc12CmdEntry 50092 }


	iqudc12LoudMonitorBlock2PauseSession OBJECT-TYPE
		SYNTAX		INTEGER { noAction(0),val-PauseSession(1) }
		MAX-ACCESS		read-write
		STATUS			current
		DESCRIPTION
				"TYPE: - Button
				 PAGE: - LoudMonitor
					PauseSession  cmdID= 50072  value= 1  "
		::= { iqudc12CmdEntry 50072 }


	iqudc12LoudMonitorBlock2StartSession OBJECT-TYPE
		SYNTAX		INTEGER { noAction(0),val-StartSession(1) }
		MAX-ACCESS		read-write
		STATUS			current
		DESCRIPTION
				"TYPE: - Button
				 PAGE: - LoudMonitor
					StartSession  cmdID= 50052  value= 1  "
		::= { iqudc12CmdEntry 50052 }


	iqudc12LoudMonitorBlock2StopSession OBJECT-TYPE
		SYNTAX		INTEGER { noAction(0),val-StopSession(1) }
		MAX-ACCESS		read-write
		STATUS			current
		DESCRIPTION
				"TYPE: - Button
				 PAGE: - LoudMonitor
					StopSession  cmdID= 50132  value= 1  "
		::= { iqudc12CmdEntry 50132 }


	iqudc12LoudMonitorBlock2IntegratedLevel OBJECT-TYPE
		SYNTAX		RollCallString
		MAX-ACCESS		read-only
		STATUS			current
		DESCRIPTION
				"TYPE: - Display
				 PAGE: - LoudMonitor
					IntegratedLevel  cmdID= 43218  format=   "
		::= { iqudc12CmdEntry 43218 }


	iqudc12LoudMonitorBlock2ShortTermLevel OBJECT-TYPE
		SYNTAX		RollCallString
		MAX-ACCESS		read-only
		STATUS			current
		DESCRIPTION
				"TYPE: - Display
				 PAGE: - LoudMonitor
					ShortTermLevel  cmdID= 43220  format=   "
		::= { iqudc12CmdEntry 43220 }


	iqudc12LoudMonitorBlock2MomentaryLevel OBJECT-TYPE
		SYNTAX		RollCallString
		MAX-ACCESS		read-only
		STATUS			current
		DESCRIPTION
				"TYPE: - Display
				 PAGE: - LoudMonitor
					MomentaryLevel  cmdID= 43216  format=   "
		::= { iqudc12CmdEntry 43216 }


	iqudc12LoudMonitorBlock2LRA OBJECT-TYPE
		SYNTAX		RollCallString
		MAX-ACCESS		read-only
		STATUS			current
		DESCRIPTION
				"TYPE: - Display
				 PAGE: - LoudMonitor
					LRA  cmdID= 43222  format=   "
		::= { iqudc12CmdEntry 43222 }


	iqudc12LoudMonitorBlock2MTPL OBJECT-TYPE
		SYNTAX		RollCallString
		MAX-ACCESS		read-only
		STATUS			current
		DESCRIPTION
				"TYPE: - Display
				 PAGE: - LoudMonitor
					MTPL  cmdID= 43224  format=   "
		::= { iqudc12CmdEntry 43224 }


	iqudc12LoudMonitorBlock2SessTime OBJECT-TYPE
		SYNTAX		RollCallString
		MAX-ACCESS		read-only
		STATUS			current
		DESCRIPTION
				"TYPE: - Display
				 PAGE: - LoudMonitor
					SessTime  cmdID= 43227  format=   "
		::= { iqudc12CmdEntry 43227 }


	iqudc12LoudMonitorBlock2LkfsDispMode OBJECT-TYPE
		SYNTAX		INTEGER {
							val-Relative-LU(0),
							val-Absolute-LUFS(1)
							}
		MAX-ACCESS		read-write
		STATUS			current
		DESCRIPTION
				"TYPE: - RadiobuttonList
				 PAGE: - LoudMonitor
					LkfsDispMode  cmdID= 43235 
					Relative (LU)  value= 0  
					Absolute (LUFS)  value= 1  "
		::= { iqudc12CmdEntry 43235 }


	iqudc12LoudMonitorBlock2Units OBJECT-TYPE
		SYNTAX		RollCallString
		MAX-ACCESS		read-only
		STATUS			current
		DESCRIPTION
				"TYPE: - Display
				 PAGE: - LoudMonitor
					Units  cmdID= 43237  format=   "
		::= { iqudc12CmdEntry 43237 }


	iqudc12LoudMonitorBlock2LiveUnits OBJECT-TYPE
		SYNTAX		RollCallString
		MAX-ACCESS		read-only
		STATUS			current
		DESCRIPTION
				"TYPE: - Display
				 PAGE: - LoudMonitor
					LiveUnits  cmdID= 43238  format=   "
		::= { iqudc12CmdEntry 43238 }


	iqudc12LoudMonitorBlock2Proc2State OBJECT-TYPE
		SYNTAX		INTEGER {
							val-Started(1),
							val-Stopped(3),
							val-Paused(0),
							val-Reset(2)
							}
		MAX-ACCESS		read-write
		STATUS			current
		DESCRIPTION
				"TYPE: - RadiobuttonList
				 PAGE: - LoudMonitor
					Proc2 State  cmdID= 43240 
					Started  value= 1  
					Stopped  value= 3  
					Paused  value= 0  
					Reset  value= 2  "
		::= { iqudc12CmdEntry 43240 }


	iqudc12LoudMonitorBlock2Proc2Status OBJECT-TYPE
		SYNTAX		RollCallString
		MAX-ACCESS		read-only
		STATUS			current
		DESCRIPTION
				"TYPE: - Display
				 PAGE: - LoudMonitor
					Proc2 Status  cmdID= 50112  format=   "
		::= { iqudc12CmdEntry 50112 }


	iqudc12LoudMonitorBlock2Proc2UpdRate OBJECT-TYPE
		SYNTAX		INTEGER {
							val-Rate-1Hz(0),
							val-Rate-10Hz(1)
							}
		MAX-ACCESS		read-write
		STATUS			current
		DESCRIPTION
				"TYPE: - RadiobuttonList
				 PAGE: - LoudMonitor
					Proc2 UpdRate  cmdID= 50032 
					Rate 1Hz  value= 0  
					Rate 10Hz  value= 1  "
		::= { iqudc12CmdEntry 50032 }


	iqudc12LoudMonitorBlock2Proc2MinMax OBJECT-TYPE
		SYNTAX		RollCallString
		MAX-ACCESS		read-only
		STATUS			current
		DESCRIPTION
				"TYPE: - Display
				 PAGE: - LoudMonitor
					Proc2MinMax  cmdID= 50012  format=   "
		::= { iqudc12CmdEntry 50012 }


	iqudc12LoudMonitorBlock2RollcallUpdate OBJECT-TYPE
		SYNTAX		INTEGER { disable(0), enable(1) }
		MAX-ACCESS		read-write
		STATUS			current
		DESCRIPTION
				"TYPE: - Checkbox
				 PAGE: - LoudMonitor
					RollcallUpdate  cmdID= 43241 "
		::= { iqudc12CmdEntry 43241 }


	iqudc12LoudMonitorBlock2Prog1ID OBJECT-TYPE
		SYNTAX		RollCallString
		MAX-ACCESS		read-write
		STATUS			current
		DESCRIPTION
				"TYPE: - Editstring
				 PAGE: - LoudMonitor
					Prog1ID  cmdID= 50151  "
		::= { iqudc12CmdEntry 50151 }


	iqudc12LoudMonitorBlock2Prog2ID OBJECT-TYPE
		SYNTAX		RollCallString
		MAX-ACCESS		read-write
		STATUS			current
		DESCRIPTION
				"TYPE: - Editstring
				 PAGE: - LoudMonitor
					Prog2ID  cmdID= 50152  "
		::= { iqudc12CmdEntry 50152 }


	iqudc12LoudMonitorBlock2Chan1ID OBJECT-TYPE
		SYNTAX		RollCallString
		MAX-ACCESS		read-write
		STATUS			current
		DESCRIPTION
				"TYPE: - Editstring
				 PAGE: - LoudMonitor
					Chan1ID  cmdID= 50171  "
		::= { iqudc12CmdEntry 50171 }


	iqudc12LoudMonitorBlock2Chan2ID OBJECT-TYPE
		SYNTAX		RollCallString
		MAX-ACCESS		read-write
		STATUS			current
		DESCRIPTION
				"TYPE: - Editstring
				 PAGE: - LoudMonitor
					Chan2ID  cmdID= 50172  "
		::= { iqudc12CmdEntry 50172 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: unknown
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:02:00
--				: 
-- Comments		: 
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
-- Vary			: YES
--
-- Value(s)		: 16
--				: 
-- Comments		: 
--
---------------------------------------------------------------------------------------------------
-- Header		: INPUT_VI
--
-- MIB ref		: swCardEventLogSlotXX       .8.73.78.80.85.84.95.86.73
-- absolute OID	: 1.3.6.1.4.1.7995.2.6.1.1.XX.8.73.78.80.85.84.95.86.73
-- Vary			: YES
--
-- Value(s)		: -
--				: 
-- Comments		: 
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
-- Vary			: YES
--
-- Value(s)		: INPUT 1 SERIAL IN
--				: 
-- Comments		: 
--
---------------------------------------------------------------------------------------------------
-- Header		: OUTPUT_2
--
-- MIB ref		: swCardEventLogSlotXX       .8.79.85.84.80.85.84.95.50
-- absolute OID	: 1.3.6.1.4.1.7995.2.6.1.1.XX.8.79.85.84.80.85.84.95.50
-- Vary			: YES
--
-- Value(s)		: INPUT 1 SERIAL IN
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				: 
-- Comments		: 
--
---------------------------------------------------------------------------------------------------
-- Header		: INPUT_AFD
--
-- MIB ref		: swCardEventLogSlotXX       .9.73.78.80.85.84.95.65.70.68
-- absolute OID	: 1.3.6.1.4.1.7995.2.6.1.1.XX.9.73.78.80.85.84.95.65.70.68
-- Vary			: YES
--
-- Value(s)		: None
--				: 
-- Comments		: 
--
---------------------------------------------------------------------------------------------------
-- Header		: INPUT_WSS
--
-- MIB ref		: swCardEventLogSlotXX       .9.73.78.80.85.84.95.87.83.83
-- absolute OID	: 1.3.6.1.4.1.7995.2.6.1.1.XX.9.73.78.80.85.84.95.87.83.83
-- Vary			: YES
--
-- Value(s)		: -
--				: 
-- Comments		: 
--
---------------------------------------------------------------------------------------------------
-- Header		: INPUT_2016
--
-- MIB ref		: swCardEventLogSlotXX       .10.73.78.80.85.84.95.50.48.49.54
-- absolute OID	: 1.3.6.1.4.1.7995.2.6.1.1.XX.10.73.78.80.85.84.95.50.48.49.54
-- Vary			: YES
--
-- Value(s)		: -
--				: 
-- Comments		: 
--
---------------------------------------------------------------------------------------------------
-- Header		: INPUT_VITC
--
-- MIB ref		: swCardEventLogSlotXX       .10.73.78.80.85.84.95.86.73.84.67
-- absolute OID	: 1.3.6.1.4.1.7995.2.6.1.1.XX.10.73.78.80.85.84.95.86.73.84.67
-- Vary			: YES
--
-- Value(s)		: -
--				: 
-- Comments		: 
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				: 
-- Comments		: 
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
-- Vary			: YES
--
-- Value(s)		: 5
--				: 
-- Comments		: 
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
-- Vary			: YES
--
-- Value(s)		: 2
--				: 
-- Comments		: 
--
---------------------------------------------------------------------------------------------------
-- Header		: POWER_USAGE
--
-- MIB ref		: swCardEventLogSlotXX       .11.80.79.87.69.82.95.85.83.65.71.69
-- absolute OID	: 1.3.6.1.4.1.7995.2.6.1.1.XX.11.80.79.87.69.82.95.85.83.65.71.69
-- Vary			: YES
--
-- Value(s)		: 31.5W/28.8LU
--				: 
-- Comments		: 
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
-- Vary			: YES
--
-- Value(s)		: WARN:Type Mismatch
--				: 
-- Comments		: 
--
---------------------------------------------------------------------------------------------------
-- Header		: TEMP_1_NAME
--
-- MIB ref		: swCardEventLogSlotXX       .11.84.69.77.80.95.49.95.78.65.77.69
-- absolute OID	: 1.3.6.1.4.1.7995.2.6.1.1.XX.11.84.69.77.80.95.49.95.78.65.77.69
-- Vary			: YES
--
-- Value(s)		: Temperature FPGA
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 0009204671
--				: 
-- Comments		: 
--
---------------------------------------------------------------------------------------------------
-- Header		: INPUT_1_NAME
--
-- MIB ref		: swCardEventLogSlotXX       .12.73.78.80.85.84.95.49.95.78.65.77.69
-- absolute OID	: 1.3.6.1.4.1.7995.2.6.1.1.XX.12.73.78.80.85.84.95.49.95.78.65.77.69
-- Vary			: YES
--
-- Value(s)		: INPUT 1 SERIAL IN
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD/SD/3G SDI
--				: 
-- Comments		: 
--
---------------------------------------------------------------------------------------------------
-- Header		: INPUT_2_NAME
--
-- MIB ref		: swCardEventLogSlotXX       .12.73.78.80.85.84.95.50.95.78.65.77.69
-- absolute OID	: 1.3.6.1.4.1.7995.2.6.1.1.XX.12.73.78.80.85.84.95.50.95.78.65.77.69
-- Vary			: YES
--
-- Value(s)		: INPUT 2 SERIAL IN
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: HD/SD/3G SDI
--				: 
-- Comments		: 
--
---------------------------------------------------------------------------------------------------
-- Header		: INPUT_ASPECT
--
-- MIB ref		: swCardEventLogSlotXX       .12.73.78.80.85.84.95.65.83.80.69.67.84
-- absolute OID	: 1.3.6.1.4.1.7995.2.6.1.1.XX.12.73.78.80.85.84.95.65.83.80.69.67.84
-- Vary			: YES
--
-- Value(s)		: -
--				: 
-- Comments		: 
--
---------------------------------------------------------------------------------------------------
-- Header		: OUTPUT_1_AFD
--
-- MIB ref		: swCardEventLogSlotXX       .12.79.85.84.80.85.84.95.49.95.65.70.68
-- absolute OID	: 1.3.6.1.4.1.7995.2.6.1.1.XX.12.79.85.84.80.85.84.95.49.95.65.70.68
-- Vary			: YES
--
-- Value(s)		: <Disabled>
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2014-11-13T15:18:18Z
--				: 
-- Comments		: 
--
---------------------------------------------------------------------------------------------------
-- Header		: TEMP_1_STATE
--
-- MIB ref		: swCardEventLogSlotXX       .12.84.69.77.80.95.49.95.83.84.65.84.69
-- absolute OID	: 1.3.6.1.4.1.7995.2.6.1.1.XX.12.84.69.77.80.95.49.95.83.84.65.84.69
-- Vary			: YES
--
-- Value(s)		: OK
--				: 
-- Comments		: 
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: YES
--
-- Value(s)		: SER IN 1
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: 
-- Comments		: 
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
-- Vary			: YES
--
-- Value(s)		: SER IN 2
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: FAIL:Lost
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: HD/SD/3G SDI
--				: 
-- Comments		: 
--
---------------------------------------------------------------------------------------------------
-- Header		: OUTPUT_2_TYPE
--
-- MIB ref		: swCardEventLogSlotXX       .13.79.85.84.80.85.84.95.50.95.84.89.80.69
-- absolute OID	: 1.3.6.1.4.1.7995.2.6.1.1.XX.13.79.85.84.80.85.84.95.50.95.84.89.80.69
-- Vary			: YES
--
-- Value(s)		: HD/SD/3G SDI
--				: 
-- Comments		: 
--
---------------------------------------------------------------------------------------------------
-- Header		: INPUT_REF_VITC
--
-- MIB ref		: swCardEventLogSlotXX       .14.73.78.80.85.84.95.82.69.70.95.86.73.84.67
-- absolute OID	: 1.3.6.1.4.1.7995.2.6.1.1.XX.14.73.78.80.85.84.95.82.69.70.95.86.73.84.67
-- Vary			: YES
--
-- Value(s)		: LOST:REF-VITC
--				: 
-- Comments		: 
--
---------------------------------------------------------------------------------------------------
-- Header		: INPUT_VI_STATE
--
-- MIB ref		: swCardEventLogSlotXX       .14.73.78.80.85.84.95.86.73.95.83.84.65.84.69
-- absolute OID	: 1.3.6.1.4.1.7995.2.6.1.1.XX.14.73.78.80.85.84.95.86.73.95.83.84.65.84.69
-- Vary			: YES
--
-- Value(s)		: -
--				: 
-- Comments		: 
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: WARN:Black
--				: 
-- Comments		: 
--
---------------------------------------------------------------------------------------------------
-- Header		: OUTPUT_2_STATE
--
-- MIB ref		: swCardEventLogSlotXX       .14.79.85.84.80.85.84.95.50.95.83.84.65.84.69
-- absolute OID	: 1.3.6.1.4.1.7995.2.6.1.1.XX.14.79.85.84.80.85.84.95.50.95.83.84.65.84.69
-- Vary			: YES
--
-- Value(s)		: WARN:Black
--				: 
-- Comments		: 
--
---------------------------------------------------------------------------------------------------
-- Header		: GENLOCK_1_STATE
--
-- MIB ref		: swCardEventLogSlotXX       .15.71.69.78.76.79.67.75.95.49.95.83.84.65.84.69
-- absolute OID	: 1.3.6.1.4.1.7995.2.6.1.1.XX.15.71.69.78.76.79.67.75.95.49.95.83.84.65.84.69
-- Vary			: YES
--
-- Value(s)		: WARN:Freerun
--				: 
-- Comments		: 
--
---------------------------------------------------------------------------------------------------
-- Header		: INPUT_VI_ASPECT
--
-- MIB ref		: swCardEventLogSlotXX       .15.73.78.80.85.84.95.86.73.95.65.83.80.69.67.84
-- absolute OID	: 1.3.6.1.4.1.7995.2.6.1.1.XX.15.73.78.80.85.84.95.86.73.95.65.83.80.69.67.84
-- Vary			: YES
--
-- Value(s)		: -
--				: 
-- Comments		: 
--
---------------------------------------------------------------------------------------------------
-- Header		: INPUT_WSS_STATE
--
-- MIB ref		: swCardEventLogSlotXX       .15.73.78.80.85.84.95.87.83.83.95.83.84.65.84.69
-- absolute OID	: 1.3.6.1.4.1.7995.2.6.1.1.XX.15.73.78.80.85.84.95.87.83.83.95.83.84.65.84.69
-- Vary			: YES
--
-- Value(s)		: -
--				: 
-- Comments		: 
--
---------------------------------------------------------------------------------------------------
-- Header		: OUTPUT_1_ASPECT
--
-- MIB ref		: swCardEventLogSlotXX       .15.79.85.84.80.85.84.95.49.95.65.83.80.69.67.84
-- absolute OID	: 1.3.6.1.4.1.7995.2.6.1.1.XX.15.79.85.84.80.85.84.95.49.95.65.83.80.69.67.84
-- Vary			: YES
--
-- Value(s)		: -
--				: 
-- Comments		: 
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 0713007125
--				: 
-- Comments		: 
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: RGMPP1C
--				: 
-- Comments		: 
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: 
-- Comments		: 
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--				: 
-- Comments		: 
--
---------------------------------------------------------------------------------------------------
-- Header		: INPUT_2016_STATE
--
-- MIB ref		: swCardEventLogSlotXX       .16.73.78.80.85.84.95.50.48.49.54.95.83.84.65.84.69
-- absolute OID	: 1.3.6.1.4.1.7995.2.6.1.1.XX.16.73.78.80.85.84.95.50.48.49.54.95.83.84.65.84.69
-- Vary			: YES
--
-- Value(s)		: -
--				: 
-- Comments		: 
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
-- Vary			: YES
--
-- Value(s)		: OK
--				: 
-- Comments		: 
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: Unknown
--				: 
-- Comments		: 
--
---------------------------------------------------------------------------------------------------
-- Header		: INPUT_ANC_LINE_7
--
-- MIB ref		: swCardEventLogSlotXX       .16.73.78.80.85.84.95.65.78.67.95.76.73.78.69.95.55
-- absolute OID	: 1.3.6.1.4.1.7995.2.6.1.1.XX.16.73.78.80.85.84.95.65.78.67.95.76.73.78.69.95.55
-- Vary			: YES
--
-- Value(s)		: -
--				: 
-- Comments		: 
--
---------------------------------------------------------------------------------------------------
-- Header		: INPUT_ANC_LINE_8
--
-- MIB ref		: swCardEventLogSlotXX       .16.73.78.80.85.84.95.65.78.67.95.76.73.78.69.95.56
-- absolute OID	: 1.3.6.1.4.1.7995.2.6.1.1.XX.16.73.78.80.85.84.95.65.78.67.95.76.73.78.69.95.56
-- Vary			: YES
--
-- Value(s)		: -
--				: 
-- Comments		: 
--
---------------------------------------------------------------------------------------------------
-- Header		: INPUT_ANC_LINE_9
--
-- MIB ref		: swCardEventLogSlotXX       .16.73.78.80.85.84.95.65.78.67.95.76.73.78.69.95.57
-- absolute OID	: 1.3.6.1.4.1.7995.2.6.1.1.XX.16.73.78.80.85.84.95.65.78.67.95.76.73.78.69.95.57
-- Vary			: YES
--
-- Value(s)		: -
--				: 
-- Comments		: 
--
---------------------------------------------------------------------------------------------------
-- Header		: INPUT_WSS_ASPECT
--
-- MIB ref		: swCardEventLogSlotXX       .16.73.78.80.85.84.95.87.83.83.95.65.83.80.69.67.84
-- absolute OID	: 1.3.6.1.4.1.7995.2.6.1.1.XX.16.73.78.80.85.84.95.87.83.83.95.65.83.80.69.67.84
-- Vary			: YES
--
-- Value(s)		: -
--				: 
-- Comments		: 
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
-- Vary			: YES
--
-- Value(s)		: FAIL:No File
--				: 
-- Comments		: 
--
---------------------------------------------------------------------------------------------------
-- Header		: OUTPUT_1_CAPTION
--
-- MIB ref		: swCardEventLogSlotXX       .16.79.85.84.80.85.84.95.49.95.67.65.80.84.73.79.78
-- absolute OID	: 1.3.6.1.4.1.7995.2.6.1.1.XX.16.79.85.84.80.85.84.95.49.95.67.65.80.84.73.79.78
-- Vary			: YES
--
-- Value(s)		: OK:Off
--				: 
-- Comments		: 
--
---------------------------------------------------------------------------------------------------
-- Header		: OUTPUT_2_CAPTION
--
-- MIB ref		: swCardEventLogSlotXX       .16.79.85.84.80.85.84.95.50.95.67.65.80.84.73.79.78
-- absolute OID	: 1.3.6.1.4.1.7995.2.6.1.1.XX.16.79.85.84.80.85.84.95.50.95.67.65.80.84.73.79.78
-- Vary			: YES
--
-- Value(s)		: OK:Off
--				: 
-- Comments		: 
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
-- Vary			: YES
--
-- Value(s)		: WARN:Unknown
--				: 
-- Comments		: 
--
---------------------------------------------------------------------------------------------------
-- Header		: AES_INPUT_1_STATE
--
-- MIB ref		: swCardEventLogSlotXX       .17.65.69.83.95.73.78.80.85.84.95.49.95.83.84.65.84.69
-- absolute OID	: 1.3.6.1.4.1.7995.2.6.1.1.XX.17.65.69.83.95.73.78.80.85.84.95.49.95.83.84.65.84.69
-- Vary			: YES
--
-- Value(s)		: FAIL:Lost
--				: 
-- Comments		: 
--
---------------------------------------------------------------------------------------------------
-- Header		: AES_INPUT_2_STATE
--
-- MIB ref		: swCardEventLogSlotXX       .17.65.69.83.95.73.78.80.85.84.95.50.95.83.84.65.84.69
-- absolute OID	: 1.3.6.1.4.1.7995.2.6.1.1.XX.17.65.69.83.95.73.78.80.85.84.95.50.95.83.84.65.84.69
-- Vary			: YES
--
-- Value(s)		: FAIL:Lost
--				: 
-- Comments		: 
--
---------------------------------------------------------------------------------------------------
-- Header		: AES_INPUT_3_STATE
--
-- MIB ref		: swCardEventLogSlotXX       .17.65.69.83.95.73.78.80.85.84.95.51.95.83.84.65.84.69
-- absolute OID	: 1.3.6.1.4.1.7995.2.6.1.1.XX.17.65.69.83.95.73.78.80.85.84.95.51.95.83.84.65.84.69
-- Vary			: YES
--
-- Value(s)		: FAIL:Lost
--				: 
-- Comments		: 
--
---------------------------------------------------------------------------------------------------
-- Header		: AES_INPUT_4_STATE
--
-- MIB ref		: swCardEventLogSlotXX       .17.65.69.83.95.73.78.80.85.84.95.52.95.83.84.65.84.69
-- absolute OID	: 1.3.6.1.4.1.7995.2.6.1.1.XX.17.65.69.83.95.73.78.80.85.84.95.52.95.83.84.65.84.69
-- Vary			: YES
--
-- Value(s)		: FAIL:Lost
--				: 
-- Comments		: 
--
---------------------------------------------------------------------------------------------------
-- Header		: AES_INPUT_5_STATE
--
-- MIB ref		: swCardEventLogSlotXX       .17.65.69.83.95.73.78.80.85.84.95.53.95.83.84.65.84.69
-- absolute OID	: 1.3.6.1.4.1.7995.2.6.1.1.XX.17.65.69.83.95.73.78.80.85.84.95.53.95.83.84.65.84.69
-- Vary			: YES
--
-- Value(s)		: FAIL:Lost
--				: 
-- Comments		: 
--
---------------------------------------------------------------------------------------------------
-- Header		: AES_INPUT_6_STATE
--
-- MIB ref		: swCardEventLogSlotXX       .17.65.69.83.95.73.78.80.85.84.95.54.95.83.84.65.84.69
-- absolute OID	: 1.3.6.1.4.1.7995.2.6.1.1.XX.17.65.69.83.95.73.78.80.85.84.95.54.95.83.84.65.84.69
-- Vary			: YES
--
-- Value(s)		: FAIL:Lost
--				: 
-- Comments		: 
--
---------------------------------------------------------------------------------------------------
-- Header		: AES_INPUT_7_STATE
--
-- MIB ref		: swCardEventLogSlotXX       .17.65.69.83.95.73.78.80.85.84.95.55.95.83.84.65.84.69
-- absolute OID	: 1.3.6.1.4.1.7995.2.6.1.1.XX.17.65.69.83.95.73.78.80.85.84.95.55.95.83.84.65.84.69
-- Vary			: YES
--
-- Value(s)		: FAIL:Lost
--				: 
-- Comments		: 
--
---------------------------------------------------------------------------------------------------
-- Header		: AES_INPUT_8_STATE
--
-- MIB ref		: swCardEventLogSlotXX       .17.65.69.83.95.73.78.80.85.84.95.56.95.83.84.65.84.69
-- absolute OID	: 1.3.6.1.4.1.7995.2.6.1.1.XX.17.65.69.83.95.73.78.80.85.84.95.56.95.83.84.65.84.69
-- Vary			: YES
--
-- Value(s)		: FAIL:Lost
--				: 
-- Comments		: 
--
---------------------------------------------------------------------------------------------------
-- Header		: INPUT_2016_ASPECT
--
-- MIB ref		: swCardEventLogSlotXX       .17.73.78.80.85.84.95.50.48.49.54.95.65.83.80.69.67.84
-- absolute OID	: 1.3.6.1.4.1.7995.2.6.1.1.XX.17.73.78.80.85.84.95.50.48.49.54.95.65.83.80.69.67.84
-- Vary			: YES
--
-- Value(s)		: -
--				: 
-- Comments		: 
--
---------------------------------------------------------------------------------------------------
-- Header		: INPUT_ANC_LINE_10
--
-- MIB ref		: swCardEventLogSlotXX       .17.73.78.80.85.84.95.65.78.67.95.76.73.78.69.95.49.48
-- absolute OID	: 1.3.6.1.4.1.7995.2.6.1.1.XX.17.73.78.80.85.84.95.65.78.67.95.76.73.78.69.95.49.48
-- Vary			: YES
--
-- Value(s)		: -
--				: 
-- Comments		: 
--
---------------------------------------------------------------------------------------------------
-- Header		: INPUT_ANC_LINE_11
--
-- MIB ref		: swCardEventLogSlotXX       .17.73.78.80.85.84.95.65.78.67.95.76.73.78.69.95.49.49
-- absolute OID	: 1.3.6.1.4.1.7995.2.6.1.1.XX.17.73.78.80.85.84.95.65.78.67.95.76.73.78.69.95.49.49
-- Vary			: YES
--
-- Value(s)		: -
--				: 
-- Comments		: 
--
---------------------------------------------------------------------------------------------------
-- Header		: INPUT_ANC_LINE_12
--
-- MIB ref		: swCardEventLogSlotXX       .17.73.78.80.85.84.95.65.78.67.95.76.73.78.69.95.49.50
-- absolute OID	: 1.3.6.1.4.1.7995.2.6.1.1.XX.17.73.78.80.85.84.95.65.78.67.95.76.73.78.69.95.49.50
-- Vary			: YES
--
-- Value(s)		: -
--				: 
-- Comments		: 
--
---------------------------------------------------------------------------------------------------
-- Header		: INPUT_ANC_LINE_13
--
-- MIB ref		: swCardEventLogSlotXX       .17.73.78.80.85.84.95.65.78.67.95.76.73.78.69.95.49.51
-- absolute OID	: 1.3.6.1.4.1.7995.2.6.1.1.XX.17.73.78.80.85.84.95.65.78.67.95.76.73.78.69.95.49.51
-- Vary			: YES
--
-- Value(s)		: -
--				: 
-- Comments		: 
--
---------------------------------------------------------------------------------------------------
-- Header		: INPUT_ANC_LINE_14
--
-- MIB ref		: swCardEventLogSlotXX       .17.73.78.80.85.84.95.65.78.67.95.76.73.78.69.95.49.52
-- absolute OID	: 1.3.6.1.4.1.7995.2.6.1.1.XX.17.73.78.80.85.84.95.65.78.67.95.76.73.78.69.95.49.52
-- Vary			: YES
--
-- Value(s)		: -
--				: 
-- Comments		: 
--
---------------------------------------------------------------------------------------------------
-- Header		: INPUT_ANC_LINE_15
--
-- MIB ref		: swCardEventLogSlotXX       .17.73.78.80.85.84.95.65.78.67.95.76.73.78.69.95.49.53
-- absolute OID	: 1.3.6.1.4.1.7995.2.6.1.1.XX.17.73.78.80.85.84.95.65.78.67.95.76.73.78.69.95.49.53
-- Vary			: YES
--
-- Value(s)		: -
--				: 
-- Comments		: 
--
---------------------------------------------------------------------------------------------------
-- Header		: INPUT_ANC_LINE_16
--
-- MIB ref		: swCardEventLogSlotXX       .17.73.78.80.85.84.95.65.78.67.95.76.73.78.69.95.49.54
-- absolute OID	: 1.3.6.1.4.1.7995.2.6.1.1.XX.17.73.78.80.85.84.95.65.78.67.95.76.73.78.69.95.49.54
-- Vary			: YES
--
-- Value(s)		: -
--				: 
-- Comments		: 
--
---------------------------------------------------------------------------------------------------
-- Header		: INPUT_ANC_LINE_17
--
-- MIB ref		: swCardEventLogSlotXX       .17.73.78.80.85.84.95.65.78.67.95.76.73.78.69.95.49.55
-- absolute OID	: 1.3.6.1.4.1.7995.2.6.1.1.XX.17.73.78.80.85.84.95.65.78.67.95.76.73.78.69.95.49.55
-- Vary			: YES
--
-- Value(s)		: -
--				: 
-- Comments		: 
--
---------------------------------------------------------------------------------------------------
-- Header		: INPUT_ANC_LINE_18
--
-- MIB ref		: swCardEventLogSlotXX       .17.73.78.80.85.84.95.65.78.67.95.76.73.78.69.95.49.56
-- absolute OID	: 1.3.6.1.4.1.7995.2.6.1.1.XX.17.73.78.80.85.84.95.65.78.67.95.76.73.78.69.95.49.56
-- Vary			: YES
--
-- Value(s)		: -
--				: 
-- Comments		: 
--
---------------------------------------------------------------------------------------------------
-- Header		: INPUT_ANC_LINE_19
--
-- MIB ref		: swCardEventLogSlotXX       .17.73.78.80.85.84.95.65.78.67.95.76.73.78.69.95.49.57
-- absolute OID	: 1.3.6.1.4.1.7995.2.6.1.1.XX.17.73.78.80.85.84.95.65.78.67.95.76.73.78.69.95.49.57
-- Vary			: YES
--
-- Value(s)		: -
--				: 
-- Comments		: 
--
---------------------------------------------------------------------------------------------------
-- Header		: INPUT_ANC_LINE_20
--
-- MIB ref		: swCardEventLogSlotXX       .17.73.78.80.85.84.95.65.78.67.95.76.73.78.69.95.50.48
-- absolute OID	: 1.3.6.1.4.1.7995.2.6.1.1.XX.17.73.78.80.85.84.95.65.78.67.95.76.73.78.69.95.50.48
-- Vary			: YES
--
-- Value(s)		: -
--				: 
-- Comments		: 
--
---------------------------------------------------------------------------------------------------
-- Header		: INPUT_ANC_LINE_21
--
-- MIB ref		: swCardEventLogSlotXX       .17.73.78.80.85.84.95.65.78.67.95.76.73.78.69.95.50.49
-- absolute OID	: 1.3.6.1.4.1.7995.2.6.1.1.XX.17.73.78.80.85.84.95.65.78.67.95.76.73.78.69.95.50.49
-- Vary			: YES
--
-- Value(s)		: -
--				: 
-- Comments		: 
--
---------------------------------------------------------------------------------------------------
-- Header		: INPUT_ANC_LINE_22
--
-- MIB ref		: swCardEventLogSlotXX       .17.73.78.80.85.84.95.65.78.67.95.76.73.78.69.95.50.50
-- absolute OID	: 1.3.6.1.4.1.7995.2.6.1.1.XX.17.73.78.80.85.84.95.65.78.67.95.76.73.78.69.95.50.50
-- Vary			: YES
--
-- Value(s)		: -
--				: 
-- Comments		: 
--
---------------------------------------------------------------------------------------------------
-- Header		: INPUT_ANC_LINE_23
--
-- MIB ref		: swCardEventLogSlotXX       .17.73.78.80.85.84.95.65.78.67.95.76.73.78.69.95.50.51
-- absolute OID	: 1.3.6.1.4.1.7995.2.6.1.1.XX.17.73.78.80.85.84.95.65.78.67.95.76.73.78.69.95.50.51
-- Vary			: YES
--
-- Value(s)		: -
--				: 
-- Comments		: 
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: 1080/25i
--				: 
-- Comments		: 
--
---------------------------------------------------------------------------------------------------
-- Header		: OUTPUT_1_TIMECODE
--
-- MIB ref		: swCardEventLogSlotXX       .17.79.85.84.80.85.84.95.49.95.84.73.77.69.67.79.68.69
-- absolute OID	: 1.3.6.1.4.1.7995.2.6.1.1.XX.17.79.85.84.80.85.84.95.49.95.84.73.77.69.67.79.68.69
-- Vary			: YES
--
-- Value(s)		: 
--				: 
-- Comments		: 
--
---------------------------------------------------------------------------------------------------
-- Header		: OUTPUT_2_STANDARD
--
-- MIB ref		: swCardEventLogSlotXX       .17.79.85.84.80.85.84.95.50.95.83.84.65.78.68.65.82.68
-- absolute OID	: 1.3.6.1.4.1.7995.2.6.1.1.XX.17.79.85.84.80.85.84.95.50.95.83.84.65.78.68.65.82.68
-- Vary			: YES
--
-- Value(s)		: 1080/25i
--				: 
-- Comments		: 
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
-- Vary			: YES
--
-- Value(s)		: FAIL:Lost
--				: 
-- Comments		: 
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
-- Vary			: YES
--
-- Value(s)		: 0
--				: 
-- Comments		: 
--
---------------------------------------------------------------------------------------------------
-- Header		: INPUT_2_SDI_ERRSEC
--
-- MIB ref		: swCardEventLogSlotXX       .18.73.78.80.85.84.95.50.95.83.68.73.95.69.82.82.83.69.67
-- absolute OID	: 1.3.6.1.4.1.7995.2.6.1.1.XX.18.73.78.80.85.84.95.50.95.83.68.73.95.69.82.82.83.69.67
-- Vary			: YES
--
-- Value(s)		: 0
--				: 
-- Comments		: 
--
---------------------------------------------------------------------------------------------------
-- Header		: LICENSED_OPTIONS_2
--
-- MIB ref		: swCardEventLogSlotXX       .18.76.73.67.69.78.83.69.68.95.79.80.84.73.79.78.83.95.50
-- absolute OID	: 1.3.6.1.4.1.7995.2.6.1.1.XX.18.76.73.67.69.78.83.69.68.95.79.80.84.73.79.78.83.95.50
-- Vary			: YES
--
-- Value(s)		: OK:0 Option(s)
--				: 
-- Comments		: 
--
---------------------------------------------------------------------------------------------------
-- Header		: OUTPUT_1_ANC_LINE_7
--
-- MIB ref		: swCardEventLogSlotXX       .19.79.85.84.80.85.84.95.49.95.65.78.67.95.76.73.78.69.95.55
-- absolute OID	: 1.3.6.1.4.1.7995.2.6.1.1.XX.19.79.85.84.80.85.84.95.49.95.65.78.67.95.76.73.78.69.95.55
-- Vary			: YES
--
-- Value(s)		: -
--				: 
-- Comments		: 
--
---------------------------------------------------------------------------------------------------
-- Header		: OUTPUT_1_ANC_LINE_8
--
-- MIB ref		: swCardEventLogSlotXX       .19.79.85.84.80.85.84.95.49.95.65.78.67.95.76.73.78.69.95.56
-- absolute OID	: 1.3.6.1.4.1.7995.2.6.1.1.XX.19.79.85.84.80.85.84.95.49.95.65.78.67.95.76.73.78.69.95.56
-- Vary			: YES
--
-- Value(s)		: -
--				: 
-- Comments		: 
--
---------------------------------------------------------------------------------------------------
-- Header		: OUTPUT_1_ANC_LINE_9
--
-- MIB ref		: swCardEventLogSlotXX       .19.79.85.84.80.85.84.95.49.95.65.78.67.95.76.73.78.69.95.57
-- absolute OID	: 1.3.6.1.4.1.7995.2.6.1.1.XX.19.79.85.84.80.85.84.95.49.95.65.78.67.95.76.73.78.69.95.57
-- Vary			: YES
--
-- Value(s)		: -
--				: 
-- Comments		: 
--
---------------------------------------------------------------------------------------------------
-- Header		: AES_OUTPUT_1_1_STATE
--
-- MIB ref		: swCardEventLogSlotXX       .20.65.69.83.95.79.85.84.80.85.84.95.49.95.49.95.83.84.65.84.69
-- absolute OID	: 1.3.6.1.4.1.7995.2.6.1.1.XX.20.65.69.83.95.79.85.84.80.85.84.95.49.95.49.95.83.84.65.84.69
-- Vary			: YES
--
-- Value(s)		: OK:Input
--				: 
-- Comments		: 
--
---------------------------------------------------------------------------------------------------
-- Header		: AES_OUTPUT_1_2_STATE
--
-- MIB ref		: swCardEventLogSlotXX       .20.65.69.83.95.79.85.84.80.85.84.95.49.95.50.95.83.84.65.84.69
-- absolute OID	: 1.3.6.1.4.1.7995.2.6.1.1.XX.20.65.69.83.95.79.85.84.80.85.84.95.49.95.50.95.83.84.65.84.69
-- Vary			: YES
--
-- Value(s)		: OK:Input
--				: 
-- Comments		: 
--
---------------------------------------------------------------------------------------------------
-- Header		: AES_OUTPUT_2_1_STATE
--
-- MIB ref		: swCardEventLogSlotXX       .20.65.69.83.95.79.85.84.80.85.84.95.50.95.49.95.83.84.65.84.69
-- absolute OID	: 1.3.6.1.4.1.7995.2.6.1.1.XX.20.65.69.83.95.79.85.84.80.85.84.95.50.95.49.95.83.84.65.84.69
-- Vary			: YES
--
-- Value(s)		: OK:Input
--				: 
-- Comments		: 
--
---------------------------------------------------------------------------------------------------
-- Header		: AES_OUTPUT_2_2_STATE
--
-- MIB ref		: swCardEventLogSlotXX       .20.65.69.83.95.79.85.84.80.85.84.95.50.95.50.95.83.84.65.84.69
-- absolute OID	: 1.3.6.1.4.1.7995.2.6.1.1.XX.20.65.69.83.95.79.85.84.80.85.84.95.50.95.50.95.83.84.65.84.69
-- Vary			: YES
--
-- Value(s)		: OK:Input
--				: 
-- Comments		: 
--
---------------------------------------------------------------------------------------------------
-- Header		: AES_OUTPUT_3_1_STATE
--
-- MIB ref		: swCardEventLogSlotXX       .20.65.69.83.95.79.85.84.80.85.84.95.51.95.49.95.83.84.65.84.69
-- absolute OID	: 1.3.6.1.4.1.7995.2.6.1.1.XX.20.65.69.83.95.79.85.84.80.85.84.95.51.95.49.95.83.84.65.84.69
-- Vary			: YES
--
-- Value(s)		: OK:Input
--				: 
-- Comments		: 
--
---------------------------------------------------------------------------------------------------
-- Header		: AES_OUTPUT_3_2_STATE
--
-- MIB ref		: swCardEventLogSlotXX       .20.65.69.83.95.79.85.84.80.85.84.95.51.95.50.95.83.84.65.84.69
-- absolute OID	: 1.3.6.1.4.1.7995.2.6.1.1.XX.20.65.69.83.95.79.85.84.80.85.84.95.51.95.50.95.83.84.65.84.69
-- Vary			: YES
--
-- Value(s)		: OK:Input
--				: 
-- Comments		: 
--
---------------------------------------------------------------------------------------------------
-- Header		: AES_OUTPUT_4_1_STATE
--
-- MIB ref		: swCardEventLogSlotXX       .20.65.69.83.95.79.85.84.80.85.84.95.52.95.49.95.83.84.65.84.69
-- absolute OID	: 1.3.6.1.4.1.7995.2.6.1.1.XX.20.65.69.83.95.79.85.84.80.85.84.95.52.95.49.95.83.84.65.84.69
-- Vary			: YES
--
-- Value(s)		: OK:Input
--				: 
-- Comments		: 
--
---------------------------------------------------------------------------------------------------
-- Header		: AES_OUTPUT_4_2_STATE
--
-- MIB ref		: swCardEventLogSlotXX       .20.65.69.83.95.79.85.84.80.85.84.95.52.95.50.95.83.84.65.84.69
-- absolute OID	: 1.3.6.1.4.1.7995.2.6.1.1.XX.20.65.69.83.95.79.85.84.80.85.84.95.52.95.50.95.83.84.65.84.69
-- Vary			: YES
--
-- Value(s)		: OK:Input
--				: 
-- Comments		: 
--
---------------------------------------------------------------------------------------------------
-- Header		: AES_OUTPUT_5_1_STATE
--
-- MIB ref		: swCardEventLogSlotXX       .20.65.69.83.95.79.85.84.80.85.84.95.53.95.49.95.83.84.65.84.69
-- absolute OID	: 1.3.6.1.4.1.7995.2.6.1.1.XX.20.65.69.83.95.79.85.84.80.85.84.95.53.95.49.95.83.84.65.84.69
-- Vary			: YES
--
-- Value(s)		: OK:Input
--				: 
-- Comments		: 
--
---------------------------------------------------------------------------------------------------
-- Header		: AES_OUTPUT_5_2_STATE
--
-- MIB ref		: swCardEventLogSlotXX       .20.65.69.83.95.79.85.84.80.85.84.95.53.95.50.95.83.84.65.84.69
-- absolute OID	: 1.3.6.1.4.1.7995.2.6.1.1.XX.20.65.69.83.95.79.85.84.80.85.84.95.53.95.50.95.83.84.65.84.69
-- Vary			: YES
--
-- Value(s)		: OK:Input
--				: 
-- Comments		: 
--
---------------------------------------------------------------------------------------------------
-- Header		: AES_OUTPUT_6_1_STATE
--
-- MIB ref		: swCardEventLogSlotXX       .20.65.69.83.95.79.85.84.80.85.84.95.54.95.49.95.83.84.65.84.69
-- absolute OID	: 1.3.6.1.4.1.7995.2.6.1.1.XX.20.65.69.83.95.79.85.84.80.85.84.95.54.95.49.95.83.84.65.84.69
-- Vary			: YES
--
-- Value(s)		: OK:Input
--				: 
-- Comments		: 
--
---------------------------------------------------------------------------------------------------
-- Header		: AES_OUTPUT_6_2_STATE
--
-- MIB ref		: swCardEventLogSlotXX       .20.65.69.83.95.79.85.84.80.85.84.95.54.95.50.95.83.84.65.84.69
-- absolute OID	: 1.3.6.1.4.1.7995.2.6.1.1.XX.20.65.69.83.95.79.85.84.80.85.84.95.54.95.50.95.83.84.65.84.69
-- Vary			: YES
--
-- Value(s)		: OK:Input
--				: 
-- Comments		: 
--
---------------------------------------------------------------------------------------------------
-- Header		: AES_OUTPUT_7_1_STATE
--
-- MIB ref		: swCardEventLogSlotXX       .20.65.69.83.95.79.85.84.80.85.84.95.55.95.49.95.83.84.65.84.69
-- absolute OID	: 1.3.6.1.4.1.7995.2.6.1.1.XX.20.65.69.83.95.79.85.84.80.85.84.95.55.95.49.95.83.84.65.84.69
-- Vary			: YES
--
-- Value(s)		: OK:Input
--				: 
-- Comments		: 
--
---------------------------------------------------------------------------------------------------
-- Header		: AES_OUTPUT_7_2_STATE
--
-- MIB ref		: swCardEventLogSlotXX       .20.65.69.83.95.79.85.84.80.85.84.95.55.95.50.95.83.84.65.84.69
-- absolute OID	: 1.3.6.1.4.1.7995.2.6.1.1.XX.20.65.69.83.95.79.85.84.80.85.84.95.55.95.50.95.83.84.65.84.69
-- Vary			: YES
--
-- Value(s)		: OK:Input
--				: 
-- Comments		: 
--
---------------------------------------------------------------------------------------------------
-- Header		: AES_OUTPUT_8_1_STATE
--
-- MIB ref		: swCardEventLogSlotXX       .20.65.69.83.95.79.85.84.80.85.84.95.56.95.49.95.83.84.65.84.69
-- absolute OID	: 1.3.6.1.4.1.7995.2.6.1.1.XX.20.65.69.83.95.79.85.84.80.85.84.95.56.95.49.95.83.84.65.84.69
-- Vary			: YES
--
-- Value(s)		: OK:Input
--				: 
-- Comments		: 
--
---------------------------------------------------------------------------------------------------
-- Header		: AES_OUTPUT_8_2_STATE
--
-- MIB ref		: swCardEventLogSlotXX       .20.65.69.83.95.79.85.84.80.85.84.95.56.95.50.95.83.84.65.84.69
-- absolute OID	: 1.3.6.1.4.1.7995.2.6.1.1.XX.20.65.69.83.95.79.85.84.80.85.84.95.56.95.50.95.83.84.65.84.69
-- Vary			: YES
--
-- Value(s)		: OK:Input
--				: 
-- Comments		: 
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: 
-- Comments		: 
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
-- Vary			: YES
--
-- Value(s)		: OK
--				: 
-- Comments		: 
--
---------------------------------------------------------------------------------------------------
-- Header		: OUTPUT_1_ANC_LINE_10
--
-- MIB ref		: swCardEventLogSlotXX       .20.79.85.84.80.85.84.95.49.95.65.78.67.95.76.73.78.69.95.49.48
-- absolute OID	: 1.3.6.1.4.1.7995.2.6.1.1.XX.20.79.85.84.80.85.84.95.49.95.65.78.67.95.76.73.78.69.95.49.48
-- Vary			: YES
--
-- Value(s)		: -
--				: 
-- Comments		: 
--
---------------------------------------------------------------------------------------------------
-- Header		: OUTPUT_1_ANC_LINE_11
--
-- MIB ref		: swCardEventLogSlotXX       .20.79.85.84.80.85.84.95.49.95.65.78.67.95.76.73.78.69.95.49.49
-- absolute OID	: 1.3.6.1.4.1.7995.2.6.1.1.XX.20.79.85.84.80.85.84.95.49.95.65.78.67.95.76.73.78.69.95.49.49
-- Vary			: YES
--
-- Value(s)		: -
--				: 
-- Comments		: 
--
---------------------------------------------------------------------------------------------------
-- Header		: OUTPUT_1_ANC_LINE_12
--
-- MIB ref		: swCardEventLogSlotXX       .20.79.85.84.80.85.84.95.49.95.65.78.67.95.76.73.78.69.95.49.50
-- absolute OID	: 1.3.6.1.4.1.7995.2.6.1.1.XX.20.79.85.84.80.85.84.95.49.95.65.78.67.95.76.73.78.69.95.49.50
-- Vary			: YES
--
-- Value(s)		: -
--				: 
-- Comments		: 
--
---------------------------------------------------------------------------------------------------
-- Header		: OUTPUT_1_ANC_LINE_13
--
-- MIB ref		: swCardEventLogSlotXX       .20.79.85.84.80.85.84.95.49.95.65.78.67.95.76.73.78.69.95.49.51
-- absolute OID	: 1.3.6.1.4.1.7995.2.6.1.1.XX.20.79.85.84.80.85.84.95.49.95.65.78.67.95.76.73.78.69.95.49.51
-- Vary			: YES
--
-- Value(s)		: -
--				: 
-- Comments		: 
--
---------------------------------------------------------------------------------------------------
-- Header		: OUTPUT_1_ANC_LINE_14
--
-- MIB ref		: swCardEventLogSlotXX       .20.79.85.84.80.85.84.95.49.95.65.78.67.95.76.73.78.69.95.49.52
-- absolute OID	: 1.3.6.1.4.1.7995.2.6.1.1.XX.20.79.85.84.80.85.84.95.49.95.65.78.67.95.76.73.78.69.95.49.52
-- Vary			: YES
--
-- Value(s)		: -
--				: 
-- Comments		: 
--
---------------------------------------------------------------------------------------------------
-- Header		: OUTPUT_1_ANC_LINE_15
--
-- MIB ref		: swCardEventLogSlotXX       .20.79.85.84.80.85.84.95.49.95.65.78.67.95.76.73.78.69.95.49.53
-- absolute OID	: 1.3.6.1.4.1.7995.2.6.1.1.XX.20.79.85.84.80.85.84.95.49.95.65.78.67.95.76.73.78.69.95.49.53
-- Vary			: YES
--
-- Value(s)		: -
--				: 
-- Comments		: 
--
---------------------------------------------------------------------------------------------------
-- Header		: OUTPUT_1_ANC_LINE_16
--
-- MIB ref		: swCardEventLogSlotXX       .20.79.85.84.80.85.84.95.49.95.65.78.67.95.76.73.78.69.95.49.54
-- absolute OID	: 1.3.6.1.4.1.7995.2.6.1.1.XX.20.79.85.84.80.85.84.95.49.95.65.78.67.95.76.73.78.69.95.49.54
-- Vary			: YES
--
-- Value(s)		: -
--				: 
-- Comments		: 
--
---------------------------------------------------------------------------------------------------
-- Header		: OUTPUT_1_ANC_LINE_17
--
-- MIB ref		: swCardEventLogSlotXX       .20.79.85.84.80.85.84.95.49.95.65.78.67.95.76.73.78.69.95.49.55
-- absolute OID	: 1.3.6.1.4.1.7995.2.6.1.1.XX.20.79.85.84.80.85.84.95.49.95.65.78.67.95.76.73.78.69.95.49.55
-- Vary			: YES
--
-- Value(s)		: -
--				: 
-- Comments		: 
--
---------------------------------------------------------------------------------------------------
-- Header		: OUTPUT_1_ANC_LINE_18
--
-- MIB ref		: swCardEventLogSlotXX       .20.79.85.84.80.85.84.95.49.95.65.78.67.95.76.73.78.69.95.49.56
-- absolute OID	: 1.3.6.1.4.1.7995.2.6.1.1.XX.20.79.85.84.80.85.84.95.49.95.65.78.67.95.76.73.78.69.95.49.56
-- Vary			: YES
--
-- Value(s)		: -
--				: 
-- Comments		: 
--
---------------------------------------------------------------------------------------------------
-- Header		: OUTPUT_1_ANC_LINE_19
--
-- MIB ref		: swCardEventLogSlotXX       .20.79.85.84.80.85.84.95.49.95.65.78.67.95.76.73.78.69.95.49.57
-- absolute OID	: 1.3.6.1.4.1.7995.2.6.1.1.XX.20.79.85.84.80.85.84.95.49.95.65.78.67.95.76.73.78.69.95.49.57
-- Vary			: YES
--
-- Value(s)		: -
--				: 
-- Comments		: 
--
---------------------------------------------------------------------------------------------------
-- Header		: OUTPUT_1_ANC_LINE_20
--
-- MIB ref		: swCardEventLogSlotXX       .20.79.85.84.80.85.84.95.49.95.65.78.67.95.76.73.78.69.95.50.48
-- absolute OID	: 1.3.6.1.4.1.7995.2.6.1.1.XX.20.79.85.84.80.85.84.95.49.95.65.78.67.95.76.73.78.69.95.50.48
-- Vary			: YES
--
-- Value(s)		: -
--				: 
-- Comments		: 
--
---------------------------------------------------------------------------------------------------
-- Header		: OUTPUT_1_ANC_LINE_21
--
-- MIB ref		: swCardEventLogSlotXX       .20.79.85.84.80.85.84.95.49.95.65.78.67.95.76.73.78.69.95.50.49
-- absolute OID	: 1.3.6.1.4.1.7995.2.6.1.1.XX.20.79.85.84.80.85.84.95.49.95.65.78.67.95.76.73.78.69.95.50.49
-- Vary			: YES
--
-- Value(s)		: -
--				: 
-- Comments		: 
--
---------------------------------------------------------------------------------------------------
-- Header		: OUTPUT_1_ANC_LINE_22
--
-- MIB ref		: swCardEventLogSlotXX       .20.79.85.84.80.85.84.95.49.95.65.78.67.95.76.73.78.69.95.50.50
-- absolute OID	: 1.3.6.1.4.1.7995.2.6.1.1.XX.20.79.85.84.80.85.84.95.49.95.65.78.67.95.76.73.78.69.95.50.50
-- Vary			: YES
--
-- Value(s)		: -
--				: 
-- Comments		: 
--
---------------------------------------------------------------------------------------------------
-- Header		: OUTPUT_1_ANC_LINE_23
--
-- MIB ref		: swCardEventLogSlotXX       .20.79.85.84.80.85.84.95.49.95.65.78.67.95.76.73.78.69.95.50.51
-- absolute OID	: 1.3.6.1.4.1.7995.2.6.1.1.XX.20.79.85.84.80.85.84.95.49.95.65.78.67.95.76.73.78.69.95.50.51
-- Vary			: YES
--
-- Value(s)		: -
--				: 
-- Comments		: 
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
-- Vary			: YES
--
-- Value(s)		: Unknown
--				: 
-- Comments		: 
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
-- Vary			: YES
--
-- Value(s)		: 0
--				: 
-- Comments		: 
--
---------------------------------------------------------------------------------------------------
-- Header		: INPUT_2_SDI_ANC_ERRSECS
--
-- MIB ref		: swCardEventLogSlotXX       .23.73.78.80.85.84.95.50.95.83.68.73.95.65.78.67.95.69.82.82.83.69.67.83
-- absolute OID	: 1.3.6.1.4.1.7995.2.6.1.1.XX.23.73.78.80.85.84.95.50.95.83.68.73.95.65.78.67.95.69.82.82.83.69.67.83
-- Vary			: YES
--
-- Value(s)		: 0
--				: 
-- Comments		: 
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: FAIL:Lost
--				: 
-- Comments		: 
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: FAIL:Lost
--				: 
-- Comments		: 
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: FAIL:Lost
--				: 
-- Comments		: 
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: FAIL:Lost
--				: 
-- Comments		: 
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: FAIL:Lost
--				: 
-- Comments		: 
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: FAIL:Lost
--				: 
-- Comments		: 
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: FAIL:Lost
--				: 
-- Comments		: 
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: FAIL:Lost
--				: 
-- Comments		: 
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
-- Vary			: YES
--
-- Value(s)		: FAIL:Lost
--				: 
-- Comments		: 
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
-- Vary			: YES
--
-- Value(s)		: FAIL:Lost
--				: 
-- Comments		: 
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
-- Vary			: YES
--
-- Value(s)		: FAIL:Lost
--				: 
-- Comments		: 
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
-- Vary			: YES
--
-- Value(s)		: FAIL:Lost
--				: 
-- Comments		: 
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
-- Vary			: YES
--
-- Value(s)		: FAIL:Lost
--				: 
-- Comments		: 
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
-- Vary			: YES
--
-- Value(s)		: FAIL:Lost
--				: 
-- Comments		: 
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
-- Vary			: YES
--
-- Value(s)		: FAIL:Lost
--				: 
-- Comments		: 
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
-- Vary			: YES
--
-- Value(s)		: FAIL:Lost
--				: 
-- Comments		: 
--
---------------------------------------------------------------------------------------------------
-- Header		: OUTPUT_1_EMBED_AUDIO_1_1_STATE
--
-- MIB ref		: swCardEventLogSlotXX       .30.79.85.84.80.85.84.95.49.95.69.77.66.69.68.95.65.85.68.73.79.95.49.95.49.95.83.84.65.84.69
-- absolute OID	: 1.3.6.1.4.1.7995.2.6.1.1.XX.30.79.85.84.80.85.84.95.49.95.69.77.66.69.68.95.65.85.68.73.79.95.49.95.49.95.83.84.65.84.69
-- Vary			: YES
--
-- Value(s)		: FAIL:Lost
--				: 
-- Comments		: 
--
---------------------------------------------------------------------------------------------------
-- Header		: OUTPUT_1_EMBED_AUDIO_1_2_STATE
--
-- MIB ref		: swCardEventLogSlotXX       .30.79.85.84.80.85.84.95.49.95.69.77.66.69.68.95.65.85.68.73.79.95.49.95.50.95.83.84.65.84.69
-- absolute OID	: 1.3.6.1.4.1.7995.2.6.1.1.XX.30.79.85.84.80.85.84.95.49.95.69.77.66.69.68.95.65.85.68.73.79.95.49.95.50.95.83.84.65.84.69
-- Vary			: YES
--
-- Value(s)		: FAIL:Lost
--				: 
-- Comments		: 
--
---------------------------------------------------------------------------------------------------
-- Header		: OUTPUT_1_EMBED_AUDIO_2_1_STATE
--
-- MIB ref		: swCardEventLogSlotXX       .30.79.85.84.80.85.84.95.49.95.69.77.66.69.68.95.65.85.68.73.79.95.50.95.49.95.83.84.65.84.69
-- absolute OID	: 1.3.6.1.4.1.7995.2.6.1.1.XX.30.79.85.84.80.85.84.95.49.95.69.77.66.69.68.95.65.85.68.73.79.95.50.95.49.95.83.84.65.84.69
-- Vary			: YES
--
-- Value(s)		: FAIL:Lost
--				: 
-- Comments		: 
--
---------------------------------------------------------------------------------------------------
-- Header		: OUTPUT_1_EMBED_AUDIO_2_2_STATE
--
-- MIB ref		: swCardEventLogSlotXX       .30.79.85.84.80.85.84.95.49.95.69.77.66.69.68.95.65.85.68.73.79.95.50.95.50.95.83.84.65.84.69
-- absolute OID	: 1.3.6.1.4.1.7995.2.6.1.1.XX.30.79.85.84.80.85.84.95.49.95.69.77.66.69.68.95.65.85.68.73.79.95.50.95.50.95.83.84.65.84.69
-- Vary			: YES
--
-- Value(s)		: FAIL:Lost
--				: 
-- Comments		: 
--
---------------------------------------------------------------------------------------------------
-- Header		: OUTPUT_1_EMBED_AUDIO_3_1_STATE
--
-- MIB ref		: swCardEventLogSlotXX       .30.79.85.84.80.85.84.95.49.95.69.77.66.69.68.95.65.85.68.73.79.95.51.95.49.95.83.84.65.84.69
-- absolute OID	: 1.3.6.1.4.1.7995.2.6.1.1.XX.30.79.85.84.80.85.84.95.49.95.69.77.66.69.68.95.65.85.68.73.79.95.51.95.49.95.83.84.65.84.69
-- Vary			: YES
--
-- Value(s)		: FAIL:Lost
--				: 
-- Comments		: 
--
---------------------------------------------------------------------------------------------------
-- Header		: OUTPUT_1_EMBED_AUDIO_3_2_STATE
--
-- MIB ref		: swCardEventLogSlotXX       .30.79.85.84.80.85.84.95.49.95.69.77.66.69.68.95.65.85.68.73.79.95.51.95.50.95.83.84.65.84.69
-- absolute OID	: 1.3.6.1.4.1.7995.2.6.1.1.XX.30.79.85.84.80.85.84.95.49.95.69.77.66.69.68.95.65.85.68.73.79.95.51.95.50.95.83.84.65.84.69
-- Vary			: YES
--
-- Value(s)		: FAIL:Lost
--				: 
-- Comments		: 
--
---------------------------------------------------------------------------------------------------
-- Header		: OUTPUT_1_EMBED_AUDIO_4_1_STATE
--
-- MIB ref		: swCardEventLogSlotXX       .30.79.85.84.80.85.84.95.49.95.69.77.66.69.68.95.65.85.68.73.79.95.52.95.49.95.83.84.65.84.69
-- absolute OID	: 1.3.6.1.4.1.7995.2.6.1.1.XX.30.79.85.84.80.85.84.95.49.95.69.77.66.69.68.95.65.85.68.73.79.95.52.95.49.95.83.84.65.84.69
-- Vary			: YES
--
-- Value(s)		: FAIL:Lost
--				: 
-- Comments		: 
--
---------------------------------------------------------------------------------------------------
-- Header		: OUTPUT_1_EMBED_AUDIO_4_2_STATE
--
-- MIB ref		: swCardEventLogSlotXX       .30.79.85.84.80.85.84.95.49.95.69.77.66.69.68.95.65.85.68.73.79.95.52.95.50.95.83.84.65.84.69
-- absolute OID	: 1.3.6.1.4.1.7995.2.6.1.1.XX.30.79.85.84.80.85.84.95.49.95.69.77.66.69.68.95.65.85.68.73.79.95.52.95.50.95.83.84.65.84.69
-- Vary			: YES
--
-- Value(s)		: FAIL:Lost
--				: 
-- Comments		: 
--
---------------------------------------------------------------------------------------------------
-- Header		: OUTPUT_1_EMBED_AUDIO_5_1_STATE
--
-- MIB ref		: swCardEventLogSlotXX       .30.79.85.84.80.85.84.95.49.95.69.77.66.69.68.95.65.85.68.73.79.95.53.95.49.95.83.84.65.84.69
-- absolute OID	: 1.3.6.1.4.1.7995.2.6.1.1.XX.30.79.85.84.80.85.84.95.49.95.69.77.66.69.68.95.65.85.68.73.79.95.53.95.49.95.83.84.65.84.69
-- Vary			: YES
--
-- Value(s)		: FAIL:Lost
--				: 
-- Comments		: 
--
---------------------------------------------------------------------------------------------------
-- Header		: OUTPUT_1_EMBED_AUDIO_5_2_STATE
--
-- MIB ref		: swCardEventLogSlotXX       .30.79.85.84.80.85.84.95.49.95.69.77.66.69.68.95.65.85.68.73.79.95.53.95.50.95.83.84.65.84.69
-- absolute OID	: 1.3.6.1.4.1.7995.2.6.1.1.XX.30.79.85.84.80.85.84.95.49.95.69.77.66.69.68.95.65.85.68.73.79.95.53.95.50.95.83.84.65.84.69
-- Vary			: YES
--
-- Value(s)		: FAIL:Lost
--				: 
-- Comments		: 
--
---------------------------------------------------------------------------------------------------
-- Header		: OUTPUT_1_EMBED_AUDIO_6_1_STATE
--
-- MIB ref		: swCardEventLogSlotXX       .30.79.85.84.80.85.84.95.49.95.69.77.66.69.68.95.65.85.68.73.79.95.54.95.49.95.83.84.65.84.69
-- absolute OID	: 1.3.6.1.4.1.7995.2.6.1.1.XX.30.79.85.84.80.85.84.95.49.95.69.77.66.69.68.95.65.85.68.73.79.95.54.95.49.95.83.84.65.84.69
-- Vary			: YES
--
-- Value(s)		: FAIL:Lost
--				: 
-- Comments		: 
--
---------------------------------------------------------------------------------------------------
-- Header		: OUTPUT_1_EMBED_AUDIO_6_2_STATE
--
-- MIB ref		: swCardEventLogSlotXX       .30.79.85.84.80.85.84.95.49.95.69.77.66.69.68.95.65.85.68.73.79.95.54.95.50.95.83.84.65.84.69
-- absolute OID	: 1.3.6.1.4.1.7995.2.6.1.1.XX.30.79.85.84.80.85.84.95.49.95.69.77.66.69.68.95.65.85.68.73.79.95.54.95.50.95.83.84.65.84.69
-- Vary			: YES
--
-- Value(s)		: FAIL:Lost
--				: 
-- Comments		: 
--
---------------------------------------------------------------------------------------------------
-- Header		: OUTPUT_1_EMBED_AUDIO_7_1_STATE
--
-- MIB ref		: swCardEventLogSlotXX       .30.79.85.84.80.85.84.95.49.95.69.77.66.69.68.95.65.85.68.73.79.95.55.95.49.95.83.84.65.84.69
-- absolute OID	: 1.3.6.1.4.1.7995.2.6.1.1.XX.30.79.85.84.80.85.84.95.49.95.69.77.66.69.68.95.65.85.68.73.79.95.55.95.49.95.83.84.65.84.69
-- Vary			: YES
--
-- Value(s)		: FAIL:Lost
--				: 
-- Comments		: 
--
---------------------------------------------------------------------------------------------------
-- Header		: OUTPUT_1_EMBED_AUDIO_7_2_STATE
--
-- MIB ref		: swCardEventLogSlotXX       .30.79.85.84.80.85.84.95.49.95.69.77.66.69.68.95.65.85.68.73.79.95.55.95.50.95.83.84.65.84.69
-- absolute OID	: 1.3.6.1.4.1.7995.2.6.1.1.XX.30.79.85.84.80.85.84.95.49.95.69.77.66.69.68.95.65.85.68.73.79.95.55.95.50.95.83.84.65.84.69
-- Vary			: YES
--
-- Value(s)		: FAIL:Lost
--				: 
-- Comments		: 
--
---------------------------------------------------------------------------------------------------
-- Header		: OUTPUT_1_EMBED_AUDIO_8_1_STATE
--
-- MIB ref		: swCardEventLogSlotXX       .30.79.85.84.80.85.84.95.49.95.69.77.66.69.68.95.65.85.68.73.79.95.56.95.49.95.83.84.65.84.69
-- absolute OID	: 1.3.6.1.4.1.7995.2.6.1.1.XX.30.79.85.84.80.85.84.95.49.95.69.77.66.69.68.95.65.85.68.73.79.95.56.95.49.95.83.84.65.84.69
-- Vary			: YES
--
-- Value(s)		: FAIL:Lost
--				: 
-- Comments		: 
--
---------------------------------------------------------------------------------------------------
-- Header		: OUTPUT_1_EMBED_AUDIO_8_2_STATE
--
-- MIB ref		: swCardEventLogSlotXX       .30.79.85.84.80.85.84.95.49.95.69.77.66.69.68.95.65.85.68.73.79.95.56.95.50.95.83.84.65.84.69
-- absolute OID	: 1.3.6.1.4.1.7995.2.6.1.1.XX.30.79.85.84.80.85.84.95.49.95.69.77.66.69.68.95.65.85.68.73.79.95.56.95.50.95.83.84.65.84.69
-- Vary			: YES
--
-- Value(s)		: FAIL:Lost
--				: 
-- Comments		: 
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
-- Vary			: YES
--
-- Value(s)		: NONE
--				: 
-- Comments		: 
--
---------------------------------------------------------------------------------------------------
-- Header		: OUTPUT_1_EMBEDDED_AUDIO_2_DOLBY
--
-- MIB ref		: swCardEventLogSlotXX       .31.79.85.84.80.85.84.95.49.95.69.77.66.69.68.68.69.68.95.65.85.68.73.79.95.50.95.68.79.76.66.89
-- absolute OID	: 1.3.6.1.4.1.7995.2.6.1.1.XX.31.79.85.84.80.85.84.95.49.95.69.77.66.69.68.68.69.68.95.65.85.68.73.79.95.50.95.68.79.76.66.89
-- Vary			: YES
--
-- Value(s)		: NONE
--				: 
-- Comments		: 
--
---------------------------------------------------------------------------------------------------
-- Header		: OUTPUT_1_EMBEDDED_AUDIO_3_DOLBY
--
-- MIB ref		: swCardEventLogSlotXX       .31.79.85.84.80.85.84.95.49.95.69.77.66.69.68.68.69.68.95.65.85.68.73.79.95.51.95.68.79.76.66.89
-- absolute OID	: 1.3.6.1.4.1.7995.2.6.1.1.XX.31.79.85.84.80.85.84.95.49.95.69.77.66.69.68.68.69.68.95.65.85.68.73.79.95.51.95.68.79.76.66.89
-- Vary			: YES
--
-- Value(s)		: NONE
--				: 
-- Comments		: 
--
---------------------------------------------------------------------------------------------------
-- Header		: OUTPUT_1_EMBEDDED_AUDIO_4_DOLBY
--
-- MIB ref		: swCardEventLogSlotXX       .31.79.85.84.80.85.84.95.49.95.69.77.66.69.68.68.69.68.95.65.85.68.73.79.95.52.95.68.79.76.66.89
-- absolute OID	: 1.3.6.1.4.1.7995.2.6.1.1.XX.31.79.85.84.80.85.84.95.49.95.69.77.66.69.68.68.69.68.95.65.85.68.73.79.95.52.95.68.79.76.66.89
-- Vary			: YES
--
-- Value(s)		: NONE
--				: 
-- Comments		: 
--
---------------------------------------------------------------------------------------------------
-- Header		: OUTPUT_1_EMBEDDED_AUDIO_5_DOLBY
--
-- MIB ref		: swCardEventLogSlotXX       .31.79.85.84.80.85.84.95.49.95.69.77.66.69.68.68.69.68.95.65.85.68.73.79.95.53.95.68.79.76.66.89
-- absolute OID	: 1.3.6.1.4.1.7995.2.6.1.1.XX.31.79.85.84.80.85.84.95.49.95.69.77.66.69.68.68.69.68.95.65.85.68.73.79.95.53.95.68.79.76.66.89
-- Vary			: YES
--
-- Value(s)		: NONE
--				: 
-- Comments		: 
--
---------------------------------------------------------------------------------------------------
-- Header		: OUTPUT_1_EMBEDDED_AUDIO_6_DOLBY
--
-- MIB ref		: swCardEventLogSlotXX       .31.79.85.84.80.85.84.95.49.95.69.77.66.69.68.68.69.68.95.65.85.68.73.79.95.54.95.68.79.76.66.89
-- absolute OID	: 1.3.6.1.4.1.7995.2.6.1.1.XX.31.79.85.84.80.85.84.95.49.95.69.77.66.69.68.68.69.68.95.65.85.68.73.79.95.54.95.68.79.76.66.89
-- Vary			: YES
--
-- Value(s)		: NONE
--				: 
-- Comments		: 
--
---------------------------------------------------------------------------------------------------
-- Header		: OUTPUT_1_EMBEDDED_AUDIO_7_DOLBY
--
-- MIB ref		: swCardEventLogSlotXX       .31.79.85.84.80.85.84.95.49.95.69.77.66.69.68.68.69.68.95.65.85.68.73.79.95.55.95.68.79.76.66.89
-- absolute OID	: 1.3.6.1.4.1.7995.2.6.1.1.XX.31.79.85.84.80.85.84.95.49.95.69.77.66.69.68.68.69.68.95.65.85.68.73.79.95.55.95.68.79.76.66.89
-- Vary			: YES
--
-- Value(s)		: NONE
--				: 
-- Comments		: 
--
---------------------------------------------------------------------------------------------------
-- Header		: OUTPUT_1_EMBEDDED_AUDIO_8_DOLBY
--
-- MIB ref		: swCardEventLogSlotXX       .31.79.85.84.80.85.84.95.49.95.69.77.66.69.68.68.69.68.95.65.85.68.73.79.95.56.95.68.79.76.66.89
-- absolute OID	: 1.3.6.1.4.1.7995.2.6.1.1.XX.31.79.85.84.80.85.84.95.49.95.69.77.66.69.68.68.69.68.95.65.85.68.73.79.95.56.95.68.79.76.66.89
-- Vary			: YES
--
-- Value(s)		: NONE
--				: 
-- Comments		: 
--
---------------------------------------------------------------------------------------------------
