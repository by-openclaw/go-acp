-- ************************************************************************************
-- Snell&Wilcox Card:IQDPR
--        Module Id#:230
--       Command Set:9
--          Filename:SNELL-IQDPR-CMD-MIB.mib
--            Author:Jonathan Riches
--              Date:30/06/2005
--              Time:10:00
--
-- Copyright (c) 2005 Snell & Wilcox Ltd
-- All rights reserved.
--
-- ************************************************************************************

SNELL-IQDPR-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDPR,
    moduleIQDPRMIB
        FROM SNELL-WILCOX-PRODUCT-REG;

 moduleIQDPRCmdMi MODULE-IDENTITY
    LAST-UPDATED "0506301000Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDPRMIB 1 }




--********************************************************************************
--*
--*  Snell Wilcox Card:
--*  command set:
--*  list commands/menus:
--*
--******************************************************************************
	iqdprCmdTable OBJECT-TYPE
		SYNTAX			SEQUENCE OF IqdprCmdEntry
		MAX-ACCESS		not-accessible
		STATUS			current
		DESCRIPTION
				"Note the instance of this table is relected in the command set Version"
		::= { moduleIQDPR 1 }

	iqdprCmdEntry OBJECT-TYPE
		SYNTAX		IqdprCmdEntry
		MAX-ACCESS		not-accessible
		STATUS			current
		DESCRIPTION
				"Entry in command table."
		INDEX	{ iqdprSlotIndex }
		::= { iqdprCmdTable 1 }

	IqdprCmdEntry ::=
		SEQUENCE {
			iqdprSlotIndex
				Unsigned32,
			iqdprProcAmpLumaGain
				INTEGER,
			iqdprProcAmpChromaGain
				INTEGER,
			iqdprProcAmpBlackLevel
				INTEGER,
			iqdprProcAmpBlackStretch
				INTEGER,
			iqdprProcAmpHue
				INTEGER,
			iqdprProcAmpChromaLineAverage
				INTEGER,
			iqdprProcAmpOffsetsCbOffset
				INTEGER,
			iqdprProcAmpOffsetsCrOffset
				INTEGER,
			iqdprProcAmpOffsetsCbGainOffset
				INTEGER,
			iqdprLimitingDefaultYUVLimiter
				INTEGER,
			iqdprLimitingMinCClipLevel
				INTEGER,
			iqdprLimitingMaxCClipLevel
				INTEGER,
			iqdprLimitingMinYClipLevel
				INTEGER,
			iqdprLimitingMaxYClipLevel
				INTEGER,
			iqdprLimitingEnableinVBI
				INTEGER,
			iqdprTimingYCDelayHorizontal
				INTEGER,
			iqdprTimingPicturePosition
				INTEGER,
			iqdprUserMemoryReadMem
				INTEGER,
			iqdprUserMemorySaveMem
				INTEGER,
			iqdprUserMemoryNameMemMemory1
				RollCallString,
			iqdprUserMemoryNameMemMemory2
				RollCallString,
			iqdprUserMemoryNameMemMemory3
				RollCallString,
			iqdprUserMemoryNameMemMemory4
				RollCallString,
			iqdprUserMemoryNameMemMemory5
				RollCallString,
			iqdprUserMemoryNameMemMemory6
				RollCallString,
			iqdprUserMemoryNameMemMemory7
				RollCallString,
			iqdprUserMemoryNameMemMemory8
				RollCallString,
			iqdprUserMemoryNameMemMemory9
				RollCallString,
			iqdprUserMemoryNameMemMemory10
				RollCallString,
			iqdprUserMemoryNameMemMemory11
				RollCallString,
			iqdprUserMemoryNameMemMemory12
				RollCallString,
			iqdprUserMemoryNameMemMemory13
				RollCallString,
			iqdprUserMemoryNameMemMemory14
				RollCallString,
			iqdprUserMemoryNameMemMemory15
				RollCallString,
			iqdprUserMemoryNameMemMemory16
				RollCallString,
			iqdprUserMemoryNameMemPresetAllNames
				INTEGER,
			iqdprUserMemoryClearMem
				INTEGER,
			iqdprBypass
				INTEGER,
			iqdprSetupPatternsPatternOn
				INTEGER,
			iqdprSetupPatternsIncludeCaption
				INTEGER,
			iqdprSetupPatterns
				INTEGER,
			iqdprSetupVerticalData525
				INTEGER,
			iqdprSetupVerticalData525PreserveLine21
				INTEGER,
			iqdprSetupVerticalData525PreserveL283L284
				INTEGER,
			iqdprVerticalData525SetLines525BlankL10
				INTEGER,
			iqdprVerticalData525SetLines525BlankL272
				INTEGER,
			iqdprVerticalData525SetLines525BlankL11
				INTEGER,
			iqdprVerticalData525SetLines525BlankL273
				INTEGER,
			iqdprVerticalData525SetLines525BlankL12
				INTEGER,
			iqdprVerticalData525SetLines525BlankL274
				INTEGER,
			iqdprVerticalData525SetLines525BlankL13
				INTEGER,
			iqdprVerticalData525SetLines525BlankL275
				INTEGER,
			iqdprVerticalData525SetLines525BlankL14
				INTEGER,
			iqdprVerticalData525SetLines525BlankL276
				INTEGER,
			iqdprVerticalData525SetLines525BlankL15
				INTEGER,
			iqdprVerticalData525SetLines525BlankL277
				INTEGER,
			iqdprVerticalData525SetLines525BlankL16
				INTEGER,
			iqdprVerticalData525SetLines525BlankL278
				INTEGER,
			iqdprVerticalData525SetLines525BlankL17
				INTEGER,
			iqdprVerticalData525SetLines525BlankL279
				INTEGER,
			iqdprVerticalData525SetLines525BlankL18
				INTEGER,
			iqdprVerticalData525SetLines525BlankL280
				INTEGER,
			iqdprVerticalData525SetLines525BlankL19
				INTEGER,
			iqdprVerticalData525SetLines525BlankL281
				INTEGER,
			iqdprVerticalData525SetLines525BlankL20
				INTEGER,
			iqdprVerticalData525SetLines525BlankL282
				INTEGER,
			iqdprVerticalData525SetLines525BlankL21
				INTEGER,
			iqdprVerticalData525SetLines525BlankL283
				INTEGER,
			iqdprVerticalData525SetLines525BlankL22
				INTEGER,
			iqdprVerticalData525SetLines525BlankL284
				INTEGER,
			iqdprSetupVerticalData625
				INTEGER,
			iqdprSetupVerticalData625PreserveLine23
				INTEGER,
			iqdprVerticalData625SetLines625BlankL6
				INTEGER,
			iqdprVerticalData625SetLines625BlankL318
				INTEGER,
			iqdprVerticalData625SetLines625BlankL7
				INTEGER,
			iqdprVerticalData625SetLines625BlankL319
				INTEGER,
			iqdprVerticalData625SetLines625BlankL8
				INTEGER,
			iqdprVerticalData625SetLines625BlankL320
				INTEGER,
			iqdprVerticalData625SetLines625BlankL9
				INTEGER,
			iqdprVerticalData625SetLines625BlankL321
				INTEGER,
			iqdprVerticalData625SetLines625BlankL10
				INTEGER,
			iqdprVerticalData625SetLines625BlankL322
				INTEGER,
			iqdprVerticalData625SetLines625BlankL11
				INTEGER,
			iqdprVerticalData625SetLines625BlankL323
				INTEGER,
			iqdprVerticalData625SetLines625BlankL12
				INTEGER,
			iqdprVerticalData625SetLines625BlankL324
				INTEGER,
			iqdprVerticalData625SetLines625BlankL13
				INTEGER,
			iqdprVerticalData625SetLines625BlankL325
				INTEGER,
			iqdprVerticalData625SetLines625BlankL14
				INTEGER,
			iqdprVerticalData625SetLines625BlankL326
				INTEGER,
			iqdprVerticalData625SetLines625BlankL15
				INTEGER,
			iqdprVerticalData625SetLines625BlankL327
				INTEGER,
			iqdprVerticalData625SetLines625BlankL16
				INTEGER,
			iqdprVerticalData625SetLines625BlankL328
				INTEGER,
			iqdprVerticalData625SetLines625BlankL17
				INTEGER,
			iqdprVerticalData625SetLines625BlankL329
				INTEGER,
			iqdprVerticalData625SetLines625BlankL18
				INTEGER,
			iqdprVerticalData625SetLines625BlankL330
				INTEGER,
			iqdprVerticalData625SetLines625BlankL19
				INTEGER,
			iqdprVerticalData625SetLines625BlankL331
				INTEGER,
			iqdprVerticalData625SetLines625BlankL20
				INTEGER,
			iqdprVerticalData625SetLines625BlankL332
				INTEGER,
			iqdprVerticalData625SetLines625BlankL21
				INTEGER,
			iqdprVerticalData625SetLines625BlankL333
				INTEGER,
			iqdprVerticalData625SetLines625BlankL22
				INTEGER,
			iqdprVerticalData625SetLines625BlankL334
				INTEGER,
			iqdprVerticalData625SetLines625BlankL23
				INTEGER,
			iqdprVerticalData625SetLines625BlankL335
				INTEGER,
			iqdprVerticalData625SetLines625BlankL24
				INTEGER,
			iqdprVerticalData625SetLines625BlankL336
				INTEGER,
			iqdprSetupHANCPass
				INTEGER,
			iqdprSetupDefaultOutputOutputStandard
				INTEGER,
			iqdprSetupDefaultOutputIncludeCaption
				INTEGER,
			iqdprSetupDefaultOutput
				INTEGER,
			iqdprSetupEditCaption
				RollCallString,
			iqdprSetupCaptionOverrideCaptionOn
				INTEGER,
			iqdprSetupCaptionOverride
				INTEGER,
			iqdprSetupEDHShowStats
				INTEGER,
			iqdprSetupEDHResetStats
				INTEGER,
			iqdprSetupGPIInputsGPI1
				INTEGER,
			iqdprSetupGPIInputsGPI1GPI1Function
				INTEGER,
			iqdprSetupGPIInputsGPI2
				INTEGER,
			iqdprSetupGPIInputsGPI2GPI2Function
				INTEGER,
			iqdprSetupGPIInputsGPI3
				INTEGER,
			iqdprSetupGPIInputsGPI3GPI3Function
				INTEGER,
			iqdprSetupLoggingInputChange
				INTEGER,
			iqdprSetupLoggingEDHErrors
				INTEGER,
			iqdprSetupPresetUnit
				INTEGER,
			iqdprSetupSoftwareVersion
				RollCallString,
			iqdprSetupSerialNo
				RollCallString,
			iqdprSetupRestart
				INTEGER
		}

	iqdprSlotIndex OBJECT-TYPE
		SYNTAX		Unsigned32
		MAX-ACCESS		not-accessible
		STATUS			current
		DESCRIPTION
				"The unique Index value for each slot.  Its value
					ranges between 1 and the value of slotNumber."
		::= { iqdprCmdEntry 0 }


	iqdprProcAmpLumaGain OBJECT-TYPE
		SYNTAX		INTEGER
		MAX-ACCESS		read-write
		STATUS			current
		DESCRIPTION
				"TYPE: - Number
					Luma_Gain  cmdID= 5  min= -60  max= 60  step= 1  format= %1.1f dB  div_scale= 10 
					Min = -6.0 dB  Max = 6.0 dB  Step = 0.1 dB "
		::= { iqdprCmdEntry 5 }


	iqdprProcAmpChromaGain OBJECT-TYPE
		SYNTAX		INTEGER
		MAX-ACCESS		read-write
		STATUS			current
		DESCRIPTION
				"TYPE: - Number
					Chroma_Gain  cmdID= 6  min= -60  max= 60  step= 1  format= %1.1f dB  div_scale= 10 
					Min = -6.0 dB  Max = 6.0 dB  Step = 0.1 dB "
		::= { iqdprCmdEntry 6 }


	iqdprProcAmpBlackLevel OBJECT-TYPE
		SYNTAX		INTEGER
		MAX-ACCESS		read-write
		STATUS			current
		DESCRIPTION
				"TYPE: - Number
					Black_Level  cmdID= 7  min= -1000  max= 1000  step= 8  format= %1.1f mV  div_scale= 10 
					Min = -100.0 mV  Max = 100.0 mV  Step = 0.8 mV "
		::= { iqdprCmdEntry 7 }


	iqdprProcAmpBlackStretch OBJECT-TYPE
		SYNTAX		INTEGER
		MAX-ACCESS		read-write
		STATUS			current
		DESCRIPTION
				"TYPE: - Number
					Black_Stretch  cmdID= 9  min= 0  max= 9  step= 1  format= %f  div_scale= 1 
					Min = 0.000000  Max = 9.000000  Step = 1.000000 "
		::= { iqdprCmdEntry 9 }


	iqdprProcAmpHue OBJECT-TYPE
		SYNTAX		INTEGER
		MAX-ACCESS		read-write
		STATUS			current
		DESCRIPTION
				"TYPE: - Number
					Hue  cmdID= 130  min= -180  max= 179  step= 1  format= %1.0f Deg  div_scale= 1 
					Min = -180 Deg  Max = 179 Deg  Step = 1 Deg "
		::= { iqdprCmdEntry 130 }


	iqdprProcAmpChromaLineAverage OBJECT-TYPE
		SYNTAX		INTEGER { disable(0), enable(1) }
		MAX-ACCESS		read-write
		STATUS			current
		DESCRIPTION
				"TYPE: - Checkbox
					Chroma_Line_Average  cmdID= 107 "
		::= { iqdprCmdEntry 107 }


	iqdprProcAmpOffsetsCbOffset OBJECT-TYPE
		SYNTAX		INTEGER
		MAX-ACCESS		read-write
		STATUS			current
		DESCRIPTION
				"TYPE: - Number
					Cb_Offset  cmdID= 109  min= -504  max= 504  step= 8  format= %1.1f mV  div_scale= 10 
					Min = -50.4 mV  Max = 50.4 mV  Step = 0.8 mV "
		::= { iqdprCmdEntry 109 }


	iqdprProcAmpOffsetsCrOffset OBJECT-TYPE
		SYNTAX		INTEGER
		MAX-ACCESS		read-write
		STATUS			current
		DESCRIPTION
				"TYPE: - Number
					Cr_Offset  cmdID= 110  min= -504  max= 504  step= 8  format= %1.1f mV  div_scale= 10 
					Min = -50.4 mV  Max = 50.4 mV  Step = 0.8 mV "
		::= { iqdprCmdEntry 110 }


	iqdprProcAmpOffsetsCbGainOffset OBJECT-TYPE
		SYNTAX		INTEGER
		MAX-ACCESS		read-write
		STATUS			current
		DESCRIPTION
				"TYPE: - Number
					Cb_Gain_Offset  cmdID= 111  min= -10  max= 10  step= 1  format= %1.1f dB  div_scale= 10 
					Min = -1.0 dB  Max = 1.0 dB  Step = 0.1 dB "
		::= { iqdprCmdEntry 111 }


	iqdprLimitingDefaultYUVLimiter OBJECT-TYPE
		SYNTAX		INTEGER { disable(0), enable(1) }
		MAX-ACCESS		read-write
		STATUS			current
		DESCRIPTION
				"TYPE: - Checkbox
					Default_YUV_Limiter  cmdID= 137 "
		::= { iqdprCmdEntry 137 }


	iqdprLimitingMinCClipLevel OBJECT-TYPE
		SYNTAX		INTEGER
		MAX-ACCESS		read-write
		STATUS			current
		DESCRIPTION
				"TYPE: - Number
					Min_C_Clip_Level  cmdID= 11  min= -396980  max= -200447  step= 783  format= %4.1f mV  div_scale= 1000 
					Min = -397.0 mV  Max = -200.4 mV  Step =  0.8 mV "
		::= { iqdprCmdEntry 11 }


	iqdprLimitingMaxCClipLevel OBJECT-TYPE
		SYNTAX		INTEGER
		MAX-ACCESS		read-write
		STATUS			current
		DESCRIPTION
				"TYPE: - Number
					Max_C_Clip_Level  cmdID= 12  min= 200447  max= 393848  step= 783  format= %4.1f mV  div_scale= 1000 
					Min = 200.4 mV  Max = 393.8 mV  Step =  0.8 mV "
		::= { iqdprCmdEntry 12 }


	iqdprLimitingMinYClipLevel OBJECT-TYPE
		SYNTAX		INTEGER
		MAX-ACCESS		read-write
		STATUS			current
		DESCRIPTION
				"TYPE: - Number
					Min_Y_Clip_Level  cmdID= 13  min= -48000  max= 48000  step= 800  format= %4.1f mV  div_scale= 1000 
					Min = -48.0 mV  Max = 48.0 mV  Step =  0.8 mV "
		::= { iqdprCmdEntry 13 }


	iqdprLimitingMaxYClipLevel OBJECT-TYPE
		SYNTAX		INTEGER
		MAX-ACCESS		read-write
		STATUS			current
		DESCRIPTION
				"TYPE: - Number
					Max_Y_Clip_Level  cmdID= 14  min= 600000  max= 760800  step= 800  format= %4.1f mV  div_scale= 1000 
					Min = 600.0 mV  Max = 760.8 mV  Step =  0.8 mV "
		::= { iqdprCmdEntry 14 }


	iqdprLimitingEnableinVBI OBJECT-TYPE
		SYNTAX		INTEGER { disable(0), enable(1) }
		MAX-ACCESS		read-write
		STATUS			current
		DESCRIPTION
				"TYPE: - Checkbox
					Enable_in_VBI  cmdID= 139 "
		::= { iqdprCmdEntry 139 }


	iqdprTimingYCDelayHorizontal OBJECT-TYPE
		SYNTAX		INTEGER
		MAX-ACCESS		read-write
		STATUS			current
		DESCRIPTION
				"TYPE: - Number
					YC_Delay_Horizontal  cmdID= 18  min= -444  max= 444  step= 148  format= %1.0f ns  div_scale= 1 
					Min = -444 ns  Max = 444 ns  Step = 148 ns "
		::= { iqdprCmdEntry 18 }


	iqdprTimingPicturePosition OBJECT-TYPE
		SYNTAX		INTEGER
		MAX-ACCESS		read-write
		STATUS			current
		DESCRIPTION
				"TYPE: - Number
					Picture_Position  cmdID= 19  min= -592  max= 592  step= 148  format= %1.0f ns  div_scale= 1 
					Min = -592 ns  Max = 592 ns  Step = 148 ns "
		::= { iqdprCmdEntry 19 }


	iqdprUserMemoryReadMem OBJECT-TYPE
		SYNTAX		INTEGER {
							val_Memory_1(0),
							val_Memory_2(1),
							val_Memory_3(2),
							val_Memory_4(3),
							val_Memory_5(4),
							val_Memory_6(5),
							val_Memory_7(6),
							val_Memory_8(7),
							val_Memory_9(8),
							val_Memory_10(9),
							val_Memory_11(10),
							val_Memory_12(11),
							val_Memory_13(12),
							val_Memory_14(13),
							val_Memory_15(14),
							val_Memory_16(15)
							}
		MAX-ACCESS		read-write
		STATUS			current
		DESCRIPTION
				"TYPE: - RadiobuttonList
					Read_Mem  cmdID= 20 
					Memory_1  value= 0  
					Memory_2  value= 1  
					Memory_3  value= 2  
					Memory_4  value= 3  
					Memory_5  value= 4  
					Memory_6  value= 5  
					Memory_7  value= 6  
					Memory_8  value= 7  
					Memory_9  value= 8  
					Memory_10  value= 9  
					Memory_11  value= 10  
					Memory_12  value= 11  
					Memory_13  value= 12  
					Memory_14  value= 13  
					Memory_15  value= 14  
					Memory_16  value= 15  "
		::= { iqdprCmdEntry 20 }


	iqdprUserMemorySaveMem OBJECT-TYPE
		SYNTAX		INTEGER {
							val_Memory_1(0),
							val_Memory_2(1),
							val_Memory_3(2),
							val_Memory_4(3),
							val_Memory_5(4),
							val_Memory_6(5),
							val_Memory_7(6),
							val_Memory_8(7),
							val_Memory_9(8),
							val_Memory_10(9),
							val_Memory_11(10),
							val_Memory_12(11),
							val_Memory_13(12),
							val_Memory_14(13),
							val_Memory_15(14),
							val_Memory_16(15)
							}
		MAX-ACCESS		read-write
		STATUS			current
		DESCRIPTION
				"TYPE: - RadiobuttonList
					Save_Mem  cmdID= 21 
					Memory_1  value= 0  
					Memory_2  value= 1  
					Memory_3  value= 2  
					Memory_4  value= 3  
					Memory_5  value= 4  
					Memory_6  value= 5  
					Memory_7  value= 6  
					Memory_8  value= 7  
					Memory_9  value= 8  
					Memory_10  value= 9  
					Memory_11  value= 10  
					Memory_12  value= 11  
					Memory_13  value= 12  
					Memory_14  value= 13  
					Memory_15  value= 14  
					Memory_16  value= 15  "
		::= { iqdprCmdEntry 21 }


	iqdprUserMemoryNameMemMemory1 OBJECT-TYPE
		SYNTAX		RollCallString
		MAX-ACCESS		read-write
		STATUS			current
		DESCRIPTION
				"TYPE: - Editstring
					Memory_1  cmdID= 114  "
		::= { iqdprCmdEntry 114 }


	iqdprUserMemoryNameMemMemory2 OBJECT-TYPE
		SYNTAX		RollCallString
		MAX-ACCESS		read-write
		STATUS			current
		DESCRIPTION
				"TYPE: - Editstring
					Memory_2  cmdID= 115  "
		::= { iqdprCmdEntry 115 }


	iqdprUserMemoryNameMemMemory3 OBJECT-TYPE
		SYNTAX		RollCallString
		MAX-ACCESS		read-write
		STATUS			current
		DESCRIPTION
				"TYPE: - Editstring
					Memory_3  cmdID= 116  "
		::= { iqdprCmdEntry 116 }


	iqdprUserMemoryNameMemMemory4 OBJECT-TYPE
		SYNTAX		RollCallString
		MAX-ACCESS		read-write
		STATUS			current
		DESCRIPTION
				"TYPE: - Editstring
					Memory_4  cmdID= 117  "
		::= { iqdprCmdEntry 117 }


	iqdprUserMemoryNameMemMemory5 OBJECT-TYPE
		SYNTAX		RollCallString
		MAX-ACCESS		read-write
		STATUS			current
		DESCRIPTION
				"TYPE: - Editstring
					Memory_5  cmdID= 118  "
		::= { iqdprCmdEntry 118 }


	iqdprUserMemoryNameMemMemory6 OBJECT-TYPE
		SYNTAX		RollCallString
		MAX-ACCESS		read-write
		STATUS			current
		DESCRIPTION
				"TYPE: - Editstring
					Memory_6  cmdID= 119  "
		::= { iqdprCmdEntry 119 }


	iqdprUserMemoryNameMemMemory7 OBJECT-TYPE
		SYNTAX		RollCallString
		MAX-ACCESS		read-write
		STATUS			current
		DESCRIPTION
				"TYPE: - Editstring
					Memory_7  cmdID= 120  "
		::= { iqdprCmdEntry 120 }


	iqdprUserMemoryNameMemMemory8 OBJECT-TYPE
		SYNTAX		RollCallString
		MAX-ACCESS		read-write
		STATUS			current
		DESCRIPTION
				"TYPE: - Editstring
					Memory_8  cmdID= 121  "
		::= { iqdprCmdEntry 121 }


	iqdprUserMemoryNameMemMemory9 OBJECT-TYPE
		SYNTAX		RollCallString
		MAX-ACCESS		read-write
		STATUS			current
		DESCRIPTION
				"TYPE: - Editstring
					Memory_9  cmdID= 122  "
		::= { iqdprCmdEntry 122 }


	iqdprUserMemoryNameMemMemory10 OBJECT-TYPE
		SYNTAX		RollCallString
		MAX-ACCESS		read-write
		STATUS			current
		DESCRIPTION
				"TYPE: - Editstring
					Memory_10  cmdID= 123  "
		::= { iqdprCmdEntry 123 }


	iqdprUserMemoryNameMemMemory11 OBJECT-TYPE
		SYNTAX		RollCallString
		MAX-ACCESS		read-write
		STATUS			current
		DESCRIPTION
				"TYPE: - Editstring
					Memory_11  cmdID= 124  "
		::= { iqdprCmdEntry 124 }


	iqdprUserMemoryNameMemMemory12 OBJECT-TYPE
		SYNTAX		RollCallString
		MAX-ACCESS		read-write
		STATUS			current
		DESCRIPTION
				"TYPE: - Editstring
					Memory_12  cmdID= 125  "
		::= { iqdprCmdEntry 125 }


	iqdprUserMemoryNameMemMemory13 OBJECT-TYPE
		SYNTAX		RollCallString
		MAX-ACCESS		read-write
		STATUS			current
		DESCRIPTION
				"TYPE: - Editstring
					Memory_13  cmdID= 126  "
		::= { iqdprCmdEntry 126 }


	iqdprUserMemoryNameMemMemory14 OBJECT-TYPE
		SYNTAX		RollCallString
		MAX-ACCESS		read-write
		STATUS			current
		DESCRIPTION
				"TYPE: - Editstring
					Memory_14  cmdID= 127  "
		::= { iqdprCmdEntry 127 }


	iqdprUserMemoryNameMemMemory15 OBJECT-TYPE
		SYNTAX		RollCallString
		MAX-ACCESS		read-write
		STATUS			current
		DESCRIPTION
				"TYPE: - Editstring
					Memory_15  cmdID= 128  "
		::= { iqdprCmdEntry 128 }


	iqdprUserMemoryNameMemMemory16 OBJECT-TYPE
		SYNTAX		RollCallString
		MAX-ACCESS		read-write
		STATUS			current
		DESCRIPTION
				"TYPE: - Editstring
					Memory_16  cmdID= 129  "
		::= { iqdprCmdEntry 129 }


	iqdprUserMemoryNameMemPresetAllNames OBJECT-TYPE
		SYNTAX		INTEGER {
							val_Preset_All_Names(1)
							}
		MAX-ACCESS		read-write
		STATUS			current
		DESCRIPTION
				"TYPE: - RadiobuttonList
					Preset_All_Names  cmdID= 25 
					Preset_All_Names  value= 1  "
		::= { iqdprCmdEntry 25 }


	iqdprUserMemoryClearMem OBJECT-TYPE
		SYNTAX		INTEGER {
							val_Memory_1(0),
							val_Memory_2(1),
							val_Memory_3(2),
							val_Memory_4(3),
							val_Memory_5(4),
							val_Memory_6(5),
							val_Memory_7(6),
							val_Memory_8(7),
							val_Memory_9(8),
							val_Memory_10(9),
							val_Memory_11(10),
							val_Memory_12(11),
							val_Memory_13(12),
							val_Memory_14(13),
							val_Memory_15(14),
							val_Memory_16(15)
							}
		MAX-ACCESS		read-write
		STATUS			current
		DESCRIPTION
				"TYPE: - RadiobuttonList
					Clear_Mem  cmdID= 22 
					Memory_1  value= 0  
					Memory_2  value= 1  
					Memory_3  value= 2  
					Memory_4  value= 3  
					Memory_5  value= 4  
					Memory_6  value= 5  
					Memory_7  value= 6  
					Memory_8  value= 7  
					Memory_9  value= 8  
					Memory_10  value= 9  
					Memory_11  value= 10  
					Memory_12  value= 11  
					Memory_13  value= 12  
					Memory_14  value= 13  
					Memory_15  value= 14  
					Memory_16  value= 15  "
		::= { iqdprCmdEntry 22 }


	iqdprBypass OBJECT-TYPE
		SYNTAX		INTEGER { disable(0), enable(1) }
		MAX-ACCESS		read-write
		STATUS			current
		DESCRIPTION
				"TYPE: - Checkbox
					Bypass  cmdID= 106 "
		::= { iqdprCmdEntry 106 }


	iqdprSetupPatternsPatternOn OBJECT-TYPE
		SYNTAX		INTEGER { disable(0), enable(1) }
		MAX-ACCESS		read-write
		STATUS			current
		DESCRIPTION
				"TYPE: - Checkbox
					Pattern_On  cmdID= 93 "
		::= { iqdprCmdEntry 93 }


	iqdprSetupPatternsIncludeCaption OBJECT-TYPE
		SYNTAX		INTEGER {
							val_Off(0),
							val_In_Pattern(1),
							val_In_VBI(2)
							}
		MAX-ACCESS		read-write
		STATUS			current
		DESCRIPTION
				"TYPE: - RadiobuttonList
					Include_Caption  cmdID= 135 
					Off  value= 0  
					In_Pattern  value= 1  
					In_VBI  value= 2  "
		::= { iqdprCmdEntry 135 }


	iqdprSetupPatterns OBJECT-TYPE
		SYNTAX		INTEGER {
							val_Black(0),
							val_EBU_Bars(3),
							val_100_Bars(2),
							val_Valid_Ramp(1),
							val_Multi_Burst(4),
							val_Pulse_and_Bar(5),
							val_Green(6)
							}
		MAX-ACCESS		read-write
		STATUS			current
		DESCRIPTION
				"TYPE: - Button
					Black  cmdID= 94  value= 0  
					EBU_Bars  cmdID= 94  value= 3  
					100%_Bars  cmdID= 94  value= 2  
					Valid_Ramp  cmdID= 94  value= 1  
					Multi_Burst  cmdID= 94  value= 4  
					Pulse_and_Bar  cmdID= 94  value= 5  
					Green  cmdID= 94  value= 6  "
		::= { iqdprCmdEntry 94 }


	iqdprSetupVerticalData525 OBJECT-TYPE
		SYNTAX		INTEGER {
							val_Blank_Vits(0),
							val_Pass_Vits(1)
							}
		MAX-ACCESS		read-write
		STATUS			current
		DESCRIPTION
				"TYPE: - Button
					Blank_Vits  cmdID= 23  value= 0  
					Pass_Vits  cmdID= 23  value= 1  "
		::= { iqdprCmdEntry 23 }


	iqdprSetupVerticalData525PreserveLine21 OBJECT-TYPE
		SYNTAX		INTEGER { disable(0), enable(1) }
		MAX-ACCESS		read-write
		STATUS			current
		DESCRIPTION
				"TYPE: - Checkbox
					Preserve_Line_21  cmdID= 112 "
		::= { iqdprCmdEntry 112 }


	iqdprSetupVerticalData525PreserveL283L284 OBJECT-TYPE
		SYNTAX		INTEGER { disable(0), enable(1) }
		MAX-ACCESS		read-write
		STATUS			current
		DESCRIPTION
				"TYPE: - Checkbox
					Preserve_L283/L284  cmdID= 138 "
		::= { iqdprCmdEntry 138 }


	iqdprVerticalData525SetLines525BlankL10 OBJECT-TYPE
		SYNTAX		INTEGER { disable(0), enable(1) }
		MAX-ACCESS		read-write
		STATUS			current
		DESCRIPTION
				"TYPE: - Checkbox
				 PAGE: - Set_Lines_525
					Blank_L10  cmdID= 65 "
		::= { iqdprCmdEntry 65 }


	iqdprVerticalData525SetLines525BlankL272 OBJECT-TYPE
		SYNTAX		INTEGER { disable(0), enable(1) }
		MAX-ACCESS		read-write
		STATUS			current
		DESCRIPTION
				"TYPE: - Checkbox
				 PAGE: - Set_Lines_525
					Blank_L272  cmdID= 78 "
		::= { iqdprCmdEntry 78 }


	iqdprVerticalData525SetLines525BlankL11 OBJECT-TYPE
		SYNTAX		INTEGER { disable(0), enable(1) }
		MAX-ACCESS		read-write
		STATUS			current
		DESCRIPTION
				"TYPE: - Checkbox
				 PAGE: - Set_Lines_525
					Blank_L11  cmdID= 66 "
		::= { iqdprCmdEntry 66 }


	iqdprVerticalData525SetLines525BlankL273 OBJECT-TYPE
		SYNTAX		INTEGER { disable(0), enable(1) }
		MAX-ACCESS		read-write
		STATUS			current
		DESCRIPTION
				"TYPE: - Checkbox
				 PAGE: - Set_Lines_525
					Blank_L273  cmdID= 79 "
		::= { iqdprCmdEntry 79 }


	iqdprVerticalData525SetLines525BlankL12 OBJECT-TYPE
		SYNTAX		INTEGER { disable(0), enable(1) }
		MAX-ACCESS		read-write
		STATUS			current
		DESCRIPTION
				"TYPE: - Checkbox
				 PAGE: - Set_Lines_525
					Blank_L12  cmdID= 67 "
		::= { iqdprCmdEntry 67 }


	iqdprVerticalData525SetLines525BlankL274 OBJECT-TYPE
		SYNTAX		INTEGER { disable(0), enable(1) }
		MAX-ACCESS		read-write
		STATUS			current
		DESCRIPTION
				"TYPE: - Checkbox
				 PAGE: - Set_Lines_525
					Blank_L274  cmdID= 80 "
		::= { iqdprCmdEntry 80 }


	iqdprVerticalData525SetLines525BlankL13 OBJECT-TYPE
		SYNTAX		INTEGER { disable(0), enable(1) }
		MAX-ACCESS		read-write
		STATUS			current
		DESCRIPTION
				"TYPE: - Checkbox
				 PAGE: - Set_Lines_525
					Blank_L13  cmdID= 68 "
		::= { iqdprCmdEntry 68 }


	iqdprVerticalData525SetLines525BlankL275 OBJECT-TYPE
		SYNTAX		INTEGER { disable(0), enable(1) }
		MAX-ACCESS		read-write
		STATUS			current
		DESCRIPTION
				"TYPE: - Checkbox
				 PAGE: - Set_Lines_525
					Blank_L275  cmdID= 81 "
		::= { iqdprCmdEntry 81 }


	iqdprVerticalData525SetLines525BlankL14 OBJECT-TYPE
		SYNTAX		INTEGER { disable(0), enable(1) }
		MAX-ACCESS		read-write
		STATUS			current
		DESCRIPTION
				"TYPE: - Checkbox
				 PAGE: - Set_Lines_525
					Blank_L14  cmdID= 69 "
		::= { iqdprCmdEntry 69 }


	iqdprVerticalData525SetLines525BlankL276 OBJECT-TYPE
		SYNTAX		INTEGER { disable(0), enable(1) }
		MAX-ACCESS		read-write
		STATUS			current
		DESCRIPTION
				"TYPE: - Checkbox
				 PAGE: - Set_Lines_525
					Blank_L276  cmdID= 82 "
		::= { iqdprCmdEntry 82 }


	iqdprVerticalData525SetLines525BlankL15 OBJECT-TYPE
		SYNTAX		INTEGER { disable(0), enable(1) }
		MAX-ACCESS		read-write
		STATUS			current
		DESCRIPTION
				"TYPE: - Checkbox
				 PAGE: - Set_Lines_525
					Blank_L15  cmdID= 70 "
		::= { iqdprCmdEntry 70 }


	iqdprVerticalData525SetLines525BlankL277 OBJECT-TYPE
		SYNTAX		INTEGER { disable(0), enable(1) }
		MAX-ACCESS		read-write
		STATUS			current
		DESCRIPTION
				"TYPE: - Checkbox
				 PAGE: - Set_Lines_525
					Blank_L277  cmdID= 83 "
		::= { iqdprCmdEntry 83 }


	iqdprVerticalData525SetLines525BlankL16 OBJECT-TYPE
		SYNTAX		INTEGER { disable(0), enable(1) }
		MAX-ACCESS		read-write
		STATUS			current
		DESCRIPTION
				"TYPE: - Checkbox
				 PAGE: - Set_Lines_525
					Blank_L16  cmdID= 71 "
		::= { iqdprCmdEntry 71 }


	iqdprVerticalData525SetLines525BlankL278 OBJECT-TYPE
		SYNTAX		INTEGER { disable(0), enable(1) }
		MAX-ACCESS		read-write
		STATUS			current
		DESCRIPTION
				"TYPE: - Checkbox
				 PAGE: - Set_Lines_525
					Blank_L278  cmdID= 84 "
		::= { iqdprCmdEntry 84 }


	iqdprVerticalData525SetLines525BlankL17 OBJECT-TYPE
		SYNTAX		INTEGER { disable(0), enable(1) }
		MAX-ACCESS		read-write
		STATUS			current
		DESCRIPTION
				"TYPE: - Checkbox
				 PAGE: - Set_Lines_525
					Blank_L17  cmdID= 72 "
		::= { iqdprCmdEntry 72 }


	iqdprVerticalData525SetLines525BlankL279 OBJECT-TYPE
		SYNTAX		INTEGER { disable(0), enable(1) }
		MAX-ACCESS		read-write
		STATUS			current
		DESCRIPTION
				"TYPE: - Checkbox
				 PAGE: - Set_Lines_525
					Blank_L279  cmdID= 85 "
		::= { iqdprCmdEntry 85 }


	iqdprVerticalData525SetLines525BlankL18 OBJECT-TYPE
		SYNTAX		INTEGER { disable(0), enable(1) }
		MAX-ACCESS		read-write
		STATUS			current
		DESCRIPTION
				"TYPE: - Checkbox
				 PAGE: - Set_Lines_525
					Blank_L18  cmdID= 73 "
		::= { iqdprCmdEntry 73 }


	iqdprVerticalData525SetLines525BlankL280 OBJECT-TYPE
		SYNTAX		INTEGER { disable(0), enable(1) }
		MAX-ACCESS		read-write
		STATUS			current
		DESCRIPTION
				"TYPE: - Checkbox
				 PAGE: - Set_Lines_525
					Blank_L280  cmdID= 86 "
		::= { iqdprCmdEntry 86 }


	iqdprVerticalData525SetLines525BlankL19 OBJECT-TYPE
		SYNTAX		INTEGER { disable(0), enable(1) }
		MAX-ACCESS		read-write
		STATUS			current
		DESCRIPTION
				"TYPE: - Checkbox
				 PAGE: - Set_Lines_525
					Blank_L19  cmdID= 74 "
		::= { iqdprCmdEntry 74 }


	iqdprVerticalData525SetLines525BlankL281 OBJECT-TYPE
		SYNTAX		INTEGER { disable(0), enable(1) }
		MAX-ACCESS		read-write
		STATUS			current
		DESCRIPTION
				"TYPE: - Checkbox
				 PAGE: - Set_Lines_525
					Blank_L281  cmdID= 87 "
		::= { iqdprCmdEntry 87 }


	iqdprVerticalData525SetLines525BlankL20 OBJECT-TYPE
		SYNTAX		INTEGER { disable(0), enable(1) }
		MAX-ACCESS		read-write
		STATUS			current
		DESCRIPTION
				"TYPE: - Checkbox
				 PAGE: - Set_Lines_525
					Blank_L20  cmdID= 75 "
		::= { iqdprCmdEntry 75 }


	iqdprVerticalData525SetLines525BlankL282 OBJECT-TYPE
		SYNTAX		INTEGER { disable(0), enable(1) }
		MAX-ACCESS		read-write
		STATUS			current
		DESCRIPTION
				"TYPE: - Checkbox
				 PAGE: - Set_Lines_525
					Blank_L282  cmdID= 88 "
		::= { iqdprCmdEntry 88 }


	iqdprVerticalData525SetLines525BlankL21 OBJECT-TYPE
		SYNTAX		INTEGER { disable(0), enable(1) }
		MAX-ACCESS		read-write
		STATUS			current
		DESCRIPTION
				"TYPE: - Checkbox
				 PAGE: - Set_Lines_525
					Blank_L21  cmdID= 76 "
		::= { iqdprCmdEntry 76 }


	iqdprVerticalData525SetLines525BlankL283 OBJECT-TYPE
		SYNTAX		INTEGER { disable(0), enable(1) }
		MAX-ACCESS		read-write
		STATUS			current
		DESCRIPTION
				"TYPE: - Checkbox
				 PAGE: - Set_Lines_525
					Blank_L283  cmdID= 89 "
		::= { iqdprCmdEntry 89 }


	iqdprVerticalData525SetLines525BlankL22 OBJECT-TYPE
		SYNTAX		INTEGER { disable(0), enable(1) }
		MAX-ACCESS		read-write
		STATUS			current
		DESCRIPTION
				"TYPE: - Checkbox
				 PAGE: - Set_Lines_525
					Blank_L22  cmdID= 77 "
		::= { iqdprCmdEntry 77 }


	iqdprVerticalData525SetLines525BlankL284 OBJECT-TYPE
		SYNTAX		INTEGER { disable(0), enable(1) }
		MAX-ACCESS		read-write
		STATUS			current
		DESCRIPTION
				"TYPE: - Checkbox
				 PAGE: - Set_Lines_525
					Blank_L284  cmdID= 90 "
		::= { iqdprCmdEntry 90 }


	iqdprSetupVerticalData625 OBJECT-TYPE
		SYNTAX		INTEGER {
							val_Blank_Vits(0),
							val_Pass_Vits(1)
							}
		MAX-ACCESS		read-write
		STATUS			current
		DESCRIPTION
				"TYPE: - Button
					Blank_Vits  cmdID= 24  value= 0  
					Pass_Vits  cmdID= 24  value= 1  "
		::= { iqdprCmdEntry 24 }


	iqdprSetupVerticalData625PreserveLine23 OBJECT-TYPE
		SYNTAX		INTEGER { disable(0), enable(1) }
		MAX-ACCESS		read-write
		STATUS			current
		DESCRIPTION
				"TYPE: - Checkbox
					Preserve_Line_23  cmdID= 113 "
		::= { iqdprCmdEntry 113 }


	iqdprVerticalData625SetLines625BlankL6 OBJECT-TYPE
		SYNTAX		INTEGER { disable(0), enable(1) }
		MAX-ACCESS		read-write
		STATUS			current
		DESCRIPTION
				"TYPE: - Checkbox
				 PAGE: - Set_Lines_625
					Blank_L6  cmdID= 27 "
		::= { iqdprCmdEntry 27 }


	iqdprVerticalData625SetLines625BlankL318 OBJECT-TYPE
		SYNTAX		INTEGER { disable(0), enable(1) }
		MAX-ACCESS		read-write
		STATUS			current
		DESCRIPTION
				"TYPE: - Checkbox
				 PAGE: - Set_Lines_625
					Blank_L318  cmdID= 46 "
		::= { iqdprCmdEntry 46 }


	iqdprVerticalData625SetLines625BlankL7 OBJECT-TYPE
		SYNTAX		INTEGER { disable(0), enable(1) }
		MAX-ACCESS		read-write
		STATUS			current
		DESCRIPTION
				"TYPE: - Checkbox
				 PAGE: - Set_Lines_625
					Blank_L7  cmdID= 28 "
		::= { iqdprCmdEntry 28 }


	iqdprVerticalData625SetLines625BlankL319 OBJECT-TYPE
		SYNTAX		INTEGER { disable(0), enable(1) }
		MAX-ACCESS		read-write
		STATUS			current
		DESCRIPTION
				"TYPE: - Checkbox
				 PAGE: - Set_Lines_625
					Blank_L319  cmdID= 47 "
		::= { iqdprCmdEntry 47 }


	iqdprVerticalData625SetLines625BlankL8 OBJECT-TYPE
		SYNTAX		INTEGER { disable(0), enable(1) }
		MAX-ACCESS		read-write
		STATUS			current
		DESCRIPTION
				"TYPE: - Checkbox
				 PAGE: - Set_Lines_625
					Blank_L8  cmdID= 29 "
		::= { iqdprCmdEntry 29 }


	iqdprVerticalData625SetLines625BlankL320 OBJECT-TYPE
		SYNTAX		INTEGER { disable(0), enable(1) }
		MAX-ACCESS		read-write
		STATUS			current
		DESCRIPTION
				"TYPE: - Checkbox
				 PAGE: - Set_Lines_625
					Blank_L320  cmdID= 48 "
		::= { iqdprCmdEntry 48 }


	iqdprVerticalData625SetLines625BlankL9 OBJECT-TYPE
		SYNTAX		INTEGER { disable(0), enable(1) }
		MAX-ACCESS		read-write
		STATUS			current
		DESCRIPTION
				"TYPE: - Checkbox
				 PAGE: - Set_Lines_625
					Blank_L9  cmdID= 30 "
		::= { iqdprCmdEntry 30 }


	iqdprVerticalData625SetLines625BlankL321 OBJECT-TYPE
		SYNTAX		INTEGER { disable(0), enable(1) }
		MAX-ACCESS		read-write
		STATUS			current
		DESCRIPTION
				"TYPE: - Checkbox
				 PAGE: - Set_Lines_625
					Blank_L321  cmdID= 49 "
		::= { iqdprCmdEntry 49 }


	iqdprVerticalData625SetLines625BlankL10 OBJECT-TYPE
		SYNTAX		INTEGER { disable(0), enable(1) }
		MAX-ACCESS		read-write
		STATUS			current
		DESCRIPTION
				"TYPE: - Checkbox
				 PAGE: - Set_Lines_625
					Blank_L10  cmdID= 31 "
		::= { iqdprCmdEntry 31 }


	iqdprVerticalData625SetLines625BlankL322 OBJECT-TYPE
		SYNTAX		INTEGER { disable(0), enable(1) }
		MAX-ACCESS		read-write
		STATUS			current
		DESCRIPTION
				"TYPE: - Checkbox
				 PAGE: - Set_Lines_625
					Blank_L322  cmdID= 50 "
		::= { iqdprCmdEntry 50 }


	iqdprVerticalData625SetLines625BlankL11 OBJECT-TYPE
		SYNTAX		INTEGER { disable(0), enable(1) }
		MAX-ACCESS		read-write
		STATUS			current
		DESCRIPTION
				"TYPE: - Checkbox
				 PAGE: - Set_Lines_625
					Blank_L11  cmdID= 32 "
		::= { iqdprCmdEntry 32 }


	iqdprVerticalData625SetLines625BlankL323 OBJECT-TYPE
		SYNTAX		INTEGER { disable(0), enable(1) }
		MAX-ACCESS		read-write
		STATUS			current
		DESCRIPTION
				"TYPE: - Checkbox
				 PAGE: - Set_Lines_625
					Blank_L323  cmdID= 51 "
		::= { iqdprCmdEntry 51 }


	iqdprVerticalData625SetLines625BlankL12 OBJECT-TYPE
		SYNTAX		INTEGER { disable(0), enable(1) }
		MAX-ACCESS		read-write
		STATUS			current
		DESCRIPTION
				"TYPE: - Checkbox
				 PAGE: - Set_Lines_625
					Blank_L12  cmdID= 33 "
		::= { iqdprCmdEntry 33 }


	iqdprVerticalData625SetLines625BlankL324 OBJECT-TYPE
		SYNTAX		INTEGER { disable(0), enable(1) }
		MAX-ACCESS		read-write
		STATUS			current
		DESCRIPTION
				"TYPE: - Checkbox
				 PAGE: - Set_Lines_625
					Blank_L324  cmdID= 52 "
		::= { iqdprCmdEntry 52 }


	iqdprVerticalData625SetLines625BlankL13 OBJECT-TYPE
		SYNTAX		INTEGER { disable(0), enable(1) }
		MAX-ACCESS		read-write
		STATUS			current
		DESCRIPTION
				"TYPE: - Checkbox
				 PAGE: - Set_Lines_625
					Blank_L13  cmdID= 34 "
		::= { iqdprCmdEntry 34 }


	iqdprVerticalData625SetLines625BlankL325 OBJECT-TYPE
		SYNTAX		INTEGER { disable(0), enable(1) }
		MAX-ACCESS		read-write
		STATUS			current
		DESCRIPTION
				"TYPE: - Checkbox
				 PAGE: - Set_Lines_625
					Blank_L325  cmdID= 53 "
		::= { iqdprCmdEntry 53 }


	iqdprVerticalData625SetLines625BlankL14 OBJECT-TYPE
		SYNTAX		INTEGER { disable(0), enable(1) }
		MAX-ACCESS		read-write
		STATUS			current
		DESCRIPTION
				"TYPE: - Checkbox
				 PAGE: - Set_Lines_625
					Blank_L14  cmdID= 35 "
		::= { iqdprCmdEntry 35 }


	iqdprVerticalData625SetLines625BlankL326 OBJECT-TYPE
		SYNTAX		INTEGER { disable(0), enable(1) }
		MAX-ACCESS		read-write
		STATUS			current
		DESCRIPTION
				"TYPE: - Checkbox
				 PAGE: - Set_Lines_625
					Blank_L326  cmdID= 54 "
		::= { iqdprCmdEntry 54 }


	iqdprVerticalData625SetLines625BlankL15 OBJECT-TYPE
		SYNTAX		INTEGER { disable(0), enable(1) }
		MAX-ACCESS		read-write
		STATUS			current
		DESCRIPTION
				"TYPE: - Checkbox
				 PAGE: - Set_Lines_625
					Blank_L15  cmdID= 36 "
		::= { iqdprCmdEntry 36 }


	iqdprVerticalData625SetLines625BlankL327 OBJECT-TYPE
		SYNTAX		INTEGER { disable(0), enable(1) }
		MAX-ACCESS		read-write
		STATUS			current
		DESCRIPTION
				"TYPE: - Checkbox
				 PAGE: - Set_Lines_625
					Blank_L327  cmdID= 55 "
		::= { iqdprCmdEntry 55 }


	iqdprVerticalData625SetLines625BlankL16 OBJECT-TYPE
		SYNTAX		INTEGER { disable(0), enable(1) }
		MAX-ACCESS		read-write
		STATUS			current
		DESCRIPTION
				"TYPE: - Checkbox
				 PAGE: - Set_Lines_625
					Blank_L16  cmdID= 37 "
		::= { iqdprCmdEntry 37 }


	iqdprVerticalData625SetLines625BlankL328 OBJECT-TYPE
		SYNTAX		INTEGER { disable(0), enable(1) }
		MAX-ACCESS		read-write
		STATUS			current
		DESCRIPTION
				"TYPE: - Checkbox
				 PAGE: - Set_Lines_625
					Blank_L328  cmdID= 56 "
		::= { iqdprCmdEntry 56 }


	iqdprVerticalData625SetLines625BlankL17 OBJECT-TYPE
		SYNTAX		INTEGER { disable(0), enable(1) }
		MAX-ACCESS		read-write
		STATUS			current
		DESCRIPTION
				"TYPE: - Checkbox
				 PAGE: - Set_Lines_625
					Blank_L17  cmdID= 38 "
		::= { iqdprCmdEntry 38 }


	iqdprVerticalData625SetLines625BlankL329 OBJECT-TYPE
		SYNTAX		INTEGER { disable(0), enable(1) }
		MAX-ACCESS		read-write
		STATUS			current
		DESCRIPTION
				"TYPE: - Checkbox
				 PAGE: - Set_Lines_625
					Blank_L329  cmdID= 57 "
		::= { iqdprCmdEntry 57 }


	iqdprVerticalData625SetLines625BlankL18 OBJECT-TYPE
		SYNTAX		INTEGER { disable(0), enable(1) }
		MAX-ACCESS		read-write
		STATUS			current
		DESCRIPTION
				"TYPE: - Checkbox
				 PAGE: - Set_Lines_625
					Blank_L18  cmdID= 39 "
		::= { iqdprCmdEntry 39 }


	iqdprVerticalData625SetLines625BlankL330 OBJECT-TYPE
		SYNTAX		INTEGER { disable(0), enable(1) }
		MAX-ACCESS		read-write
		STATUS			current
		DESCRIPTION
				"TYPE: - Checkbox
				 PAGE: - Set_Lines_625
					Blank_L330  cmdID= 58 "
		::= { iqdprCmdEntry 58 }


	iqdprVerticalData625SetLines625BlankL19 OBJECT-TYPE
		SYNTAX		INTEGER { disable(0), enable(1) }
		MAX-ACCESS		read-write
		STATUS			current
		DESCRIPTION
				"TYPE: - Checkbox
				 PAGE: - Set_Lines_625
					Blank_L19  cmdID= 40 "
		::= { iqdprCmdEntry 40 }


	iqdprVerticalData625SetLines625BlankL331 OBJECT-TYPE
		SYNTAX		INTEGER { disable(0), enable(1) }
		MAX-ACCESS		read-write
		STATUS			current
		DESCRIPTION
				"TYPE: - Checkbox
				 PAGE: - Set_Lines_625
					Blank_L331  cmdID= 59 "
		::= { iqdprCmdEntry 59 }


	iqdprVerticalData625SetLines625BlankL20 OBJECT-TYPE
		SYNTAX		INTEGER { disable(0), enable(1) }
		MAX-ACCESS		read-write
		STATUS			current
		DESCRIPTION
				"TYPE: - Checkbox
				 PAGE: - Set_Lines_625
					Blank_L20  cmdID= 41 "
		::= { iqdprCmdEntry 41 }


	iqdprVerticalData625SetLines625BlankL332 OBJECT-TYPE
		SYNTAX		INTEGER { disable(0), enable(1) }
		MAX-ACCESS		read-write
		STATUS			current
		DESCRIPTION
				"TYPE: - Checkbox
				 PAGE: - Set_Lines_625
					Blank_L332  cmdID= 60 "
		::= { iqdprCmdEntry 60 }


	iqdprVerticalData625SetLines625BlankL21 OBJECT-TYPE
		SYNTAX		INTEGER { disable(0), enable(1) }
		MAX-ACCESS		read-write
		STATUS			current
		DESCRIPTION
				"TYPE: - Checkbox
				 PAGE: - Set_Lines_625
					Blank_L21  cmdID= 42 "
		::= { iqdprCmdEntry 42 }


	iqdprVerticalData625SetLines625BlankL333 OBJECT-TYPE
		SYNTAX		INTEGER { disable(0), enable(1) }
		MAX-ACCESS		read-write
		STATUS			current
		DESCRIPTION
				"TYPE: - Checkbox
				 PAGE: - Set_Lines_625
					Blank_L333  cmdID= 61 "
		::= { iqdprCmdEntry 61 }


	iqdprVerticalData625SetLines625BlankL22 OBJECT-TYPE
		SYNTAX		INTEGER { disable(0), enable(1) }
		MAX-ACCESS		read-write
		STATUS			current
		DESCRIPTION
				"TYPE: - Checkbox
				 PAGE: - Set_Lines_625
					Blank_L22  cmdID= 43 "
		::= { iqdprCmdEntry 43 }


	iqdprVerticalData625SetLines625BlankL334 OBJECT-TYPE
		SYNTAX		INTEGER { disable(0), enable(1) }
		MAX-ACCESS		read-write
		STATUS			current
		DESCRIPTION
				"TYPE: - Checkbox
				 PAGE: - Set_Lines_625
					Blank_L334  cmdID= 62 "
		::= { iqdprCmdEntry 62 }


	iqdprVerticalData625SetLines625BlankL23 OBJECT-TYPE
		SYNTAX		INTEGER { disable(0), enable(1) }
		MAX-ACCESS		read-write
		STATUS			current
		DESCRIPTION
				"TYPE: - Checkbox
				 PAGE: - Set_Lines_625
					Blank_L23  cmdID= 44 "
		::= { iqdprCmdEntry 44 }


	iqdprVerticalData625SetLines625BlankL335 OBJECT-TYPE
		SYNTAX		INTEGER { disable(0), enable(1) }
		MAX-ACCESS		read-write
		STATUS			current
		DESCRIPTION
				"TYPE: - Checkbox
				 PAGE: - Set_Lines_625
					Blank_L335  cmdID= 63 "
		::= { iqdprCmdEntry 63 }


	iqdprVerticalData625SetLines625BlankL24 OBJECT-TYPE
		SYNTAX		INTEGER { disable(0), enable(1) }
		MAX-ACCESS		read-write
		STATUS			current
		DESCRIPTION
				"TYPE: - Checkbox
				 PAGE: - Set_Lines_625
					Blank_L24  cmdID= 45 "
		::= { iqdprCmdEntry 45 }


	iqdprVerticalData625SetLines625BlankL336 OBJECT-TYPE
		SYNTAX		INTEGER { disable(0), enable(1) }
		MAX-ACCESS		read-write
		STATUS			current
		DESCRIPTION
				"TYPE: - Checkbox
				 PAGE: - Set_Lines_625
					Blank_L336  cmdID= 64 "
		::= { iqdprCmdEntry 64 }


	iqdprSetupHANCPass OBJECT-TYPE
		SYNTAX		INTEGER { disable(0), enable(1) }
		MAX-ACCESS		read-write
		STATUS			current
		DESCRIPTION
				"TYPE: - Checkbox
					HANC_Pass  cmdID= 108 "
		::= { iqdprCmdEntry 108 }


	iqdprSetupDefaultOutputOutputStandard OBJECT-TYPE
		SYNTAX		INTEGER {
							val_Auto(0),
							val_625(1),
							val_525(2)
							}
		MAX-ACCESS		read-write
		STATUS			current
		DESCRIPTION
				"TYPE: - RadiobuttonList
					Output_Standard  cmdID= 91 
					Auto  value= 0  
					625  value= 1  
					525  value= 2  "
		::= { iqdprCmdEntry 91 }


	iqdprSetupDefaultOutputIncludeCaption OBJECT-TYPE
		SYNTAX		INTEGER {
							val_Off(0),
							val_In_Default(1),
							val_In_VBI(2)
							}
		MAX-ACCESS		read-write
		STATUS			current
		DESCRIPTION
				"TYPE: - RadiobuttonList
					Include_Caption  cmdID= 134 
					Off  value= 0  
					In_Default  value= 1  
					In_VBI  value= 2  "
		::= { iqdprCmdEntry 134 }


	iqdprSetupDefaultOutput OBJECT-TYPE
		SYNTAX		INTEGER {
							val_Black(0),
							val_EBU_Bars(3),
							val_100_Bars(2),
							val_Valid_Ramp(1),
							val_Multi_Burst(4),
							val_Pulse_and_Bar(5),
							val_Green(6)
							}
		MAX-ACCESS		read-write
		STATUS			current
		DESCRIPTION
				"TYPE: - Button
					Black  cmdID= 92  value= 0  
					EBU_Bars  cmdID= 92  value= 3  
					100%_Bars  cmdID= 92  value= 2  
					Valid_Ramp  cmdID= 92  value= 1  
					Multi_Burst  cmdID= 92  value= 4  
					Pulse_and_Bar  cmdID= 92  value= 5  
					Green  cmdID= 92  value= 6  "
		::= { iqdprCmdEntry 92 }


	iqdprSetupEditCaption OBJECT-TYPE
		SYNTAX		RollCallString
		MAX-ACCESS		read-write
		STATUS			current
		DESCRIPTION
				"TYPE: - Editstring
					Edit_Caption  cmdID= 103  "
		::= { iqdprCmdEntry 103 }


	iqdprSetupCaptionOverrideCaptionOn OBJECT-TYPE
		SYNTAX		INTEGER { disable(0), enable(1) }
		MAX-ACCESS		read-write
		STATUS			current
		DESCRIPTION
				"TYPE: - Checkbox
					Caption_On  cmdID= 136 "
		::= { iqdprCmdEntry 136 }


	iqdprSetupCaptionOverride OBJECT-TYPE
		SYNTAX		INTEGER {
							val_Insert_On_Video(0),
							val_Insert_On_VBI(1)
							}
		MAX-ACCESS		read-write
		STATUS			current
		DESCRIPTION
				"TYPE: - Button
					Insert_On_Video  cmdID= 104  value= 0  
					Insert_On_VBI  cmdID= 104  value= 1  "
		::= { iqdprCmdEntry 104 }


	iqdprSetupEDHShowStats OBJECT-TYPE
		SYNTAX		INTEGER { disable(0), enable(1) }
		MAX-ACCESS		read-write
		STATUS			current
		DESCRIPTION
				"TYPE: - Checkbox
					Show_Stats  cmdID= 100 "
		::= { iqdprCmdEntry 100 }


	iqdprSetupEDHResetStats OBJECT-TYPE
		SYNTAX		INTEGER { noAction(0),val_Reset_Stats(1) }
		MAX-ACCESS		read-write
		STATUS			current
		DESCRIPTION
				"TYPE: - Button
					Reset_Stats  cmdID= 101  value= 1  "
		::= { iqdprCmdEntry 101 }


	iqdprSetupGPIInputsGPI1 OBJECT-TYPE
		SYNTAX		INTEGER {
							val_Off(2),
							val_Latch(0),
							val_Edge(1)
							}
		MAX-ACCESS		read-write
		STATUS			current
		DESCRIPTION
				"TYPE: - Button
				 PAGE: - Setup_GPI_Inputs
					Off  cmdID= 95  value= 2  
					Latch  cmdID= 95  value= 0  
					Edge  cmdID= 95  value= 1  "
		::= { iqdprCmdEntry 95 }


	iqdprSetupGPIInputsGPI1GPI1Function OBJECT-TYPE
		SYNTAX		INTEGER {
							val_ByPass(0),
							val_Gamut(1),
							val_Pattern(2),
							val_HANC_Pass(3),
							val_Caption_On(4),
							val_Memory_1(5),
							val_Memory_2(6),
							val_Memory_3(7),
							val_Memory_4(8),
							val_Memory_5(9),
							val_Memory_6(10),
							val_Memory_7(11),
							val_Memory_8(12),
							val_Memory_9(13),
							val_Memory_10(14),
							val_Memory_11(15),
							val_Memory_12(16),
							val_Memory_13(17),
							val_Memory_14(18),
							val_Memory_15(19),
							val_Memory_16(20)
							}
		MAX-ACCESS		read-write
		STATUS			current
		DESCRIPTION
				"TYPE: - RadiobuttonList
				 PAGE: - Setup_GPI_Inputs
					GPI_1_Function  cmdID= 131 
					ByPass  value= 0  
					Gamut  value= 1  
					Pattern  value= 2  
					HANC_Pass  value= 3  
					Caption_On  value= 4  
					Memory_1  value= 5  
					Memory_2  value= 6  
					Memory_3  value= 7  
					Memory_4  value= 8  
					Memory_5  value= 9  
					Memory_6  value= 10  
					Memory_7  value= 11  
					Memory_8  value= 12  
					Memory_9  value= 13  
					Memory_10  value= 14  
					Memory_11  value= 15  
					Memory_12  value= 16  
					Memory_13  value= 17  
					Memory_14  value= 18  
					Memory_15  value= 19  
					Memory_16  value= 20  "
		::= { iqdprCmdEntry 131 }


	iqdprSetupGPIInputsGPI2 OBJECT-TYPE
		SYNTAX		INTEGER {
							val_Off(2),
							val_Latch(0),
							val_Edge(1)
							}
		MAX-ACCESS		read-write
		STATUS			current
		DESCRIPTION
				"TYPE: - Button
				 PAGE: - Setup_GPI_Inputs
					Off  cmdID= 96  value= 2  
					Latch  cmdID= 96  value= 0  
					Edge  cmdID= 96  value= 1  "
		::= { iqdprCmdEntry 96 }


	iqdprSetupGPIInputsGPI2GPI2Function OBJECT-TYPE
		SYNTAX		INTEGER {
							val_ByPass(0),
							val_Gamut(1),
							val_Pattern(2),
							val_HANC_Pass(3),
							val_Caption_On(4),
							val_Memory_1(5),
							val_Memory_2(6),
							val_Memory_3(7),
							val_Memory_4(8),
							val_Memory_5(9),
							val_Memory_6(10),
							val_Memory_7(11),
							val_Memory_8(12),
							val_Memory_9(13),
							val_Memory_10(14),
							val_Memory_11(15),
							val_Memory_12(16),
							val_Memory_13(17),
							val_Memory_14(18),
							val_Memory_15(19),
							val_Memory_16(20)
							}
		MAX-ACCESS		read-write
		STATUS			current
		DESCRIPTION
				"TYPE: - RadiobuttonList
				 PAGE: - Setup_GPI_Inputs
					GPI_2_Function  cmdID= 132 
					ByPass  value= 0  
					Gamut  value= 1  
					Pattern  value= 2  
					HANC_Pass  value= 3  
					Caption_On  value= 4  
					Memory_1  value= 5  
					Memory_2  value= 6  
					Memory_3  value= 7  
					Memory_4  value= 8  
					Memory_5  value= 9  
					Memory_6  value= 10  
					Memory_7  value= 11  
					Memory_8  value= 12  
					Memory_9  value= 13  
					Memory_10  value= 14  
					Memory_11  value= 15  
					Memory_12  value= 16  
					Memory_13  value= 17  
					Memory_14  value= 18  
					Memory_15  value= 19  
					Memory_16  value= 20  "
		::= { iqdprCmdEntry 132 }


	iqdprSetupGPIInputsGPI3 OBJECT-TYPE
		SYNTAX		INTEGER {
							val_Off(2),
							val_Latch(0),
							val_Edge(1)
							}
		MAX-ACCESS		read-write
		STATUS			current
		DESCRIPTION
				"TYPE: - Button
				 PAGE: - Setup_GPI_Inputs
					Off  cmdID= 97  value= 2  
					Latch  cmdID= 97  value= 0  
					Edge  cmdID= 97  value= 1  "
		::= { iqdprCmdEntry 97 }


	iqdprSetupGPIInputsGPI3GPI3Function OBJECT-TYPE
		SYNTAX		INTEGER {
							val_ByPass(0),
							val_Gamut(1),
							val_Pattern(2),
							val_HANC_Pass(3),
							val_Caption_On(4),
							val_Memory_1(5),
							val_Memory_2(6),
							val_Memory_3(7),
							val_Memory_4(8),
							val_Memory_5(9),
							val_Memory_6(10),
							val_Memory_7(11),
							val_Memory_8(12),
							val_Memory_9(13),
							val_Memory_10(14),
							val_Memory_11(15),
							val_Memory_12(16),
							val_Memory_13(17),
							val_Memory_14(18),
							val_Memory_15(19),
							val_Memory_16(20)
							}
		MAX-ACCESS		read-write
		STATUS			current
		DESCRIPTION
				"TYPE: - RadiobuttonList
				 PAGE: - Setup_GPI_Inputs
					GPI_3_Function  cmdID= 133 
					ByPass  value= 0  
					Gamut  value= 1  
					Pattern  value= 2  
					HANC_Pass  value= 3  
					Caption_On  value= 4  
					Memory_1  value= 5  
					Memory_2  value= 6  
					Memory_3  value= 7  
					Memory_4  value= 8  
					Memory_5  value= 9  
					Memory_6  value= 10  
					Memory_7  value= 11  
					Memory_8  value= 12  
					Memory_9  value= 13  
					Memory_10  value= 14  
					Memory_11  value= 15  
					Memory_12  value= 16  
					Memory_13  value= 17  
					Memory_14  value= 18  
					Memory_15  value= 19  
					Memory_16  value= 20  "
		::= { iqdprCmdEntry 133 }


	iqdprSetupLoggingInputChange OBJECT-TYPE
		SYNTAX		INTEGER { disable(0), enable(1) }
		MAX-ACCESS		read-write
		STATUS			current
		DESCRIPTION
				"TYPE: - Checkbox
					Input_Change  cmdID= 98 "
		::= { iqdprCmdEntry 98 }


	iqdprSetupLoggingEDHErrors OBJECT-TYPE
		SYNTAX		INTEGER { disable(0), enable(1) }
		MAX-ACCESS		read-write
		STATUS			current
		DESCRIPTION
				"TYPE: - Checkbox
					EDH_Errors  cmdID= 99 "
		::= { iqdprCmdEntry 99 }


	iqdprSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqdprCmdEntry 3 }


	iqdprSetupSoftwareVersion OBJECT-TYPE
		SYNTAX		RollCallString
		MAX-ACCESS		read-only
		STATUS			current
		DESCRIPTION
				"TYPE: - Display
					Software_Version  cmdID= 2  format=   "
		::= { iqdprCmdEntry 2 }


	iqdprSetupSerialNo OBJECT-TYPE
		SYNTAX		RollCallString
		MAX-ACCESS		read-only
		STATUS			current
		DESCRIPTION
				"TYPE: - Display
					Serial_No  cmdID= 1  format=   "
		::= { iqdprCmdEntry 1 }


	iqdprSetupRestart OBJECT-TYPE
		SYNTAX		INTEGER { noAction(0),val_Restart(1) }
		MAX-ACCESS		read-write
		STATUS			current
		DESCRIPTION
				"TYPE: - Button
					Restart  cmdID= 4  value= 1  "
		::= { iqdprCmdEntry 4 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE
--				: OK
--				: FAIL
--				: RESET
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: UNKNOWN
--				: 525
--				: 625
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
--				: ERR
-- Comments		: 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
-- Vary Number  : YES
-- Value(s)		: 
--				: 
-- Comments		: 
--
---------------------------------------------------------------------------------------------------
