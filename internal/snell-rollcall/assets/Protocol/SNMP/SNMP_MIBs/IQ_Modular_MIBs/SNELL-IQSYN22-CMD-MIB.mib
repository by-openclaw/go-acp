-- ************************************************************************************
--        Snell Card:IQSYN22
--        Module Id#:538
--       Command Set:24
--          Filename:SNELL-IQSYN22-CMD-MIB.mib
--       Source File:syncombined.xml
--        Source Ver:10.5.24
--    Logging Source:logsyn22.csv
--            Author:robinbrown
--              Date:14/03/2011
--              Time:15:42
--
-- Copyright (c) 2010 Snell Ltd
-- All rights reserved.
--
-- ************************************************************************************

SNELL-IQSYN22-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQSYN22,
    moduleIQSYN22MIB
        FROM SNELL-WILCOX-PRODUCT-REG;

moduleIQSYN22CmdMi MODULE-IDENTITY
    LAST-UPDATED "1103141542Z"
    ORGANIZATION "Snell Ltd"
    CONTACT-INFO
        "Primary Author:robinbrown

         postal:    Hartman House
                    Danehill
                    Lower Earley,
                    Reading, Berks
                    RG6 4PB
         phone:     +44 (0)118 9866123
         email:     support.uk@snellgroup.com"
    DESCRIPTION
        "This file defines the Snell card, command set translations."
    ::= { moduleIQSYN22MIB 1 }




--********************************************************************************
--*
--*  Snell Card:
--*  command set:
--*  list commands/menus:
--*
--******************************************************************************
    iqsyn22CmdTable OBJECT-TYPE
        SYNTAX          SEQUENCE OF Iqsyn22CmdEntry
        MAX-ACCESS      not-accessible
        STATUS          current
        DESCRIPTION
                "Note the instance of this table is relected in the command set Version"
        ::= { moduleIQSYN22 1 }

    iqsyn22CmdEntry OBJECT-TYPE
        SYNTAX          Iqsyn22CmdEntry
        MAX-ACCESS      not-accessible
        STATUS          current
        DESCRIPTION
                "Entry in command table."
        INDEX   { iqsyn22SlotIndex }
        ::= { iqsyn22CmdTable 1 }

    Iqsyn22CmdEntry ::=
        SEQUENCE {
            iqsyn22SlotIndex
                Unsigned32,
            iqsyn22InputIPSelect
                INTEGER,
            iqsyn22InputIPLoss
                INTEGER,
            iqsyn22InputValidStandardsAllValid
                INTEGER,
            iqsyn22InputValidStandardsAllInvalid
                INTEGER,
            iqsyn22InputValidStandards108023sF
                INTEGER,
            iqsyn22InputValidStandards108023p
                INTEGER,
            iqsyn22InputValidStandards108024sF
                INTEGER,
            iqsyn22InputValidStandards108024p
                INTEGER,
            iqsyn22InputValidStandards108025i
                INTEGER,
            iqsyn22InputValidStandards108025p
                INTEGER,
            iqsyn22InputValidStandards103529i
                INTEGER,
            iqsyn22InputValidStandards108029i
                INTEGER,
            iqsyn22InputValidStandards108029p
                INTEGER,
            iqsyn22InputValidStandards103530i
                INTEGER,
            iqsyn22InputValidStandards108030i
                INTEGER,
            iqsyn22InputValidStandards108030p
                INTEGER,
            iqsyn22InputValidStandards72050p
                INTEGER,
            iqsyn22InputValidStandards72059p
                INTEGER,
            iqsyn22InputValidStandards72060p
                INTEGER,
            iqsyn22InputValidStandards62525i
                INTEGER,
            iqsyn22InputValidStandards52529i
                INTEGER,
            iqsyn22InputAgileVLock
                INTEGER,
            iqsyn22InputErrorsCRCErrs
                RollCallString,
            iqsyn22InputErrorsCRCErrSec
                RollCallString,
            iqsyn22InputErrorsANCErrs
                RollCallString,
            iqsyn22InputErrorsANCErrSec
                RollCallString,
            iqsyn22InputErrorsResetSec
                RollCallString,
            iqsyn22InputErrorsErrorReset
                INTEGER,
            iqsyn22OutputOPStd
                INTEGER,
            iqsyn22OutputVideoProcMasterGain
                INTEGER,
            iqsyn22OutputVideoProcYGain
                INTEGER,
            iqsyn22OutputVideoProcCGain
                INTEGER,
            iqsyn22OutputVideoProcBlackLevel
                INTEGER,
            iqsyn22OutputVideoProcHue
                INTEGER,
            iqsyn22OutputDefaultOutput
                INTEGER,
            iqsyn22OutputOutputStandard
                INTEGER,
            iqsyn22OutputDefaultOPStd
                INTEGER,
            iqsyn22PictureOutputLumaClipperEnable
                INTEGER,
            iqsyn22PictureOutputLumaClipperWhitemax
                INTEGER,
            iqsyn22PictureOutputLumaClipperBlackmin
                INTEGER,
            iqsyn22PictureOutputRGBLegaliserEnable
                INTEGER,
            iqsyn22PictureOutputRGBLegaliserRange
                INTEGER,
            iqsyn22PictureOutputAdvancedHEnhanceEnable
                INTEGER,
            iqsyn22PictureOutputAdvancedHEnhanceFrequencyBand
                INTEGER,
            iqsyn22PictureOutputAdvancedHEnhancePreset
                INTEGER,
            iqsyn22PictureOutputAdvancedHEnhanceGain
                INTEGER,
            iqsyn22PictureOutputAdvancedHEnhanceNoiseRejection
                INTEGER,
            iqsyn22AudioDelayADelaySourcesManual
                INTEGER,
            iqsyn22AudioDelayADelaySourcesGPIPWM
                INTEGER,
            iqsyn22AudioDelayADelaySourcesRollTrack14
                INTEGER,
            iqsyn22AudioDelayADelaySourcesRollTrack15
                INTEGER,
            iqsyn22AudioDelayADelaySourcesRollTrack16
                INTEGER,
            iqsyn22AudioDelayADelaySourcesRollTrack17
                INTEGER,
            iqsyn22AudioDelayAAdjustManualDelay
                INTEGER,
            iqsyn22AudioDelayACurrentAudioDelay
                RollCallString,
            iqsyn22AudioDelayBDelaySourcesManual
                INTEGER,
            iqsyn22AudioDelayBDelaySourcesGPIPWM
                INTEGER,
            iqsyn22AudioDelayBDelaySourcesRollTrack14
                INTEGER,
            iqsyn22AudioDelayBDelaySourcesRollTrack15
                INTEGER,
            iqsyn22AudioDelayBDelaySourcesRollTrack16
                INTEGER,
            iqsyn22AudioDelayBDelaySourcesRollTrack17
                INTEGER,
            iqsyn22AudioDelayBAdjustManualDelay
                INTEGER,
            iqsyn22AudioDelayBCurrentAudioDelay
                RollCallString,
            iqsyn22AudioDelaySelectDelay1
                INTEGER,
            iqsyn22AudDelaysEMBDelaySelectInternal1
                INTEGER,
            iqsyn22AudDelaysEMBDelaySelectAutoDolbyEPhaseBus1
                INTEGER,
            iqsyn22AudDelaysEMBDelaySelectDelayLimitBus1
                RollCallString,
            iqsyn22AudDelaysEMBDelaySelectEMB1FineDelay
                INTEGER,
            iqsyn22AudioDelaySelectDelay2
                INTEGER,
            iqsyn22AudDelaysEMBDelaySelectInternal2
                INTEGER,
            iqsyn22AudDelaysEMBDelaySelectAutoDolbyEPhaseBus2
                INTEGER,
            iqsyn22AudDelaysEMBDelaySelectDelayLimitBus2
                RollCallString,
            iqsyn22AudDelaysEMBDelaySelectEMB2FineDelay
                INTEGER,
            iqsyn22AudioDelaySelectDelay3
                INTEGER,
            iqsyn22AudDelaysEMBDelaySelectInternal3
                INTEGER,
            iqsyn22AudDelaysEMBDelaySelectAutoDolbyEPhaseBus3
                INTEGER,
            iqsyn22AudDelaysEMBDelaySelectDelayLimitBus3
                RollCallString,
            iqsyn22AudDelaysEMBDelaySelectEMB3FineDelay
                INTEGER,
            iqsyn22AudioDelaySelectDelay4
                INTEGER,
            iqsyn22AudDelaysEMBDelaySelectInternal4
                INTEGER,
            iqsyn22AudDelaysEMBDelaySelectAutoDolbyEPhaseBus4
                INTEGER,
            iqsyn22AudDelaysEMBDelaySelectDelayLimitBus4
                RollCallString,
            iqsyn22AudDelaysEMBDelaySelectEMB4FineDelay
                INTEGER,
            iqsyn22AudioDelaySelectDelay5
                INTEGER,
            iqsyn22AudDelaysEMBDelaySelectInternal5
                INTEGER,
            iqsyn22AudDelaysEMBDelaySelectAutoDolbyEPhaseBus5
                INTEGER,
            iqsyn22AudDelaysEMBDelaySelectDelayLimitBus5
                RollCallString,
            iqsyn22AudDelaysEMBDelaySelectEMB5FineDelay
                INTEGER,
            iqsyn22AudioDelaySelectDelay6
                INTEGER,
            iqsyn22AudDelaysEMBDelaySelectInternal6
                INTEGER,
            iqsyn22AudDelaysEMBDelaySelectAutoDolbyEPhaseBus6
                INTEGER,
            iqsyn22AudDelaysEMBDelaySelectDelayLimitBus6
                RollCallString,
            iqsyn22AudDelaysEMBDelaySelectEMB6FineDelay
                INTEGER,
            iqsyn22AudioDelaySelectDelay7
                INTEGER,
            iqsyn22AudDelaysEMBDelaySelectInternal7
                INTEGER,
            iqsyn22AudDelaysEMBDelaySelectAutoDolbyEPhaseBus7
                INTEGER,
            iqsyn22AudDelaysEMBDelaySelectDelayLimitBus7
                RollCallString,
            iqsyn22AudDelaysEMBDelaySelectEMB7FineDelay
                INTEGER,
            iqsyn22AudioDelaySelectDelay8
                INTEGER,
            iqsyn22AudDelaysEMBDelaySelectInternal8
                INTEGER,
            iqsyn22AudDelaysEMBDelaySelectDelayLimitBus8
                RollCallString,
            iqsyn22AudDelaysEMBDelaySelectAutoDolbyEPhaseBus8
                INTEGER,
            iqsyn22AudDelaysEMBDelaySelectEMB8FineDelay
                INTEGER,
            iqsyn22AudioDelaysRollTrack14
                RollCallString,
            iqsyn22AudioDelaysRollTrack15
                RollCallString,
            iqsyn22AudioDelaysRollTrack16
                RollCallString,
            iqsyn22AudioDelaysRollTrack17
                RollCallString,
            iqsyn22AudioAudDelaysCrashSRCLimit
                INTEGER,
            iqsyn22EmbCtrlGroupGroup1Active
                INTEGER,
            iqsyn22EmbCtrlGroupGroup2Active
                INTEGER,
            iqsyn22EmbCtrlGroupGroup3Active
                INTEGER,
            iqsyn22EmbCtrlGroupGroup4Active
                INTEGER,
            iqsyn22EmbCtrlChannelPair1LActive
                INTEGER,
            iqsyn22EmbCtrlChannelPair1RActive
                INTEGER,
            iqsyn22EmbCtrlChannelPair2LActive
                INTEGER,
            iqsyn22EmbCtrlChannelPair2RActive
                INTEGER,
            iqsyn22EmbCtrlChannelPair3LActive
                INTEGER,
            iqsyn22EmbCtrlChannelPair3RActive
                INTEGER,
            iqsyn22EmbCtrlChannelPair4LActive
                INTEGER,
            iqsyn22EmbCtrlChannelPair4RActive
                INTEGER,
            iqsyn22EmbCtrlChannelPair5LActive
                INTEGER,
            iqsyn22EmbCtrlChannelPair5RActive
                INTEGER,
            iqsyn22EmbCtrlChannelPair6LActive
                INTEGER,
            iqsyn22EmbCtrlChannelPair6RActive
                INTEGER,
            iqsyn22EmbCtrlChannelPair7LActive
                INTEGER,
            iqsyn22EmbCtrlChannelPair7RActive
                INTEGER,
            iqsyn22EmbCtrlChannelPair8LActive
                INTEGER,
            iqsyn22EmbCtrlChannelPair8RActive
                INTEGER,
            iqsyn22AudioEmbCtrlEmbedderPriority
                INTEGER,
            iqsyn22EmbGainEmbedPair1Embed1MuteL
                INTEGER,
            iqsyn22EmbGainEmbedPair1Embed1MuteR
                INTEGER,
            iqsyn22EmbGainEmbedPair1Embed1LGain
                INTEGER,
            iqsyn22EmbGainEmbedPair1Embed1RGain
                INTEGER,
            iqsyn22EmbGainEmbedPair1Stereo
                INTEGER,
            iqsyn22EmbGainEmbedPair1Embed1InvertL
                INTEGER,
            iqsyn22EmbGainEmbedPair1Embed1InvertR
                INTEGER,
            iqsyn22EmbGainEmbedPair1Embed1LClip
                RollCallString,
            iqsyn22EmbGainEmbedPair1Embed1RClip
                RollCallString,
            iqsyn22EmbGainEmbedPair2Embed2MuteL
                INTEGER,
            iqsyn22EmbGainEmbedPair2Embed2MuteR
                INTEGER,
            iqsyn22EmbGainEmbedPair2Embed2LGain
                INTEGER,
            iqsyn22EmbGainEmbedPair2Embed2RGain
                INTEGER,
            iqsyn22EmbGainEmbedPair2Stereo
                INTEGER,
            iqsyn22EmbGainEmbedPair2Embed2InvertL
                INTEGER,
            iqsyn22EmbGainEmbedPair2Embed2InvertR
                INTEGER,
            iqsyn22EmbGainEmbedPair2Embed2LClip
                RollCallString,
            iqsyn22EmbGainEmbedPair2Embed2RClip
                RollCallString,
            iqsyn22EmbGainEmbedPair3Embed3MuteL
                INTEGER,
            iqsyn22EmbGainEmbedPair3Embed3MuteR
                INTEGER,
            iqsyn22EmbGainEmbedPair3Embed3LGain
                INTEGER,
            iqsyn22EmbGainEmbedPair3Embed3RGain
                INTEGER,
            iqsyn22EmbGainEmbedPair3Stereo
                INTEGER,
            iqsyn22EmbGainEmbedPair3Embed3InvertL
                INTEGER,
            iqsyn22EmbGainEmbedPair3Embed3InvertR
                INTEGER,
            iqsyn22EmbGainEmbedPair3Embed3LClip
                RollCallString,
            iqsyn22EmbGainEmbedPair3Embed3RClip
                RollCallString,
            iqsyn22EmbGainEmbedPair4Embed4MuteL
                INTEGER,
            iqsyn22EmbGainEmbedPair4Embed4MuteR
                INTEGER,
            iqsyn22EmbGainEmbedPair4Embed4LGain
                INTEGER,
            iqsyn22EmbGainEmbedPair4Embed4RGain
                INTEGER,
            iqsyn22EmbGainEmbedPair4Stereo
                INTEGER,
            iqsyn22EmbGainEmbedPair4Embed4InvertL
                INTEGER,
            iqsyn22EmbGainEmbedPair4Embed4InvertR
                INTEGER,
            iqsyn22EmbGainEmbedPair4Embed4LClip
                RollCallString,
            iqsyn22EmbGainEmbedPair4Embed4RClip
                RollCallString,
            iqsyn22EmbGainEmbedPair5Embed5MuteL
                INTEGER,
            iqsyn22EmbGainEmbedPair5Embed5MuteR
                INTEGER,
            iqsyn22EmbGainEmbedPair5Embed5LGain
                INTEGER,
            iqsyn22EmbGainEmbedPair5Embed5RGain
                INTEGER,
            iqsyn22EmbGainEmbedPair5Stereo
                INTEGER,
            iqsyn22EmbGainEmbedPair5Embed5InvertL
                INTEGER,
            iqsyn22EmbGainEmbedPair5Embed5InvertR
                INTEGER,
            iqsyn22EmbGainEmbedPair5Embed5LClip
                RollCallString,
            iqsyn22EmbGainEmbedPair5Embed5RClip
                RollCallString,
            iqsyn22EmbGainEmbedPair6Embed6MuteL
                INTEGER,
            iqsyn22EmbGainEmbedPair6Embed6MuteR
                INTEGER,
            iqsyn22EmbGainEmbedPair6Embed6LGain
                INTEGER,
            iqsyn22EmbGainEmbedPair6Embed6RGain
                INTEGER,
            iqsyn22EmbGainEmbedPair6Stereo
                INTEGER,
            iqsyn22EmbGainEmbedPair6Embed6InvertL
                INTEGER,
            iqsyn22EmbGainEmbedPair6Embed6InvertR
                INTEGER,
            iqsyn22EmbGainEmbedPair6Embed6LClip
                RollCallString,
            iqsyn22EmbGainEmbedPair6Embed6RClip
                RollCallString,
            iqsyn22EmbGainEmbedPair7Embed7MuteL
                INTEGER,
            iqsyn22EmbGainEmbedPair7Embed7MuteR
                INTEGER,
            iqsyn22EmbGainEmbedPair7Embed7LGain
                INTEGER,
            iqsyn22EmbGainEmbedPair7Embed7RGain
                INTEGER,
            iqsyn22EmbGainEmbedPair7Stereo
                INTEGER,
            iqsyn22EmbGainEmbedPair7Embed7InvertL
                INTEGER,
            iqsyn22EmbGainEmbedPair7Embed7InvertR
                INTEGER,
            iqsyn22EmbGainEmbedPair7Embed7LClip
                RollCallString,
            iqsyn22EmbGainEmbedPair7Embed7RClip
                RollCallString,
            iqsyn22EmbGainEmbedPair8Embed8MuteL
                INTEGER,
            iqsyn22EmbGainEmbedPair8Embed8MuteR
                INTEGER,
            iqsyn22EmbGainEmbedPair8Embed8LGain
                INTEGER,
            iqsyn22EmbGainEmbedPair8Embed8RGain
                INTEGER,
            iqsyn22EmbGainEmbedPair8Stereo
                INTEGER,
            iqsyn22EmbGainEmbedPair8Embed8InvertL
                INTEGER,
            iqsyn22EmbGainEmbedPair8Embed8InvertR
                INTEGER,
            iqsyn22EmbGainEmbedPair8Embed8LClip
                RollCallString,
            iqsyn22EmbGainEmbedPair8Embed8RClip
                RollCallString,
            iqsyn22EmbOutEmbedPair1Left
                INTEGER,
            iqsyn22EmbOutEmbedPair1Right
                INTEGER,
            iqsyn22EmbOutEmbedPair1LinkLRSelection
                INTEGER,
            iqsyn22EmbOutEmbedPair2Left
                INTEGER,
            iqsyn22EmbOutEmbedPair2Right
                INTEGER,
            iqsyn22EmbOutEmbedPair2LinkLRSelection
                INTEGER,
            iqsyn22EmbOutEmbedPair3Left
                INTEGER,
            iqsyn22EmbOutEmbedPair3Right
                INTEGER,
            iqsyn22EmbOutEmbedPair3LinkLRSelection
                INTEGER,
            iqsyn22EmbOutEmbedPair4Left
                INTEGER,
            iqsyn22EmbOutEmbedPair4Right
                INTEGER,
            iqsyn22EmbOutEmbedPair4LinkLRSelection
                INTEGER,
            iqsyn22EmbOutEmbedPair5Left
                INTEGER,
            iqsyn22EmbOutEmbedPair5Right
                INTEGER,
            iqsyn22EmbOutEmbedPair5LinkLRSelection
                INTEGER,
            iqsyn22EmbOutEmbedPair6Left
                INTEGER,
            iqsyn22EmbOutEmbedPair6Right
                INTEGER,
            iqsyn22EmbOutEmbedPair6LinkLRSelection
                INTEGER,
            iqsyn22EmbOutEmbedPair7Left
                INTEGER,
            iqsyn22EmbOutEmbedPair7Right
                INTEGER,
            iqsyn22EmbOutEmbedPair7LinkLRSelection
                INTEGER,
            iqsyn22EmbOutEmbedPair8Left
                INTEGER,
            iqsyn22EmbOutEmbedPair8Right
                INTEGER,
            iqsyn22EmbOutEmbedPair8LinkLRSelection
                INTEGER,
            iqsyn22AudioEmbDataInput1
                INTEGER,
            iqsyn22AudioEmbDataInput2
                INTEGER,
            iqsyn22AudioEmbDataInput3
                INTEGER,
            iqsyn22AudioEmbDataInput4
                INTEGER,
            iqsyn22AudioEmbDataInput5
                INTEGER,
            iqsyn22AudioEmbDataInput6
                INTEGER,
            iqsyn22AudioEmbDataInput7
                INTEGER,
            iqsyn22AudioEmbDataInput8
                INTEGER,
            iqsyn22DisembedderNamesDisemb1L
                RollCallString,
            iqsyn22DisembedderNamesDisemb1R
                RollCallString,
            iqsyn22DisembedderNamesDisemb2L
                RollCallString,
            iqsyn22DisembedderNamesDisemb2R
                RollCallString,
            iqsyn22DisembedderNamesDisemb3L
                RollCallString,
            iqsyn22DisembedderNamesDisemb3R
                RollCallString,
            iqsyn22DisembedderNamesDisemb4L
                RollCallString,
            iqsyn22DisembedderNamesDisemb4R
                RollCallString,
            iqsyn22DisembedderNamesDisemb5L
                RollCallString,
            iqsyn22DisembedderNamesDisemb5R
                RollCallString,
            iqsyn22DisembedderNamesDisemb6L
                RollCallString,
            iqsyn22DisembedderNamesDisemb6R
                RollCallString,
            iqsyn22DisembedderNamesDisemb7L
                RollCallString,
            iqsyn22DisembedderNamesDisemb7R
                RollCallString,
            iqsyn22DisembedderNamesDisemb8L
                RollCallString,
            iqsyn22DisembedderNamesDisemb8R
                RollCallString,
            iqsyn22DisembedderNamesEmbeddedOPEmbed1L
                RollCallString,
            iqsyn22DisembedderNamesEmbeddedOPEmbed1R
                RollCallString,
            iqsyn22DisembedderNamesEmbeddedOPEmbed2L
                RollCallString,
            iqsyn22DisembedderNamesEmbeddedOPEmbed2R
                RollCallString,
            iqsyn22DisembedderNamesEmbeddedOPEmbed3L
                RollCallString,
            iqsyn22DisembedderNamesEmbeddedOPEmbed3R
                RollCallString,
            iqsyn22DisembedderNamesEmbeddedOPEmbed4L
                RollCallString,
            iqsyn22DisembedderNamesEmbeddedOPEmbed4R
                RollCallString,
            iqsyn22DisembedderNamesEmbeddedOPEmbed5L
                RollCallString,
            iqsyn22DisembedderNamesEmbeddedOPEmbed5R
                RollCallString,
            iqsyn22DisembedderNamesEmbeddedOPEmbed6L
                RollCallString,
            iqsyn22DisembedderNamesEmbeddedOPEmbed6R
                RollCallString,
            iqsyn22DisembedderNamesEmbeddedOPEmbed7L
                RollCallString,
            iqsyn22DisembedderNamesEmbeddedOPEmbed7R
                RollCallString,
            iqsyn22DisembedderNamesEmbeddedOPEmbed8L
                RollCallString,
            iqsyn22DisembedderNamesEmbeddedOPEmbed8R
                RollCallString,
            iqsyn22DisembedderNamesIPNamesStereoDisemb1
                INTEGER,
            iqsyn22DisembedderNamesIPNamesStereoDisemb2
                INTEGER,
            iqsyn22DisembedderNamesIPNamesStereoDisemb3
                INTEGER,
            iqsyn22DisembedderNamesIPNamesStereoDisemb4
                INTEGER,
            iqsyn22DisembedderNamesIPNamesStereoDisemb5
                INTEGER,
            iqsyn22DisembedderNamesIPNamesStereoDisemb6
                INTEGER,
            iqsyn22DisembedderNamesIPNamesStereoDisemb7
                INTEGER,
            iqsyn22DisembedderNamesIPNamesStereoDisemb8
                INTEGER,
            iqsyn22DisembedderNamesOPNamesStereoEmbed1
                INTEGER,
            iqsyn22DisembedderNamesOPNamesStereoEmbed2
                INTEGER,
            iqsyn22DisembedderNamesOPNamesStereoEmbed3
                INTEGER,
            iqsyn22DisembedderNamesOPNamesStereoEmbed4
                INTEGER,
            iqsyn22DisembedderNamesOPNamesStereoEmbed5
                INTEGER,
            iqsyn22DisembedderNamesOPNamesStereoEmbed6
                INTEGER,
            iqsyn22DisembedderNamesOPNamesStereoEmbed7
                INTEGER,
            iqsyn22DisembedderNamesOPNamesStereoEmbed8
                INTEGER,
            iqsyn22NamesMixNamesMix1
                RollCallString,
            iqsyn22NamesMixNamesMix2
                RollCallString,
            iqsyn22NamesMixNamesMix3
                RollCallString,
            iqsyn22NamesMixNamesMix4
                RollCallString,
            iqsyn22Mix1Mix1RoutingSource1
                INTEGER,
            iqsyn22Mix1Mix1RoutingInvert1
                INTEGER,
            iqsyn22Mix1Mix1RoutingSource2
                INTEGER,
            iqsyn22Mix1Mix1RoutingInvert2
                INTEGER,
            iqsyn22Mix1Mix1RoutingSource3
                INTEGER,
            iqsyn22Mix1Mix1RoutingInvert3
                INTEGER,
            iqsyn22Mix1Mix1RoutingSource4
                INTEGER,
            iqsyn22Mix1Mix1RoutingInvert4
                INTEGER,
            iqsyn22Mix1Mix1GainGain1
                INTEGER,
            iqsyn22Mix1Mix1GainMute1
                INTEGER,
            iqsyn22Mix1Mix1GainGain2
                INTEGER,
            iqsyn22Mix1Mix1GainMute2
                INTEGER,
            iqsyn22Mix1Mix1GainGain3
                INTEGER,
            iqsyn22Mix1Mix1GainMute3
                INTEGER,
            iqsyn22Mix1Mix1GainGain4
                INTEGER,
            iqsyn22Mix1Mix1GainMute4
                INTEGER,
            iqsyn22Mix1Mix1GainInp1Clip
                RollCallString,
            iqsyn22Mix1Mix1GainInp2Clip
                RollCallString,
            iqsyn22Mix1Mix1GainInp3Clip
                RollCallString,
            iqsyn22Mix1Mix1GainInp4Clip
                RollCallString,
            iqsyn22Mix1Mix1GainOPClip
                RollCallString,
            iqsyn22Mix2Mix2RoutingSource1
                INTEGER,
            iqsyn22Mix2Mix2RoutingInvert1
                INTEGER,
            iqsyn22Mix2Mix2RoutingSource2
                INTEGER,
            iqsyn22Mix2Mix2RoutingInvert2
                INTEGER,
            iqsyn22Mix2Mix2RoutingSource3
                INTEGER,
            iqsyn22Mix2Mix2RoutingInvert3
                INTEGER,
            iqsyn22Mix2Mix2RoutingSource4
                INTEGER,
            iqsyn22Mix2Mix2RoutingInvert4
                INTEGER,
            iqsyn22Mix2Mix2GainGain1
                INTEGER,
            iqsyn22Mix2Mix2GainMute1
                INTEGER,
            iqsyn22Mix2Mix2GainGain2
                INTEGER,
            iqsyn22Mix2Mix2GainMute2
                INTEGER,
            iqsyn22Mix2Mix2GainGain3
                INTEGER,
            iqsyn22Mix2Mix2GainMute3
                INTEGER,
            iqsyn22Mix2Mix2GainGain4
                INTEGER,
            iqsyn22Mix2Mix2GainMute4
                INTEGER,
            iqsyn22Mix2Mix2GainInp1Clip
                RollCallString,
            iqsyn22Mix2Mix2GainInp2Clip
                RollCallString,
            iqsyn22Mix2Mix2GainInp3Clip
                RollCallString,
            iqsyn22Mix2Mix2GainInp4Clip
                RollCallString,
            iqsyn22Mix2Mix2GainOPClip
                RollCallString,
            iqsyn22Mix3Mix3RoutingSource1
                INTEGER,
            iqsyn22Mix3Mix3RoutingInvert1
                INTEGER,
            iqsyn22Mix3Mix3RoutingSource2
                INTEGER,
            iqsyn22Mix3Mix3RoutingInvert2
                INTEGER,
            iqsyn22Mix3Mix3RoutingSource3
                INTEGER,
            iqsyn22Mix3Mix3RoutingInvert3
                INTEGER,
            iqsyn22Mix3Mix3RoutingSource4
                INTEGER,
            iqsyn22Mix3Mix3RoutingInvert4
                INTEGER,
            iqsyn22Mix3Mix3GainGain1
                INTEGER,
            iqsyn22Mix3Mix3GainMute1
                INTEGER,
            iqsyn22Mix3Mix3GainGain2
                INTEGER,
            iqsyn22Mix3Mix3GainMute2
                INTEGER,
            iqsyn22Mix3Mix3GainGain3
                INTEGER,
            iqsyn22Mix3Mix3GainMute3
                INTEGER,
            iqsyn22Mix3Mix3GainGain4
                INTEGER,
            iqsyn22Mix3Mix3GainMute4
                INTEGER,
            iqsyn22Mix3Mix3GainInp1Clip
                RollCallString,
            iqsyn22Mix3Mix3GainInp2Clip
                RollCallString,
            iqsyn22Mix3Mix3GainInp3Clip
                RollCallString,
            iqsyn22Mix3Mix3GainInp4Clip
                RollCallString,
            iqsyn22Mix3Mix3GainOPClip
                RollCallString,
            iqsyn22Mix4Mix4RoutingSource1
                INTEGER,
            iqsyn22Mix4Mix4RoutingInvert1
                INTEGER,
            iqsyn22Mix4Mix4RoutingSource2
                INTEGER,
            iqsyn22Mix4Mix4RoutingInvert2
                INTEGER,
            iqsyn22Mix4Mix4RoutingSource3
                INTEGER,
            iqsyn22Mix4Mix4RoutingInvert3
                INTEGER,
            iqsyn22Mix4Mix4RoutingSource4
                INTEGER,
            iqsyn22Mix4Mix4RoutingInvert4
                INTEGER,
            iqsyn22Mix4Mix4GainGain1
                INTEGER,
            iqsyn22Mix4Mix4GainMute1
                INTEGER,
            iqsyn22Mix4Mix4GainGain2
                INTEGER,
            iqsyn22Mix4Mix4GainMute2
                INTEGER,
            iqsyn22Mix4Mix4GainGain3
                INTEGER,
            iqsyn22Mix4Mix4GainMute3
                INTEGER,
            iqsyn22Mix4Mix4GainGain4
                INTEGER,
            iqsyn22Mix4Mix4GainMute4
                INTEGER,
            iqsyn22Mix4Mix4GainInp1Clip
                RollCallString,
            iqsyn22Mix4Mix4GainInp2Clip
                RollCallString,
            iqsyn22Mix4Mix4GainInp3Clip
                RollCallString,
            iqsyn22Mix4Mix4GainInp4Clip
                RollCallString,
            iqsyn22Mix4Mix4GainOPClip
                RollCallString,
            iqsyn22AudioDolbyETimingSelAudioPair
                INTEGER,
            iqsyn22AudioDolbyETimingRelativeTiming
                RollCallString,
            iqsyn22AudioDolbyETimingStatus
                RollCallString,
            iqsyn22AudioDolbyETimingError
                RollCallString,
            iqsyn22DolbyETimingDolbyELineStandard
                INTEGER,
            iqsyn22DolbyETimingDolbyELineAutoLineNo
                INTEGER,
            iqsyn22DolbyELineUserDolbyELinePair1
                INTEGER,
            iqsyn22DolbyELineUserDolbyELinePair2
                INTEGER,
            iqsyn22DolbyELineUserDolbyELinePair3
                INTEGER,
            iqsyn22DolbyELineUserDolbyELinePair4
                INTEGER,
            iqsyn22DolbyELineUserDolbyELinePair5
                INTEGER,
            iqsyn22DolbyELineUserDolbyELinePair6
                INTEGER,
            iqsyn22DolbyELineUserDolbyELinePair7
                INTEGER,
            iqsyn22DolbyELineUserDolbyELinePair8
                INTEGER,
            iqsyn22DolbyETimingDolbyELineSmoothCapRange
                INTEGER,
            iqsyn22GenlockDelayMode
                INTEGER,
            iqsyn22GenlockRefTimeDelayFrames
                INTEGER,
            iqsyn22GenlockRefTimeVerticalTiming
                INTEGER,
            iqsyn22GenlockRefTimeHorizontalTiming
                INTEGER,
            iqsyn22GenlockSetDelayDelayms
                INTEGER,
            iqsyn22GenlockRefTimeCurrentDelay
                RollCallString,
            iqsyn22GenlockSyncAmplitude
                RollCallString,
            iqsyn22GenlockUseEmbDelayFback
                INTEGER,
            iqsyn22GenlockSampleNumber
                RollCallString,
            iqsyn22GenlockLineNumber
                RollCallString,
            iqsyn22BackupEnable
                INTEGER,
            iqsyn22BackupORInput1State
                RollCallString,
            iqsyn22BackupORInput2State
                RollCallString,
            iqsyn22BackupRevertDelay
                INTEGER,
            iqsyn22BackupPriority
                INTEGER,
            iqsyn22BackupQualifyCRCErr
                INTEGER,
            iqsyn22BackupQualifyANCErr
                INTEGER,
            iqsyn22BackupInput1SelStatInp1OK
                RollCallString,
            iqsyn22BackupInput1SelStatInp2FAIL
                RollCallString,
            iqsyn22BackupInput1SelStatInp2Err
                RollCallString,
            iqsyn22BackupInput1SelStatAUDFail2
                RollCallString,
            iqsyn22BackupInput1SelStatStd2
                RollCallString,
            iqsyn22BackupInput1SelStatGPI1
                RollCallString,
            iqsyn22BackupInput1SelStatGPI2
                RollCallString,
            iqsyn22BackupInput1SelEnblInp1OK
                INTEGER,
            iqsyn22BackupInput1SelEnblInp2FAIL
                INTEGER,
            iqsyn22BackupInput1SelEnblInp2Err
                INTEGER,
            iqsyn22BackupInput1SelEnblAudInp2Err
                INTEGER,
            iqsyn22BackupInput1SelEnblStdInp2
                INTEGER,
            iqsyn22BackupInput1SelEnblGPI1
                INTEGER,
            iqsyn22BackupInput1SelEnblGPI2
                INTEGER,
            iqsyn22BackupInput1SelDlyInp1OK
                INTEGER,
            iqsyn22BackupInput1SelDlyInp2FAIL
                INTEGER,
            iqsyn22BackupInput1SelDlyInp2Err
                INTEGER,
            iqsyn22BackupInput1SelDlyGPI1
                INTEGER,
            iqsyn22BackupInput1SelDlyGPI2
                INTEGER,
            iqsyn22BackupInput1SelDlyAud2FAIL
                INTEGER,
            iqsyn22BackupInput1SelDlyStd2
                INTEGER,
            iqsyn22BackupInput1SelGPI1State
                INTEGER,
            iqsyn22BackupInput1SelGPI2State
                INTEGER,
            iqsyn22BackupInput1SelInp12AudFailG1C1
                INTEGER,
            iqsyn22BackupInput1SelInp12AudFailG1C2
                INTEGER,
            iqsyn22BackupInput1SelInp12AudFailG2C1
                INTEGER,
            iqsyn22BackupInput1SelInp12AudFailG2C2
                INTEGER,
            iqsyn22BackupInput1SelInp12AudFailG3C1
                INTEGER,
            iqsyn22BackupInput1SelInp12AudFailG3C2
                INTEGER,
            iqsyn22BackupInput1SelInp12AudFailG4C1
                INTEGER,
            iqsyn22BackupInput1SelInp12AudFailG4C2
                INTEGER,
            iqsyn22BackupInput1SelInp12AudFailLockGrp
                INTEGER,
            iqsyn22BackupInput1SelSelAll
                INTEGER,
            iqsyn22BackupInput1SelSelNone
                INTEGER,
            iqsyn22BackupInput2SelStatInp2OK
                RollCallString,
            iqsyn22BackupInput2SelStatInp1FAIL
                RollCallString,
            iqsyn22BackupInput2SelStatInp1Err
                RollCallString,
            iqsyn22BackupInput2SelStatAUDFail1
                RollCallString,
            iqsyn22BackupInput2SelStatStd1
                RollCallString,
            iqsyn22BackupInput2SelStatGPI1
                RollCallString,
            iqsyn22BackupInput2SelStatGPI2
                RollCallString,
            iqsyn22BackupInput2SelEnblInp2OK
                INTEGER,
            iqsyn22BackupInput2SelEnblInp1FAIL
                INTEGER,
            iqsyn22BackupInput2SelEnblInp1Err
                INTEGER,
            iqsyn22BackupInput2SelEnblGPI1
                INTEGER,
            iqsyn22BackupInput2SelEnblGPI2
                INTEGER,
            iqsyn22BackupInput2SelEnblAudInp1Err
                INTEGER,
            iqsyn22BackupInput2SelEnblStdInp1
                INTEGER,
            iqsyn22BackupInput2SelDlyInp2OK
                INTEGER,
            iqsyn22BackupInput2SelDlyInp1FAIL
                INTEGER,
            iqsyn22BackupInput2SelDlyInp1Err
                INTEGER,
            iqsyn22BackupInput2SelDlyAud2FAIL
                INTEGER,
            iqsyn22BackupInput2SelDlyStd1
                INTEGER,
            iqsyn22BackupInput2SelDlyGPI1
                INTEGER,
            iqsyn22BackupInput2SelDlyGPI2
                INTEGER,
            iqsyn22BackupInput2SelGPI1State
                INTEGER,
            iqsyn22BackupInput2SelGPI2State
                INTEGER,
            iqsyn22BackupInput2SelInp21AudFailG1C1
                INTEGER,
            iqsyn22BackupInput2SelInp21AudFailG1C2
                INTEGER,
            iqsyn22BackupInput2SelInp21AudFailG2C1
                INTEGER,
            iqsyn22BackupInput2SelInp21AudFailG2C2
                INTEGER,
            iqsyn22BackupInput2SelInp21AudFailG3C1
                INTEGER,
            iqsyn22BackupInput2SelInp21AudFailG3C2
                INTEGER,
            iqsyn22BackupInput2SelInp21AudFailG4C1
                INTEGER,
            iqsyn22BackupInput2SelInp21AudFailG4C2
                INTEGER,
            iqsyn22BackupInput2SelInp21AudFailLockGrp
                INTEGER,
            iqsyn22BackupInput2SelSelAll
                INTEGER,
            iqsyn22BackupInput2SelSelNone
                INTEGER,
            iqsyn22UtilsPatternsPatternEnable
                INTEGER,
            iqsyn22UtilsPatternsScrollPattern
                INTEGER,
            iqsyn22UtilsPatternsPatternType
                INTEGER,
            iqsyn22UtilsANCblankonMismat
                INTEGER,
            iqsyn22UtilsFreezeForceFreeze
                INTEGER,
            iqsyn22UtilsFreezeFreezeType
                INTEGER,
            iqsyn22UtilsMonochrome
                INTEGER,
            iqsyn22UtilsMonochromeMonochromeType
                INTEGER,
            iqsyn22UtilsHANCVBIBlankingANCMode
                INTEGER,
            iqsyn22UtilsHANCVBIBlankingStandard
                INTEGER,
            iqsyn22UtilsHANCVBIBlankingBlankAll
                INTEGER,
            iqsyn22UtilsHANCVBIBlankingPassAll
                INTEGER,
            iqsyn22UtilsHANCVBIBlankingBlank1
                INTEGER,
            iqsyn22UtilsHANCVBIBlankingBlank2
                INTEGER,
            iqsyn22UtilsHANCVBIBlankingBlank3
                INTEGER,
            iqsyn22UtilsHANCVBIBlankingBlank4
                INTEGER,
            iqsyn22UtilsHANCVBIBlankingBlank5
                INTEGER,
            iqsyn22UtilsHANCVBIBlankingBlank6
                INTEGER,
            iqsyn22UtilsHANCVBIBlankingBlank7
                INTEGER,
            iqsyn22UtilsHANCVBIBlankingBlank8
                INTEGER,
            iqsyn22UtilsHANCVBIBlankingBlank9
                INTEGER,
            iqsyn22UtilsHANCVBIBlankingBlank10
                INTEGER,
            iqsyn22UtilsHANCVBIBlankingBlank11
                INTEGER,
            iqsyn22UtilsHANCVBIBlankingBlank12
                INTEGER,
            iqsyn22UtilsHANCVBIBlankingBlank13
                INTEGER,
            iqsyn22UtilsHANCVBIBlankingBlank14
                INTEGER,
            iqsyn22UtilsHANCVBIBlankingBlank15
                INTEGER,
            iqsyn22UtilsHANCVBIBlankingBlank16
                INTEGER,
            iqsyn22UtilsHANCVBIBlankingBlank17
                INTEGER,
            iqsyn22UtilsHANCVBIBlankingBlank18
                INTEGER,
            iqsyn22UtilsHANCVBIBlankingBlank19
                INTEGER,
            iqsyn22UtilsHANCVBIBlankingBlank20
                INTEGER,
            iqsyn22UtilsHANCVBIBlankingBlank21
                INTEGER,
            iqsyn22UtilsHANCVBIBlankingBlank22
                INTEGER,
            iqsyn22UtilsHANCVBIBlankingBlank23
                INTEGER,
            iqsyn22UtilsHANCVBIBlankingBlank24
                INTEGER,
            iqsyn22UtilsHANCVBIBlankingBlank25
                INTEGER,
            iqsyn22UtilsHANCVBIBlankingBlank26
                INTEGER,
            iqsyn22UtilsHANCVBIBlankingBlank27
                INTEGER,
            iqsyn22UtilsHANCVBIBlankingBlank28
                INTEGER,
            iqsyn22UtilsHANCVBIBlankingBlank29
                INTEGER,
            iqsyn22UtilsHANCVBIBlankingBlank30
                INTEGER,
            iqsyn22UtilsHANCVBIBlankingBlank31
                INTEGER,
            iqsyn22UtilsHANCVBIBlankingBlank32
                INTEGER,
            iqsyn22UtilsHANCVBIBlankingBlank33
                INTEGER,
            iqsyn22UtilsHANCVBIBlankingBlank34
                INTEGER,
            iqsyn22UtilsUserCaptionsEnable
                INTEGER,
            iqsyn22UtilsUserCaptionsText
                RollCallString,
            iqsyn22UtilsUserCaptionsXPos
                INTEGER,
            iqsyn22UtilsUserCaptionsYPos
                INTEGER,
            iqsyn22UtilsUserCaptionsXSize
                INTEGER,
            iqsyn22UtilsUserCaptionsYSize
                INTEGER,
            iqsyn22UtilsSmpte2016Enable
                INTEGER,
            iqsyn22UtilsSmpte2016EnableUseAfdLine
                INTEGER,
            iqsyn22UtilsSmpte2016Line1ReadNum
                RollCallString,
            iqsyn22UtilsSmpte2016Line1ReadAFD
                RollCallString,
            iqsyn22UtilsSmpte2016Line1ReadAR
                RollCallString,
            iqsyn22UtilsSmpte2016Line2ReadNum
                RollCallString,
            iqsyn22UtilsSmpte2016Line2ReadAFD
                RollCallString,
            iqsyn22UtilsSmpte2016Line2ReadAR
                RollCallString,
            iqsyn22UtilsSmpte2016Line1Inuse
                RollCallString,
            iqsyn22UtilsSmpte2016Line1WriteAFD
                RollCallString,
            iqsyn22UtilsSmpte2016Line2Inuse
                RollCallString,
            iqsyn22UtilsSmpte2016Line2WriteAFD
                RollCallString,
            iqsyn22UtilsSmpte2016Line1WriteAR
                RollCallString,
            iqsyn22UtilsSmpte2016Line2WriteAR
                RollCallString,
            iqsyn22UtilsSmpte2016Line1WriteNum
                INTEGER,
            iqsyn22UtilsSmpte2016Line2WriteNum
                INTEGER,
            iqsyn22UtilsSmpte201643Mapping0
                INTEGER,
            iqsyn22UtilsSmpte201643Mapping1
                INTEGER,
            iqsyn22UtilsSmpte201643Mapping2
                INTEGER,
            iqsyn22UtilsSmpte201643Mapping3
                INTEGER,
            iqsyn22UtilsSmpte201643Mapping4
                INTEGER,
            iqsyn22UtilsSmpte201643Mapping5
                INTEGER,
            iqsyn22UtilsSmpte201643Mapping6
                INTEGER,
            iqsyn22UtilsSmpte201643Mapping7
                INTEGER,
            iqsyn22UtilsSmpte201643Mapping8
                INTEGER,
            iqsyn22UtilsSmpte201643Mapping9
                INTEGER,
            iqsyn22UtilsSmpte201643Mapping10
                INTEGER,
            iqsyn22UtilsSmpte201643Mapping11
                INTEGER,
            iqsyn22UtilsSmpte201643Mapping12
                INTEGER,
            iqsyn22UtilsSmpte201643Mapping13
                INTEGER,
            iqsyn22UtilsSmpte201643Mapping14
                INTEGER,
            iqsyn22UtilsSmpte201643Mapping15
                INTEGER,
            iqsyn22UtilsSmpte201643Mapping16
                INTEGER,
            iqsyn22UtilsSmpte2016169Mapping0
                INTEGER,
            iqsyn22UtilsSmpte2016169Mapping1
                INTEGER,
            iqsyn22UtilsSmpte2016169Mapping2
                INTEGER,
            iqsyn22UtilsSmpte2016169Mapping3
                INTEGER,
            iqsyn22UtilsSmpte2016169Mapping4
                INTEGER,
            iqsyn22UtilsSmpte2016169Mapping5
                INTEGER,
            iqsyn22UtilsSmpte2016169Mapping6
                INTEGER,
            iqsyn22UtilsSmpte2016169Mapping7
                INTEGER,
            iqsyn22UtilsSmpte2016169Mapping8
                INTEGER,
            iqsyn22UtilsSmpte2016169Mapping9
                INTEGER,
            iqsyn22UtilsSmpte2016169Mapping10
                INTEGER,
            iqsyn22UtilsSmpte2016169Mapping11
                INTEGER,
            iqsyn22UtilsSmpte2016169Mapping12
                INTEGER,
            iqsyn22UtilsSmpte2016169Mapping13
                INTEGER,
            iqsyn22UtilsSmpte2016169Mapping14
                INTEGER,
            iqsyn22UtilsSmpte2016169Mapping15
                INTEGER,
            iqsyn22UtilsSmpte2016ReaderIndex
                INTEGER,
            iqsyn22UtilsSmpte2016WriterIndex
                INTEGER,
            iqsyn22UtilsSmpte2016PresetReader
                INTEGER,
            iqsyn22UtilsSmpte2016PresetDelete
                INTEGER,
            iqsyn22GPIGPI1GPIO1Mode
                INTEGER,
            iqsyn22GPIGPI1GPI1ipSelect
                INTEGER,
            iqsyn22GPIGPI1GPO1opSelect
                INTEGER,
            iqsyn22GPIGPI1InvertGPIO1
                INTEGER,
            iqsyn22GPIGPI2GPIO2Mode
                INTEGER,
            iqsyn22GPIGPI2GPI2ipSelect
                INTEGER,
            iqsyn22GPIGPI2GPO2opSelect
                INTEGER,
            iqsyn22GPIGPI2InvertGPIO2
                INTEGER,
            iqsyn22GPIGPIPWMDelayTimerTimerSource
                INTEGER,
            iqsyn22GPIGPIPWMDelayTimerActiveHigh
                INTEGER,
            iqsyn22MemoriesRecallMemory
                INTEGER,
            iqsyn22MemoriesSelMemory
                INTEGER,
            iqsyn22MemoriesSaveMemory
                INTEGER,
            iqsyn22MemoriesClearMemory
                INTEGER,
            iqsyn22MemoriesMemoryNameChangeName
                RollCallString,
            iqsyn22MemoriesLastUserMemory
                RollCallString,
            iqsyn22MemoriesMemoryName1
                RollCallString,
            iqsyn22MemoriesMemoryName2
                RollCallString,
            iqsyn22MemoriesMemoryName3
                RollCallString,
            iqsyn22MemoriesMemoryName4
                RollCallString,
            iqsyn22MemoriesMemoryName5
                RollCallString,
            iqsyn22MemoriesMemoryName6
                RollCallString,
            iqsyn22MemoriesMemoryName7
                RollCallString,
            iqsyn22MemoriesMemoryName8
                RollCallString,
            iqsyn22MemoriesMemoryName9
                RollCallString,
            iqsyn22MemoriesMemoryName10
                RollCallString,
            iqsyn22MemoriesMemoryName11
                RollCallString,
            iqsyn22MemoriesMemoryName12
                RollCallString,
            iqsyn22MemoriesMemoryName13
                RollCallString,
            iqsyn22MemoriesMemoryName14
                RollCallString,
            iqsyn22MemoriesMemoryName15
                RollCallString,
            iqsyn22MemoriesMemoryName16
                RollCallString,
            iqsyn22LoggingVideoInputLogInput1Type
                INTEGER,
            iqsyn22LoggingVideoInputInput1Type
                RollCallString,
            iqsyn22LoggingVideoInputLogInput1Status
                INTEGER,
            iqsyn22LoggingVideoInputInput1Status
                RollCallString,
            iqsyn22LoggingVideoInputLogInput1Std
                INTEGER,
            iqsyn22LoggingVideoInputInput1Std
                RollCallString,
            iqsyn22LoggingVideoInputLogInput1Errors
                INTEGER,
            iqsyn22LoggingVideoInputInput1Errors
                RollCallString,
            iqsyn22LoggingVideoInputLogInput1ErrSecs
                INTEGER,
            iqsyn22LoggingVideoInputInput1ErrSecs
                RollCallString,
            iqsyn22LoggingVideoInputLogInput1ANCErr
                INTEGER,
            iqsyn22LoggingVideoInputInput1ANCErrors
                RollCallString,
            iqsyn22LoggingVideoInputLogInput1ANCErrSecs
                INTEGER,
            iqsyn22LoggingVideoInputInput1ANCErrSecs
                RollCallString,
            iqsyn22LoggingVideoInputLogInput2Type
                INTEGER,
            iqsyn22LoggingVideoInputInput2Type
                RollCallString,
            iqsyn22LoggingVideoInputLogInput2Status
                INTEGER,
            iqsyn22LoggingVideoInputInput2Status
                RollCallString,
            iqsyn22LoggingVideoInputLogInput2Std
                INTEGER,
            iqsyn22LoggingVideoInputInput2Std
                RollCallString,
            iqsyn22LoggingVideoInputLogInput2Errors
                INTEGER,
            iqsyn22LoggingVideoInputInput2Errors
                RollCallString,
            iqsyn22LoggingVideoInputLogInput2ErrSecs
                INTEGER,
            iqsyn22LoggingVideoInputInput2ErrSecs
                RollCallString,
            iqsyn22LoggingVideoInputLogInput2ANCErr
                INTEGER,
            iqsyn22LoggingVideoInputInput2ANCErrors
                RollCallString,
            iqsyn22LoggingVideoInputLogInput2ANCErrSecs
                INTEGER,
            iqsyn22LoggingVideoInputInput2ANCErrSecs
                RollCallString,
            iqsyn22LoggingRefOutputLogOutputState
                INTEGER,
            iqsyn22LoggingRefOutputOutputState
                RollCallString,
            iqsyn22LoggingRefOutputLogOutputType
                INTEGER,
            iqsyn22LoggingRefOutputOutputType
                RollCallString,
            iqsyn22LoggingRefOutputLogOutputStandard
                INTEGER,
            iqsyn22LoggingRefOutputOutputStandard
                RollCallString,
            iqsyn22LoggingVideoOutLoggingLogoutputANCstate
                INTEGER,
            iqsyn22LoggingVideoOutLoggingOutputANCstate
                RollCallString,
            iqsyn22LoggingRefOutputLogOutputSource
                INTEGER,
            iqsyn22LoggingRefOutputOutputSource
                RollCallString,
            iqsyn22LoggingIn1AudStateLogInp1Emb1stat
                INTEGER,
            iqsyn22LoggingIn1AudStateInp1Emb1state
                RollCallString,
            iqsyn22LoggingIn1AudStateLogInp1Emb2stat
                INTEGER,
            iqsyn22LoggingIn1AudStateInp1Emb2state
                RollCallString,
            iqsyn22LoggingIn1AudStateLogInp1Emb3stat
                INTEGER,
            iqsyn22LoggingIn1AudStateInp1Emb3state
                RollCallString,
            iqsyn22LoggingIn1AudStateLogInp1Emb4stat
                INTEGER,
            iqsyn22LoggingIn1AudStateInp1Emb4state
                RollCallString,
            iqsyn22LoggingIn1AudStateLogInp1Emb5stat
                INTEGER,
            iqsyn22LoggingIn1AudStateInp1Emb5state
                RollCallString,
            iqsyn22LoggingIn1AudStateLogInp1Emb6stat
                INTEGER,
            iqsyn22LoggingIn1AudStateInp1Emb6state
                RollCallString,
            iqsyn22LoggingIn1AudStateLogInp1Emb7stat
                INTEGER,
            iqsyn22LoggingIn1AudStateInp1Emb7state
                RollCallString,
            iqsyn22LoggingIn1AudStateLogInp1Emb8stat
                INTEGER,
            iqsyn22LoggingIn1AudStateInp1Emb8state
                RollCallString,
            iqsyn22LoggingIn1AudTypeLogInp1Emb1type
                INTEGER,
            iqsyn22LoggingIn1AudTypeInp1Emb1type
                RollCallString,
            iqsyn22LoggingIn1AudTypeLogInp1Emb2type
                INTEGER,
            iqsyn22LoggingIn1AudTypeInp1Emb2type
                RollCallString,
            iqsyn22LoggingIn1AudTypeLogInp1Emb3type
                INTEGER,
            iqsyn22LoggingIn1AudTypeInp1Emb3type
                RollCallString,
            iqsyn22LoggingIn1AudTypeLogInp1Emb4type
                INTEGER,
            iqsyn22LoggingIn1AudTypeInp1Emb4type
                RollCallString,
            iqsyn22LoggingIn1AudTypeLogInp1Emb5type
                INTEGER,
            iqsyn22LoggingIn1AudTypeInp1Emb5type
                RollCallString,
            iqsyn22LoggingIn1AudTypeLogInp1Emb6type
                INTEGER,
            iqsyn22LoggingIn1AudTypeInp1Emb6type
                RollCallString,
            iqsyn22LoggingIn1AudTypeLogInp1Emb7type
                INTEGER,
            iqsyn22LoggingIn1AudTypeInp1Emb7type
                RollCallString,
            iqsyn22LoggingIn1AudTypeLogInp1Emb8type
                INTEGER,
            iqsyn22LoggingIn1AudTypeInp1Emb8type
                RollCallString,
            iqsyn22LoggingIn2AudStateLogInp2Emb1stat
                INTEGER,
            iqsyn22LoggingIn2AudStateInp2Emb1state
                RollCallString,
            iqsyn22LoggingIn2AudStateLogInp2Emb2stat
                INTEGER,
            iqsyn22LoggingIn2AudStateInp2Emb2state
                RollCallString,
            iqsyn22LoggingIn2AudStateLogInp2Emb3stat
                INTEGER,
            iqsyn22LoggingIn2AudStateInp2Emb3state
                RollCallString,
            iqsyn22LoggingIn2AudStateLogInp2Emb4stat
                INTEGER,
            iqsyn22LoggingIn2AudStateInp2Emb4state
                RollCallString,
            iqsyn22LoggingIn2AudStateLogInp2Emb5stat
                INTEGER,
            iqsyn22LoggingIn2AudStateInp2Emb5state
                RollCallString,
            iqsyn22LoggingIn2AudStateLogInp2Emb6stat
                INTEGER,
            iqsyn22LoggingIn2AudStateInp2Emb6state
                RollCallString,
            iqsyn22LoggingIn2AudStateLogInp2Emb7stat
                INTEGER,
            iqsyn22LoggingIn2AudStateInp2Emb7state
                RollCallString,
            iqsyn22LoggingIn2AudStateLogInp2Emb8stat
                INTEGER,
            iqsyn22LoggingIn2AudStateInp2Emb8state
                RollCallString,
            iqsyn22LoggingIn1AudTypeLogInp2Emb1type
                INTEGER,
            iqsyn22LoggingIn1AudTypeInp2Emb1type
                RollCallString,
            iqsyn22LoggingIn1AudTypeLogInp2Emb2type
                INTEGER,
            iqsyn22LoggingIn1AudTypeInp2Emb2type
                RollCallString,
            iqsyn22LoggingIn1AudTypeLogInp2Emb3type
                INTEGER,
            iqsyn22LoggingIn1AudTypeInp2Emb3type
                RollCallString,
            iqsyn22LoggingIn1AudTypeLogInp2Emb4type
                INTEGER,
            iqsyn22LoggingIn1AudTypeInp2Emb4type
                RollCallString,
            iqsyn22LoggingIn1AudTypeLogInp2Emb5type
                INTEGER,
            iqsyn22LoggingIn1AudTypeInp2Emb5type
                RollCallString,
            iqsyn22LoggingIn1AudTypeLogInp2Emb6type
                INTEGER,
            iqsyn22LoggingIn1AudTypeInp2Emb6type
                RollCallString,
            iqsyn22LoggingIn1AudTypeLogInp2Emb7type
                INTEGER,
            iqsyn22LoggingIn1AudTypeInp2Emb7type
                RollCallString,
            iqsyn22LoggingIn1AudTypeLogInp2Emb8type
                INTEGER,
            iqsyn22LoggingIn1AudTypeInp2Emb8type
                RollCallString,
            iqsyn22LoggingOPAudStateLogOutEmb1state
                INTEGER,
            iqsyn22LoggingOPAudStateOutEmb1state
                RollCallString,
            iqsyn22LoggingOPAudStateLogOutEmb2state
                INTEGER,
            iqsyn22LoggingOPAudStateOutEmb2state
                RollCallString,
            iqsyn22LoggingOPAudStateLogOutEmb3state
                INTEGER,
            iqsyn22LoggingOPAudStateOutEmb3state
                RollCallString,
            iqsyn22LoggingOPAudStateLogOutEmb4state
                INTEGER,
            iqsyn22LoggingOPAudStateOutEmb4state
                RollCallString,
            iqsyn22LoggingOPAudStateLogOutEmb5state
                INTEGER,
            iqsyn22LoggingOPAudStateOutEmb5state
                RollCallString,
            iqsyn22LoggingOPAudStateLogOutEmb6state
                INTEGER,
            iqsyn22LoggingOPAudStateOutEmb6state
                RollCallString,
            iqsyn22LoggingOPAudStateLogOutEmb7state
                INTEGER,
            iqsyn22LoggingOPAudStateOutEmb7state
                RollCallString,
            iqsyn22LoggingOPAudStateLogOutEmb8state
                INTEGER,
            iqsyn22LoggingOPAudStateOutEmb8state
                RollCallString,
            iqsyn22LoggingOPAudTypeLogOutEmb1type
                INTEGER,
            iqsyn22LoggingOPAudTypeOutEmb1type
                RollCallString,
            iqsyn22LoggingOPAudTypeLogOutEmb2type
                INTEGER,
            iqsyn22LoggingOPAudTypeOutEmb2type
                RollCallString,
            iqsyn22LoggingOPAudTypeLogOutEmb3type
                INTEGER,
            iqsyn22LoggingOPAudTypeOutEmb3type
                RollCallString,
            iqsyn22LoggingOPAudTypeLogOutEmb4type
                INTEGER,
            iqsyn22LoggingOPAudTypeOutEmb4type
                RollCallString,
            iqsyn22LoggingOPAudTypeLogOutEmb5type
                INTEGER,
            iqsyn22LoggingOPAudTypeOutEmb5type
                RollCallString,
            iqsyn22LoggingOPAudTypeLogOutEmb6type
                INTEGER,
            iqsyn22LoggingOPAudTypeOutEmb6type
                RollCallString,
            iqsyn22LoggingOPAudTypeLogOutEmb7type
                INTEGER,
            iqsyn22LoggingOPAudTypeOutEmb7type
                RollCallString,
            iqsyn22LoggingOPAudTypeLogOutEmb8type
                INTEGER,
            iqsyn22LoggingOPAudTypeOutEmb8type
                RollCallString,
            iqsyn22LoggingOPAudLevelLogOutEmb1LLev
                INTEGER,
            iqsyn22LoggingOPAudLevelOutEmb1LLevel
                RollCallString,
            iqsyn22LoggingOPAudLevelLogOutEmb1RLev
                INTEGER,
            iqsyn22LoggingOPAudLevelOutEmb1RLevel
                RollCallString,
            iqsyn22LoggingOPAudLevelLogOutEmb2LLev
                INTEGER,
            iqsyn22LoggingOPAudLevelOutEmb2LLevel
                RollCallString,
            iqsyn22LoggingOPAudLevelLogOutEmb2RLev
                INTEGER,
            iqsyn22LoggingOPAudLevelOutEmb2RLevel
                RollCallString,
            iqsyn22LoggingOPAudLevelLogOutEmb3LLev
                INTEGER,
            iqsyn22LoggingOPAudLevelOutEmb3LLevel
                RollCallString,
            iqsyn22LoggingOPAudLevelLogOutEmb3RLev
                INTEGER,
            iqsyn22LoggingOPAudLevelOutEmb3RLevel
                RollCallString,
            iqsyn22LoggingOPAudLevelLogOutEmb4LLev
                INTEGER,
            iqsyn22LoggingOPAudLevelOutEmb4LLevel
                RollCallString,
            iqsyn22LoggingOPAudLevelLogOutEmb4RLev
                INTEGER,
            iqsyn22LoggingOPAudLevelOutEmb4RLevel
                RollCallString,
            iqsyn22LoggingOPAudLevelLogOutEmb5LLev
                INTEGER,
            iqsyn22LoggingOPAudLevelOutEmb5LLevel
                RollCallString,
            iqsyn22LoggingOPAudLevelLogOutEmb5RLev
                INTEGER,
            iqsyn22LoggingOPAudLevelOutEmb5RLevel
                RollCallString,
            iqsyn22LoggingOPAudLevelLogOutEmb6LLev
                INTEGER,
            iqsyn22LoggingOPAudLevelOutEmb6LLevel
                RollCallString,
            iqsyn22LoggingOPAudLevelLogOutEmb6RLev
                INTEGER,
            iqsyn22LoggingOPAudLevelOutEmb6RLevel
                RollCallString,
            iqsyn22LoggingOPAudLevelLogOutEmb7LLev
                INTEGER,
            iqsyn22LoggingOPAudLevelOutEmb7LLevel
                RollCallString,
            iqsyn22LoggingOPAudLevelLogOutEmb7RLev
                INTEGER,
            iqsyn22LoggingOPAudLevelOutEmb7RLevel
                RollCallString,
            iqsyn22LoggingOPAudLevelLogOutEmb8LLev
                INTEGER,
            iqsyn22LoggingOPAudLevelOutEmb8LLevel
                RollCallString,
            iqsyn22LoggingOPAudLevelLogOutEmb8RLev
                INTEGER,
            iqsyn22LoggingOPAudLevelOutEmb8RLevel
                RollCallString,
            iqsyn22LoggingOPDolbyELoggingLogEmbDolbyE1
                INTEGER,
            iqsyn22LoggingOPDolbyELoggingEmbDolbyE1
                RollCallString,
            iqsyn22LoggingOPDolbyELoggingLogEmbDolbyE2
                INTEGER,
            iqsyn22LoggingOPDolbyELoggingEmbDolbyE2
                RollCallString,
            iqsyn22LoggingOPDolbyELoggingLogEmbDolbyE3
                INTEGER,
            iqsyn22LoggingOPDolbyELoggingEmbDolbyE3
                RollCallString,
            iqsyn22LoggingOPDolbyELoggingLogEmbDolbyE4
                INTEGER,
            iqsyn22LoggingOPDolbyELoggingEmbDolbyE4
                RollCallString,
            iqsyn22LoggingOPDolbyELoggingLogEmbDolbyE5
                INTEGER,
            iqsyn22LoggingOPDolbyELoggingEmbDolbyE5
                RollCallString,
            iqsyn22LoggingOPDolbyELoggingLogEmbDolbyE6
                INTEGER,
            iqsyn22LoggingOPDolbyELoggingEmbDolbyE6
                RollCallString,
            iqsyn22LoggingOPDolbyELoggingLogEmbDolbyE7
                INTEGER,
            iqsyn22LoggingOPDolbyELoggingEmbDolbyE7
                RollCallString,
            iqsyn22LoggingOPDolbyELoggingLogEmbDolbyE8
                INTEGER,
            iqsyn22LoggingOPDolbyELoggingEmbDolbyE8
                RollCallString,
            iqsyn22LoggingWideScreenLoggingLogInput1Aspect
                INTEGER,
            iqsyn22LoggingWideScreenLoggingInput1Aspect
                RollCallString,
            iqsyn22LoggingWideScreenLoggingLogInput1AFD
                INTEGER,
            iqsyn22LoggingWideScreenLoggingInput1AFD
                RollCallString,
            iqsyn22LoggingWideScreenLoggingLogInput2Aspect
                INTEGER,
            iqsyn22LoggingWideScreenLoggingInput2Aspect
                RollCallString,
            iqsyn22LoggingWideScreenLoggingLogInput2AFD
                INTEGER,
            iqsyn22LoggingWideScreenLoggingInput2AFD
                RollCallString,
            iqsyn22LoggingWideScreenLoggingLogOutputAFDEnable
                INTEGER,
            iqsyn22LoggingWideScreenLoggingOutputAFD
                RollCallString,
            iqsyn22LoggingWideScreenLoggingLogOutputAFDEnable
                INTEGER,
            iqsyn22LoggingWideScreenLoggingOutputAFD
                RollCallString,
            iqsyn22LoggingMiscLogSerialNo
                INTEGER,
            iqsyn22LoggingMiscSerialNo
                RollCallString,
            iqsyn22LoggingMiscLogOSVersion
                INTEGER,
            iqsyn22LoggingMiscOSVersion
                RollCallString,
            iqsyn22LoggingMiscLogBuildNo
                INTEGER,
            iqsyn22LoggingMiscBuildNo
                RollCallString,
            iqsyn22LoggingMiscLogHardwareVer
                INTEGER,
            iqsyn22LoggingMiscHardwareVer
                RollCallString,
            iqsyn22LoggingMiscLogFirmwareVer
                INTEGER,
            iqsyn22LoggingMiscFirmwareVer
                RollCallString,
            iqsyn22LoggingMiscLogUpTime
                INTEGER,
            iqsyn22LoggingMiscUpTime
                RollCallString,
            iqsyn22LoggingRefOutputLogReferenceType
                INTEGER,
            iqsyn22LoggingRefOutputReferenceType
                RollCallString,
            iqsyn22LoggingRefOutputLogReferenceState
                INTEGER,
            iqsyn22LoggingRefOutputReferenceState
                RollCallString,
            iqsyn22LoggingRefOutputLogReferenceStand
                INTEGER,
            iqsyn22LoggingRefOutputReferenceStandard
                RollCallString,
            iqsyn22RollCallRollTrackDisableAll
                INTEGER,
            iqsyn22RollCallRollTrackIndex
                INTEGER,
            iqsyn22RollCallRollTrackSource
                INTEGER,
            iqsyn22RollCallRollTrackAddress
                RollCallString,
            iqsyn22RollCallRollTrackCommand
                RollCallString,
            iqsyn22RollCallRollTrackStatus
                RollCallString,
            iqsyn22RollCallRollTrackSending
                RollCallString,
            iqsyn22SetupProduct
                RollCallString,
            iqsyn22SetupRelease
                RollCallString,
            iqsyn22SetupBuild
                RollCallString,
            iqsyn22SetupKOS
                RollCallString,
            iqsyn22SetupSerial
                RollCallString,
            iqsyn22SetupFirmware
                RollCallString,
            iqsyn22SetupPCB
                RollCallString,
            iqsyn22SetupFactoryDefault
                INTEGER,
            iqsyn22SetupRestart
                INTEGER,
            iqsyn22MemoriesMemorySave
                INTEGER,
            iqsyn22SetupDisplay
                INTEGER,
            iqsyn22SetupSerialNumber
                RollCallString,
            iqsyn22SetupBoardID
                INTEGER,
            iqsyn22SetupSaveID
                INTEGER,
            iqsyn22EngineerPassword
                RollCallString,
            iqsyn22EngineerShowEngineer
                INTEGER,
            iqsyn22EngineerPageUndoChanges
                INTEGER,
            iqsyn22EngineerShowEngineer2
                INTEGER,
            iqsyn22EngineerShowEngineer3
                INTEGER
        }

    iqsyn22SlotIndex OBJECT-TYPE
        SYNTAX            Unsigned32
        MAX-ACCESS        not-accessible
        STATUS            current
        DESCRIPTION
                "The unique Index value for each slot.  Its value
                ranges between 1 and the value of slotNumber."
        ::= { iqsyn22CmdEntry 99999 }


    iqsyn22InputIPSelect OBJECT-TYPE
        SYNTAX            INTEGER {
                            valInput1(1),
                            valInput2(2),
                            valInputAnalog(2)
                            }
        MAX-ACCESS        read-write
        STATUS            current
        DESCRIPTION
                "CMNT: - Select video input
                 TYPE: - RadiobuttonList
                 PAGE: - Input
                    I/P Select  cmdID= 32930
                    Input 1  value= 1
                    Input 2  value= 2
                    Input Analog  value= 2  "
        ::= { iqsyn22CmdEntry 32930 }


    iqsyn22InputIPLoss OBJECT-TYPE
        SYNTAX            INTEGER {
                            valNoInput(0),
                            valInOutStdMismatch(1)
                            }
        MAX-ACCESS        read-write
        STATUS            current
        DESCRIPTION
                "CMNT: - Input loss on standard mismatch enable
                 TYPE: - RadiobuttonList
                 PAGE: - Input
                    I/P Loss  cmdID= 33030
                    No Input  value= 0
                    In/Out Std.Mismatch  value= 1  "
        ::= { iqsyn22CmdEntry 33030 }


    iqsyn22InputValidStandardsAllValid OBJECT-TYPE
        SYNTAX            INTEGER { noAction(0),valAllValid(1) }
        MAX-ACCESS        read-write
        STATUS            current
        DESCRIPTION
                "CMNT: - All input standards valid
                 TYPE: - Button
                 PAGE: - Input
                    All Valid  cmdID= 32900
                    value= 1  "
        ::= { iqsyn22CmdEntry 32900 }


    iqsyn22InputValidStandardsAllInvalid OBJECT-TYPE
        SYNTAX            INTEGER { noAction(0),valAllInvalid(1) }
        MAX-ACCESS        read-write
        STATUS            current
        DESCRIPTION
                "CMNT: - NO input standards valid
                 TYPE: - Button
                 PAGE: - Input
                    AllInvalid  cmdID= 32901
                    value= 1  "
        ::= { iqsyn22CmdEntry 32901 }


    iqsyn22InputValidStandards108023sF OBJECT-TYPE
        SYNTAX            INTEGER { disable(0), enable(1)  }
        MAX-ACCESS        read-write
        STATUS            current
        DESCRIPTION
                "CMNT: - Select valid input standards
                 TYPE: - Checkbox
                 PAGE: - Input
                    1080/23sF  cmdID= 32916  "
        ::= { iqsyn22CmdEntry 32916 }


    iqsyn22InputValidStandards108023p OBJECT-TYPE
        SYNTAX            INTEGER { disable(0), enable(1)  }
        MAX-ACCESS        read-write
        STATUS            current
        DESCRIPTION
                "CMNT: - Select valid input standards
                 TYPE: - Checkbox
                 PAGE: - Input
                    1080/23p  cmdID= 32915  "
        ::= { iqsyn22CmdEntry 32915 }


    iqsyn22InputValidStandards108024sF OBJECT-TYPE
        SYNTAX            INTEGER { disable(0), enable(1)  }
        MAX-ACCESS        read-write
        STATUS            current
        DESCRIPTION
                "CMNT: - Select valid input standards
                 TYPE: - Checkbox
                 PAGE: - Input
                    1080/24sF  cmdID= 32917  "
        ::= { iqsyn22CmdEntry 32917 }


    iqsyn22InputValidStandards108024p OBJECT-TYPE
        SYNTAX            INTEGER { disable(0), enable(1)  }
        MAX-ACCESS        read-write
        STATUS            current
        DESCRIPTION
                "CMNT: - Select valid input standards
                 TYPE: - Checkbox
                 PAGE: - Input
                    1080/24p  cmdID= 32914  "
        ::= { iqsyn22CmdEntry 32914 }


    iqsyn22InputValidStandards108025i OBJECT-TYPE
        SYNTAX            INTEGER { disable(0), enable(1)  }
        MAX-ACCESS        read-write
        STATUS            current
        DESCRIPTION
                "CMNT: - Select valid input standards
                 TYPE: - Checkbox
                 PAGE: - Input
                    1080/25i  cmdID= 32910  "
        ::= { iqsyn22CmdEntry 32910 }


    iqsyn22InputValidStandards108025p OBJECT-TYPE
        SYNTAX            INTEGER { disable(0), enable(1)  }
        MAX-ACCESS        read-write
        STATUS            current
        DESCRIPTION
                "CMNT: - Select valid input standards
                 TYPE: - Checkbox
                 PAGE: - Input
                    1080/25p  cmdID= 32911  "
        ::= { iqsyn22CmdEntry 32911 }


    iqsyn22InputValidStandards103529i OBJECT-TYPE
        SYNTAX            INTEGER { disable(0), enable(1)  }
        MAX-ACCESS        read-write
        STATUS            current
        DESCRIPTION
                "CMNT: - Select valid input standards
                 TYPE: - Checkbox
                 PAGE: - Input
                    1035/29i  cmdID= 32921  "
        ::= { iqsyn22CmdEntry 32921 }


    iqsyn22InputValidStandards108029i OBJECT-TYPE
        SYNTAX            INTEGER { disable(0), enable(1)  }
        MAX-ACCESS        read-write
        STATUS            current
        DESCRIPTION
                "CMNT: - Select valid input standards
                 TYPE: - Checkbox
                 PAGE: - Input
                    1080/29i  cmdID= 32919  "
        ::= { iqsyn22CmdEntry 32919 }


    iqsyn22InputValidStandards108029p OBJECT-TYPE
        SYNTAX            INTEGER { disable(0), enable(1)  }
        MAX-ACCESS        read-write
        STATUS            current
        DESCRIPTION
                "CMNT: - Select valid input standards
                 TYPE: - Checkbox
                 PAGE: - Input
                    1080/29p  cmdID= 32918  "
        ::= { iqsyn22CmdEntry 32918 }


    iqsyn22InputValidStandards103530i OBJECT-TYPE
        SYNTAX            INTEGER { disable(0), enable(1)  }
        MAX-ACCESS        read-write
        STATUS            current
        DESCRIPTION
                "CMNT: - Select valid input standards
                 TYPE: - Checkbox
                 PAGE: - Input
                    1035/30i  cmdID= 32920  "
        ::= { iqsyn22CmdEntry 32920 }


    iqsyn22InputValidStandards108030i OBJECT-TYPE
        SYNTAX            INTEGER { disable(0), enable(1)  }
        MAX-ACCESS        read-write
        STATUS            current
        DESCRIPTION
                "CMNT: - Select valid input standards
                 TYPE: - Checkbox
                 PAGE: - Input
                    1080/30i  cmdID= 32912  "
        ::= { iqsyn22CmdEntry 32912 }


    iqsyn22InputValidStandards108030p OBJECT-TYPE
        SYNTAX            INTEGER { disable(0), enable(1)  }
        MAX-ACCESS        read-write
        STATUS            current
        DESCRIPTION
                "CMNT: - Select valid input standards
                 TYPE: - Checkbox
                 PAGE: - Input
                    1080/30p  cmdID= 32913  "
        ::= { iqsyn22CmdEntry 32913 }


    iqsyn22InputValidStandards72050p OBJECT-TYPE
        SYNTAX            INTEGER { disable(0), enable(1)  }
        MAX-ACCESS        read-write
        STATUS            current
        DESCRIPTION
                "CMNT: - Select valid input standards
                 TYPE: - Checkbox
                 PAGE: - Input
                    720/50p  cmdID= 32922  "
        ::= { iqsyn22CmdEntry 32922 }


    iqsyn22InputValidStandards72059p OBJECT-TYPE
        SYNTAX            INTEGER { disable(0), enable(1)  }
        MAX-ACCESS        read-write
        STATUS            current
        DESCRIPTION
                "CMNT: - Select valid input standards
                 TYPE: - Checkbox
                 PAGE: - Input
                    720/59p  cmdID= 32924  "
        ::= { iqsyn22CmdEntry 32924 }


    iqsyn22InputValidStandards72060p OBJECT-TYPE
        SYNTAX            INTEGER { disable(0), enable(1)  }
        MAX-ACCESS        read-write
        STATUS            current
        DESCRIPTION
                "CMNT: - Select valid input standards
                 TYPE: - Checkbox
                 PAGE: - Input
                    720/60p  cmdID= 32923  "
        ::= { iqsyn22CmdEntry 32923 }


    iqsyn22InputValidStandards62525i OBJECT-TYPE
        SYNTAX            INTEGER { disable(0), enable(1)  }
        MAX-ACCESS        read-write
        STATUS            current
        DESCRIPTION
                "CMNT: - Select valid input standards
                 TYPE: - Checkbox
                 PAGE: - Input
                    625/25i  cmdID= 32925  "
        ::= { iqsyn22CmdEntry 32925 }


    iqsyn22InputValidStandards52529i OBJECT-TYPE
        SYNTAX            INTEGER { disable(0), enable(1)  }
        MAX-ACCESS        read-write
        STATUS            current
        DESCRIPTION
                "CMNT: - Select valid input standards
                 TYPE: - Checkbox
                 PAGE: - Input
                    525/29i  cmdID= 32926  "
        ::= { iqsyn22CmdEntry 32926 }


    iqsyn22InputAgileVLock OBJECT-TYPE
        SYNTAX            INTEGER { disable(0), enable(1)  }
        MAX-ACCESS        read-write
        STATUS            current
        DESCRIPTION
                "CMNT: - Select Agile V-Lock for an input
                 TYPE: - Checkbox
                 PAGE: - Input
                    Agile V-Lock  cmdID= 32932  "
        ::= { iqsyn22CmdEntry 32932 }


    iqsyn22InputErrorsCRCErrs OBJECT-TYPE
        SYNTAX            RollCallString
        MAX-ACCESS        read-only
        STATUS            current
        DESCRIPTION
                "CMNT: - 
                 TYPE: - Display
                 PAGE: - Input
                    CRC Errs  cmdID= 33050  "
        ::= { iqsyn22CmdEntry 33050 }


    iqsyn22InputErrorsCRCErrSec OBJECT-TYPE
        SYNTAX            RollCallString
        MAX-ACCESS        read-only
        STATUS            current
        DESCRIPTION
                "CMNT: - 
                 TYPE: - Display
                 PAGE: - Input
                    CRC ErrSec  cmdID= 33051  "
        ::= { iqsyn22CmdEntry 33051 }


    iqsyn22InputErrorsANCErrs OBJECT-TYPE
        SYNTAX            RollCallString
        MAX-ACCESS        read-only
        STATUS            current
        DESCRIPTION
                "CMNT: - 
                 TYPE: - Display
                 PAGE: - Input
                    ANC Errs  cmdID= 33053  "
        ::= { iqsyn22CmdEntry 33053 }


    iqsyn22InputErrorsANCErrSec OBJECT-TYPE
        SYNTAX            RollCallString
        MAX-ACCESS        read-only
        STATUS            current
        DESCRIPTION
                "CMNT: - 
                 TYPE: - Display
                 PAGE: - Input
                    ANC ErrSec  cmdID= 33054  "
        ::= { iqsyn22CmdEntry 33054 }


    iqsyn22InputErrorsResetSec OBJECT-TYPE
        SYNTAX            RollCallString
        MAX-ACCESS        read-only
        STATUS            current
        DESCRIPTION
                "CMNT: - 
                 TYPE: - Display
                 PAGE: - Input
                    ResetSec  cmdID= 33055  "
        ::= { iqsyn22CmdEntry 33055 }


    iqsyn22InputErrorsErrorReset OBJECT-TYPE
        SYNTAX            INTEGER { noAction(0),valErrorReset(1) }
        MAX-ACCESS        read-write
        STATUS            current
        DESCRIPTION
                "CMNT: - 
                 TYPE: - Button
                 PAGE: - Input
                    Error Reset  cmdID= 33052
                    value= 1  "
        ::= { iqsyn22CmdEntry 33052 }


    iqsyn22OutputOPStd OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - Select output standard
                 TYPE: - RadiobuttonList
                 PAGE: - Output
                    O/P Std.  cmdID= 33010
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn22CmdEntry 33010 }


    iqsyn22OutputVideoProcMasterGain OBJECT-TYPE
        SYNTAX            INTEGER
        MAX-ACCESS        read-write
        STATUS            current
        DESCRIPTION
                "CMNT: - Video Master Gain
                 TYPE: - Number
                 PAGE: - Output
                    Master Gain  cmdID= 33000
                    min= -600  max= 600  step= 10  format= %0.1f dB  div_scale= 100  preset= 0
                    Min = -6.0 dB  Max = 6.0 dB  Step = 0.1 dB  Preset = 0.0 dB  "
        ::= { iqsyn22CmdEntry 33000 }


    iqsyn22OutputVideoProcYGain OBJECT-TYPE
        SYNTAX            INTEGER
        MAX-ACCESS        read-write
        STATUS            current
        DESCRIPTION
                "CMNT: - Video Luminance gain
                 TYPE: - Number
                 PAGE: - Output
                    Y Gain  cmdID= 33001
                    min= -600  max= 600  step= 10  format= %0.1f dB  div_scale= 100  preset= 0
                    Min = -6.0 dB  Max = 6.0 dB  Step = 0.1 dB  Preset = 0.0 dB  "
        ::= { iqsyn22CmdEntry 33001 }


    iqsyn22OutputVideoProcCGain OBJECT-TYPE
        SYNTAX            INTEGER
        MAX-ACCESS        read-write
        STATUS            current
        DESCRIPTION
                "CMNT: - Video CbCr Gain
                 TYPE: - Number
                 PAGE: - Output
                    C Gain  cmdID= 33003
                    min= -600  max= 600  step= 10  format= %0.1f dB  div_scale= 100  preset= 0
                    Min = -6.0 dB  Max = 6.0 dB  Step = 0.1 dB  Preset = 0.0 dB  "
        ::= { iqsyn22CmdEntry 33003 }


    iqsyn22OutputVideoProcBlackLevel OBJECT-TYPE
        SYNTAX            INTEGER
        MAX-ACCESS        read-write
        STATUS            current
        DESCRIPTION
                "CMNT: - Video Black Level
                 TYPE: - Number
                 PAGE: - Output
                    Black Level  cmdID= 33002
                    min= -200  max= 200  step= 1  format= %0.0f mV  div_scale= 1  preset= 0
                    Min = -200 mV  Max = 200 mV  Step = 1 mV  Preset = 0 mV  "
        ::= { iqsyn22CmdEntry 33002 }


    iqsyn22OutputVideoProcHue OBJECT-TYPE
        SYNTAX            INTEGER
        MAX-ACCESS        read-write
        STATUS            current
        DESCRIPTION
                "CMNT: - 
                 TYPE: - Number
                 PAGE: - Output
                    Hue  cmdID= 4908
                    min= -45  max= 45  step= 1  format= %0.0f degs  div_scale= 1  preset= 0
                    Min = -45 degs  Max = 45 degs  Step = 1 degs  Preset = 0 degs  "
        ::= { iqsyn22CmdEntry 4908 }


    iqsyn22OutputDefaultOutput OBJECT-TYPE
        SYNTAX            INTEGER {
                            valFreezeFrame(1),
                            valFreezeField(5),
                            valBlack(2),
                            valInput(3),
                            valOutPattern(4)
                            }
        MAX-ACCESS        read-write
        STATUS            current
        DESCRIPTION
                "CMNT: - What to do on input loss
                 TYPE: - RadiobuttonList
                 PAGE: - Output
                    Default Output  cmdID= 33031
                    Freeze Frame  value= 1
                    Freeze Field  value= 5
                    Black  value= 2
                    Input  value= 3
                    Out Pattern  value= 4  "
        ::= { iqsyn22CmdEntry 33031 }


    iqsyn22OutputOutputStandard OBJECT-TYPE
        SYNTAX            INTEGER {
                            valManualSelection(0),
                            valFollowsInputStd(1),
                            valFollowsRefStd(2)
                            }
        MAX-ACCESS        read-write
        STATUS            current
        DESCRIPTION
                "CMNT: - Output follows std: Man/Input/Ext.Reference
                 TYPE: - RadiobuttonList
                 PAGE: - Output
                    Output Standard  cmdID= 33011
                    Manual Selection  value= 0
                    Follows Input Std.  value= 1
                    Follows Ref. Std.  value= 2  "
        ::= { iqsyn22CmdEntry 33011 }


    iqsyn22OutputDefaultOPStd OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - 
                 TYPE: - RadiobuttonList
                 PAGE: - Output
                    Default O/P Std.  cmdID= 33012
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn22CmdEntry 33012 }


    iqsyn22PictureOutputLumaClipperEnable OBJECT-TYPE
        SYNTAX            INTEGER { disable(0), enable(1)  }
        MAX-ACCESS        read-write
        STATUS            current
        DESCRIPTION
                "CMNT: - 
                 TYPE: - Checkbox
                 PAGE: - Picture Output
                    Enable  cmdID= 6070  "
        ::= { iqsyn22CmdEntry 6070 }


    iqsyn22PictureOutputLumaClipperWhitemax OBJECT-TYPE
        SYNTAX            INTEGER
        MAX-ACCESS        read-write
        STATUS            current
        DESCRIPTION
                "CMNT: - 
                 TYPE: - Number
                 PAGE: - Picture Output
                    White max  cmdID= 6071
                    min= 90  max= 109  step= 1  format= %0.0f %%  div_scale= 1  preset= 103
                    Min = 90 %  Max = 109 %  Step = 1 %  Preset = 103 %  "
        ::= { iqsyn22CmdEntry 6071 }


    iqsyn22PictureOutputLumaClipperBlackmin OBJECT-TYPE
        SYNTAX            INTEGER
        MAX-ACCESS        read-write
        STATUS            current
        DESCRIPTION
                "CMNT: - 
                 TYPE: - Number
                 PAGE: - Picture Output
                    Black min  cmdID= 6072
                    min= -7  max= 10  step= 1  format= %0.0f %%  div_scale= 1  preset= -1
                    Min = -7 %  Max = 10 %  Step = 1 %  Preset = -1 %  "
        ::= { iqsyn22CmdEntry 6072 }


    iqsyn22PictureOutputRGBLegaliserEnable OBJECT-TYPE
        SYNTAX            INTEGER { disable(0), enable(1)  }
        MAX-ACCESS        read-write
        STATUS            current
        DESCRIPTION
                "CMNT: - 
                 TYPE: - Checkbox
                 PAGE: - Picture Output
                    Enable  cmdID= 6060  "
        ::= { iqsyn22CmdEntry 6060 }


    iqsyn22PictureOutputRGBLegaliserRange OBJECT-TYPE
        SYNTAX            INTEGER {
                            val700mV(0),
                            val721mV(1),
                            val735mV(2)
                            }
        MAX-ACCESS        read-write
        STATUS            current
        DESCRIPTION
                "CMNT: - 
                 TYPE: - RadiobuttonList
                 PAGE: - Picture Output
                    Range  cmdID= 6061
                    700 mV  value= 0
                    721 mV  value= 1
                    735 mV  value= 2  "
        ::= { iqsyn22CmdEntry 6061 }


    iqsyn22PictureOutputAdvancedHEnhanceEnable OBJECT-TYPE
        SYNTAX            INTEGER { disable(0), enable(1)  }
        MAX-ACCESS        read-write
        STATUS            current
        DESCRIPTION
                "CMNT: - 
                 TYPE: - Checkbox
                 PAGE: - Picture Output
                    Enable  cmdID= 6030  "
        ::= { iqsyn22CmdEntry 6030 }


    iqsyn22PictureOutputAdvancedHEnhanceFrequencyBand OBJECT-TYPE
        SYNTAX            INTEGER {
                            valLow(2),
                            valMedium(1),
                            valHigh(0)
                            }
        MAX-ACCESS        read-write
        STATUS            current
        DESCRIPTION
                "CMNT: - 
                 TYPE: - RadiobuttonList
                 PAGE: - Picture Output
                    Frequency Band  cmdID= 6031
                    Low  value= 2
                    Medium  value= 1
                    High  value= 0  "
        ::= { iqsyn22CmdEntry 6031 }


    iqsyn22PictureOutputAdvancedHEnhancePreset OBJECT-TYPE
        SYNTAX            INTEGER {
                            valLow(1),
                            valMedium(2),
                            valHigh(3),
                            valSuper(4),
                            valCustom(0)
                            }
        MAX-ACCESS        read-write
        STATUS            current
        DESCRIPTION
                "CMNT: - 
                 TYPE: - RadiobuttonList
                 PAGE: - Picture Output
                    Preset  cmdID= 6034
                    Low  value= 1
                    Medium  value= 2
                    High  value= 3
                    Super  value= 4
                    Custom  value= 0  "
        ::= { iqsyn22CmdEntry 6034 }


    iqsyn22PictureOutputAdvancedHEnhanceGain OBJECT-TYPE
        SYNTAX            INTEGER
        MAX-ACCESS        read-write
        STATUS            current
        DESCRIPTION
                "CMNT: - 
                 TYPE: - Number
                 PAGE: - Picture Output
                    Gain  cmdID= 6032
                    min= 0  max= 192  step= 8  format= %0.1f  div_scale= 16  preset= 0
                    Min = 0.0  Max = 12.0  Step = 0.5  Preset = 0.0  "
        ::= { iqsyn22CmdEntry 6032 }


    iqsyn22PictureOutputAdvancedHEnhanceNoiseRejection OBJECT-TYPE
        SYNTAX            INTEGER
        MAX-ACCESS        read-write
        STATUS            current
        DESCRIPTION
                "CMNT: - 
                 TYPE: - Number
                 PAGE: - Picture Output
                    Noise Rejection  cmdID= 6033
                    min= 0  max= 100  step= 1  format= %0.0f%%  div_scale= 1  preset= 0
                    Min = 0%  Max = 100%  Step = 1%  Preset = 0%  "
        ::= { iqsyn22CmdEntry 6033 }


    iqsyn22AudioDelayADelaySourcesManual OBJECT-TYPE
        SYNTAX            INTEGER { disable(0), enable(1)  }
        MAX-ACCESS        read-write
        STATUS            current
        DESCRIPTION
                "CMNT: - Use manual delay select
                 TYPE: - Checkbox
                 PAGE: - Audio Delay-A
                    Manual  cmdID= 38041  "
        ::= { iqsyn22CmdEntry 38041 }


    iqsyn22AudioDelayADelaySourcesGPIPWM OBJECT-TYPE
        SYNTAX            INTEGER { disable(0), enable(1)  }
        MAX-ACCESS        read-write
        STATUS            current
        DESCRIPTION
                "CMNT: - Use GPIO PWM for delay
                 TYPE: - Checkbox
                 PAGE: - Audio Delay-A
                    GPI PWM  cmdID= 38042  "
        ::= { iqsyn22CmdEntry 38042 }


    iqsyn22AudioDelayADelaySourcesRollTrack14 OBJECT-TYPE
        SYNTAX            INTEGER { disable(0), enable(1)  }
        MAX-ACCESS        read-write
        STATUS            current
        DESCRIPTION
                "CMNT: - Use rolltrack14 data for delay
                 TYPE: - Checkbox
                 PAGE: - Audio Delay-A
                    RollTrack14  cmdID= 38044  "
        ::= { iqsyn22CmdEntry 38044 }


    iqsyn22AudioDelayADelaySourcesRollTrack15 OBJECT-TYPE
        SYNTAX            INTEGER { disable(0), enable(1)  }
        MAX-ACCESS        read-write
        STATUS            current
        DESCRIPTION
                "CMNT: - Use rolltrack15 data for delay
                 TYPE: - Checkbox
                 PAGE: - Audio Delay-A
                    RollTrack15  cmdID= 38045  "
        ::= { iqsyn22CmdEntry 38045 }


    iqsyn22AudioDelayADelaySourcesRollTrack16 OBJECT-TYPE
        SYNTAX            INTEGER { disable(0), enable(1)  }
        MAX-ACCESS        read-write
        STATUS            current
        DESCRIPTION
                "CMNT: - Use rolltrack16 data for delay
                 TYPE: - Checkbox
                 PAGE: - Audio Delay-A
                    RollTrack16  cmdID= 38046  "
        ::= { iqsyn22CmdEntry 38046 }


    iqsyn22AudioDelayADelaySourcesRollTrack17 OBJECT-TYPE
        SYNTAX            INTEGER { disable(0), enable(1)  }
        MAX-ACCESS        read-write
        STATUS            current
        DESCRIPTION
                "CMNT: - Use rolltrack17 data for delay
                 TYPE: - Checkbox
                 PAGE: - Audio Delay-A
                    RollTrack17  cmdID= 38047  "
        ::= { iqsyn22CmdEntry 38047 }


    iqsyn22AudioDelayAAdjustManualDelay OBJECT-TYPE
        SYNTAX            INTEGER
        MAX-ACCESS        read-write
        STATUS            current
        DESCRIPTION
                "CMNT: - Set Manual delay
                 TYPE: - Number
                 PAGE: - Aud.Delays
                    Adjust Coarse Delay  cmdID= 38043
                    min= -4000  max= 200000  step= 25  format= %0.2f ms  div_scale= 100  preset= 0
                    Min = -40.00 ms  Max = 2000.00 ms  Step = 0.25 ms  Preset = 0.00 ms  "
        ::= { iqsyn22CmdEntry 38043 }


    iqsyn22AudioDelayACurrentAudioDelay OBJECT-TYPE
        SYNTAX            RollCallString
        MAX-ACCESS        read-only
        STATUS            current
        DESCRIPTION
                "CMNT: - Current Value for Audio Delay A
                 TYPE: - Display
                 PAGE: - Aud.Delays
                    Current Audio Delay  cmdID= 38048  "
        ::= { iqsyn22CmdEntry 38048 }


    iqsyn22AudioDelayBDelaySourcesManual OBJECT-TYPE
        SYNTAX            INTEGER { disable(0), enable(1)  }
        MAX-ACCESS        read-write
        STATUS            current
        DESCRIPTION
                "CMNT: - Use manual delay select
                 TYPE: - Checkbox
                 PAGE: - Audio Delay-B
                    Manual  cmdID= 38061  "
        ::= { iqsyn22CmdEntry 38061 }


    iqsyn22AudioDelayBDelaySourcesGPIPWM OBJECT-TYPE
        SYNTAX            INTEGER { disable(0), enable(1)  }
        MAX-ACCESS        read-write
        STATUS            current
        DESCRIPTION
                "CMNT: - Use GPIO PWM for delay
                 TYPE: - Checkbox
                 PAGE: - Audio Delay-B
                    GPI PWM  cmdID= 38062  "
        ::= { iqsyn22CmdEntry 38062 }


    iqsyn22AudioDelayBDelaySourcesRollTrack14 OBJECT-TYPE
        SYNTAX            INTEGER { disable(0), enable(1)  }
        MAX-ACCESS        read-write
        STATUS            current
        DESCRIPTION
                "CMNT: - Use rolltrack14 data for delay
                 TYPE: - Checkbox
                 PAGE: - Audio Delay-B
                    RollTrack14  cmdID= 38064  "
        ::= { iqsyn22CmdEntry 38064 }


    iqsyn22AudioDelayBDelaySourcesRollTrack15 OBJECT-TYPE
        SYNTAX            INTEGER { disable(0), enable(1)  }
        MAX-ACCESS        read-write
        STATUS            current
        DESCRIPTION
                "CMNT: - Use rolltrack15 data for delay
                 TYPE: - Checkbox
                 PAGE: - Audio Delay-B
                    RollTrack15  cmdID= 38065  "
        ::= { iqsyn22CmdEntry 38065 }


    iqsyn22AudioDelayBDelaySourcesRollTrack16 OBJECT-TYPE
        SYNTAX            INTEGER { disable(0), enable(1)  }
        MAX-ACCESS        read-write
        STATUS            current
        DESCRIPTION
                "CMNT: - Use rolltrack16 data for delay
                 TYPE: - Checkbox
                 PAGE: - Audio Delay-B
                    RollTrack16  cmdID= 38066  "
        ::= { iqsyn22CmdEntry 38066 }


    iqsyn22AudioDelayBDelaySourcesRollTrack17 OBJECT-TYPE
        SYNTAX            INTEGER { disable(0), enable(1)  }
        MAX-ACCESS        read-write
        STATUS            current
        DESCRIPTION
                "CMNT: - Use rolltrack17 data for delay
                 TYPE: - Checkbox
                 PAGE: - Audio Delay-B
                    RollTrack17  cmdID= 38067  "
        ::= { iqsyn22CmdEntry 38067 }


    iqsyn22AudioDelayBAdjustManualDelay OBJECT-TYPE
        SYNTAX            INTEGER
        MAX-ACCESS        read-write
        STATUS            current
        DESCRIPTION
                "CMNT: - Set Manual delay
                 TYPE: - Number
                 PAGE: - Aud.Delays
                    Adjust Coarse Delay  cmdID= 38063
                    min= -4000  max= 200000  step= 25  format= %0.2f ms  div_scale= 100  preset= 0
                    Min = -40.00 ms  Max = 2000.00 ms  Step = 0.25 ms  Preset = 0.00 ms  "
        ::= { iqsyn22CmdEntry 38063 }


    iqsyn22AudioDelayBCurrentAudioDelay OBJECT-TYPE
        SYNTAX            RollCallString
        MAX-ACCESS        read-only
        STATUS            current
        DESCRIPTION
                "CMNT: - Current Value for Audio Delay B
                 TYPE: - Display
                 PAGE: - Aud.Delays
                    Current Audio Delay  cmdID= 38068  "
        ::= { iqsyn22CmdEntry 38068 }


    iqsyn22AudioDelaySelectDelay1 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-1  cmdID= 38080
                    Min  value= 0
                    Delay A  value= 1
                    Delay B  value= 2  "
        ::= { iqsyn22CmdEntry 38080 }


    iqsyn22AudDelaysEMBDelaySelectInternal1 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-1  cmdID= 38100  "
        ::= { iqsyn22CmdEntry 38100 }


    iqsyn22AudDelaysEMBDelaySelectAutoDolbyEPhaseBus1 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38110  cmdID= 38110  "
        ::= { iqsyn22CmdEntry 38110 }


    iqsyn22AudDelaysEMBDelaySelectDelayLimitBus1 OBJECT-TYPE
        SYNTAX            RollCallString
        MAX-ACCESS        read-only
        STATUS            current
        DESCRIPTION
                "CMNT: - 
                 TYPE: - Display
                 PAGE: - Aud.Delays
                    Delay Limit38308  cmdID= 38308  "
        ::= { iqsyn22CmdEntry 38308 }


    iqsyn22AudDelaysEMBDelaySelectEMB1FineDelay OBJECT-TYPE
        SYNTAX            INTEGER
        MAX-ACCESS        read-write
        STATUS            current
        DESCRIPTION
                "CMNT: - Set Manual delay
                 TYPE: - Number
                 PAGE: - Aud.Delays
                    EMB 1 Fine Delay  cmdID= 38138
                    min= -2450  max= 2450  step= 52  format= %0.3f ms  div_scale= 10000  preset= 0
                    Min = -0.245 ms  Max = 0.245 ms  Step = 0.005 ms  Preset = 0.000 ms  "
        ::= { iqsyn22CmdEntry 38138 }


    iqsyn22AudioDelaySelectDelay2 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-2  cmdID= 38081
                    Min  value= 0
                    Delay A  value= 1
                    Delay B  value= 2  "
        ::= { iqsyn22CmdEntry 38081 }


    iqsyn22AudDelaysEMBDelaySelectInternal2 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-2  cmdID= 38101  "
        ::= { iqsyn22CmdEntry 38101 }


    iqsyn22AudDelaysEMBDelaySelectAutoDolbyEPhaseBus2 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38111  cmdID= 38111  "
        ::= { iqsyn22CmdEntry 38111 }


    iqsyn22AudDelaysEMBDelaySelectDelayLimitBus2 OBJECT-TYPE
        SYNTAX            RollCallString
        MAX-ACCESS        read-only
        STATUS            current
        DESCRIPTION
                "CMNT: - 
                 TYPE: - Display
                 PAGE: - Aud.Delays
                    Delay Limit38309  cmdID= 38309  "
        ::= { iqsyn22CmdEntry 38309 }


    iqsyn22AudDelaysEMBDelaySelectEMB2FineDelay OBJECT-TYPE
        SYNTAX            INTEGER
        MAX-ACCESS        read-write
        STATUS            current
        DESCRIPTION
                "CMNT: - Set Manual delay
                 TYPE: - Number
                 PAGE: - Aud.Delays
                    EMB 2 Fine Delay  cmdID= 38139
                    min= -2450  max= 2450  step= 52  format= %0.3f ms  div_scale= 10000  preset= 0
                    Min = -0.245 ms  Max = 0.245 ms  Step = 0.005 ms  Preset = 0.000 ms  "
        ::= { iqsyn22CmdEntry 38139 }


    iqsyn22AudioDelaySelectDelay3 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-3  cmdID= 38082
                    Min  value= 0
                    Delay A  value= 1
                    Delay B  value= 2  "
        ::= { iqsyn22CmdEntry 38082 }


    iqsyn22AudDelaysEMBDelaySelectInternal3 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-3  cmdID= 38102  "
        ::= { iqsyn22CmdEntry 38102 }


    iqsyn22AudDelaysEMBDelaySelectAutoDolbyEPhaseBus3 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38112  cmdID= 38112  "
        ::= { iqsyn22CmdEntry 38112 }


    iqsyn22AudDelaysEMBDelaySelectDelayLimitBus3 OBJECT-TYPE
        SYNTAX            RollCallString
        MAX-ACCESS        read-only
        STATUS            current
        DESCRIPTION
                "CMNT: - 
                 TYPE: - Display
                 PAGE: - Aud.Delays
                    Delay Limit38310  cmdID= 38310  "
        ::= { iqsyn22CmdEntry 38310 }


    iqsyn22AudDelaysEMBDelaySelectEMB3FineDelay OBJECT-TYPE
        SYNTAX            INTEGER
        MAX-ACCESS        read-write
        STATUS            current
        DESCRIPTION
                "CMNT: - Set Manual delay
                 TYPE: - Number
                 PAGE: - Aud.Delays
                    EMB 3 Fine Delay  cmdID= 38140
                    min= -2450  max= 2450  step= 52  format= %0.3f ms  div_scale= 10000  preset= 0
                    Min = -0.245 ms  Max = 0.245 ms  Step = 0.005 ms  Preset = 0.000 ms  "
        ::= { iqsyn22CmdEntry 38140 }


    iqsyn22AudioDelaySelectDelay4 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-4  cmdID= 38083
                    Min  value= 0
                    Delay A  value= 1
                    Delay B  value= 2  "
        ::= { iqsyn22CmdEntry 38083 }


    iqsyn22AudDelaysEMBDelaySelectInternal4 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-4  cmdID= 38103  "
        ::= { iqsyn22CmdEntry 38103 }


    iqsyn22AudDelaysEMBDelaySelectAutoDolbyEPhaseBus4 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38113  cmdID= 38113  "
        ::= { iqsyn22CmdEntry 38113 }


    iqsyn22AudDelaysEMBDelaySelectDelayLimitBus4 OBJECT-TYPE
        SYNTAX            RollCallString
        MAX-ACCESS        read-only
        STATUS            current
        DESCRIPTION
                "CMNT: - 
                 TYPE: - Display
                 PAGE: - Aud.Delays
                    Delay Limit38311  cmdID= 38311  "
        ::= { iqsyn22CmdEntry 38311 }


    iqsyn22AudDelaysEMBDelaySelectEMB4FineDelay OBJECT-TYPE
        SYNTAX            INTEGER
        MAX-ACCESS        read-write
        STATUS            current
        DESCRIPTION
                "CMNT: - Set Manual delay
                 TYPE: - Number
                 PAGE: - Aud.Delays
                    EMB 4 Fine Delay  cmdID= 38141
                    min= -2450  max= 2450  step= 52  format= %0.3f ms  div_scale= 10000  preset= 0
                    Min = -0.245 ms  Max = 0.245 ms  Step = 0.005 ms  Preset = 0.000 ms  "
        ::= { iqsyn22CmdEntry 38141 }


    iqsyn22AudioDelaySelectDelay5 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-5  cmdID= 38084
                    Min  value= 0
                    Delay A  value= 1
                    Delay B  value= 2  "
        ::= { iqsyn22CmdEntry 38084 }


    iqsyn22AudDelaysEMBDelaySelectInternal5 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-5  cmdID= 38104  "
        ::= { iqsyn22CmdEntry 38104 }


    iqsyn22AudDelaysEMBDelaySelectAutoDolbyEPhaseBus5 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38114  cmdID= 38114  "
        ::= { iqsyn22CmdEntry 38114 }


    iqsyn22AudDelaysEMBDelaySelectDelayLimitBus5 OBJECT-TYPE
        SYNTAX            RollCallString
        MAX-ACCESS        read-only
        STATUS            current
        DESCRIPTION
                "CMNT: - 
                 TYPE: - Display
                 PAGE: - Aud.Delays
                    Delay Limit38312  cmdID= 38312  "
        ::= { iqsyn22CmdEntry 38312 }


    iqsyn22AudDelaysEMBDelaySelectEMB5FineDelay OBJECT-TYPE
        SYNTAX            INTEGER
        MAX-ACCESS        read-write
        STATUS            current
        DESCRIPTION
                "CMNT: - Set Manual delay
                 TYPE: - Number
                 PAGE: - Aud.Delays
                    EMB 5 Fine Delay  cmdID= 38142
                    min= -2450  max= 2450  step= 52  format= %0.3f ms  div_scale= 10000  preset= 0
                    Min = -0.245 ms  Max = 0.245 ms  Step = 0.005 ms  Preset = 0.000 ms  "
        ::= { iqsyn22CmdEntry 38142 }


    iqsyn22AudioDelaySelectDelay6 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-6  cmdID= 38085
                    Min  value= 0
                    Delay A  value= 1
                    Delay B  value= 2  "
        ::= { iqsyn22CmdEntry 38085 }


    iqsyn22AudDelaysEMBDelaySelectInternal6 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-6  cmdID= 38105  "
        ::= { iqsyn22CmdEntry 38105 }


    iqsyn22AudDelaysEMBDelaySelectAutoDolbyEPhaseBus6 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38115  cmdID= 38115  "
        ::= { iqsyn22CmdEntry 38115 }


    iqsyn22AudDelaysEMBDelaySelectDelayLimitBus6 OBJECT-TYPE
        SYNTAX            RollCallString
        MAX-ACCESS        read-only
        STATUS            current
        DESCRIPTION
                "CMNT: - 
                 TYPE: - Display
                 PAGE: - Aud.Delays
                    Delay Limit38313  cmdID= 38313  "
        ::= { iqsyn22CmdEntry 38313 }


    iqsyn22AudDelaysEMBDelaySelectEMB6FineDelay OBJECT-TYPE
        SYNTAX            INTEGER
        MAX-ACCESS        read-write
        STATUS            current
        DESCRIPTION
                "CMNT: - Set Manual delay
                 TYPE: - Number
                 PAGE: - Aud.Delays
                    EMB 6 Fine Delay  cmdID= 38143
                    min= -2450  max= 2450  step= 52  format= %0.3f ms  div_scale= 10000  preset= 0
                    Min = -0.245 ms  Max = 0.245 ms  Step = 0.005 ms  Preset = 0.000 ms  "
        ::= { iqsyn22CmdEntry 38143 }


    iqsyn22AudioDelaySelectDelay7 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-7  cmdID= 38086
                    Min  value= 0
                    Delay A  value= 1
                    Delay B  value= 2  "
        ::= { iqsyn22CmdEntry 38086 }


    iqsyn22AudDelaysEMBDelaySelectInternal7 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-7  cmdID= 38106  "
        ::= { iqsyn22CmdEntry 38106 }


    iqsyn22AudDelaysEMBDelaySelectAutoDolbyEPhaseBus7 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38116  cmdID= 38116  "
        ::= { iqsyn22CmdEntry 38116 }


    iqsyn22AudDelaysEMBDelaySelectDelayLimitBus7 OBJECT-TYPE
        SYNTAX            RollCallString
        MAX-ACCESS        read-only
        STATUS            current
        DESCRIPTION
                "CMNT: - 
                 TYPE: - Display
                 PAGE: - Aud.Delays
                    Delay Limit38314  cmdID= 38314  "
        ::= { iqsyn22CmdEntry 38314 }


    iqsyn22AudDelaysEMBDelaySelectEMB7FineDelay OBJECT-TYPE
        SYNTAX            INTEGER
        MAX-ACCESS        read-write
        STATUS            current
        DESCRIPTION
                "CMNT: - Set Manual delay
                 TYPE: - Number
                 PAGE: - Aud.Delays
                    EMB 7 Fine Delay  cmdID= 38144
                    min= -2450  max= 2450  step= 52  format= %0.3f ms  div_scale= 10000  preset= 0
                    Min = -0.245 ms  Max = 0.245 ms  Step = 0.005 ms  Preset = 0.000 ms  "
        ::= { iqsyn22CmdEntry 38144 }


    iqsyn22AudioDelaySelectDelay8 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-8  cmdID= 38087
                    Min  value= 0
                    Delay A  value= 1
                    Delay B  value= 2  "
        ::= { iqsyn22CmdEntry 38087 }


    iqsyn22AudDelaysEMBDelaySelectInternal8 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-8  cmdID= 38107  "
        ::= { iqsyn22CmdEntry 38107 }


    iqsyn22AudDelaysEMBDelaySelectDelayLimitBus8 OBJECT-TYPE
        SYNTAX            RollCallString
        MAX-ACCESS        read-only
        STATUS            current
        DESCRIPTION
                "CMNT: - 
                 TYPE: - Display
                 PAGE: - Aud.Delays
                    Delay Limit38315  cmdID= 38315  "
        ::= { iqsyn22CmdEntry 38315 }


    iqsyn22AudDelaysEMBDelaySelectAutoDolbyEPhaseBus8 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38117  cmdID= 38117  "
        ::= { iqsyn22CmdEntry 38117 }


    iqsyn22AudDelaysEMBDelaySelectEMB8FineDelay OBJECT-TYPE
        SYNTAX            INTEGER
        MAX-ACCESS        read-write
        STATUS            current
        DESCRIPTION
                "CMNT: - Set Manual delay
                 TYPE: - Number
                 PAGE: - Aud.Delays
                    EMB 8 Fine Delay  cmdID= 38145
                    min= -2450  max= 2450  step= 52  format= %0.3f ms  div_scale= 10000  preset= 0
                    Min = -0.245 ms  Max = 0.245 ms  Step = 0.005 ms  Preset = 0.000 ms  "
        ::= { iqsyn22CmdEntry 38145 }


    iqsyn22AudioDelaysRollTrack14 OBJECT-TYPE
        SYNTAX            RollCallString
        MAX-ACCESS        read-only
        STATUS            current
        DESCRIPTION
                "CMNT: - Rolltrack input command for delays
                 TYPE: - Display
                 PAGE: - Audio
                    RollTrack14  cmdID= 14  "
        ::= { iqsyn22CmdEntry 14 }


    iqsyn22AudioDelaysRollTrack15 OBJECT-TYPE
        SYNTAX            RollCallString
        MAX-ACCESS        read-only
        STATUS            current
        DESCRIPTION
                "CMNT: - Rolltrack input command for delays
                 TYPE: - Display
                 PAGE: - Audio
                    RollTrack15  cmdID= 15  "
        ::= { iqsyn22CmdEntry 15 }


    iqsyn22AudioDelaysRollTrack16 OBJECT-TYPE
        SYNTAX            RollCallString
        MAX-ACCESS        read-only
        STATUS            current
        DESCRIPTION
                "CMNT: - Rolltrack input command for delays
                 TYPE: - Display
                 PAGE: - Audio
                    RollTrack16  cmdID= 16  "
        ::= { iqsyn22CmdEntry 16 }


    iqsyn22AudioDelaysRollTrack17 OBJECT-TYPE
        SYNTAX            RollCallString
        MAX-ACCESS        read-only
        STATUS            current
        DESCRIPTION
                "CMNT: - Rolltrack input command for delays
                 TYPE: - Display
                 PAGE: - Audio
                    RollTrack17  cmdID= 17  "
        ::= { iqsyn22CmdEntry 17 }


    iqsyn22AudioAudDelaysCrashSRCLimit OBJECT-TYPE
        SYNTAX            INTEGER
        MAX-ACCESS        read-write
        STATUS            current
        DESCRIPTION
                "CMNT: - Set Audio Crash SRC limit
                 TYPE: - Number
                 PAGE: - Audio
                    Crash SRC Limit  cmdID= 38678
                    min= 0  max= 80  step= 1  format= %0.0f ms  div_scale= 1  preset= 80
                    Min = 0 ms  Max = 80 ms  Step = 1 ms  Preset = 80 ms  "
        ::= { iqsyn22CmdEntry 38678 }


    iqsyn22EmbCtrlGroupGroup1Active OBJECT-TYPE
        SYNTAX            INTEGER {
                            valPass(0),
                            valBlank(2),
                            valEmbed(1)
                            }
        MAX-ACCESS        read-write
        STATUS            current
        DESCRIPTION
                "CMNT: - Embedded output audio group enabled
                 TYPE: - RadiobuttonList
                 PAGE: - Audio
                    Group 1 Audio  cmdID= 37450
                    Pass  value= 0
                    Blank  value= 2
                    Embed  value= 1  "
        ::= { iqsyn22CmdEntry 37450 }


    iqsyn22EmbCtrlGroupGroup2Active OBJECT-TYPE
        SYNTAX            INTEGER {
                            valPass(0),
                            valBlank(2),
                            valEmbed(1)
                            }
        MAX-ACCESS        read-write
        STATUS            current
        DESCRIPTION
                "CMNT: - Embedded output audio group enabled
                 TYPE: - RadiobuttonList
                 PAGE: - Audio
                    Group 2 Audio  cmdID= 37451
                    Pass  value= 0
                    Blank  value= 2
                    Embed  value= 1  "
        ::= { iqsyn22CmdEntry 37451 }


    iqsyn22EmbCtrlGroupGroup3Active OBJECT-TYPE
        SYNTAX            INTEGER {
                            valPass(0),
                            valBlank(2),
                            valEmbed(1)
                            }
        MAX-ACCESS        read-write
        STATUS            current
        DESCRIPTION
                "CMNT: - Embedded output audio group enabled
                 TYPE: - RadiobuttonList
                 PAGE: - Audio
                    Group 3 Audio  cmdID= 37452
                    Pass  value= 0
                    Blank  value= 2
                    Embed  value= 1  "
        ::= { iqsyn22CmdEntry 37452 }


    iqsyn22EmbCtrlGroupGroup4Active OBJECT-TYPE
        SYNTAX            INTEGER {
                            valPass(0),
                            valBlank(2),
                            valEmbed(1)
                            }
        MAX-ACCESS        read-write
        STATUS            current
        DESCRIPTION
                "CMNT: - Embedded output audio group enabled
                 TYPE: - RadiobuttonList
                 PAGE: - Audio
                    Group 4 Audio  cmdID= 37453
                    Pass  value= 0
                    Blank  value= 2
                    Embed  value= 1  "
        ::= { iqsyn22CmdEntry 37453 }


    iqsyn22EmbCtrlChannelPair1LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 1-L Active  cmdID= 37431  "
        ::= { iqsyn22CmdEntry 37431 }


    iqsyn22EmbCtrlChannelPair1RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 1-R Active  cmdID= 37432  "
        ::= { iqsyn22CmdEntry 37432 }


    iqsyn22EmbCtrlChannelPair2LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 2-L Active  cmdID= 37433  "
        ::= { iqsyn22CmdEntry 37433 }


    iqsyn22EmbCtrlChannelPair2RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 2-R Active  cmdID= 37434  "
        ::= { iqsyn22CmdEntry 37434 }


    iqsyn22EmbCtrlChannelPair3LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 3-L Active  cmdID= 37435  "
        ::= { iqsyn22CmdEntry 37435 }


    iqsyn22EmbCtrlChannelPair3RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 3-R Active  cmdID= 37436  "
        ::= { iqsyn22CmdEntry 37436 }


    iqsyn22EmbCtrlChannelPair4LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 4-L Active  cmdID= 37437  "
        ::= { iqsyn22CmdEntry 37437 }


    iqsyn22EmbCtrlChannelPair4RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 4-R Active  cmdID= 37438  "
        ::= { iqsyn22CmdEntry 37438 }


    iqsyn22EmbCtrlChannelPair5LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 5-L Active  cmdID= 37439  "
        ::= { iqsyn22CmdEntry 37439 }


    iqsyn22EmbCtrlChannelPair5RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 5-R Active  cmdID= 37440  "
        ::= { iqsyn22CmdEntry 37440 }


    iqsyn22EmbCtrlChannelPair6LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 6-L Active  cmdID= 37441  "
        ::= { iqsyn22CmdEntry 37441 }


    iqsyn22EmbCtrlChannelPair6RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 6-R Active  cmdID= 37442  "
        ::= { iqsyn22CmdEntry 37442 }


    iqsyn22EmbCtrlChannelPair7LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 7-L Active  cmdID= 37443  "
        ::= { iqsyn22CmdEntry 37443 }


    iqsyn22EmbCtrlChannelPair7RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 7-R Active  cmdID= 37444  "
        ::= { iqsyn22CmdEntry 37444 }


    iqsyn22EmbCtrlChannelPair8LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 8-L Active  cmdID= 37445  "
        ::= { iqsyn22CmdEntry 37445 }


    iqsyn22EmbCtrlChannelPair8RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 8-R Active  cmdID= 37446  "
        ::= { iqsyn22CmdEntry 37446 }


    iqsyn22AudioEmbCtrlEmbedderPriority OBJECT-TYPE
        SYNTAX            INTEGER {
                            valNormal(0),
                            valAudioDolbynE(1)
                            }
        MAX-ACCESS        read-write
        STATUS            current
        DESCRIPTION
                "CMNT: - Set priority of ANC embedded data
                 TYPE: - RadiobuttonList
                 PAGE: - Audio
                    Embedder Priority  cmdID= 37460
                    Normal  value= 0
                    Audio (Dolby-E)  value= 1  "
        ::= { iqsyn22CmdEntry 37460 }


    iqsyn22EmbGainEmbedPair1Embed1MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 1 Mute L  cmdID= 37340  "
        ::= { iqsyn22CmdEntry 37340 }


    iqsyn22EmbGainEmbedPair1Embed1MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 1 Mute R  cmdID= 37341  "
        ::= { iqsyn22CmdEntry 37341 }


    iqsyn22EmbGainEmbedPair1Embed1LGain OBJECT-TYPE
        SYNTAX            INTEGER
        MAX-ACCESS        read-write
        STATUS            current
        DESCRIPTION
                "CMNT: - Embedded audio gain
                 TYPE: - Number
                 PAGE: - Emb.Gain
                    Embed 1 L Gain  cmdID= 37320
                    min= -661  max= 120  step= 1  format= %0.1f dB  div_scale= 10  preset= 0
                    Min = -66.1 dB  Max = 12.0 dB  Step = 0.1 dB  Preset = 0.0 dB  "
        ::= { iqsyn22CmdEntry 37320 }


    iqsyn22EmbGainEmbedPair1Embed1RGain OBJECT-TYPE
        SYNTAX            INTEGER
        MAX-ACCESS        read-write
        STATUS            current
        DESCRIPTION
                "CMNT: - Embedded audio gain
                 TYPE: - Number
                 PAGE: - Emb.Gain
                    Embed 1 R Gain  cmdID= 37321
                    min= -661  max= 120  step= 1  format= %0.1f dB  div_scale= 10  preset= 0
                    Min = -66.1 dB  Max = 12.0 dB  Step = 0.1 dB  Preset = 0.0 dB  "
        ::= { iqsyn22CmdEntry 37321 }


    iqsyn22EmbGainEmbedPair1Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37380  "
        ::= { iqsyn22CmdEntry 37380 }


    iqsyn22EmbGainEmbedPair1Embed1InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 1 Invert L  cmdID= 37360  "
        ::= { iqsyn22CmdEntry 37360 }


    iqsyn22EmbGainEmbedPair1Embed1InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 1 Invert R  cmdID= 37361  "
        ::= { iqsyn22CmdEntry 37361 }


    iqsyn22EmbGainEmbedPair1Embed1LClip OBJECT-TYPE
        SYNTAX            RollCallString
        MAX-ACCESS        read-only
        STATUS            current
        DESCRIPTION
                "CMNT: - Embedded audio output clip
                 TYPE: - Display
                 PAGE: - Emb.Gain
                    Embed 1-L Clip  cmdID= 37540  "
        ::= { iqsyn22CmdEntry 37540 }


    iqsyn22EmbGainEmbedPair1Embed1RClip OBJECT-TYPE
        SYNTAX            RollCallString
        MAX-ACCESS        read-only
        STATUS            current
        DESCRIPTION
                "CMNT: - Embedded audio output clip
                 TYPE: - Display
                 PAGE: - Emb.Gain
                    Embed 1-R Clip  cmdID= 37541  "
        ::= { iqsyn22CmdEntry 37541 }


    iqsyn22EmbGainEmbedPair2Embed2MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 2 Mute L  cmdID= 37342  "
        ::= { iqsyn22CmdEntry 37342 }


    iqsyn22EmbGainEmbedPair2Embed2MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 2 Mute R  cmdID= 37343  "
        ::= { iqsyn22CmdEntry 37343 }


    iqsyn22EmbGainEmbedPair2Embed2LGain OBJECT-TYPE
        SYNTAX            INTEGER
        MAX-ACCESS        read-write
        STATUS            current
        DESCRIPTION
                "CMNT: - Embedded audio gain
                 TYPE: - Number
                 PAGE: - Emb.Gain
                    Embed 2 L Gain  cmdID= 37322
                    min= -661  max= 120  step= 1  format= %0.1f dB  div_scale= 10  preset= 0
                    Min = -66.1 dB  Max = 12.0 dB  Step = 0.1 dB  Preset = 0.0 dB  "
        ::= { iqsyn22CmdEntry 37322 }


    iqsyn22EmbGainEmbedPair2Embed2RGain OBJECT-TYPE
        SYNTAX            INTEGER
        MAX-ACCESS        read-write
        STATUS            current
        DESCRIPTION
                "CMNT: - Embedded audio gain
                 TYPE: - Number
                 PAGE: - Emb.Gain
                    Embed 2 R Gain  cmdID= 37323
                    min= -661  max= 120  step= 1  format= %0.1f dB  div_scale= 10  preset= 0
                    Min = -66.1 dB  Max = 12.0 dB  Step = 0.1 dB  Preset = 0.0 dB  "
        ::= { iqsyn22CmdEntry 37323 }


    iqsyn22EmbGainEmbedPair2Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37381  "
        ::= { iqsyn22CmdEntry 37381 }


    iqsyn22EmbGainEmbedPair2Embed2InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 2 Invert L  cmdID= 37362  "
        ::= { iqsyn22CmdEntry 37362 }


    iqsyn22EmbGainEmbedPair2Embed2InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 2 Invert R  cmdID= 37363  "
        ::= { iqsyn22CmdEntry 37363 }


    iqsyn22EmbGainEmbedPair2Embed2LClip OBJECT-TYPE
        SYNTAX            RollCallString
        MAX-ACCESS        read-only
        STATUS            current
        DESCRIPTION
                "CMNT: - Embedded audio output clip
                 TYPE: - Display
                 PAGE: - Emb.Gain
                    Embed 2-L Clip  cmdID= 37542  "
        ::= { iqsyn22CmdEntry 37542 }


    iqsyn22EmbGainEmbedPair2Embed2RClip OBJECT-TYPE
        SYNTAX            RollCallString
        MAX-ACCESS        read-only
        STATUS            current
        DESCRIPTION
                "CMNT: - Embedded audio output clip
                 TYPE: - Display
                 PAGE: - Emb.Gain
                    Embed 2-R Clip  cmdID= 37543  "
        ::= { iqsyn22CmdEntry 37543 }


    iqsyn22EmbGainEmbedPair3Embed3MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 3 Mute L  cmdID= 37344  "
        ::= { iqsyn22CmdEntry 37344 }


    iqsyn22EmbGainEmbedPair3Embed3MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 3 Mute R  cmdID= 37345  "
        ::= { iqsyn22CmdEntry 37345 }


    iqsyn22EmbGainEmbedPair3Embed3LGain OBJECT-TYPE
        SYNTAX            INTEGER
        MAX-ACCESS        read-write
        STATUS            current
        DESCRIPTION
                "CMNT: - Embedded audio gain
                 TYPE: - Number
                 PAGE: - Emb.Gain
                    Embed 3 L Gain  cmdID= 37324
                    min= -661  max= 120  step= 1  format= %0.1f dB  div_scale= 10  preset= 0
                    Min = -66.1 dB  Max = 12.0 dB  Step = 0.1 dB  Preset = 0.0 dB  "
        ::= { iqsyn22CmdEntry 37324 }


    iqsyn22EmbGainEmbedPair3Embed3RGain OBJECT-TYPE
        SYNTAX            INTEGER
        MAX-ACCESS        read-write
        STATUS            current
        DESCRIPTION
                "CMNT: - Embedded audio gain
                 TYPE: - Number
                 PAGE: - Emb.Gain
                    Embed 3 R Gain  cmdID= 37325
                    min= -661  max= 120  step= 1  format= %0.1f dB  div_scale= 10  preset= 0
                    Min = -66.1 dB  Max = 12.0 dB  Step = 0.1 dB  Preset = 0.0 dB  "
        ::= { iqsyn22CmdEntry 37325 }


    iqsyn22EmbGainEmbedPair3Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37382  "
        ::= { iqsyn22CmdEntry 37382 }


    iqsyn22EmbGainEmbedPair3Embed3InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 3 Invert L  cmdID= 37364  "
        ::= { iqsyn22CmdEntry 37364 }


    iqsyn22EmbGainEmbedPair3Embed3InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 3 Invert R  cmdID= 37365  "
        ::= { iqsyn22CmdEntry 37365 }


    iqsyn22EmbGainEmbedPair3Embed3LClip OBJECT-TYPE
        SYNTAX            RollCallString
        MAX-ACCESS        read-only
        STATUS            current
        DESCRIPTION
                "CMNT: - Embedded audio output clip
                 TYPE: - Display
                 PAGE: - Emb.Gain
                    Embed 3-L Clip  cmdID= 37544  "
        ::= { iqsyn22CmdEntry 37544 }


    iqsyn22EmbGainEmbedPair3Embed3RClip OBJECT-TYPE
        SYNTAX            RollCallString
        MAX-ACCESS        read-only
        STATUS            current
        DESCRIPTION
                "CMNT: - Embedded audio output clip
                 TYPE: - Display
                 PAGE: - Emb.Gain
                    Embed 3-R Clip  cmdID= 37545  "
        ::= { iqsyn22CmdEntry 37545 }


    iqsyn22EmbGainEmbedPair4Embed4MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 4 Mute L  cmdID= 37346  "
        ::= { iqsyn22CmdEntry 37346 }


    iqsyn22EmbGainEmbedPair4Embed4MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 4 Mute R  cmdID= 37347  "
        ::= { iqsyn22CmdEntry 37347 }


    iqsyn22EmbGainEmbedPair4Embed4LGain OBJECT-TYPE
        SYNTAX            INTEGER
        MAX-ACCESS        read-write
        STATUS            current
        DESCRIPTION
                "CMNT: - Embedded audio gain
                 TYPE: - Number
                 PAGE: - Emb.Gain
                    Embed 4 L Gain  cmdID= 37326
                    min= -661  max= 120  step= 1  format= %0.1f dB  div_scale= 10  preset= 0
                    Min = -66.1 dB  Max = 12.0 dB  Step = 0.1 dB  Preset = 0.0 dB  "
        ::= { iqsyn22CmdEntry 37326 }


    iqsyn22EmbGainEmbedPair4Embed4RGain OBJECT-TYPE
        SYNTAX            INTEGER
        MAX-ACCESS        read-write
        STATUS            current
        DESCRIPTION
                "CMNT: - Embedded audio gain
                 TYPE: - Number
                 PAGE: - Emb.Gain
                    Embed 4 R Gain  cmdID= 37327
                    min= -661  max= 120  step= 1  format= %0.1f dB  div_scale= 10  preset= 0
                    Min = -66.1 dB  Max = 12.0 dB  Step = 0.1 dB  Preset = 0.0 dB  "
        ::= { iqsyn22CmdEntry 37327 }


    iqsyn22EmbGainEmbedPair4Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37383  "
        ::= { iqsyn22CmdEntry 37383 }


    iqsyn22EmbGainEmbedPair4Embed4InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 4 Invert L  cmdID= 37366  "
        ::= { iqsyn22CmdEntry 37366 }


    iqsyn22EmbGainEmbedPair4Embed4InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 4 Invert R  cmdID= 37367  "
        ::= { iqsyn22CmdEntry 37367 }


    iqsyn22EmbGainEmbedPair4Embed4LClip OBJECT-TYPE
        SYNTAX            RollCallString
        MAX-ACCESS        read-only
        STATUS            current
        DESCRIPTION
                "CMNT: - Embedded audio output clip
                 TYPE: - Display
                 PAGE: - Emb.Gain
                    Embed 4-L Clip  cmdID= 37546  "
        ::= { iqsyn22CmdEntry 37546 }


    iqsyn22EmbGainEmbedPair4Embed4RClip OBJECT-TYPE
        SYNTAX            RollCallString
        MAX-ACCESS        read-only
        STATUS            current
        DESCRIPTION
                "CMNT: - Embedded audio output clip
                 TYPE: - Display
                 PAGE: - Emb.Gain
                    Embed 4-R Clip  cmdID= 37547  "
        ::= { iqsyn22CmdEntry 37547 }


    iqsyn22EmbGainEmbedPair5Embed5MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 5 Mute L  cmdID= 37348  "
        ::= { iqsyn22CmdEntry 37348 }


    iqsyn22EmbGainEmbedPair5Embed5MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 5 Mute R  cmdID= 37349  "
        ::= { iqsyn22CmdEntry 37349 }


    iqsyn22EmbGainEmbedPair5Embed5LGain OBJECT-TYPE
        SYNTAX            INTEGER
        MAX-ACCESS        read-write
        STATUS            current
        DESCRIPTION
                "CMNT: - Embedded audio gain
                 TYPE: - Number
                 PAGE: - Emb.Gain
                    Embed 5 L Gain  cmdID= 37328
                    min= -661  max= 120  step= 1  format= %0.1f dB  div_scale= 10  preset= 0
                    Min = -66.1 dB  Max = 12.0 dB  Step = 0.1 dB  Preset = 0.0 dB  "
        ::= { iqsyn22CmdEntry 37328 }


    iqsyn22EmbGainEmbedPair5Embed5RGain OBJECT-TYPE
        SYNTAX            INTEGER
        MAX-ACCESS        read-write
        STATUS            current
        DESCRIPTION
                "CMNT: - Embedded audio gain
                 TYPE: - Number
                 PAGE: - Emb.Gain
                    Embed 5 R Gain  cmdID= 37329
                    min= -661  max= 120  step= 1  format= %0.1f dB  div_scale= 10  preset= 0
                    Min = -66.1 dB  Max = 12.0 dB  Step = 0.1 dB  Preset = 0.0 dB  "
        ::= { iqsyn22CmdEntry 37329 }


    iqsyn22EmbGainEmbedPair5Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37384  "
        ::= { iqsyn22CmdEntry 37384 }


    iqsyn22EmbGainEmbedPair5Embed5InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 5 Invert L  cmdID= 37368  "
        ::= { iqsyn22CmdEntry 37368 }


    iqsyn22EmbGainEmbedPair5Embed5InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 5 Invert R  cmdID= 37369  "
        ::= { iqsyn22CmdEntry 37369 }


    iqsyn22EmbGainEmbedPair5Embed5LClip OBJECT-TYPE
        SYNTAX            RollCallString
        MAX-ACCESS        read-only
        STATUS            current
        DESCRIPTION
                "CMNT: - Embedded audio output clip
                 TYPE: - Display
                 PAGE: - Emb.Gain
                    Embed 5-L Clip  cmdID= 37548  "
        ::= { iqsyn22CmdEntry 37548 }


    iqsyn22EmbGainEmbedPair5Embed5RClip OBJECT-TYPE
        SYNTAX            RollCallString
        MAX-ACCESS        read-only
        STATUS            current
        DESCRIPTION
                "CMNT: - Embedded audio output clip
                 TYPE: - Display
                 PAGE: - Emb.Gain
                    Embed 5-R Clip  cmdID= 37549  "
        ::= { iqsyn22CmdEntry 37549 }


    iqsyn22EmbGainEmbedPair6Embed6MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 6 Mute L  cmdID= 37350  "
        ::= { iqsyn22CmdEntry 37350 }


    iqsyn22EmbGainEmbedPair6Embed6MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 6 Mute R  cmdID= 37351  "
        ::= { iqsyn22CmdEntry 37351 }


    iqsyn22EmbGainEmbedPair6Embed6LGain OBJECT-TYPE
        SYNTAX            INTEGER
        MAX-ACCESS        read-write
        STATUS            current
        DESCRIPTION
                "CMNT: - Embedded audio gain
                 TYPE: - Number
                 PAGE: - Emb.Gain
                    Embed 6 L Gain  cmdID= 37330
                    min= -661  max= 120  step= 1  format= %0.1f dB  div_scale= 10  preset= 0
                    Min = -66.1 dB  Max = 12.0 dB  Step = 0.1 dB  Preset = 0.0 dB  "
        ::= { iqsyn22CmdEntry 37330 }


    iqsyn22EmbGainEmbedPair6Embed6RGain OBJECT-TYPE
        SYNTAX            INTEGER
        MAX-ACCESS        read-write
        STATUS            current
        DESCRIPTION
                "CMNT: - Embedded audio gain
                 TYPE: - Number
                 PAGE: - Emb.Gain
                    Embed 6 R Gain  cmdID= 37331
                    min= -661  max= 120  step= 1  format= %0.1f dB  div_scale= 10  preset= 0
                    Min = -66.1 dB  Max = 12.0 dB  Step = 0.1 dB  Preset = 0.0 dB  "
        ::= { iqsyn22CmdEntry 37331 }


    iqsyn22EmbGainEmbedPair6Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37385  "
        ::= { iqsyn22CmdEntry 37385 }


    iqsyn22EmbGainEmbedPair6Embed6InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 6 Invert L  cmdID= 37370  "
        ::= { iqsyn22CmdEntry 37370 }


    iqsyn22EmbGainEmbedPair6Embed6InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 6 Invert R  cmdID= 37371  "
        ::= { iqsyn22CmdEntry 37371 }


    iqsyn22EmbGainEmbedPair6Embed6LClip OBJECT-TYPE
        SYNTAX            RollCallString
        MAX-ACCESS        read-only
        STATUS            current
        DESCRIPTION
                "CMNT: - Embedded audio output clip
                 TYPE: - Display
                 PAGE: - Emb.Gain
                    Embed 6-L Clip  cmdID= 37550  "
        ::= { iqsyn22CmdEntry 37550 }


    iqsyn22EmbGainEmbedPair6Embed6RClip OBJECT-TYPE
        SYNTAX            RollCallString
        MAX-ACCESS        read-only
        STATUS            current
        DESCRIPTION
                "CMNT: - Embedded audio output clip
                 TYPE: - Display
                 PAGE: - Emb.Gain
                    Embed 6-R Clip  cmdID= 37551  "
        ::= { iqsyn22CmdEntry 37551 }


    iqsyn22EmbGainEmbedPair7Embed7MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 7 Mute L  cmdID= 37352  "
        ::= { iqsyn22CmdEntry 37352 }


    iqsyn22EmbGainEmbedPair7Embed7MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 7 Mute R  cmdID= 37353  "
        ::= { iqsyn22CmdEntry 37353 }


    iqsyn22EmbGainEmbedPair7Embed7LGain OBJECT-TYPE
        SYNTAX            INTEGER
        MAX-ACCESS        read-write
        STATUS            current
        DESCRIPTION
                "CMNT: - Embedded audio gain
                 TYPE: - Number
                 PAGE: - Emb.Gain
                    Embed 7 L Gain  cmdID= 37332
                    min= -661  max= 120  step= 1  format= %0.1f dB  div_scale= 10  preset= 0
                    Min = -66.1 dB  Max = 12.0 dB  Step = 0.1 dB  Preset = 0.0 dB  "
        ::= { iqsyn22CmdEntry 37332 }


    iqsyn22EmbGainEmbedPair7Embed7RGain OBJECT-TYPE
        SYNTAX            INTEGER
        MAX-ACCESS        read-write
        STATUS            current
        DESCRIPTION
                "CMNT: - Embedded audio gain
                 TYPE: - Number
                 PAGE: - Emb.Gain
                    Embed 7 R Gain  cmdID= 37333
                    min= -661  max= 120  step= 1  format= %0.1f dB  div_scale= 10  preset= 0
                    Min = -66.1 dB  Max = 12.0 dB  Step = 0.1 dB  Preset = 0.0 dB  "
        ::= { iqsyn22CmdEntry 37333 }


    iqsyn22EmbGainEmbedPair7Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37386  "
        ::= { iqsyn22CmdEntry 37386 }


    iqsyn22EmbGainEmbedPair7Embed7InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 7 Invert L  cmdID= 37372  "
        ::= { iqsyn22CmdEntry 37372 }


    iqsyn22EmbGainEmbedPair7Embed7InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 7 Invert R  cmdID= 37373  "
        ::= { iqsyn22CmdEntry 37373 }


    iqsyn22EmbGainEmbedPair7Embed7LClip OBJECT-TYPE
        SYNTAX            RollCallString
        MAX-ACCESS        read-only
        STATUS            current
        DESCRIPTION
                "CMNT: - Embedded audio output clip
                 TYPE: - Display
                 PAGE: - Emb.Gain
                    Embed 7-L Clip  cmdID= 37552  "
        ::= { iqsyn22CmdEntry 37552 }


    iqsyn22EmbGainEmbedPair7Embed7RClip OBJECT-TYPE
        SYNTAX            RollCallString
        MAX-ACCESS        read-only
        STATUS            current
        DESCRIPTION
                "CMNT: - Embedded audio output clip
                 TYPE: - Display
                 PAGE: - Emb.Gain
                    Embed 7-R Clip  cmdID= 37553  "
        ::= { iqsyn22CmdEntry 37553 }


    iqsyn22EmbGainEmbedPair8Embed8MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 8 Mute L  cmdID= 37354  "
        ::= { iqsyn22CmdEntry 37354 }


    iqsyn22EmbGainEmbedPair8Embed8MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 8 Mute R  cmdID= 37355  "
        ::= { iqsyn22CmdEntry 37355 }


    iqsyn22EmbGainEmbedPair8Embed8LGain OBJECT-TYPE
        SYNTAX            INTEGER
        MAX-ACCESS        read-write
        STATUS            current
        DESCRIPTION
                "CMNT: - Embedded audio gain
                 TYPE: - Number
                 PAGE: - Emb.Gain
                    Embed 8 L Gain  cmdID= 37334
                    min= -661  max= 120  step= 1  format= %0.1f dB  div_scale= 10  preset= 0
                    Min = -66.1 dB  Max = 12.0 dB  Step = 0.1 dB  Preset = 0.0 dB  "
        ::= { iqsyn22CmdEntry 37334 }


    iqsyn22EmbGainEmbedPair8Embed8RGain OBJECT-TYPE
        SYNTAX            INTEGER
        MAX-ACCESS        read-write
        STATUS            current
        DESCRIPTION
                "CMNT: - Embedded audio gain
                 TYPE: - Number
                 PAGE: - Emb.Gain
                    Embed 8 R Gain  cmdID= 37335
                    min= -661  max= 120  step= 1  format= %0.1f dB  div_scale= 10  preset= 0
                    Min = -66.1 dB  Max = 12.0 dB  Step = 0.1 dB  Preset = 0.0 dB  "
        ::= { iqsyn22CmdEntry 37335 }


    iqsyn22EmbGainEmbedPair8Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37387  "
        ::= { iqsyn22CmdEntry 37387 }


    iqsyn22EmbGainEmbedPair8Embed8InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 8 Invert L  cmdID= 37374  "
        ::= { iqsyn22CmdEntry 37374 }


    iqsyn22EmbGainEmbedPair8Embed8InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 8 Invert R  cmdID= 37375  "
        ::= { iqsyn22CmdEntry 37375 }


    iqsyn22EmbGainEmbedPair8Embed8LClip OBJECT-TYPE
        SYNTAX            RollCallString
        MAX-ACCESS        read-only
        STATUS            current
        DESCRIPTION
                "CMNT: - Embedded audio output clip
                 TYPE: - Display
                 PAGE: - Emb.Gain
                    Embed 8-L Clip  cmdID= 37554  "
        ::= { iqsyn22CmdEntry 37554 }


    iqsyn22EmbGainEmbedPair8Embed8RClip OBJECT-TYPE
        SYNTAX            RollCallString
        MAX-ACCESS        read-only
        STATUS            current
        DESCRIPTION
                "CMNT: - Embedded audio output clip
                 TYPE: - Display
                 PAGE: - Emb.Gain
                    Embed 8-R Clip  cmdID= 37555  "
        ::= { iqsyn22CmdEntry 37555 }


    iqsyn22EmbOutEmbedPair1Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37300
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37300 }


    iqsyn22EmbOutEmbedPair1Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37301
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37301 }


    iqsyn22EmbOutEmbedPair1LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37390  "
        ::= { iqsyn22CmdEntry 37390 }


    iqsyn22EmbOutEmbedPair2Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37302
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37302 }


    iqsyn22EmbOutEmbedPair2Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37303
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37303 }


    iqsyn22EmbOutEmbedPair2LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37391  "
        ::= { iqsyn22CmdEntry 37391 }


    iqsyn22EmbOutEmbedPair3Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37304
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37304 }


    iqsyn22EmbOutEmbedPair3Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37305
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37305 }


    iqsyn22EmbOutEmbedPair3LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37392  "
        ::= { iqsyn22CmdEntry 37392 }


    iqsyn22EmbOutEmbedPair4Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37306
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37306 }


    iqsyn22EmbOutEmbedPair4Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37307
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37307 }


    iqsyn22EmbOutEmbedPair4LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37393  "
        ::= { iqsyn22CmdEntry 37393 }


    iqsyn22EmbOutEmbedPair5Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37308
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37308 }


    iqsyn22EmbOutEmbedPair5Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37309
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37309 }


    iqsyn22EmbOutEmbedPair5LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37394  "
        ::= { iqsyn22CmdEntry 37394 }


    iqsyn22EmbOutEmbedPair6Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37310
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37310 }


    iqsyn22EmbOutEmbedPair6Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37311
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37311 }


    iqsyn22EmbOutEmbedPair6LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37395  "
        ::= { iqsyn22CmdEntry 37395 }


    iqsyn22EmbOutEmbedPair7Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37312
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37312 }


    iqsyn22EmbOutEmbedPair7Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37313
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37313 }


    iqsyn22EmbOutEmbedPair7LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37396  "
        ::= { iqsyn22CmdEntry 37396 }


    iqsyn22EmbOutEmbedPair8Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37314
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37314 }


    iqsyn22EmbOutEmbedPair8Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37315
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37315 }


    iqsyn22EmbOutEmbedPair8LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37397  "
        ::= { iqsyn22CmdEntry 37397 }


    iqsyn22AudioEmbDataInput1 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 1  cmdID= 37420
                    PCM  value= 0
                    Data  value= 1
                    Mixed  value= 2  "
        ::= { iqsyn22CmdEntry 37420 }


    iqsyn22AudioEmbDataInput2 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 2  cmdID= 37421
                    PCM  value= 0
                    Data  value= 1
                    Mixed  value= 2  "
        ::= { iqsyn22CmdEntry 37421 }


    iqsyn22AudioEmbDataInput3 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 3  cmdID= 37422
                    PCM  value= 0
                    Data  value= 1
                    Mixed  value= 2  "
        ::= { iqsyn22CmdEntry 37422 }


    iqsyn22AudioEmbDataInput4 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 4  cmdID= 37423
                    PCM  value= 0
                    Data  value= 1
                    Mixed  value= 2  "
        ::= { iqsyn22CmdEntry 37423 }


    iqsyn22AudioEmbDataInput5 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 5  cmdID= 37424
                    PCM  value= 0
                    Data  value= 1
                    Mixed  value= 2  "
        ::= { iqsyn22CmdEntry 37424 }


    iqsyn22AudioEmbDataInput6 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 6  cmdID= 37425
                    PCM  value= 0
                    Data  value= 1
                    Mixed  value= 2  "
        ::= { iqsyn22CmdEntry 37425 }


    iqsyn22AudioEmbDataInput7 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 7  cmdID= 37426
                    PCM  value= 0
                    Data  value= 1
                    Mixed  value= 2  "
        ::= { iqsyn22CmdEntry 37426 }


    iqsyn22AudioEmbDataInput8 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 8  cmdID= 37427
                    PCM  value= 0
                    Data  value= 1
                    Mixed  value= 2  "
        ::= { iqsyn22CmdEntry 37427 }


    iqsyn22DisembedderNamesDisemb1L OBJECT-TYPE
        SYNTAX            RollCallString
        MAX-ACCESS        read-write
        STATUS            current
        DESCRIPTION
                "CMNT: - Embedded audio input name
                 TYPE: - Editstring
                 PAGE: - Disembedder Names
                    Disembed 1  cmdID= 37500
                    preset= Disembed 1"
        ::= { iqsyn22CmdEntry 37500 }


    iqsyn22DisembedderNamesDisemb1R OBJECT-TYPE
        SYNTAX            RollCallString
        MAX-ACCESS        read-write
        STATUS            current
        DESCRIPTION
                "CMNT: - Embedded audio input name
                 TYPE: - Editstring
                 PAGE: - Disembedder Names
                    Disembed 1-R  cmdID= 37501
                    preset= Disembed 1-R"
        ::= { iqsyn22CmdEntry 37501 }


    iqsyn22DisembedderNamesDisemb2L OBJECT-TYPE
        SYNTAX            RollCallString
        MAX-ACCESS        read-write
        STATUS            current
        DESCRIPTION
                "CMNT: - Embedded audio input name
                 TYPE: - Editstring
                 PAGE: - Disembedder Names
                    Disembed 2  cmdID= 37502
                    preset= Disembed 2"
        ::= { iqsyn22CmdEntry 37502 }


    iqsyn22DisembedderNamesDisemb2R OBJECT-TYPE
        SYNTAX            RollCallString
        MAX-ACCESS        read-write
        STATUS            current
        DESCRIPTION
                "CMNT: - Embedded audio input name
                 TYPE: - Editstring
                 PAGE: - Disembedder Names
                    Disembed 2-R  cmdID= 37503
                    preset= Disembed 2-R"
        ::= { iqsyn22CmdEntry 37503 }


    iqsyn22DisembedderNamesDisemb3L OBJECT-TYPE
        SYNTAX            RollCallString
        MAX-ACCESS        read-write
        STATUS            current
        DESCRIPTION
                "CMNT: - Embedded audio input name
                 TYPE: - Editstring
                 PAGE: - Disembedder Names
                    Disembed 3  cmdID= 37504
                    preset= Disembed 3"
        ::= { iqsyn22CmdEntry 37504 }


    iqsyn22DisembedderNamesDisemb3R OBJECT-TYPE
        SYNTAX            RollCallString
        MAX-ACCESS        read-write
        STATUS            current
        DESCRIPTION
                "CMNT: - Embedded audio input name
                 TYPE: - Editstring
                 PAGE: - Disembedder Names
                    Disembed 3-R  cmdID= 37505
                    preset= Disembed 3-R"
        ::= { iqsyn22CmdEntry 37505 }


    iqsyn22DisembedderNamesDisemb4L OBJECT-TYPE
        SYNTAX            RollCallString
        MAX-ACCESS        read-write
        STATUS            current
        DESCRIPTION
                "CMNT: - Embedded audio input name
                 TYPE: - Editstring
                 PAGE: - Disembedder Names
                    Disembed 4  cmdID= 37506
                    preset= Disembed 4"
        ::= { iqsyn22CmdEntry 37506 }


    iqsyn22DisembedderNamesDisemb4R OBJECT-TYPE
        SYNTAX            RollCallString
        MAX-ACCESS        read-write
        STATUS            current
        DESCRIPTION
                "CMNT: - Embedded audio input name
                 TYPE: - Editstring
                 PAGE: - Disembedder Names
                    Disembed 4-R  cmdID= 37507
                    preset= Disembed 4-R"
        ::= { iqsyn22CmdEntry 37507 }


    iqsyn22DisembedderNamesDisemb5L OBJECT-TYPE
        SYNTAX            RollCallString
        MAX-ACCESS        read-write
        STATUS            current
        DESCRIPTION
                "CMNT: - Embedded audio input name
                 TYPE: - Editstring
                 PAGE: - Disembedder Names
                    Disembed 5  cmdID= 37508
                    preset= Disembed 5"
        ::= { iqsyn22CmdEntry 37508 }


    iqsyn22DisembedderNamesDisemb5R OBJECT-TYPE
        SYNTAX            RollCallString
        MAX-ACCESS        read-write
        STATUS            current
        DESCRIPTION
                "CMNT: - Embedded audio input name
                 TYPE: - Editstring
                 PAGE: - Disembedder Names
                    Disembed 5-R  cmdID= 37509
                    preset= Disembed 5-R"
        ::= { iqsyn22CmdEntry 37509 }


    iqsyn22DisembedderNamesDisemb6L OBJECT-TYPE
        SYNTAX            RollCallString
        MAX-ACCESS        read-write
        STATUS            current
        DESCRIPTION
                "CMNT: - Embedded audio input name
                 TYPE: - Editstring
                 PAGE: - Disembedder Names
                    Disembed 6  cmdID= 37510
                    preset= Disembed 6"
        ::= { iqsyn22CmdEntry 37510 }


    iqsyn22DisembedderNamesDisemb6R OBJECT-TYPE
        SYNTAX            RollCallString
        MAX-ACCESS        read-write
        STATUS            current
        DESCRIPTION
                "CMNT: - Embedded audio input name
                 TYPE: - Editstring
                 PAGE: - Disembedder Names
                    Disembed 6-R  cmdID= 37511
                    preset= Disembed 6-R"
        ::= { iqsyn22CmdEntry 37511 }


    iqsyn22DisembedderNamesDisemb7L OBJECT-TYPE
        SYNTAX            RollCallString
        MAX-ACCESS        read-write
        STATUS            current
        DESCRIPTION
                "CMNT: - Embedded audio input name
                 TYPE: - Editstring
                 PAGE: - Disembedder Names
                    Disembed 7  cmdID= 37512
                    preset= Disembed 7"
        ::= { iqsyn22CmdEntry 37512 }


    iqsyn22DisembedderNamesDisemb7R OBJECT-TYPE
        SYNTAX            RollCallString
        MAX-ACCESS        read-write
        STATUS            current
        DESCRIPTION
                "CMNT: - Embedded audio input name
                 TYPE: - Editstring
                 PAGE: - Disembedder Names
                    Disembed 7-R  cmdID= 37513
                    preset= Disembed 7-R"
        ::= { iqsyn22CmdEntry 37513 }


    iqsyn22DisembedderNamesDisemb8L OBJECT-TYPE
        SYNTAX            RollCallString
        MAX-ACCESS        read-write
        STATUS            current
        DESCRIPTION
                "CMNT: - Embedded audio input name
                 TYPE: - Editstring
                 PAGE: - Disembedder Names
                    Disembed 8  cmdID= 37514
                    preset= Disembed 8"
        ::= { iqsyn22CmdEntry 37514 }


    iqsyn22DisembedderNamesDisemb8R OBJECT-TYPE
        SYNTAX            RollCallString
        MAX-ACCESS        read-write
        STATUS            current
        DESCRIPTION
                "CMNT: - Embedded audio input name
                 TYPE: - Editstring
                 PAGE: - Disembedder Names
                    Disembed 8-R  cmdID= 37515
                    preset= Disembed 8-R"
        ::= { iqsyn22CmdEntry 37515 }


    iqsyn22DisembedderNamesEmbeddedOPEmbed1L OBJECT-TYPE
        SYNTAX            RollCallString
        MAX-ACCESS        read-write
        STATUS            current
        DESCRIPTION
                "CMNT: - Embedded audio output name
                 TYPE: - Editstring
                 PAGE: - Disembedder Names
                    Embed 1  cmdID= 37520
                    preset= Embed 1"
        ::= { iqsyn22CmdEntry 37520 }


    iqsyn22DisembedderNamesEmbeddedOPEmbed1R OBJECT-TYPE
        SYNTAX            RollCallString
        MAX-ACCESS        read-write
        STATUS            current
        DESCRIPTION
                "CMNT: - Embedded audio output name
                 TYPE: - Editstring
                 PAGE: - Disembedder Names
                    Embed 1-R  cmdID= 37521
                    preset= Embed 1-R"
        ::= { iqsyn22CmdEntry 37521 }


    iqsyn22DisembedderNamesEmbeddedOPEmbed2L OBJECT-TYPE
        SYNTAX            RollCallString
        MAX-ACCESS        read-write
        STATUS            current
        DESCRIPTION
                "CMNT: - Embedded audio output name
                 TYPE: - Editstring
                 PAGE: - Disembedder Names
                    Embed 2  cmdID= 37522
                    preset= Embed 2"
        ::= { iqsyn22CmdEntry 37522 }


    iqsyn22DisembedderNamesEmbeddedOPEmbed2R OBJECT-TYPE
        SYNTAX            RollCallString
        MAX-ACCESS        read-write
        STATUS            current
        DESCRIPTION
                "CMNT: - Embedded audio output name
                 TYPE: - Editstring
                 PAGE: - Disembedder Names
                    Embed 2-R  cmdID= 37523
                    preset= Embed 2-R"
        ::= { iqsyn22CmdEntry 37523 }


    iqsyn22DisembedderNamesEmbeddedOPEmbed3L OBJECT-TYPE
        SYNTAX            RollCallString
        MAX-ACCESS        read-write
        STATUS            current
        DESCRIPTION
                "CMNT: - Embedded audio output name
                 TYPE: - Editstring
                 PAGE: - Disembedder Names
                    Embed 3  cmdID= 37524
                    preset= Embed 3"
        ::= { iqsyn22CmdEntry 37524 }


    iqsyn22DisembedderNamesEmbeddedOPEmbed3R OBJECT-TYPE
        SYNTAX            RollCallString
        MAX-ACCESS        read-write
        STATUS            current
        DESCRIPTION
                "CMNT: - Embedded audio output name
                 TYPE: - Editstring
                 PAGE: - Disembedder Names
                    Embed 3-R  cmdID= 37525
                    preset= Embed 3-R"
        ::= { iqsyn22CmdEntry 37525 }


    iqsyn22DisembedderNamesEmbeddedOPEmbed4L OBJECT-TYPE
        SYNTAX            RollCallString
        MAX-ACCESS        read-write
        STATUS            current
        DESCRIPTION
                "CMNT: - Embedded audio output name
                 TYPE: - Editstring
                 PAGE: - Disembedder Names
                    Embed 4  cmdID= 37526
                    preset= Embed 4"
        ::= { iqsyn22CmdEntry 37526 }


    iqsyn22DisembedderNamesEmbeddedOPEmbed4R OBJECT-TYPE
        SYNTAX            RollCallString
        MAX-ACCESS        read-write
        STATUS            current
        DESCRIPTION
                "CMNT: - Embedded audio output name
                 TYPE: - Editstring
                 PAGE: - Disembedder Names
                    Embed 4-R  cmdID= 37527
                    preset= Embed 4-R"
        ::= { iqsyn22CmdEntry 37527 }


    iqsyn22DisembedderNamesEmbeddedOPEmbed5L OBJECT-TYPE
        SYNTAX            RollCallString
        MAX-ACCESS        read-write
        STATUS            current
        DESCRIPTION
                "CMNT: - Embedded audio output name
                 TYPE: - Editstring
                 PAGE: - Disembedder Names
                    Embed 5  cmdID= 37528
                    preset= Embed 5"
        ::= { iqsyn22CmdEntry 37528 }


    iqsyn22DisembedderNamesEmbeddedOPEmbed5R OBJECT-TYPE
        SYNTAX            RollCallString
        MAX-ACCESS        read-write
        STATUS            current
        DESCRIPTION
                "CMNT: - Embedded audio output name
                 TYPE: - Editstring
                 PAGE: - Disembedder Names
                    Embed 5-R  cmdID= 37529
                    preset= Embed 5-R"
        ::= { iqsyn22CmdEntry 37529 }


    iqsyn22DisembedderNamesEmbeddedOPEmbed6L OBJECT-TYPE
        SYNTAX            RollCallString
        MAX-ACCESS        read-write
        STATUS            current
        DESCRIPTION
                "CMNT: - Embedded audio output name
                 TYPE: - Editstring
                 PAGE: - Disembedder Names
                    Embed 6  cmdID= 37530
                    preset= Embed 6"
        ::= { iqsyn22CmdEntry 37530 }


    iqsyn22DisembedderNamesEmbeddedOPEmbed6R OBJECT-TYPE
        SYNTAX            RollCallString
        MAX-ACCESS        read-write
        STATUS            current
        DESCRIPTION
                "CMNT: - Embedded audio output name
                 TYPE: - Editstring
                 PAGE: - Disembedder Names
                    Embed 6-R  cmdID= 37531
                    preset= Embed 6-R"
        ::= { iqsyn22CmdEntry 37531 }


    iqsyn22DisembedderNamesEmbeddedOPEmbed7L OBJECT-TYPE
        SYNTAX            RollCallString
        MAX-ACCESS        read-write
        STATUS            current
        DESCRIPTION
                "CMNT: - Embedded audio output name
                 TYPE: - Editstring
                 PAGE: - Disembedder Names
                    Embed 7  cmdID= 37532
                    preset= Embed 7"
        ::= { iqsyn22CmdEntry 37532 }


    iqsyn22DisembedderNamesEmbeddedOPEmbed7R OBJECT-TYPE
        SYNTAX            RollCallString
        MAX-ACCESS        read-write
        STATUS            current
        DESCRIPTION
                "CMNT: - Embedded audio output name
                 TYPE: - Editstring
                 PAGE: - Disembedder Names
                    Embed 7-R  cmdID= 37533
                    preset= Embed 7-R"
        ::= { iqsyn22CmdEntry 37533 }


    iqsyn22DisembedderNamesEmbeddedOPEmbed8L OBJECT-TYPE
        SYNTAX            RollCallString
        MAX-ACCESS        read-write
        STATUS            current
        DESCRIPTION
                "CMNT: - Embedded audio output name
                 TYPE: - Editstring
                 PAGE: - Disembedder Names
                    Embed 8  cmdID= 37534
                    preset= Embed 8"
        ::= { iqsyn22CmdEntry 37534 }


    iqsyn22DisembedderNamesEmbeddedOPEmbed8R OBJECT-TYPE
        SYNTAX            RollCallString
        MAX-ACCESS        read-write
        STATUS            current
        DESCRIPTION
                "CMNT: - Embedded audio output name
                 TYPE: - Editstring
                 PAGE: - Disembedder Names
                    Embed 8-R  cmdID= 37535
                    preset= Embed 8-R"
        ::= { iqsyn22CmdEntry 37535 }


    iqsyn22DisembedderNamesIPNamesStereoDisemb1 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 1  cmdID= 37400  "
        ::= { iqsyn22CmdEntry 37400 }


    iqsyn22DisembedderNamesIPNamesStereoDisemb2 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 2  cmdID= 37401  "
        ::= { iqsyn22CmdEntry 37401 }


    iqsyn22DisembedderNamesIPNamesStereoDisemb3 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 3  cmdID= 37402  "
        ::= { iqsyn22CmdEntry 37402 }


    iqsyn22DisembedderNamesIPNamesStereoDisemb4 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 4  cmdID= 37403  "
        ::= { iqsyn22CmdEntry 37403 }


    iqsyn22DisembedderNamesIPNamesStereoDisemb5 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 5  cmdID= 37404  "
        ::= { iqsyn22CmdEntry 37404 }


    iqsyn22DisembedderNamesIPNamesStereoDisemb6 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 6  cmdID= 37405  "
        ::= { iqsyn22CmdEntry 37405 }


    iqsyn22DisembedderNamesIPNamesStereoDisemb7 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 7  cmdID= 37406  "
        ::= { iqsyn22CmdEntry 37406 }


    iqsyn22DisembedderNamesIPNamesStereoDisemb8 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 8  cmdID= 37407  "
        ::= { iqsyn22CmdEntry 37407 }


    iqsyn22DisembedderNamesOPNamesStereoEmbed1 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 1  cmdID= 37410  "
        ::= { iqsyn22CmdEntry 37410 }


    iqsyn22DisembedderNamesOPNamesStereoEmbed2 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 2  cmdID= 37411  "
        ::= { iqsyn22CmdEntry 37411 }


    iqsyn22DisembedderNamesOPNamesStereoEmbed3 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 3  cmdID= 37412  "
        ::= { iqsyn22CmdEntry 37412 }


    iqsyn22DisembedderNamesOPNamesStereoEmbed4 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 4  cmdID= 37413  "
        ::= { iqsyn22CmdEntry 37413 }


    iqsyn22DisembedderNamesOPNamesStereoEmbed5 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 5  cmdID= 37414  "
        ::= { iqsyn22CmdEntry 37414 }


    iqsyn22DisembedderNamesOPNamesStereoEmbed6 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 6  cmdID= 37415  "
        ::= { iqsyn22CmdEntry 37415 }


    iqsyn22DisembedderNamesOPNamesStereoEmbed7 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 7  cmdID= 37416  "
        ::= { iqsyn22CmdEntry 37416 }


    iqsyn22DisembedderNamesOPNamesStereoEmbed8 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 8  cmdID= 37417  "
        ::= { iqsyn22CmdEntry 37417 }


    iqsyn22NamesMixNamesMix1 OBJECT-TYPE
        SYNTAX            RollCallString
        MAX-ACCESS        read-write
        STATUS            current
        DESCRIPTION
                "CMNT: - Mixer names
                 TYPE: - Editstring
                 PAGE: - Names
                    Mix 1  cmdID= 37810
                    preset= Mixer 1"
        ::= { iqsyn22CmdEntry 37810 }


    iqsyn22NamesMixNamesMix2 OBJECT-TYPE
        SYNTAX            RollCallString
        MAX-ACCESS        read-write
        STATUS            current
        DESCRIPTION
                "CMNT: - Mixer names
                 TYPE: - Editstring
                 PAGE: - Names
                    Mix 2  cmdID= 37811
                    preset= Mixer 2"
        ::= { iqsyn22CmdEntry 37811 }


    iqsyn22NamesMixNamesMix3 OBJECT-TYPE
        SYNTAX            RollCallString
        MAX-ACCESS        read-write
        STATUS            current
        DESCRIPTION
                "CMNT: - Mixer names
                 TYPE: - Editstring
                 PAGE: - Names
                    Mix 3  cmdID= 37812
                    preset= Mixer 3"
        ::= { iqsyn22CmdEntry 37812 }


    iqsyn22NamesMixNamesMix4 OBJECT-TYPE
        SYNTAX            RollCallString
        MAX-ACCESS        read-write
        STATUS            current
        DESCRIPTION
                "CMNT: - Mixer names
                 TYPE: - Editstring
                 PAGE: - Names
                    Mix 4  cmdID= 37813
                    preset= Mixer 4"
        ::= { iqsyn22CmdEntry 37813 }


    iqsyn22Mix1Mix1RoutingSource1 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 1  cmdID= 37600
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37600 }


    iqsyn22Mix1Mix1RoutingInvert1 OBJECT-TYPE
        SYNTAX            INTEGER { disable(0), enable(1)  }
        MAX-ACCESS        read-write
        STATUS            current
        DESCRIPTION
                "CMNT: - Mixer source phase invert
                 TYPE: - Checkbox
                 PAGE: - Audio
                    Invert 1  cmdID= 37720  "
        ::= { iqsyn22CmdEntry 37720 }


    iqsyn22Mix1Mix1RoutingSource2 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 2  cmdID= 37601
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37601 }


    iqsyn22Mix1Mix1RoutingInvert2 OBJECT-TYPE
        SYNTAX            INTEGER { disable(0), enable(1)  }
        MAX-ACCESS        read-write
        STATUS            current
        DESCRIPTION
                "CMNT: - Mixer source phase invert
                 TYPE: - Checkbox
                 PAGE: - Audio
                    Invert 2  cmdID= 37721  "
        ::= { iqsyn22CmdEntry 37721 }


    iqsyn22Mix1Mix1RoutingSource3 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 3  cmdID= 37602
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37602 }


    iqsyn22Mix1Mix1RoutingInvert3 OBJECT-TYPE
        SYNTAX            INTEGER { disable(0), enable(1)  }
        MAX-ACCESS        read-write
        STATUS            current
        DESCRIPTION
                "CMNT: - Mixer source phase invert
                 TYPE: - Checkbox
                 PAGE: - Audio
                    Invert 3  cmdID= 37722  "
        ::= { iqsyn22CmdEntry 37722 }


    iqsyn22Mix1Mix1RoutingSource4 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 4  cmdID= 37603
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37603 }


    iqsyn22Mix1Mix1RoutingInvert4 OBJECT-TYPE
        SYNTAX            INTEGER { disable(0), enable(1)  }
        MAX-ACCESS        read-write
        STATUS            current
        DESCRIPTION
                "CMNT: - Mixer source phase invert
                 TYPE: - Checkbox
                 PAGE: - Audio
                    Invert 4  cmdID= 37723  "
        ::= { iqsyn22CmdEntry 37723 }


    iqsyn22Mix1Mix1GainGain1 OBJECT-TYPE
        SYNTAX            INTEGER
        MAX-ACCESS        read-write
        STATUS            current
        DESCRIPTION
                "CMNT: - Mixer source gain
                 TYPE: - Number
                 PAGE: - Audio
                    Gain 1  cmdID= 37640
                    min= -360  max= 120  step= 1  format= %0.1f dB  div_scale= 10  preset= 0
                    Min = -36.0 dB  Max = 12.0 dB  Step = 0.1 dB  Preset = 0.0 dB  "
        ::= { iqsyn22CmdEntry 37640 }


    iqsyn22Mix1Mix1GainMute1 OBJECT-TYPE
        SYNTAX            INTEGER { disable(0), enable(1)  }
        MAX-ACCESS        read-write
        STATUS            current
        DESCRIPTION
                "CMNT: - Mixer source mutes
                 TYPE: - Checkbox
                 PAGE: - Audio
                    Mute 1  cmdID= 37680  "
        ::= { iqsyn22CmdEntry 37680 }


    iqsyn22Mix1Mix1GainGain2 OBJECT-TYPE
        SYNTAX            INTEGER
        MAX-ACCESS        read-write
        STATUS            current
        DESCRIPTION
                "CMNT: - Mixer source gain
                 TYPE: - Number
                 PAGE: - Audio
                    Gain 2  cmdID= 37641
                    min= -360  max= 120  step= 1  format= %0.1f dB  div_scale= 10  preset= 0
                    Min = -36.0 dB  Max = 12.0 dB  Step = 0.1 dB  Preset = 0.0 dB  "
        ::= { iqsyn22CmdEntry 37641 }


    iqsyn22Mix1Mix1GainMute2 OBJECT-TYPE
        SYNTAX            INTEGER { disable(0), enable(1)  }
        MAX-ACCESS        read-write
        STATUS            current
        DESCRIPTION
                "CMNT: - Mixer source mutes
                 TYPE: - Checkbox
                 PAGE: - Audio
                    Mute 2  cmdID= 37681  "
        ::= { iqsyn22CmdEntry 37681 }


    iqsyn22Mix1Mix1GainGain3 OBJECT-TYPE
        SYNTAX            INTEGER
        MAX-ACCESS        read-write
        STATUS            current
        DESCRIPTION
                "CMNT: - Mixer source gain
                 TYPE: - Number
                 PAGE: - Audio
                    Gain 3  cmdID= 37642
                    min= -360  max= 120  step= 1  format= %0.1f dB  div_scale= 10  preset= 0
                    Min = -36.0 dB  Max = 12.0 dB  Step = 0.1 dB  Preset = 0.0 dB  "
        ::= { iqsyn22CmdEntry 37642 }


    iqsyn22Mix1Mix1GainMute3 OBJECT-TYPE
        SYNTAX            INTEGER { disable(0), enable(1)  }
        MAX-ACCESS        read-write
        STATUS            current
        DESCRIPTION
                "CMNT: - Mixer source mutes
                 TYPE: - Checkbox
                 PAGE: - Audio
                    Mute 3  cmdID= 37682  "
        ::= { iqsyn22CmdEntry 37682 }


    iqsyn22Mix1Mix1GainGain4 OBJECT-TYPE
        SYNTAX            INTEGER
        MAX-ACCESS        read-write
        STATUS            current
        DESCRIPTION
                "CMNT: - Mixer source gain
                 TYPE: - Number
                 PAGE: - Audio
                    Gain 4  cmdID= 37643
                    min= -360  max= 120  step= 1  format= %0.1f dB  div_scale= 10  preset= 0
                    Min = -36.0 dB  Max = 12.0 dB  Step = 0.1 dB  Preset = 0.0 dB  "
        ::= { iqsyn22CmdEntry 37643 }


    iqsyn22Mix1Mix1GainMute4 OBJECT-TYPE
        SYNTAX            INTEGER { disable(0), enable(1)  }
        MAX-ACCESS        read-write
        STATUS            current
        DESCRIPTION
                "CMNT: - Mixer source mutes
                 TYPE: - Checkbox
                 PAGE: - Audio
                    Mute 4  cmdID= 37683  "
        ::= { iqsyn22CmdEntry 37683 }


    iqsyn22Mix1Mix1GainInp1Clip OBJECT-TYPE
        SYNTAX            RollCallString
        MAX-ACCESS        read-only
        STATUS            current
        DESCRIPTION
                "CMNT: - Audio Mixer source clipped
                 TYPE: - Display
                 PAGE: - Audio
                    Inp1 Clip  cmdID= 37760  "
        ::= { iqsyn22CmdEntry 37760 }


    iqsyn22Mix1Mix1GainInp2Clip OBJECT-TYPE
        SYNTAX            RollCallString
        MAX-ACCESS        read-only
        STATUS            current
        DESCRIPTION
                "CMNT: - Audio Mixer source clipped
                 TYPE: - Display
                 PAGE: - Audio
                    Inp2 Clip  cmdID= 37761  "
        ::= { iqsyn22CmdEntry 37761 }


    iqsyn22Mix1Mix1GainInp3Clip OBJECT-TYPE
        SYNTAX            RollCallString
        MAX-ACCESS        read-only
        STATUS            current
        DESCRIPTION
                "CMNT: - Audio Mixer source clipped
                 TYPE: - Display
                 PAGE: - Audio
                    Inp3 Clip  cmdID= 37762  "
        ::= { iqsyn22CmdEntry 37762 }


    iqsyn22Mix1Mix1GainInp4Clip OBJECT-TYPE
        SYNTAX            RollCallString
        MAX-ACCESS        read-only
        STATUS            current
        DESCRIPTION
                "CMNT: - Audio Mixer source clipped
                 TYPE: - Display
                 PAGE: - Audio
                    Inp4 Clip  cmdID= 37763  "
        ::= { iqsyn22CmdEntry 37763 }


    iqsyn22Mix1Mix1GainOPClip OBJECT-TYPE
        SYNTAX            RollCallString
        MAX-ACCESS        read-only
        STATUS            current
        DESCRIPTION
                "CMNT: - Audio Mixer output clipped
                 TYPE: - Display
                 PAGE: - Audio
                    O/P Clip  cmdID= 37800  "
        ::= { iqsyn22CmdEntry 37800 }


    iqsyn22Mix2Mix2RoutingSource1 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 1  cmdID= 37604
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37604 }


    iqsyn22Mix2Mix2RoutingInvert1 OBJECT-TYPE
        SYNTAX            INTEGER { disable(0), enable(1)  }
        MAX-ACCESS        read-write
        STATUS            current
        DESCRIPTION
                "CMNT: - Mixer source phase invert
                 TYPE: - Checkbox
                 PAGE: - Audio
                    Invert 1  cmdID= 37724  "
        ::= { iqsyn22CmdEntry 37724 }


    iqsyn22Mix2Mix2RoutingSource2 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 2  cmdID= 37605
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37605 }


    iqsyn22Mix2Mix2RoutingInvert2 OBJECT-TYPE
        SYNTAX            INTEGER { disable(0), enable(1)  }
        MAX-ACCESS        read-write
        STATUS            current
        DESCRIPTION
                "CMNT: - Mixer source phase invert
                 TYPE: - Checkbox
                 PAGE: - Audio
                    Invert 2  cmdID= 37725  "
        ::= { iqsyn22CmdEntry 37725 }


    iqsyn22Mix2Mix2RoutingSource3 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 3  cmdID= 37606
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37606 }


    iqsyn22Mix2Mix2RoutingInvert3 OBJECT-TYPE
        SYNTAX            INTEGER { disable(0), enable(1)  }
        MAX-ACCESS        read-write
        STATUS            current
        DESCRIPTION
                "CMNT: - Mixer source phase invert
                 TYPE: - Checkbox
                 PAGE: - Audio
                    Invert 3  cmdID= 37726  "
        ::= { iqsyn22CmdEntry 37726 }


    iqsyn22Mix2Mix2RoutingSource4 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 4  cmdID= 37607
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37607 }


    iqsyn22Mix2Mix2RoutingInvert4 OBJECT-TYPE
        SYNTAX            INTEGER { disable(0), enable(1)  }
        MAX-ACCESS        read-write
        STATUS            current
        DESCRIPTION
                "CMNT: - Mixer source phase invert
                 TYPE: - Checkbox
                 PAGE: - Audio
                    Invert 4  cmdID= 37727  "
        ::= { iqsyn22CmdEntry 37727 }


    iqsyn22Mix2Mix2GainGain1 OBJECT-TYPE
        SYNTAX            INTEGER
        MAX-ACCESS        read-write
        STATUS            current
        DESCRIPTION
                "CMNT: - Mixer source gain
                 TYPE: - Number
                 PAGE: - Audio
                    Gain 1  cmdID= 37644
                    min= -360  max= 120  step= 1  format= %0.1f dB  div_scale= 10  preset= 0
                    Min = -36.0 dB  Max = 12.0 dB  Step = 0.1 dB  Preset = 0.0 dB  "
        ::= { iqsyn22CmdEntry 37644 }


    iqsyn22Mix2Mix2GainMute1 OBJECT-TYPE
        SYNTAX            INTEGER { disable(0), enable(1)  }
        MAX-ACCESS        read-write
        STATUS            current
        DESCRIPTION
                "CMNT: - Mixer source mutes
                 TYPE: - Checkbox
                 PAGE: - Audio
                    Mute 1  cmdID= 37684  "
        ::= { iqsyn22CmdEntry 37684 }


    iqsyn22Mix2Mix2GainGain2 OBJECT-TYPE
        SYNTAX            INTEGER
        MAX-ACCESS        read-write
        STATUS            current
        DESCRIPTION
                "CMNT: - Mixer source gain
                 TYPE: - Number
                 PAGE: - Audio
                    Gain 2  cmdID= 37645
                    min= -360  max= 120  step= 1  format= %0.1f dB  div_scale= 10  preset= 0
                    Min = -36.0 dB  Max = 12.0 dB  Step = 0.1 dB  Preset = 0.0 dB  "
        ::= { iqsyn22CmdEntry 37645 }


    iqsyn22Mix2Mix2GainMute2 OBJECT-TYPE
        SYNTAX            INTEGER { disable(0), enable(1)  }
        MAX-ACCESS        read-write
        STATUS            current
        DESCRIPTION
                "CMNT: - Mixer source mutes
                 TYPE: - Checkbox
                 PAGE: - Audio
                    Mute 2  cmdID= 37685  "
        ::= { iqsyn22CmdEntry 37685 }


    iqsyn22Mix2Mix2GainGain3 OBJECT-TYPE
        SYNTAX            INTEGER
        MAX-ACCESS        read-write
        STATUS            current
        DESCRIPTION
                "CMNT: - Mixer source gain
                 TYPE: - Number
                 PAGE: - Audio
                    Gain 3  cmdID= 37646
                    min= -360  max= 120  step= 1  format= %0.1f dB  div_scale= 10  preset= 0
                    Min = -36.0 dB  Max = 12.0 dB  Step = 0.1 dB  Preset = 0.0 dB  "
        ::= { iqsyn22CmdEntry 37646 }


    iqsyn22Mix2Mix2GainMute3 OBJECT-TYPE
        SYNTAX            INTEGER { disable(0), enable(1)  }
        MAX-ACCESS        read-write
        STATUS            current
        DESCRIPTION
                "CMNT: - Mixer source mutes
                 TYPE: - Checkbox
                 PAGE: - Audio
                    Mute 3  cmdID= 37686  "
        ::= { iqsyn22CmdEntry 37686 }


    iqsyn22Mix2Mix2GainGain4 OBJECT-TYPE
        SYNTAX            INTEGER
        MAX-ACCESS        read-write
        STATUS            current
        DESCRIPTION
                "CMNT: - Mixer source gain
                 TYPE: - Number
                 PAGE: - Audio
                    Gain 4  cmdID= 37647
                    min= -360  max= 120  step= 1  format= %0.1f dB  div_scale= 10  preset= 0
                    Min = -36.0 dB  Max = 12.0 dB  Step = 0.1 dB  Preset = 0.0 dB  "
        ::= { iqsyn22CmdEntry 37647 }


    iqsyn22Mix2Mix2GainMute4 OBJECT-TYPE
        SYNTAX            INTEGER { disable(0), enable(1)  }
        MAX-ACCESS        read-write
        STATUS            current
        DESCRIPTION
                "CMNT: - Mixer source mutes
                 TYPE: - Checkbox
                 PAGE: - Audio
                    Mute 4  cmdID= 37687  "
        ::= { iqsyn22CmdEntry 37687 }


    iqsyn22Mix2Mix2GainInp1Clip OBJECT-TYPE
        SYNTAX            RollCallString
        MAX-ACCESS        read-only
        STATUS            current
        DESCRIPTION
                "CMNT: - Audio Mixer source clipped
                 TYPE: - Display
                 PAGE: - Audio
                    Inp1 Clip  cmdID= 37764  "
        ::= { iqsyn22CmdEntry 37764 }


    iqsyn22Mix2Mix2GainInp2Clip OBJECT-TYPE
        SYNTAX            RollCallString
        MAX-ACCESS        read-only
        STATUS            current
        DESCRIPTION
                "CMNT: - Audio Mixer source clipped
                 TYPE: - Display
                 PAGE: - Audio
                    Inp2 Clip  cmdID= 37765  "
        ::= { iqsyn22CmdEntry 37765 }


    iqsyn22Mix2Mix2GainInp3Clip OBJECT-TYPE
        SYNTAX            RollCallString
        MAX-ACCESS        read-only
        STATUS            current
        DESCRIPTION
                "CMNT: - Audio Mixer source clipped
                 TYPE: - Display
                 PAGE: - Audio
                    Inp3 Clip  cmdID= 37766  "
        ::= { iqsyn22CmdEntry 37766 }


    iqsyn22Mix2Mix2GainInp4Clip OBJECT-TYPE
        SYNTAX            RollCallString
        MAX-ACCESS        read-only
        STATUS            current
        DESCRIPTION
                "CMNT: - Audio Mixer source clipped
                 TYPE: - Display
                 PAGE: - Audio
                    Inp4 Clip  cmdID= 37767  "
        ::= { iqsyn22CmdEntry 37767 }


    iqsyn22Mix2Mix2GainOPClip OBJECT-TYPE
        SYNTAX            RollCallString
        MAX-ACCESS        read-only
        STATUS            current
        DESCRIPTION
                "CMNT: - Audio Mixer output clipped
                 TYPE: - Display
                 PAGE: - Audio
                    O/P Clip  cmdID= 37801  "
        ::= { iqsyn22CmdEntry 37801 }


    iqsyn22Mix3Mix3RoutingSource1 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 1  cmdID= 37608
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37608 }


    iqsyn22Mix3Mix3RoutingInvert1 OBJECT-TYPE
        SYNTAX            INTEGER { disable(0), enable(1)  }
        MAX-ACCESS        read-write
        STATUS            current
        DESCRIPTION
                "CMNT: - Mixer source phase invert
                 TYPE: - Checkbox
                 PAGE: - Audio
                    Invert 1  cmdID= 37728  "
        ::= { iqsyn22CmdEntry 37728 }


    iqsyn22Mix3Mix3RoutingSource2 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 2  cmdID= 37609
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37609 }


    iqsyn22Mix3Mix3RoutingInvert2 OBJECT-TYPE
        SYNTAX            INTEGER { disable(0), enable(1)  }
        MAX-ACCESS        read-write
        STATUS            current
        DESCRIPTION
                "CMNT: - Mixer source phase invert
                 TYPE: - Checkbox
                 PAGE: - Audio
                    Invert 2  cmdID= 37729  "
        ::= { iqsyn22CmdEntry 37729 }


    iqsyn22Mix3Mix3RoutingSource3 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 3  cmdID= 37610
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37610 }


    iqsyn22Mix3Mix3RoutingInvert3 OBJECT-TYPE
        SYNTAX            INTEGER { disable(0), enable(1)  }
        MAX-ACCESS        read-write
        STATUS            current
        DESCRIPTION
                "CMNT: - Mixer source phase invert
                 TYPE: - Checkbox
                 PAGE: - Audio
                    Invert 3  cmdID= 37730  "
        ::= { iqsyn22CmdEntry 37730 }


    iqsyn22Mix3Mix3RoutingSource4 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 4  cmdID= 37611
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37611 }


    iqsyn22Mix3Mix3RoutingInvert4 OBJECT-TYPE
        SYNTAX            INTEGER { disable(0), enable(1)  }
        MAX-ACCESS        read-write
        STATUS            current
        DESCRIPTION
                "CMNT: - Mixer source phase invert
                 TYPE: - Checkbox
                 PAGE: - Audio
                    Invert 4  cmdID= 37731  "
        ::= { iqsyn22CmdEntry 37731 }


    iqsyn22Mix3Mix3GainGain1 OBJECT-TYPE
        SYNTAX            INTEGER
        MAX-ACCESS        read-write
        STATUS            current
        DESCRIPTION
                "CMNT: - Mixer source gain
                 TYPE: - Number
                 PAGE: - Audio
                    Gain 1  cmdID= 37648
                    min= -360  max= 120  step= 1  format= %0.1f dB  div_scale= 10  preset= 0
                    Min = -36.0 dB  Max = 12.0 dB  Step = 0.1 dB  Preset = 0.0 dB  "
        ::= { iqsyn22CmdEntry 37648 }


    iqsyn22Mix3Mix3GainMute1 OBJECT-TYPE
        SYNTAX            INTEGER { disable(0), enable(1)  }
        MAX-ACCESS        read-write
        STATUS            current
        DESCRIPTION
                "CMNT: - Mixer source mutes
                 TYPE: - Checkbox
                 PAGE: - Audio
                    Mute 1  cmdID= 37688  "
        ::= { iqsyn22CmdEntry 37688 }


    iqsyn22Mix3Mix3GainGain2 OBJECT-TYPE
        SYNTAX            INTEGER
        MAX-ACCESS        read-write
        STATUS            current
        DESCRIPTION
                "CMNT: - Mixer source gain
                 TYPE: - Number
                 PAGE: - Audio
                    Gain 2  cmdID= 37649
                    min= -360  max= 120  step= 1  format= %0.1f dB  div_scale= 10  preset= 0
                    Min = -36.0 dB  Max = 12.0 dB  Step = 0.1 dB  Preset = 0.0 dB  "
        ::= { iqsyn22CmdEntry 37649 }


    iqsyn22Mix3Mix3GainMute2 OBJECT-TYPE
        SYNTAX            INTEGER { disable(0), enable(1)  }
        MAX-ACCESS        read-write
        STATUS            current
        DESCRIPTION
                "CMNT: - Mixer source mutes
                 TYPE: - Checkbox
                 PAGE: - Audio
                    Mute 2  cmdID= 37689  "
        ::= { iqsyn22CmdEntry 37689 }


    iqsyn22Mix3Mix3GainGain3 OBJECT-TYPE
        SYNTAX            INTEGER
        MAX-ACCESS        read-write
        STATUS            current
        DESCRIPTION
                "CMNT: - Mixer source gain
                 TYPE: - Number
                 PAGE: - Audio
                    Gain 3  cmdID= 37650
                    min= -360  max= 120  step= 1  format= %0.1f dB  div_scale= 10  preset= 0
                    Min = -36.0 dB  Max = 12.0 dB  Step = 0.1 dB  Preset = 0.0 dB  "
        ::= { iqsyn22CmdEntry 37650 }


    iqsyn22Mix3Mix3GainMute3 OBJECT-TYPE
        SYNTAX            INTEGER { disable(0), enable(1)  }
        MAX-ACCESS        read-write
        STATUS            current
        DESCRIPTION
                "CMNT: - Mixer source mutes
                 TYPE: - Checkbox
                 PAGE: - Audio
                    Mute 3  cmdID= 37690  "
        ::= { iqsyn22CmdEntry 37690 }


    iqsyn22Mix3Mix3GainGain4 OBJECT-TYPE
        SYNTAX            INTEGER
        MAX-ACCESS        read-write
        STATUS            current
        DESCRIPTION
                "CMNT: - Mixer source gain
                 TYPE: - Number
                 PAGE: - Audio
                    Gain 4  cmdID= 37651
                    min= -360  max= 120  step= 1  format= %0.1f dB  div_scale= 10  preset= 0
                    Min = -36.0 dB  Max = 12.0 dB  Step = 0.1 dB  Preset = 0.0 dB  "
        ::= { iqsyn22CmdEntry 37651 }


    iqsyn22Mix3Mix3GainMute4 OBJECT-TYPE
        SYNTAX            INTEGER { disable(0), enable(1)  }
        MAX-ACCESS        read-write
        STATUS            current
        DESCRIPTION
                "CMNT: - Mixer source mutes
                 TYPE: - Checkbox
                 PAGE: - Audio
                    Mute 4  cmdID= 37691  "
        ::= { iqsyn22CmdEntry 37691 }


    iqsyn22Mix3Mix3GainInp1Clip OBJECT-TYPE
        SYNTAX            RollCallString
        MAX-ACCESS        read-only
        STATUS            current
        DESCRIPTION
                "CMNT: - Audio Mixer source clipped
                 TYPE: - Display
                 PAGE: - Audio
                    Inp1 Clip  cmdID= 37768  "
        ::= { iqsyn22CmdEntry 37768 }


    iqsyn22Mix3Mix3GainInp2Clip OBJECT-TYPE
        SYNTAX            RollCallString
        MAX-ACCESS        read-only
        STATUS            current
        DESCRIPTION
                "CMNT: - Audio Mixer source clipped
                 TYPE: - Display
                 PAGE: - Audio
                    Inp2 Clip  cmdID= 37769  "
        ::= { iqsyn22CmdEntry 37769 }


    iqsyn22Mix3Mix3GainInp3Clip OBJECT-TYPE
        SYNTAX            RollCallString
        MAX-ACCESS        read-only
        STATUS            current
        DESCRIPTION
                "CMNT: - Audio Mixer source clipped
                 TYPE: - Display
                 PAGE: - Audio
                    Inp3 Clip  cmdID= 37770  "
        ::= { iqsyn22CmdEntry 37770 }


    iqsyn22Mix3Mix3GainInp4Clip OBJECT-TYPE
        SYNTAX            RollCallString
        MAX-ACCESS        read-only
        STATUS            current
        DESCRIPTION
                "CMNT: - Audio Mixer source clipped
                 TYPE: - Display
                 PAGE: - Audio
                    Inp4 Clip  cmdID= 37771  "
        ::= { iqsyn22CmdEntry 37771 }


    iqsyn22Mix3Mix3GainOPClip OBJECT-TYPE
        SYNTAX            RollCallString
        MAX-ACCESS        read-only
        STATUS            current
        DESCRIPTION
                "CMNT: - Audio Mixer output clipped
                 TYPE: - Display
                 PAGE: - Audio
                    O/P Clip  cmdID= 37802  "
        ::= { iqsyn22CmdEntry 37802 }


    iqsyn22Mix4Mix4RoutingSource1 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 1  cmdID= 37612
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37612 }


    iqsyn22Mix4Mix4RoutingInvert1 OBJECT-TYPE
        SYNTAX            INTEGER { disable(0), enable(1)  }
        MAX-ACCESS        read-write
        STATUS            current
        DESCRIPTION
                "CMNT: - Mixer source phase invert
                 TYPE: - Checkbox
                 PAGE: - Audio
                    Invert 1  cmdID= 37732  "
        ::= { iqsyn22CmdEntry 37732 }


    iqsyn22Mix4Mix4RoutingSource2 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 2  cmdID= 37613
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37613 }


    iqsyn22Mix4Mix4RoutingInvert2 OBJECT-TYPE
        SYNTAX            INTEGER { disable(0), enable(1)  }
        MAX-ACCESS        read-write
        STATUS            current
        DESCRIPTION
                "CMNT: - Mixer source phase invert
                 TYPE: - Checkbox
                 PAGE: - Audio
                    Invert 2  cmdID= 37733  "
        ::= { iqsyn22CmdEntry 37733 }


    iqsyn22Mix4Mix4RoutingSource3 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 3  cmdID= 37614
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37614 }


    iqsyn22Mix4Mix4RoutingInvert3 OBJECT-TYPE
        SYNTAX            INTEGER { disable(0), enable(1)  }
        MAX-ACCESS        read-write
        STATUS            current
        DESCRIPTION
                "CMNT: - Mixer source phase invert
                 TYPE: - Checkbox
                 PAGE: - Audio
                    Invert 3  cmdID= 37734  "
        ::= { iqsyn22CmdEntry 37734 }


    iqsyn22Mix4Mix4RoutingSource4 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 4  cmdID= 37615
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn22CmdEntry 37615 }


    iqsyn22Mix4Mix4RoutingInvert4 OBJECT-TYPE
        SYNTAX            INTEGER { disable(0), enable(1)  }
        MAX-ACCESS        read-write
        STATUS            current
        DESCRIPTION
                "CMNT: - Mixer source phase invert
                 TYPE: - Checkbox
                 PAGE: - Audio
                    Invert 4  cmdID= 37735  "
        ::= { iqsyn22CmdEntry 37735 }


    iqsyn22Mix4Mix4GainGain1 OBJECT-TYPE
        SYNTAX            INTEGER
        MAX-ACCESS        read-write
        STATUS            current
        DESCRIPTION
                "CMNT: - Mixer source gain
                 TYPE: - Number
                 PAGE: - Audio
                    Gain 1  cmdID= 37652
                    min= -360  max= 120  step= 1  format= %0.1f dB  div_scale= 10  preset= 0
                    Min = -36.0 dB  Max = 12.0 dB  Step = 0.1 dB  Preset = 0.0 dB  "
        ::= { iqsyn22CmdEntry 37652 }


    iqsyn22Mix4Mix4GainMute1 OBJECT-TYPE
        SYNTAX            INTEGER { disable(0), enable(1)  }
        MAX-ACCESS        read-write
        STATUS            current
        DESCRIPTION
                "CMNT: - Mixer source mutes
                 TYPE: - Checkbox
                 PAGE: - Audio
                    Mute 1  cmdID= 37692  "
        ::= { iqsyn22CmdEntry 37692 }


    iqsyn22Mix4Mix4GainGain2 OBJECT-TYPE
        SYNTAX            INTEGER
        MAX-ACCESS        read-write
        STATUS            current
        DESCRIPTION
                "CMNT: - Mixer source gain
                 TYPE: - Number
                 PAGE: - Audio
                    Gain 2  cmdID= 37653
                    min= -360  max= 120  step= 1  format= %0.1f dB  div_scale= 10  preset= 0
                    Min = -36.0 dB  Max = 12.0 dB  Step = 0.1 dB  Preset = 0.0 dB  "
        ::= { iqsyn22CmdEntry 37653 }


    iqsyn22Mix4Mix4GainMute2 OBJECT-TYPE
        SYNTAX            INTEGER { disable(0), enable(1)  }
        MAX-ACCESS        read-write
        STATUS            current
        DESCRIPTION
                "CMNT: - Mixer source mutes
                 TYPE: - Checkbox
                 PAGE: - Audio
                    Mute 2  cmdID= 37693  "
        ::= { iqsyn22CmdEntry 37693 }


    iqsyn22Mix4Mix4GainGain3 OBJECT-TYPE
        SYNTAX            INTEGER
        MAX-ACCESS        read-write
        STATUS            current
        DESCRIPTION
                "CMNT: - Mixer source gain
                 TYPE: - Number
                 PAGE: - Audio
                    Gain 3  cmdID= 37654
                    min= -360  max= 120  step= 1  format= %0.1f dB  div_scale= 10  preset= 0
                    Min = -36.0 dB  Max = 12.0 dB  Step = 0.1 dB  Preset = 0.0 dB  "
        ::= { iqsyn22CmdEntry 37654 }


    iqsyn22Mix4Mix4GainMute3 OBJECT-TYPE
        SYNTAX            INTEGER { disable(0), enable(1)  }
        MAX-ACCESS        read-write
        STATUS            current
        DESCRIPTION
                "CMNT: - Mixer source mutes
                 TYPE: - Checkbox
                 PAGE: - Audio
                    Mute 3  cmdID= 37694  "
        ::= { iqsyn22CmdEntry 37694 }


    iqsyn22Mix4Mix4GainGain4 OBJECT-TYPE
        SYNTAX            INTEGER
        MAX-ACCESS        read-write
        STATUS            current
        DESCRIPTION
                "CMNT: - Mixer source gain
                 TYPE: - Number
                 PAGE: - Audio
                    Gain 4  cmdID= 37655
                    min= -360  max= 120  step= 1  format= %0.1f dB  div_scale= 10  preset= 0
                    Min = -36.0 dB  Max = 12.0 dB  Step = 0.1 dB  Preset = 0.0 dB  "
        ::= { iqsyn22CmdEntry 37655 }


    iqsyn22Mix4Mix4GainMute4 OBJECT-TYPE
        SYNTAX            INTEGER { disable(0), enable(1)  }
        MAX-ACCESS        read-write
        STATUS            current
        DESCRIPTION
                "CMNT: - Mixer source mutes
                 TYPE: - Checkbox
                 PAGE: - Audio
                    Mute 4  cmdID= 37695  "
        ::= { iqsyn22CmdEntry 37695 }


    iqsyn22Mix4Mix4GainInp1Clip OBJECT-TYPE
        SYNTAX            RollCallString
        MAX-ACCESS        read-only
        STATUS            current
        DESCRIPTION
                "CMNT: - Audio Mixer source clipped
                 TYPE: - Display
                 PAGE: - Audio
                    Inp1 Clip  cmdID= 37772  "
        ::= { iqsyn22CmdEntry 37772 }


    iqsyn22Mix4Mix4GainInp2Clip OBJECT-TYPE
        SYNTAX            RollCallString
        MAX-ACCESS        read-only
        STATUS            current
        DESCRIPTION
                "CMNT: - Audio Mixer source clipped
                 TYPE: - Display
                 PAGE: - Audio
                    Inp2 Clip  cmdID= 37773  "
        ::= { iqsyn22CmdEntry 37773 }


    iqsyn22Mix4Mix4GainInp3Clip OBJECT-TYPE
        SYNTAX            RollCallString
        MAX-ACCESS        read-only
        STATUS            current
        DESCRIPTION
                "CMNT: - Audio Mixer source clipped
                 TYPE: - Display
                 PAGE: - Audio
                    Inp3 Clip  cmdID= 37774  "
        ::= { iqsyn22CmdEntry 37774 }


    iqsyn22Mix4Mix4GainInp4Clip OBJECT-TYPE
        SYNTAX            RollCallString
        MAX-ACCESS        read-only
        STATUS            current
        DESCRIPTION
                "CMNT: - Audio Mixer source clipped
                 TYPE: - Display
                 PAGE: - Audio
                    Inp4 Clip  cmdID= 37775  "
        ::= { iqsyn22CmdEntry 37775 }


    iqsyn22Mix4Mix4GainOPClip OBJECT-TYPE
        SYNTAX            RollCallString
        MAX-ACCESS        read-only
        STATUS            current
        DESCRIPTION
                "CMNT: - Audio Mixer output clipped
                 TYPE: - Display
                 PAGE: - Audio
                    O/P Clip  cmdID= 37803  "
        ::= { iqsyn22CmdEntry 37803 }


    iqsyn22AudioDolbyETimingSelAudioPair OBJECT-TYPE
        SYNTAX            INTEGER
        MAX-ACCESS        read-write
        STATUS            current
        DESCRIPTION
                "CMNT: - 
                 TYPE: - Number
                 PAGE: - Audio
                    Sel Audio Pair  cmdID= 38650
                    min= 1  max= 8  step= 1  format= %0.0f  div_scale= 1  preset= 1
                    Min = 1  Max = 8  Step = 1  Preset = 1  "
        ::= { iqsyn22CmdEntry 38650 }


    iqsyn22AudioDolbyETimingRelativeTiming OBJECT-TYPE
        SYNTAX            RollCallString
        MAX-ACCESS        read-only
        STATUS            current
        DESCRIPTION
                "CMNT: - 
                 TYPE: - Display
                 PAGE: - Audio
                    Relative Timing  cmdID= 38653  "
        ::= { iqsyn22CmdEntry 38653 }


    iqsyn22AudioDolbyETimingStatus OBJECT-TYPE
        SYNTAX            RollCallString
        MAX-ACCESS        read-only
        STATUS            current
        DESCRIPTION
                "CMNT: - 
                 TYPE: - Display
                 PAGE: - Audio
                    Status  cmdID= 38652  "
        ::= { iqsyn22CmdEntry 38652 }


    iqsyn22AudioDolbyETimingError OBJECT-TYPE
        SYNTAX            RollCallString
        MAX-ACCESS        read-only
        STATUS            current
        DESCRIPTION
                "CMNT: - 
                 TYPE: - Display
                 PAGE: - Audio
                    Error  cmdID= 38654  "
        ::= { iqsyn22CmdEntry 38654 }


    iqsyn22DolbyETimingDolbyELineStandard OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - Select standard to display Dolby E Auto-Line for
                 TYPE: - RadiobuttonList
                 PAGE: - Dolby E Timing
                    Standard  cmdID= 38655
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn22CmdEntry 38655 }


    iqsyn22DolbyETimingDolbyELineAutoLineNo OBJECT-TYPE
        SYNTAX            INTEGER
        MAX-ACCESS        read-write
        STATUS            current
        DESCRIPTION
                "CMNT: - Select standard to display Dolby E Auto-Line for
                 TYPE: - Number
                 PAGE: - Dolby E Timing
                    Auto Line No.  cmdID= 38656
                    min= 1  max= 10000  step= 1  format= %0.0f  div_scale= 1  preset= 1
                    Min = 1  Max = 10000  Step = 1  Preset = 1  "
        ::= { iqsyn22CmdEntry 38656 }


    iqsyn22DolbyELineUserDolbyELinePair1 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 1  cmdID= 38670
                    User Line  value= 1
                    Standard Line  value= 0  "
        ::= { iqsyn22CmdEntry 38670 }


    iqsyn22DolbyELineUserDolbyELinePair2 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 2  cmdID= 38671
                    User Line  value= 1
                    Standard Line  value= 0  "
        ::= { iqsyn22CmdEntry 38671 }


    iqsyn22DolbyELineUserDolbyELinePair3 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 3  cmdID= 38672
                    User Line  value= 1
                    Standard Line  value= 0  "
        ::= { iqsyn22CmdEntry 38672 }


    iqsyn22DolbyELineUserDolbyELinePair4 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 4  cmdID= 38673
                    User Line  value= 1
                    Standard Line  value= 0  "
        ::= { iqsyn22CmdEntry 38673 }


    iqsyn22DolbyELineUserDolbyELinePair5 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 5  cmdID= 38674
                    User Line  value= 1
                    Standard Line  value= 0  "
        ::= { iqsyn22CmdEntry 38674 }


    iqsyn22DolbyELineUserDolbyELinePair6 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 6  cmdID= 38675
                    User Line  value= 1
                    Standard Line  value= 0  "
        ::= { iqsyn22CmdEntry 38675 }


    iqsyn22DolbyELineUserDolbyELinePair7 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 7  cmdID= 38676
                    User Line  value= 1
                    Standard Line  value= 0  "
        ::= { iqsyn22CmdEntry 38676 }


    iqsyn22DolbyELineUserDolbyELinePair8 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 8  cmdID= 38677
                    User Line  value= 1
                    Standard Line  value= 0  "
        ::= { iqsyn22CmdEntry 38677 }


    iqsyn22DolbyETimingDolbyELineSmoothCapRange OBJECT-TYPE
        SYNTAX            INTEGER {
                            valpn1Sample(1),
                            valpn60Samples(60)
                            }
        MAX-ACCESS        read-write
        STATUS            current
        DESCRIPTION
                "CMNT: - Dolby E Select Smooth Capture Range
                 TYPE: - RadiobuttonList
                 PAGE: - Dolby E Timing
                    Smooth Cap Range  cmdID= 38658
                    +/- 1 Sample  value= 1
                    +/- 60 Samples  value= 60  "
        ::= { iqsyn22CmdEntry 38658 }


    iqsyn22GenlockDelayMode OBJECT-TYPE
        SYNTAX            INTEGER {
                            valFreeRun(0),
                            valLocktoReference(1),
                            valMinimumAudio(3),
                            valFrames(4),
                            valManualHV(5),
                            valManualms(6)
                            }
        MAX-ACCESS        read-write
        STATUS            current
        DESCRIPTION
                "CMNT: - Video Reference Mode source: Free Run/LockRef/LockRef(Delay Mismatch)/Minimum/Frames/Manual/Manual ms
                 TYPE: - RadiobuttonList
                 PAGE: - Genlock
                    Delay Mode  cmdID= 33026
                    Free Run  value= 0
                    Lock to Reference  value= 1
                    Minimum Audio  value= 3
                    Frames  value= 4
                    Manual H/V  value= 5
                    Manual ms  value= 6  "
        ::= { iqsyn22CmdEntry 33026 }


    iqsyn22GenlockRefTimeDelayFrames OBJECT-TYPE
        SYNTAX            INTEGER
        MAX-ACCESS        read-write
        STATUS            current
        DESCRIPTION
                "CMNT: - Set video delay in frames
                 TYPE: - Number
                 PAGE: - Genlock
                    Delay Frames  cmdID= 33024
                    min= 0  max= 11  step= 1  format= %0.0f frames  div_scale= 1  preset= 0
                    Min = 0 frames  Max = 11 frames  Step = 1 frames  Preset = 0 frames  "
        ::= { iqsyn22CmdEntry 33024 }


    iqsyn22GenlockRefTimeVerticalTiming OBJECT-TYPE
        SYNTAX            INTEGER
        MAX-ACCESS        read-write
        STATUS            current
        DESCRIPTION
                "CMNT: - Reference vertical timing
                 TYPE: - Number
                 PAGE: - Genlock
                    Vertical Timing  cmdID= 33022
                    min= -1500  max= 1500  step= 1  format= %0.0f lines  div_scale= 1  preset= 0
                    Min = -1500 lines  Max = 1500 lines  Step = 1 lines  Preset = 0 lines  "
        ::= { iqsyn22CmdEntry 33022 }


    iqsyn22GenlockRefTimeHorizontalTiming OBJECT-TYPE
        SYNTAX            INTEGER
        MAX-ACCESS        read-write
        STATUS            current
        DESCRIPTION
                "CMNT: - Reference horizontal timing
                 TYPE: - Number
                 PAGE: - Genlock
                    Horizontal Timing  cmdID= 33021
                    min= -3000  max= 3000  step= 1  format= %0.0f pixels  div_scale= 1  preset= 0
                    Min = -3000 pixels  Max = 3000 pixels  Step = 1 pixels  Preset = 0 pixels  "
        ::= { iqsyn22CmdEntry 33021 }


    iqsyn22GenlockSetDelayDelayms OBJECT-TYPE
        SYNTAX            INTEGER
        MAX-ACCESS        read-write
        STATUS            current
        DESCRIPTION
                "CMNT: - Video delay set in 0.01 ms
                 TYPE: - Number
                 PAGE: - Genlock
                    Delay ms  cmdID= 33027
                    min= -48000  max= 48000  step= 5  format= %0.2f ms  div_scale= 100  preset= 0
                    Min = -480.00 ms  Max = 480.00 ms  Step = 0.05 ms  Preset = 0.00 ms  "
        ::= { iqsyn22CmdEntry 33027 }


    iqsyn22GenlockRefTimeCurrentDelay OBJECT-TYPE
        SYNTAX            RollCallString
        MAX-ACCESS        read-only
        STATUS            current
        DESCRIPTION
                "CMNT: - 
                 TYPE: - Display
                 PAGE: - Genlock
                    Internal Delay  cmdID= 33025  "
        ::= { iqsyn22CmdEntry 33025 }


    iqsyn22GenlockSyncAmplitude OBJECT-TYPE
        SYNTAX            RollCallString
        MAX-ACCESS        read-only
        STATUS            current
        DESCRIPTION
                "CMNT: - External reference amplitude
                 TYPE: - Display
                 PAGE: - Genlock
                    Sync Amplitude  cmdID= 33023  "
        ::= { iqsyn22CmdEntry 33023 }


    iqsyn22GenlockUseEmbDelayFback OBJECT-TYPE
        SYNTAX            INTEGER { disable(0), enable(1)  }
        MAX-ACCESS        read-write
        STATUS            current
        DESCRIPTION
                "CMNT: - 
                 TYPE: - Checkbox
                 PAGE: - Genlock
                    Use Emb Delay F/back  cmdID= 34049  "
        ::= { iqsyn22CmdEntry 34049 }


    iqsyn22GenlockSampleNumber OBJECT-TYPE
        SYNTAX            RollCallString
        MAX-ACCESS        read-only
        STATUS            current
        DESCRIPTION
                "CMNT: - Displays sample value for Dolby-E Timing
                 TYPE: - Display
                 PAGE: - Genlock
                    Sample Number  cmdID= 38657  "
        ::= { iqsyn22CmdEntry 38657 }


    iqsyn22GenlockLineNumber OBJECT-TYPE
        SYNTAX            RollCallString
        MAX-ACCESS        read-only
        STATUS            current
        DESCRIPTION
                "CMNT: - 
                 TYPE: - Display
                 PAGE: - Genlock
                    Line Number  cmdID= 38651  "
        ::= { iqsyn22CmdEntry 38651 }


    iqsyn22BackupEnable OBJECT-TYPE
        SYNTAX            INTEGER { disable(0), enable(1)  }
        MAX-ACCESS        read-write
        STATUS            current
        DESCRIPTION
                "CMNT: - Input Backup Enable
                 TYPE: - Checkbox
                 PAGE: - Backup
                    Backup Enable  cmdID= 39100  "
        ::= { iqsyn22CmdEntry 39100 }


    iqsyn22BackupORInput1State OBJECT-TYPE
        SYNTAX            RollCallString
        MAX-ACCESS        read-only
        STATUS            current
        DESCRIPTION
                "CMNT: - Input 1 OR State
                 TYPE: - Display
                 PAGE: - Backup
                    OR Input1 State  cmdID= 39101  "
        ::= { iqsyn22CmdEntry 39101 }


    iqsyn22BackupORInput2State OBJECT-TYPE
        SYNTAX            RollCallString
        MAX-ACCESS        read-only
        STATUS            current
        DESCRIPTION
                "CMNT: - Input 2 OR State
                 TYPE: - Display
                 PAGE: - Backup
                    OR Input2 State  cmdID= 39102  "
        ::= { iqsyn22CmdEntry 39102 }


    iqsyn22BackupRevertDelay OBJECT-TYPE
        SYNTAX            INTEGER
        MAX-ACCESS        read-write
        STATUS            current
        DESCRIPTION
                "CMNT: - Backup Reversion Delay
                 TYPE: - Number
                 PAGE: - Backup
                    Revert Delay  cmdID= 39141
                    min= 0  max= 1000  step= 10  format= %0.0f s  div_scale= 10  preset= 0
                    Min = 0 s  Max = 100 s  Step = 1 s  Preset = 0 s  "
        ::= { iqsyn22CmdEntry 39141 }


    iqsyn22BackupPriority OBJECT-TYPE
        SYNTAX            INTEGER {
                            valNone(0),
                            valPriority1(1),
                            valPriority2(2)
                            }
        MAX-ACCESS        read-write
        STATUS            current
        DESCRIPTION
                "CMNT: - Input Backup Priority
                 TYPE: - RadiobuttonList
                 PAGE: - Backup
                    Priority  cmdID= 39103
                    None  value= 0
                    Priority 1  value= 1
                    Priority 2  value= 2  "
        ::= { iqsyn22CmdEntry 39103 }


    iqsyn22BackupQualifyCRCErr OBJECT-TYPE
        SYNTAX            INTEGER { disable(0), enable(1)  }
        MAX-ACCESS        read-write
        STATUS            current
        DESCRIPTION
                "CMNT: - Backup CRC Error
                 TYPE: - Checkbox
                 PAGE: - Backup
                    Qualify CRC Err  cmdID= 39105  "
        ::= { iqsyn22CmdEntry 39105 }


    iqsyn22BackupQualifyANCErr OBJECT-TYPE
        SYNTAX            INTEGER { disable(0), enable(1)  }
        MAX-ACCESS        read-write
        STATUS            current
        DESCRIPTION
                "CMNT: - Backup ANC Error
                 TYPE: - Checkbox
                 PAGE: - Backup
                    Qualify ANC Err  cmdID= 39106  "
        ::= { iqsyn22CmdEntry 39106 }


    iqsyn22BackupInput1SelStatInp1OK OBJECT-TYPE
        SYNTAX            RollCallString
        MAX-ACCESS        read-only
        STATUS            current
        DESCRIPTION
                "CMNT: - Backup Sel 1 Inp 1 OK Status
                 TYPE: - Display
                 PAGE: - Backup
                    Stat Inp1 OK  cmdID= 39127  "
        ::= { iqsyn22CmdEntry 39127 }


    iqsyn22BackupInput1SelStatInp2FAIL OBJECT-TYPE
        SYNTAX            RollCallString
        MAX-ACCESS        read-only
        STATUS            current
        DESCRIPTION
                "CMNT: - Backup Sel 1 Inp 2 FAIL Status
                 TYPE: - Display
                 PAGE: - Backup
                    Stat Inp2 FAIL  cmdID= 39128  "
        ::= { iqsyn22CmdEntry 39128 }


    iqsyn22BackupInput1SelStatInp2Err OBJECT-TYPE
        SYNTAX            RollCallString
        MAX-ACCESS        read-only
        STATUS            current
        DESCRIPTION
                "CMNT: - Backup Sel 1 Inp 2 ERR Status
                 TYPE: - Display
                 PAGE: - Backup
                    Stat Inp2 Err  cmdID= 39139  "
        ::= { iqsyn22CmdEntry 39139 }


    iqsyn22BackupInput1SelStatAUDFail2 OBJECT-TYPE
        SYNTAX            RollCallString
        MAX-ACCESS        read-only
        STATUS            current
        DESCRIPTION
                "CMNT: - Backup Reversion Delay
                 TYPE: - Display
                 PAGE: - Backup
                    Stat AUD Fail 2  cmdID= 39144  "
        ::= { iqsyn22CmdEntry 39144 }


    iqsyn22BackupInput1SelStatStd2 OBJECT-TYPE
        SYNTAX            RollCallString
        MAX-ACCESS        read-only
        STATUS            current
        DESCRIPTION
                "CMNT: - Backup Inp2 1 Aud Fail G4C2
                 TYPE: - Display
                 PAGE: - Backup
                    Stat Std 2  cmdID= 39172  "
        ::= { iqsyn22CmdEntry 39172 }


    iqsyn22BackupInput1SelStatGPI1 OBJECT-TYPE
        SYNTAX            RollCallString
        MAX-ACCESS        read-only
        STATUS            current
        DESCRIPTION
                "CMNT: - Backup Sel 1 GPI 1 Status
                 TYPE: - Display
                 PAGE: - Backup
                    Stat GPI 1  cmdID= 39129  "
        ::= { iqsyn22CmdEntry 39129 }


    iqsyn22BackupInput1SelStatGPI2 OBJECT-TYPE
        SYNTAX            RollCallString
        MAX-ACCESS        read-only
        STATUS            current
        DESCRIPTION
                "CMNT: - Backup Sel 1 GPI 2 Status
                 TYPE: - Display
                 PAGE: - Backup
                    Stat GPI 2  cmdID= 39130  "
        ::= { iqsyn22CmdEntry 39130 }


    iqsyn22BackupInput1SelEnblInp1OK OBJECT-TYPE
        SYNTAX            INTEGER { disable(0), enable(1)  }
        MAX-ACCESS        read-write
        STATUS            current
        DESCRIPTION
                "CMNT: - Backup Sel 1 Inp 1 OK
                 TYPE: - Checkbox
                 PAGE: - Backup
                    Enbl Inp1 OK  cmdID= 39107  "
        ::= { iqsyn22CmdEntry 39107 }


    iqsyn22BackupInput1SelEnblInp2FAIL OBJECT-TYPE
        SYNTAX            INTEGER { disable(0), enable(1)  }
        MAX-ACCESS        read-write
        STATUS            current
        DESCRIPTION
                "CMNT: - Backup Sel 1 Inp 2 FAIL
                 TYPE: - Checkbox
                 PAGE: - Backup
                    Enbl Inp2 FAIL  cmdID= 39108  "
        ::= { iqsyn22CmdEntry 39108 }


    iqsyn22BackupInput1SelEnblInp2Err OBJECT-TYPE
        SYNTAX            INTEGER { disable(0), enable(1)  }
        MAX-ACCESS        read-write
        STATUS            current
        DESCRIPTION
                "CMNT: - Backup Sel 1 Inp 2 ERR
                 TYPE: - Checkbox
                 PAGE: - Backup
                    Enbl Inp2 Err  cmdID= 39135  "
        ::= { iqsyn22CmdEntry 39135 }


    iqsyn22BackupInput1SelEnblAudInp2Err OBJECT-TYPE
        SYNTAX            INTEGER { disable(0), enable(1)  }
        MAX-ACCESS        read-write
        STATUS            current
        DESCRIPTION
                "CMNT: - Backup Inp1 2 Aud Fail Enable
                 TYPE: - Checkbox
                 PAGE: - Backup
                    Enbl Aud Inp2 Err  cmdID= 39143  "
        ::= { iqsyn22CmdEntry 39143 }


    iqsyn22BackupInput1SelEnblStdInp2 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Enbl Std Inp 2  cmdID= 39171  "
        ::= { iqsyn22CmdEntry 39171 }


    iqsyn22BackupInput1SelEnblGPI1 OBJECT-TYPE
        SYNTAX            INTEGER { disable(0), enable(1)  }
        MAX-ACCESS        read-write
        STATUS            current
        DESCRIPTION
                "CMNT: - Backup Sel 1 GPI 1
                 TYPE: - Checkbox
                 PAGE: - Backup
                    Enbl GPI 1  cmdID= 39109  "
        ::= { iqsyn22CmdEntry 39109 }


    iqsyn22BackupInput1SelEnblGPI2 OBJECT-TYPE
        SYNTAX            INTEGER { disable(0), enable(1)  }
        MAX-ACCESS        read-write
        STATUS            current
        DESCRIPTION
                "CMNT: - Backup Sel 1 GPI 2
                 TYPE: - Checkbox
                 PAGE: - Backup
                    Enbl GPI 2  cmdID= 39110  "
        ::= { iqsyn22CmdEntry 39110 }


    iqsyn22BackupInput1SelDlyInp1OK OBJECT-TYPE
        SYNTAX            INTEGER
        MAX-ACCESS        read-write
        STATUS            current
        DESCRIPTION
                "CMNT: - Backup Sel 1 Inp 1 OK Delay
                 TYPE: - Number
                 PAGE: - Backup
                    Dly Inp1 OK  cmdID= 39115
                    min= 10  max= 100  step= 1  format= %0.1f s  div_scale= 10  preset= 10
                    Min = 1.0 s  Max = 10.0 s  Step = 0.1 s  Preset = 1.0 s  "
        ::= { iqsyn22CmdEntry 39115 }


    iqsyn22BackupInput1SelDlyInp2FAIL OBJECT-TYPE
        SYNTAX            INTEGER
        MAX-ACCESS        read-write
        STATUS            current
        DESCRIPTION
                "CMNT: - Backup Sel 1 Inp 2 FAIL Delay
                 TYPE: - Number
                 PAGE: - Backup
                    Dly Inp2 FAIL  cmdID= 39116
                    min= 5  max= 100  step= 1  format= %0.1f s  div_scale= 10  preset= 5
                    Min = 0.5 s  Max = 10.0 s  Step = 0.1 s  Preset = 0.5 s  "
        ::= { iqsyn22CmdEntry 39116 }


    iqsyn22BackupInput1SelDlyInp2Err OBJECT-TYPE
        SYNTAX            INTEGER
        MAX-ACCESS        read-write
        STATUS            current
        DESCRIPTION
                "CMNT: - Backup Sel 1 Inp 2 ERR Delay
                 TYPE: - Number
                 PAGE: - Backup
                    Dly Inp2 Err  cmdID= 39137
                    min= 10  max= 100  step= 10  format= %0.0f s  div_scale= 10  preset= 50
                    Min = 1 s  Max = 10 s  Step = 1 s  Preset = 5 s  "
        ::= { iqsyn22CmdEntry 39137 }


    iqsyn22BackupInput1SelDlyGPI1 OBJECT-TYPE
        SYNTAX            INTEGER
        MAX-ACCESS        read-write
        STATUS            current
        DESCRIPTION
                "CMNT: - Backup Sel 1 GPI 1 Delay
                 TYPE: - Number
                 PAGE: - Backup
                    Dly GPI 1  cmdID= 39117
                    min= 0  max= 100  step= 1  format= %0.1f s  div_scale= 10  preset= 0
                    Min = 0.0 s  Max = 10.0 s  Step = 0.1 s  Preset = 0.0 s  "
        ::= { iqsyn22CmdEntry 39117 }


    iqsyn22BackupInput1SelDlyGPI2 OBJECT-TYPE
        SYNTAX            INTEGER
        MAX-ACCESS        read-write
        STATUS            current
        DESCRIPTION
                "CMNT: - Backup Sel 1 GPI 2 Delay
                 TYPE: - Number
                 PAGE: - Backup
                    Dly GPI 2  cmdID= 39118
                    min= 0  max= 100  step= 1  format= %0.1f s  div_scale= 10  preset= 0
                    Min = 0.0 s  Max = 10.0 s  Step = 0.1 s  Preset = 0.0 s  "
        ::= { iqsyn22CmdEntry 39118 }


    iqsyn22BackupInput1SelDlyAud2FAIL OBJECT-TYPE
        SYNTAX            INTEGER
        MAX-ACCESS        read-write
        STATUS            current
        DESCRIPTION
                "CMNT: - Backup Inp1 2 aud Fail Delay
                 TYPE: - Number
                 PAGE: - Backup
                    Dly Aud2 FAIL  cmdID= 39145
                    min= 10  max= 100  step= 1  format= %0.1f s  div_scale= 10  preset= 10
                    Min = 1.0 s  Max = 10.0 s  Step = 0.1 s  Preset = 1.0 s  "
        ::= { iqsyn22CmdEntry 39145 }


    iqsyn22BackupInput1SelDlyStd2 OBJECT-TYPE
        SYNTAX            INTEGER
        MAX-ACCESS        read-write
        STATUS            current
        DESCRIPTION
                "CMNT: - Backup Inp2 1 Aud Fail G4C2
                 TYPE: - Number
                 PAGE: - Backup
                    Dly Std 2  cmdID= 39173
                    min= 10  max= 100  step= 1  format= %0.1f s  div_scale= 10  preset= 10
                    Min = 1.0 s  Max = 10.0 s  Step = 0.1 s  Preset = 1.0 s  "
        ::= { iqsyn22CmdEntry 39173 }


    iqsyn22BackupInput1SelGPI1State OBJECT-TYPE
        SYNTAX            INTEGER {
                            valHigh(1),
                            valLow(0)
                            }
        MAX-ACCESS        read-write
        STATUS            current
        DESCRIPTION
                "CMNT: - Backup Sel 1 GPI 1 val
                 TYPE: - RadiobuttonList
                 PAGE: - Backup
                    GPI 1 State  cmdID= 39123
                    High  value= 1
                    Low  value= 0  "
        ::= { iqsyn22CmdEntry 39123 }


    iqsyn22BackupInput1SelGPI2State OBJECT-TYPE
        SYNTAX            INTEGER {
                            valHigh(1),
                            valLow(0)
                            }
        MAX-ACCESS        read-write
        STATUS            current
        DESCRIPTION
                "CMNT: - Backup Sel 1 GPI 2 val
                 TYPE: - RadiobuttonList
                 PAGE: - Backup
                    GPI 2 State  cmdID= 39124
                    High  value= 1
                    Low  value= 0  "
        ::= { iqsyn22CmdEntry 39124 }


    iqsyn22BackupInput1SelInp12AudFailG1C1 OBJECT-TYPE
        SYNTAX            INTEGER { disable(0), enable(1)  }
        MAX-ACCESS        read-write
        STATUS            current
        DESCRIPTION
                "CMNT: - Backup Inp1 2 Aud Fail G1C1
                 TYPE: - Checkbox
                 PAGE: - Backup
                    Inp1 2 Aud Fail G1C1  cmdID= 39149  "
        ::= { iqsyn22CmdEntry 39149 }


    iqsyn22BackupInput1SelInp12AudFailG1C2 OBJECT-TYPE
        SYNTAX            INTEGER { disable(0), enable(1)  }
        MAX-ACCESS        read-write
        STATUS            current
        DESCRIPTION
                "CMNT: - Backup Inp1 2 Aud Fail G1C2
                 TYPE: - Checkbox
                 PAGE: - Backup
                    Inp1 2 Aud Fail G1C2  cmdID= 39150  "
        ::= { iqsyn22CmdEntry 39150 }


    iqsyn22BackupInput1SelInp12AudFailG2C1 OBJECT-TYPE
        SYNTAX            INTEGER { disable(0), enable(1)  }
        MAX-ACCESS        read-write
        STATUS            current
        DESCRIPTION
                "CMNT: - Backup Inp1 2 Aud Fail G2C1
                 TYPE: - Checkbox
                 PAGE: - Backup
                    Inp1 2 Aud Fail G2C1  cmdID= 39151  "
        ::= { iqsyn22CmdEntry 39151 }


    iqsyn22BackupInput1SelInp12AudFailG2C2 OBJECT-TYPE
        SYNTAX            INTEGER { disable(0), enable(1)  }
        MAX-ACCESS        read-write
        STATUS            current
        DESCRIPTION
                "CMNT: - Backup Inp1 2 Aud Fail G2C2
                 TYPE: - Checkbox
                 PAGE: - Backup
                    Inp1 2 Aud Fail G2C2  cmdID= 39152  "
        ::= { iqsyn22CmdEntry 39152 }


    iqsyn22BackupInput1SelInp12AudFailG3C1 OBJECT-TYPE
        SYNTAX            INTEGER { disable(0), enable(1)  }
        MAX-ACCESS        read-write
        STATUS            current
        DESCRIPTION
                "CMNT: - Backup Inp1 2 Aud Fail G3C1
                 TYPE: - Checkbox
                 PAGE: - Backup
                    Inp1 2 Aud Fail G3C1  cmdID= 39153  "
        ::= { iqsyn22CmdEntry 39153 }


    iqsyn22BackupInput1SelInp12AudFailG3C2 OBJECT-TYPE
        SYNTAX            INTEGER { disable(0), enable(1)  }
        MAX-ACCESS        read-write
        STATUS            current
        DESCRIPTION
                "CMNT: - Backup Inp1 2 Aud Fail G3C2
                 TYPE: - Checkbox
                 PAGE: - Backup
                    Inp1 2 Aud Fail G3C2  cmdID= 39154  "
        ::= { iqsyn22CmdEntry 39154 }


    iqsyn22BackupInput1SelInp12AudFailG4C1 OBJECT-TYPE
        SYNTAX            INTEGER { disable(0), enable(1)  }
        MAX-ACCESS        read-write
        STATUS            current
        DESCRIPTION
                "CMNT: - Backup Inp1 2 Aud Fail G4C1
                 TYPE: - Checkbox
                 PAGE: - Backup
                    Inp1 2 Aud Fail G4C1  cmdID= 39155  "
        ::= { iqsyn22CmdEntry 39155 }


    iqsyn22BackupInput1SelInp12AudFailG4C2 OBJECT-TYPE
        SYNTAX            INTEGER { disable(0), enable(1)  }
        MAX-ACCESS        read-write
        STATUS            current
        DESCRIPTION
                "CMNT: - Backup Inp1 2 Aud Fail G4C2
                 TYPE: - Checkbox
                 PAGE: - Backup
                    Inp1 2 Aud Fail G4C2  cmdID= 39156  "
        ::= { iqsyn22CmdEntry 39156 }


    iqsyn22BackupInput1SelInp12AudFailLockGrp OBJECT-TYPE
        SYNTAX            INTEGER { disable(0), enable(1)  }
        MAX-ACCESS        read-write
        STATUS            current
        DESCRIPTION
                "CMNT: - Backup Inp1 2 Aud Fail Lock Grp
                 TYPE: - Checkbox
                 PAGE: - Backup
                    Inp1 2 Aud Fail Lock Grp  cmdID= 39148  "
        ::= { iqsyn22CmdEntry 39148 }


    iqsyn22BackupInput1SelSelAll OBJECT-TYPE
        SYNTAX            INTEGER { noAction(0),valSelAll(1) }
        MAX-ACCESS        read-write
        STATUS            current
        DESCRIPTION
                "CMNT: - Backup Inp1 2 Aud Fail Sel All
                 TYPE: - Button
                 PAGE: - Backup
                    Sel All  cmdID= 39146
                    value= 1  "
        ::= { iqsyn22CmdEntry 39146 }


    iqsyn22BackupInput1SelSelNone OBJECT-TYPE
        SYNTAX            INTEGER { noAction(0),valSelNone(1) }
        MAX-ACCESS        read-write
        STATUS            current
        DESCRIPTION
                "CMNT: - Backup Inp1 2 Aud Fail Sel None
                 TYPE: - Button
                 PAGE: - Backup
                    Sel None  cmdID= 39147
                    value= 1  "
        ::= { iqsyn22CmdEntry 39147 }


    iqsyn22BackupInput2SelStatInp2OK OBJECT-TYPE
        SYNTAX            RollCallString
        MAX-ACCESS        read-only
        STATUS            current
        DESCRIPTION
                "CMNT: - Backup Sel 2 Inp 2 OK Status
                 TYPE: - Display
                 PAGE: - Backup
                    Stat Inp2 OK  cmdID= 39131  "
        ::= { iqsyn22CmdEntry 39131 }


    iqsyn22BackupInput2SelStatInp1FAIL OBJECT-TYPE
        SYNTAX            RollCallString
        MAX-ACCESS        read-only
        STATUS            current
        DESCRIPTION
                "CMNT: - Backup Sel 2 Inp 1 FAIL Status
                 TYPE: - Display
                 PAGE: - Backup
                    Stat Inp1 FAIL  cmdID= 39132  "
        ::= { iqsyn22CmdEntry 39132 }


    iqsyn22BackupInput2SelStatInp1Err OBJECT-TYPE
        SYNTAX            RollCallString
        MAX-ACCESS        read-only
        STATUS            current
        DESCRIPTION
                "CMNT: - Backup Sel 2 Inp 1 ERR Status
                 TYPE: - Display
                 PAGE: - Backup
                    Stat Inp1 Err  cmdID= 39140  "
        ::= { iqsyn22CmdEntry 39140 }


    iqsyn22BackupInput2SelStatAUDFail1 OBJECT-TYPE
        SYNTAX            RollCallString
        MAX-ACCESS        read-only
        STATUS            current
        DESCRIPTION
                "CMNT: - Backup Reversion Delay
                 TYPE: - Display
                 PAGE: - Backup
                    Stat AUD Fail 1  cmdID= 39158  "
        ::= { iqsyn22CmdEntry 39158 }


    iqsyn22BackupInput2SelStatStd1 OBJECT-TYPE
        SYNTAX            RollCallString
        MAX-ACCESS        read-only
        STATUS            current
        DESCRIPTION
                "CMNT: - Backup Inp2 1 Aud Fail G4C2
                 TYPE: - Display
                 PAGE: - Backup
                    Stat Std 1  cmdID= 39175  "
        ::= { iqsyn22CmdEntry 39175 }


    iqsyn22BackupInput2SelStatGPI1 OBJECT-TYPE
        SYNTAX            RollCallString
        MAX-ACCESS        read-only
        STATUS            current
        DESCRIPTION
                "CMNT: - Backup Sel 2 GPI 1 Status
                 TYPE: - Display
                 PAGE: - Backup
                    Stat GPI 1  cmdID= 39133  "
        ::= { iqsyn22CmdEntry 39133 }


    iqsyn22BackupInput2SelStatGPI2 OBJECT-TYPE
        SYNTAX            RollCallString
        MAX-ACCESS        read-only
        STATUS            current
        DESCRIPTION
                "CMNT: - Backup Sel 2 GPI 2 Status
                 TYPE: - Display
                 PAGE: - Backup
                    Stat GPI 2  cmdID= 39134  "
        ::= { iqsyn22CmdEntry 39134 }


    iqsyn22BackupInput2SelEnblInp2OK OBJECT-TYPE
        SYNTAX            INTEGER { disable(0), enable(1)  }
        MAX-ACCESS        read-write
        STATUS            current
        DESCRIPTION
                "CMNT: - Backup Sel 2 Inp 2 OK
                 TYPE: - Checkbox
                 PAGE: - Backup
                    Enbl Inp2 OK  cmdID= 39111  "
        ::= { iqsyn22CmdEntry 39111 }


    iqsyn22BackupInput2SelEnblInp1FAIL OBJECT-TYPE
        SYNTAX            INTEGER { disable(0), enable(1)  }
        MAX-ACCESS        read-write
        STATUS            current
        DESCRIPTION
                "CMNT: - Backup Sel 2 Inp 1 FAIL
                 TYPE: - Checkbox
                 PAGE: - Backup
                    Enbl Inp1 FAIL  cmdID= 39112  "
        ::= { iqsyn22CmdEntry 39112 }


    iqsyn22BackupInput2SelEnblInp1Err OBJECT-TYPE
        SYNTAX            INTEGER { disable(0), enable(1)  }
        MAX-ACCESS        read-write
        STATUS            current
        DESCRIPTION
                "CMNT: - Backup Sel 2 Inp 1 ERR
                 TYPE: - Checkbox
                 PAGE: - Backup
                    Enbl Inp1 Err  cmdID= 39136  "
        ::= { iqsyn22CmdEntry 39136 }


    iqsyn22BackupInput2SelEnblGPI1 OBJECT-TYPE
        SYNTAX            INTEGER { disable(0), enable(1)  }
        MAX-ACCESS        read-write
        STATUS            current
        DESCRIPTION
                "CMNT: - Backup Sel 2 GPI 1
                 TYPE: - Checkbox
                 PAGE: - Backup
                    Enbl GPI 1  cmdID= 39113  "
        ::= { iqsyn22CmdEntry 39113 }


    iqsyn22BackupInput2SelEnblGPI2 OBJECT-TYPE
        SYNTAX            INTEGER { disable(0), enable(1)  }
        MAX-ACCESS        read-write
        STATUS            current
        DESCRIPTION
                "CMNT: - Backup Sel 2 GPI 2
                 TYPE: - Checkbox
                 PAGE: - Backup
                    Enbl GPI 2  cmdID= 39114  "
        ::= { iqsyn22CmdEntry 39114 }


    iqsyn22BackupInput2SelEnblAudInp1Err OBJECT-TYPE
        SYNTAX            INTEGER { disable(0), enable(1)  }
        MAX-ACCESS        read-write
        STATUS            current
        DESCRIPTION
                "CMNT: - Backup Inp2 1 Aud Fail Enable
                 TYPE: - Checkbox
                 PAGE: - Backup
                    Enbl Aud Inp1 Err  cmdID= 39157  "
        ::= { iqsyn22CmdEntry 39157 }


    iqsyn22BackupInput2SelEnblStdInp1 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Enbl Std Inp 1  cmdID= 39174  "
        ::= { iqsyn22CmdEntry 39174 }


    iqsyn22BackupInput2SelDlyInp2OK OBJECT-TYPE
        SYNTAX            INTEGER
        MAX-ACCESS        read-write
        STATUS            current
        DESCRIPTION
                "CMNT: - Backup Sel 2 Inp 2 OK Delay
                 TYPE: - Number
                 PAGE: - Backup
                    Dly Inp2 OK  cmdID= 39119
                    min= 10  max= 100  step= 1  format= %0.1f s  div_scale= 10  preset= 10
                    Min = 1.0 s  Max = 10.0 s  Step = 0.1 s  Preset = 1.0 s  "
        ::= { iqsyn22CmdEntry 39119 }


    iqsyn22BackupInput2SelDlyInp1FAIL OBJECT-TYPE
        SYNTAX            INTEGER
        MAX-ACCESS        read-write
        STATUS            current
        DESCRIPTION
                "CMNT: - Backup Sel 2 Inp 1 FAIL Delay
                 TYPE: - Number
                 PAGE: - Backup
                    Dly Inp1 FAIL  cmdID= 39120
                    min= 5  max= 100  step= 1  format= %0.1f s  div_scale= 10  preset= 5
                    Min = 0.5 s  Max = 10.0 s  Step = 0.1 s  Preset = 0.5 s  "
        ::= { iqsyn22CmdEntry 39120 }


    iqsyn22BackupInput2SelDlyInp1Err OBJECT-TYPE
        SYNTAX            INTEGER
        MAX-ACCESS        read-write
        STATUS            current
        DESCRIPTION
                "CMNT: - Backup Sel 2 Inp 1 ERR Delay
                 TYPE: - Number
                 PAGE: - Backup
                    Dly Inp1 Err  cmdID= 39138
                    min= 10  max= 100  step= 10  format= %0.0f s  div_scale= 10  preset= 50
                    Min = 1 s  Max = 10 s  Step = 1 s  Preset = 5 s  "
        ::= { iqsyn22CmdEntry 39138 }


    iqsyn22BackupInput2SelDlyAud2FAIL OBJECT-TYPE
        SYNTAX            INTEGER
        MAX-ACCESS        read-write
        STATUS            current
        DESCRIPTION
                "CMNT: - Backup Inp2 1 Aud Fail Delay
                 TYPE: - Number
                 PAGE: - Backup
                    Dly Aud2 FAIL  cmdID= 39159
                    min= 10  max= 100  step= 1  format= %0.1f s  div_scale= 10  preset= 10
                    Min = 1.0 s  Max = 10.0 s  Step = 0.1 s  Preset = 1.0 s  "
        ::= { iqsyn22CmdEntry 39159 }


    iqsyn22BackupInput2SelDlyStd1 OBJECT-TYPE
        SYNTAX            INTEGER
        MAX-ACCESS        read-write
        STATUS            current
        DESCRIPTION
                "CMNT: - Backup Inp2 1 Aud Fail G4C2
                 TYPE: - Number
                 PAGE: - Backup
                    Dly Std 1  cmdID= 39176
                    min= 10  max= 100  step= 1  format= %0.1f s  div_scale= 10  preset= 10
                    Min = 1.0 s  Max = 10.0 s  Step = 0.1 s  Preset = 1.0 s  "
        ::= { iqsyn22CmdEntry 39176 }


    iqsyn22BackupInput2SelDlyGPI1 OBJECT-TYPE
        SYNTAX            INTEGER
        MAX-ACCESS        read-write
        STATUS            current
        DESCRIPTION
                "CMNT: - Backup Sel 2 GPI 1 Delay
                 TYPE: - Number
                 PAGE: - Backup
                    Dly GPI 1  cmdID= 39121
                    min= 0  max= 100  step= 1  format= %0.1f s  div_scale= 10  preset= 0
                    Min = 0.0 s  Max = 10.0 s  Step = 0.1 s  Preset = 0.0 s  "
        ::= { iqsyn22CmdEntry 39121 }


    iqsyn22BackupInput2SelDlyGPI2 OBJECT-TYPE
        SYNTAX            INTEGER
        MAX-ACCESS        read-write
        STATUS            current
        DESCRIPTION
                "CMNT: - Backup Sel 2 GPI 2 Delay
                 TYPE: - Number
                 PAGE: - Backup
                    Dly GPI 2  cmdID= 39122
                    min= 0  max= 100  step= 1  format= %0.1f s  div_scale= 10  preset= 0
                    Min = 0.0 s  Max = 10.0 s  Step = 0.1 s  Preset = 0.0 s  "
        ::= { iqsyn22CmdEntry 39122 }


    iqsyn22BackupInput2SelGPI1State OBJECT-TYPE
        SYNTAX            INTEGER {
                            valOn(0),
                            valOff(1)
                            }
        MAX-ACCESS        read-write
        STATUS            current
        DESCRIPTION
                "CMNT: - Backup Sel 2 GPI 1 val
                 TYPE: - RadiobuttonList
                 PAGE: - Backup
                    GPI 1 State  cmdID= 39125
                    On  value= 0
                    Off  value= 1  "
        ::= { iqsyn22CmdEntry 39125 }


    iqsyn22BackupInput2SelGPI2State OBJECT-TYPE
        SYNTAX            INTEGER {
                            valOn(0),
                            valOff(1)
                            }
        MAX-ACCESS        read-write
        STATUS            current
        DESCRIPTION
                "CMNT: - Backup Sel 2 GPI 2 val
                 TYPE: - RadiobuttonList
                 PAGE: - Backup
                    GPI 2 State  cmdID= 39126
                    On  value= 0
                    Off  value= 1  "
        ::= { iqsyn22CmdEntry 39126 }


    iqsyn22BackupInput2SelInp21AudFailG1C1 OBJECT-TYPE
        SYNTAX            INTEGER { disable(0), enable(1)  }
        MAX-ACCESS        read-write
        STATUS            current
        DESCRIPTION
                "CMNT: - Backup Inp2 1 Aud Fail G1C1
                 TYPE: - Checkbox
                 PAGE: - Backup
                    Inp2 1 Aud Fail G1C1  cmdID= 39163  "
        ::= { iqsyn22CmdEntry 39163 }


    iqsyn22BackupInput2SelInp21AudFailG1C2 OBJECT-TYPE
        SYNTAX            INTEGER { disable(0), enable(1)  }
        MAX-ACCESS        read-write
        STATUS            current
        DESCRIPTION
                "CMNT: - Backup Inp2 1 Aud Fail G1C2
                 TYPE: - Checkbox
                 PAGE: - Backup
                    Inp2 1 Aud Fail G1C2  cmdID= 39164  "
        ::= { iqsyn22CmdEntry 39164 }


    iqsyn22BackupInput2SelInp21AudFailG2C1 OBJECT-TYPE
        SYNTAX            INTEGER { disable(0), enable(1)  }
        MAX-ACCESS        read-write
        STATUS            current
        DESCRIPTION
                "CMNT: - Backup Inp2 1 Aud Fail G2C1
                 TYPE: - Checkbox
                 PAGE: - Backup
                    Inp2 1 Aud Fail G2C1  cmdID= 39165  "
        ::= { iqsyn22CmdEntry 39165 }


    iqsyn22BackupInput2SelInp21AudFailG2C2 OBJECT-TYPE
        SYNTAX            INTEGER { disable(0), enable(1)  }
        MAX-ACCESS        read-write
        STATUS            current
        DESCRIPTION
                "CMNT: - Backup Inp2 1 Aud Fail G2C2
                 TYPE: - Checkbox
                 PAGE: - Backup
                    Inp2 1 Aud Fail G2C2  cmdID= 39166  "
        ::= { iqsyn22CmdEntry 39166 }


    iqsyn22BackupInput2SelInp21AudFailG3C1 OBJECT-TYPE
        SYNTAX            INTEGER { disable(0), enable(1)  }
        MAX-ACCESS        read-write
        STATUS            current
        DESCRIPTION
                "CMNT: - Backup Inp2 1 Aud Fail G3C1
                 TYPE: - Checkbox
                 PAGE: - Backup
                    Inp2 1 Aud Fail G3C1  cmdID= 39167  "
        ::= { iqsyn22CmdEntry 39167 }


    iqsyn22BackupInput2SelInp21AudFailG3C2 OBJECT-TYPE
        SYNTAX            INTEGER { disable(0), enable(1)  }
        MAX-ACCESS        read-write
        STATUS            current
        DESCRIPTION
                "CMNT: - Backup Inp2 1 Aud Fail G3C2
                 TYPE: - Checkbox
                 PAGE: - Backup
                    Inp2 1 Aud Fail G3C2  cmdID= 39168  "
        ::= { iqsyn22CmdEntry 39168 }


    iqsyn22BackupInput2SelInp21AudFailG4C1 OBJECT-TYPE
        SYNTAX            INTEGER { disable(0), enable(1)  }
        MAX-ACCESS        read-write
        STATUS            current
        DESCRIPTION
                "CMNT: - Backup Inp2 1 Aud Fail G4C1
                 TYPE: - Checkbox
                 PAGE: - Backup
                    Inp2 1 Aud Fail G4C1  cmdID= 39169  "
        ::= { iqsyn22CmdEntry 39169 }


    iqsyn22BackupInput2SelInp21AudFailG4C2 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Inp2 1 Aud Fail G4C2  cmdID= 39170  "
        ::= { iqsyn22CmdEntry 39170 }


    iqsyn22BackupInput2SelInp21AudFailLockGrp OBJECT-TYPE
        SYNTAX            INTEGER { disable(0), enable(1)  }
        MAX-ACCESS        read-write
        STATUS            current
        DESCRIPTION
                "CMNT: - Backup Inp2 1 Aud Fail Lock Grp
                 TYPE: - Checkbox
                 PAGE: - Backup
                    Inp2 1 Aud Fail Lock Grp  cmdID= 39162  "
        ::= { iqsyn22CmdEntry 39162 }


    iqsyn22BackupInput2SelSelAll OBJECT-TYPE
        SYNTAX            INTEGER { noAction(0),valSelAll(1) }
        MAX-ACCESS        read-write
        STATUS            current
        DESCRIPTION
                "CMNT: - Backup Inp2 1 Aud Fail Sel All
                 TYPE: - Button
                 PAGE: - Backup
                    Sel All  cmdID= 39160
                    value= 1  "
        ::= { iqsyn22CmdEntry 39160 }


    iqsyn22BackupInput2SelSelNone OBJECT-TYPE
        SYNTAX            INTEGER { noAction(0),valSelNone(1) }
        MAX-ACCESS        read-write
        STATUS            current
        DESCRIPTION
                "CMNT: - Backup Inp2 1 Aud Fail Sel None
                 TYPE: - Button
                 PAGE: - Backup
                    Sel None  cmdID= 39161
                    value= 1  "
        ::= { iqsyn22CmdEntry 39161 }


    iqsyn22UtilsPatternsPatternEnable OBJECT-TYPE
        SYNTAX            INTEGER { disable(0), enable(1)  }
        MAX-ACCESS        read-write
        STATUS            current
        DESCRIPTION
                "CMNT: - TPG pattern enable
                 TYPE: - Checkbox
                 PAGE: - Utils
                    Pattern Enable  cmdID= 33038  "
        ::= { iqsyn22CmdEntry 33038 }


    iqsyn22UtilsPatternsScrollPattern OBJECT-TYPE
        SYNTAX            INTEGER { disable(0), enable(1)  }
        MAX-ACCESS        read-write
        STATUS            current
        DESCRIPTION
                "CMNT: - Scroll test pattern horizontally
                 TYPE: - Checkbox
                 PAGE: - Utils
                    Scroll Pattern  cmdID= 33040  "
        ::= { iqsyn22CmdEntry 33040 }


    iqsyn22UtilsPatternsPatternType OBJECT-TYPE
        SYNTAX            INTEGER {
                            val100ColorBars(1),
                            val75ColorBars(2),
                            valSMPTEBars(3),
                            valTartanBars(4),
                            valPluge(5),
                            valRamp(6),
                            valSweep(7),
                            valPulseBar(8),
                            valBurst(9),
                            valBlack(10)
                            }
        MAX-ACCESS        read-write
        STATUS            current
        DESCRIPTION
                "CMNT: - TPG pattern type
                 TYPE: - RadiobuttonList
                 PAGE: - Utils
                    Pattern Type  cmdID= 33039
                    100% Color Bars  value= 1
                    75% Color Bars  value= 2
                    SMPTE Bars  value= 3
                    Tartan Bars  value= 4
                    Pluge  value= 5
                    Ramp  value= 6
                    Sweep  value= 7
                    Pulse & Bar  value= 8
                    Burst  value= 9
                    Black  value= 10  "
        ::= { iqsyn22CmdEntry 33039 }


    iqsyn22UtilsANCblankonMismat OBJECT-TYPE
        SYNTAX            INTEGER { disable(0), enable(1)  }
        MAX-ACCESS        read-write
        STATUS            current
        DESCRIPTION
                "CMNT: - Blank all ANC if standard mismatch
                 TYPE: - Checkbox
                 PAGE: - Utils
                    ANC blank on Mismatch  cmdID= 33036  "
        ::= { iqsyn22CmdEntry 33036 }


    iqsyn22UtilsFreezeForceFreeze OBJECT-TYPE
        SYNTAX            INTEGER { disable(0), enable(1)  }
        MAX-ACCESS        read-write
        STATUS            current
        DESCRIPTION
                "CMNT: - Freeze output picture
                 TYPE: - Checkbox
                 PAGE: - Utils
                    Force Freeze  cmdID= 33032  "
        ::= { iqsyn22CmdEntry 33032 }


    iqsyn22UtilsFreezeFreezeType OBJECT-TYPE
        SYNTAX            INTEGER {
                            valFrame(0),
                            valField(1)
                            }
        MAX-ACCESS        read-write
        STATUS            current
        DESCRIPTION
                "CMNT: - Type of Frozen output: Frame/Field
                 TYPE: - RadiobuttonList
                 PAGE: - Utils
                    Freeze Type  cmdID= 33033
                    Frame  value= 0
                    Field  value= 1  "
        ::= { iqsyn22CmdEntry 33033 }


    iqsyn22UtilsMonochrome OBJECT-TYPE
        SYNTAX            INTEGER { disable(0), enable(1)  }
        MAX-ACCESS        read-write
        STATUS            current
        DESCRIPTION
                "CMNT: - Monochrome enable
                 TYPE: - Checkbox
                 PAGE: - Utils
                    Monochrome  cmdID= 33034  "
        ::= { iqsyn22CmdEntry 33034 }


    iqsyn22UtilsMonochromeMonochromeType OBJECT-TYPE
        SYNTAX            INTEGER {
                            valYonly(0),
                            valConly(1)
                            }
        MAX-ACCESS        read-write
        STATUS            current
        DESCRIPTION
                "CMNT: - Type of Monochrome output
                 TYPE: - RadiobuttonList
                 PAGE: - Utils
                    Monochrome Type  cmdID= 33035
                    Y only  value= 0
                    C only  value= 1  "
        ::= { iqsyn22CmdEntry 33035 }


    iqsyn22UtilsHANCVBIBlankingANCMode OBJECT-TYPE
        SYNTAX            INTEGER {
                            valPassInputANC(0),
                            valBlankHANC(2),
                            valBlankAllANC(1)
                            }
        MAX-ACCESS        read-write
        STATUS            current
        DESCRIPTION
                "CMNT: - Blank ANC on output (All/HANC/Pass)
                 TYPE: - RadiobuttonList
                 PAGE: - Utils
                    ANC Mode  cmdID= 33037
                    Pass Input ANC  value= 0
                    Blank HANC  value= 2
                    Blank All ANC  value= 1  "
        ::= { iqsyn22CmdEntry 33037 }


    iqsyn22UtilsHANCVBIBlankingStandard OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - Select std for VBI blank display/set
                 TYPE: - RadiobuttonList
                 PAGE: - Utils
                    Standard  cmdID= 37200
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn22CmdEntry 37200 }


    iqsyn22UtilsHANCVBIBlankingBlankAll OBJECT-TYPE
        SYNTAX            INTEGER { noAction(0),valBlankAll(1) }
        MAX-ACCESS        read-write
        STATUS            current
        DESCRIPTION
                "CMNT: - Blank all valid lines
                 TYPE: - Button
                 PAGE: - Utils
                    Blank All  cmdID= 37201
                    value= 1  "
        ::= { iqsyn22CmdEntry 37201 }


    iqsyn22UtilsHANCVBIBlankingPassAll OBJECT-TYPE
        SYNTAX            INTEGER { noAction(0),valPassAll(1) }
        MAX-ACCESS        read-write
        STATUS            current
        DESCRIPTION
                "CMNT: - Blank no lines
                 TYPE: - Button
                 PAGE: - Utils
                    Pass All  cmdID= 37202
                    value= 1  "
        ::= { iqsyn22CmdEntry 37202 }


    iqsyn22UtilsHANCVBIBlankingBlank1 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 1  cmdID= 37210  "
        ::= { iqsyn22CmdEntry 37210 }


    iqsyn22UtilsHANCVBIBlankingBlank2 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 2  cmdID= 37211  "
        ::= { iqsyn22CmdEntry 37211 }


    iqsyn22UtilsHANCVBIBlankingBlank3 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 3  cmdID= 37212  "
        ::= { iqsyn22CmdEntry 37212 }


    iqsyn22UtilsHANCVBIBlankingBlank4 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 4  cmdID= 37213  "
        ::= { iqsyn22CmdEntry 37213 }


    iqsyn22UtilsHANCVBIBlankingBlank5 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 5  cmdID= 37214  "
        ::= { iqsyn22CmdEntry 37214 }


    iqsyn22UtilsHANCVBIBlankingBlank6 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 6  cmdID= 37215  "
        ::= { iqsyn22CmdEntry 37215 }


    iqsyn22UtilsHANCVBIBlankingBlank7 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 7  cmdID= 37216  "
        ::= { iqsyn22CmdEntry 37216 }


    iqsyn22UtilsHANCVBIBlankingBlank8 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 8  cmdID= 37217  "
        ::= { iqsyn22CmdEntry 37217 }


    iqsyn22UtilsHANCVBIBlankingBlank9 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 9  cmdID= 37218  "
        ::= { iqsyn22CmdEntry 37218 }


    iqsyn22UtilsHANCVBIBlankingBlank10 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 10  cmdID= 37219  "
        ::= { iqsyn22CmdEntry 37219 }


    iqsyn22UtilsHANCVBIBlankingBlank11 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 11  cmdID= 37220  "
        ::= { iqsyn22CmdEntry 37220 }


    iqsyn22UtilsHANCVBIBlankingBlank12 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 12  cmdID= 37221  "
        ::= { iqsyn22CmdEntry 37221 }


    iqsyn22UtilsHANCVBIBlankingBlank13 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 13  cmdID= 37222  "
        ::= { iqsyn22CmdEntry 37222 }


    iqsyn22UtilsHANCVBIBlankingBlank14 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 14  cmdID= 37223  "
        ::= { iqsyn22CmdEntry 37223 }


    iqsyn22UtilsHANCVBIBlankingBlank15 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 15  cmdID= 37224  "
        ::= { iqsyn22CmdEntry 37224 }


    iqsyn22UtilsHANCVBIBlankingBlank16 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 16  cmdID= 37225  "
        ::= { iqsyn22CmdEntry 37225 }


    iqsyn22UtilsHANCVBIBlankingBlank17 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 17  cmdID= 37226  "
        ::= { iqsyn22CmdEntry 37226 }


    iqsyn22UtilsHANCVBIBlankingBlank18 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 18  cmdID= 37227  "
        ::= { iqsyn22CmdEntry 37227 }


    iqsyn22UtilsHANCVBIBlankingBlank19 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 19  cmdID= 37228  "
        ::= { iqsyn22CmdEntry 37228 }


    iqsyn22UtilsHANCVBIBlankingBlank20 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 20  cmdID= 37229  "
        ::= { iqsyn22CmdEntry 37229 }


    iqsyn22UtilsHANCVBIBlankingBlank21 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 21  cmdID= 37230  "
        ::= { iqsyn22CmdEntry 37230 }


    iqsyn22UtilsHANCVBIBlankingBlank22 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 22  cmdID= 37231  "
        ::= { iqsyn22CmdEntry 37231 }


    iqsyn22UtilsHANCVBIBlankingBlank23 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 23  cmdID= 37232  "
        ::= { iqsyn22CmdEntry 37232 }


    iqsyn22UtilsHANCVBIBlankingBlank24 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 24  cmdID= 37233  "
        ::= { iqsyn22CmdEntry 37233 }


    iqsyn22UtilsHANCVBIBlankingBlank25 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 25  cmdID= 37234  "
        ::= { iqsyn22CmdEntry 37234 }


    iqsyn22UtilsHANCVBIBlankingBlank26 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 26  cmdID= 37235  "
        ::= { iqsyn22CmdEntry 37235 }


    iqsyn22UtilsHANCVBIBlankingBlank27 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 27  cmdID= 37236  "
        ::= { iqsyn22CmdEntry 37236 }


    iqsyn22UtilsHANCVBIBlankingBlank28 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 28  cmdID= 37237  "
        ::= { iqsyn22CmdEntry 37237 }


    iqsyn22UtilsHANCVBIBlankingBlank29 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 29  cmdID= 37238  "
        ::= { iqsyn22CmdEntry 37238 }


    iqsyn22UtilsHANCVBIBlankingBlank30 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 30  cmdID= 37239  "
        ::= { iqsyn22CmdEntry 37239 }


    iqsyn22UtilsHANCVBIBlankingBlank31 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 31  cmdID= 37240  "
        ::= { iqsyn22CmdEntry 37240 }


    iqsyn22UtilsHANCVBIBlankingBlank32 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 32  cmdID= 37241  "
        ::= { iqsyn22CmdEntry 37241 }


    iqsyn22UtilsHANCVBIBlankingBlank33 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 33  cmdID= 37242  "
        ::= { iqsyn22CmdEntry 37242 }


    iqsyn22UtilsHANCVBIBlankingBlank34 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 34  cmdID= 37243  "
        ::= { iqsyn22CmdEntry 37243 }


    iqsyn22UtilsUserCaptionsEnable OBJECT-TYPE
        SYNTAX            INTEGER { disable(0), enable(1)  }
        MAX-ACCESS        read-write
        STATUS            current
        DESCRIPTION
                "CMNT: - 
                 TYPE: - Checkbox
                 PAGE: - Utils
                    Enable  cmdID= 6080  "
        ::= { iqsyn22CmdEntry 6080 }


    iqsyn22UtilsUserCaptionsText OBJECT-TYPE
        SYNTAX            RollCallString
        MAX-ACCESS        read-write
        STATUS            current
        DESCRIPTION
                "CMNT: - 
                 TYPE: - Editstring
                 PAGE: - Utils
                    Text  cmdID= 6085
                    preset= IQSYN22"
        ::= { iqsyn22CmdEntry 6085 }


    iqsyn22UtilsUserCaptionsXPos OBJECT-TYPE
        SYNTAX            INTEGER
        MAX-ACCESS        read-write
        STATUS            current
        DESCRIPTION
                "CMNT: - 
                 TYPE: - Number
                 PAGE: - Utils
                    X Pos  cmdID= 6081
                    min= 0  max= 1880  step= 1  format= %0.0f  div_scale= 1  preset= 0
                    Min = 0  Max = 1880  Step = 1  Preset = 0  "
        ::= { iqsyn22CmdEntry 6081 }


    iqsyn22UtilsUserCaptionsYPos OBJECT-TYPE
        SYNTAX            INTEGER
        MAX-ACCESS        read-write
        STATUS            current
        DESCRIPTION
                "CMNT: - 
                 TYPE: - Number
                 PAGE: - Utils
                    Y Pos  cmdID= 6082
                    min= 0  max= 680  step= 1  format= %0.0f  div_scale= 1  preset= 0
                    Min = 0  Max = 680  Step = 1  Preset = 0  "
        ::= { iqsyn22CmdEntry 6082 }


    iqsyn22UtilsUserCaptionsXSize OBJECT-TYPE
        SYNTAX            INTEGER
        MAX-ACCESS        read-write
        STATUS            current
        DESCRIPTION
                "CMNT: - 
                 TYPE: - Number
                 PAGE: - Utils
                    X Size  cmdID= 6083
                    min= 1  max= 10  step= 1  format= %0.0f  div_scale= 1  preset= 1
                    Min = 1  Max = 10  Step = 1  Preset = 1  "
        ::= { iqsyn22CmdEntry 6083 }


    iqsyn22UtilsUserCaptionsYSize OBJECT-TYPE
        SYNTAX            INTEGER
        MAX-ACCESS        read-write
        STATUS            current
        DESCRIPTION
                "CMNT: - 
                 TYPE: - Number
                 PAGE: - Utils
                    Y Size  cmdID= 6084
                    min= 1  max= 10  step= 1  format= %0.0f  div_scale= 1  preset= 1
                    Min = 1  Max = 10  Step = 1  Preset = 1  "
        ::= { iqsyn22CmdEntry 6084 }


    iqsyn22UtilsSmpte2016Enable OBJECT-TYPE
        SYNTAX            INTEGER { disable(0), enable(1)  }
        MAX-ACCESS        read-write
        STATUS            current
        DESCRIPTION
                "CMNT: - Enable for SMTPE2016
                 TYPE: - Checkbox
                 PAGE: - Utils
                    Enable39000  cmdID= 39000  "
        ::= { iqsyn22CmdEntry 39000 }


    iqsyn22UtilsSmpte2016EnableUseAfdLine OBJECT-TYPE
        SYNTAX            INTEGER { disable(0), enable(1)  }
        MAX-ACCESS        read-write
        STATUS            current
        DESCRIPTION
                "CMNT: - Enable for SMTPE2016 reader to writer lines
                 TYPE: - Checkbox
                 PAGE: - Utils
                    Enable39004  cmdID= 39004  "
        ::= { iqsyn22CmdEntry 39004 }


    iqsyn22UtilsSmpte2016Line1ReadNum OBJECT-TYPE
        SYNTAX            RollCallString
        MAX-ACCESS        read-only
        STATUS            current
        DESCRIPTION
                "CMNT: - SMTPE2016 Reader Line 1 Number
                 TYPE: - Display
                 PAGE: - Utils
                    Line1 Read Num  cmdID= 39001  "
        ::= { iqsyn22CmdEntry 39001 }


    iqsyn22UtilsSmpte2016Line1ReadAFD OBJECT-TYPE
        SYNTAX            RollCallString
        MAX-ACCESS        read-only
        STATUS            current
        DESCRIPTION
                "CMNT: - SMTPE2016 Reader Line 1 AFD
                 TYPE: - Display
                 PAGE: - Utils
                    Line1 Read AFD  cmdID= 39002  "
        ::= { iqsyn22CmdEntry 39002 }


    iqsyn22UtilsSmpte2016Line1ReadAR OBJECT-TYPE
        SYNTAX            RollCallString
        MAX-ACCESS        read-only
        STATUS            current
        DESCRIPTION
                "CMNT: - SMTPE2016 Reader Line 1 AR
                 TYPE: - Display
                 PAGE: - Utils
                    Line1 Read AR  cmdID= 39003  "
        ::= { iqsyn22CmdEntry 39003 }


    iqsyn22UtilsSmpte2016Line2ReadNum OBJECT-TYPE
        SYNTAX            RollCallString
        MAX-ACCESS        read-only
        STATUS            current
        DESCRIPTION
                "CMNT: - SMTPE2016 Reader Line 2 Number
                 TYPE: - Display
                 PAGE: - Utils
                    Line2 Read Num  cmdID= 39005  "
        ::= { iqsyn22CmdEntry 39005 }


    iqsyn22UtilsSmpte2016Line2ReadAFD OBJECT-TYPE
        SYNTAX            RollCallString
        MAX-ACCESS        read-only
        STATUS            current
        DESCRIPTION
                "CMNT: - SMTPE2016 Reader Line 2 AFD
                 TYPE: - Display
                 PAGE: - Utils
                    Line2 Read AFD  cmdID= 39006  "
        ::= { iqsyn22CmdEntry 39006 }


    iqsyn22UtilsSmpte2016Line2ReadAR OBJECT-TYPE
        SYNTAX            RollCallString
        MAX-ACCESS        read-only
        STATUS            current
        DESCRIPTION
                "CMNT: - SMTPE2016 Reader Line 2 AR
                 TYPE: - Display
                 PAGE: - Utils
                    Line2 Read AR  cmdID= 39007  "
        ::= { iqsyn22CmdEntry 39007 }


    iqsyn22UtilsSmpte2016Line1Inuse OBJECT-TYPE
        SYNTAX            RollCallString
        MAX-ACCESS        read-only
        STATUS            current
        DESCRIPTION
                "CMNT: - SMTPE2016 Write Line 1 Inuse
                 TYPE: - Display
                 PAGE: - Utils
                    Line1 Inuse  cmdID= 39053  "
        ::= { iqsyn22CmdEntry 39053 }


    iqsyn22UtilsSmpte2016Line1WriteAFD OBJECT-TYPE
        SYNTAX            RollCallString
        MAX-ACCESS        read-only
        STATUS            current
        DESCRIPTION
                "CMNT: - SMTPE2016 Writer Line 1 AFD
                 TYPE: - Display
                 PAGE: - Utils
                    Line1 Write AFD  cmdID= 39010  "
        ::= { iqsyn22CmdEntry 39010 }


    iqsyn22UtilsSmpte2016Line2Inuse OBJECT-TYPE
        SYNTAX            RollCallString
        MAX-ACCESS        read-only
        STATUS            current
        DESCRIPTION
                "CMNT: - SMTPE2016 Write Line 2 Inuse
                 TYPE: - Display
                 PAGE: - Utils
                    Line2 Inuse  cmdID= 39054  "
        ::= { iqsyn22CmdEntry 39054 }


    iqsyn22UtilsSmpte2016Line2WriteAFD OBJECT-TYPE
        SYNTAX            RollCallString
        MAX-ACCESS        read-only
        STATUS            current
        DESCRIPTION
                "CMNT: - SMTPE2016 Writer Line 2 AFD
                 TYPE: - Display
                 PAGE: - Utils
                    Line2 Write AFD  cmdID= 39013  "
        ::= { iqsyn22CmdEntry 39013 }


    iqsyn22UtilsSmpte2016Line1WriteAR OBJECT-TYPE
        SYNTAX            RollCallString
        MAX-ACCESS        read-only
        STATUS            current
        DESCRIPTION
                "CMNT: - SMTPE2016 Writer Line 1 AR
                 TYPE: - Display
                 PAGE: - Utils
                    Line1 Write AR  cmdID= 39011  "
        ::= { iqsyn22CmdEntry 39011 }


    iqsyn22UtilsSmpte2016Line2WriteAR OBJECT-TYPE
        SYNTAX            RollCallString
        MAX-ACCESS        read-only
        STATUS            current
        DESCRIPTION
                "CMNT: - SMTPE2016 Writer Line 2 AR
                 TYPE: - Display
                 PAGE: - Utils
                    Line2 Write AR  cmdID= 39014  "
        ::= { iqsyn22CmdEntry 39014 }


    iqsyn22UtilsSmpte2016Line1WriteNum OBJECT-TYPE
        SYNTAX            INTEGER
        MAX-ACCESS        read-write
        STATUS            current
        DESCRIPTION
                "CMNT: - SMTPE2016 Writer Line 1 Number
                 TYPE: - Number
                 PAGE: - Utils
                    Line1 Write Num  cmdID= 39009
                    min= 2  max= 42  step= 1  format= %0.0f  div_scale= 1  preset= 4
                    Min = 2  Max = 42  Step = 1  Preset = 4  "
        ::= { iqsyn22CmdEntry 39009 }


    iqsyn22UtilsSmpte2016Line2WriteNum OBJECT-TYPE
        SYNTAX            INTEGER
        MAX-ACCESS        read-write
        STATUS            current
        DESCRIPTION
                "CMNT: - SMTPE2016 Writer Line 2 Number
                 TYPE: - Number
                 PAGE: - Utils
                    Line2 Write Num  cmdID= 39012
                    min= 2  max= 42  step= 1  format= %0.0f  div_scale= 1  preset= 4
                    Min = 2  Max = 42  Step = 1  Preset = 4  "
        ::= { iqsyn22CmdEntry 39012 }


    iqsyn22UtilsSmpte201643Mapping0 OBJECT-TYPE
        SYNTAX            INTEGER
        MAX-ACCESS        read-write
        STATUS            current
        DESCRIPTION
                "CMNT: - SMTPE2016 4:3 AFD Mapping
                 TYPE: - Number
                 PAGE: - Utils
                    4:3 Mapping 0  cmdID= 39015
                    min= 0  max= 35  step= 1  format= 0  div_scale= 1  preset= 34
                    Min = 0  Max = 0  Step = 0  Preset = 0  "
        ::= { iqsyn22CmdEntry 39015 }


    iqsyn22UtilsSmpte201643Mapping1 OBJECT-TYPE
        SYNTAX            INTEGER
        MAX-ACCESS        read-write
        STATUS            current
        DESCRIPTION
                "CMNT: - SMTPE2016 4:3 AFD Mapping
                 TYPE: - Number
                 PAGE: - Utils
                    4:3 Mapping 1  cmdID= 39016
                    min= 0  max= 35  step= 1  format= 0  div_scale= 1  preset= 34
                    Min = 0  Max = 0  Step = 0  Preset = 0  "
        ::= { iqsyn22CmdEntry 39016 }


    iqsyn22UtilsSmpte201643Mapping2 OBJECT-TYPE
        SYNTAX            INTEGER
        MAX-ACCESS        read-write
        STATUS            current
        DESCRIPTION
                "CMNT: - SMTPE2016 4:3 AFD Mapping
                 TYPE: - Number
                 PAGE: - Utils
                    4:3 Mapping 2  cmdID= 39017
                    min= 0  max= 35  step= 1  format= 0  div_scale= 1  preset= 34
                    Min = 0  Max = 0  Step = 0  Preset = 0  "
        ::= { iqsyn22CmdEntry 39017 }


    iqsyn22UtilsSmpte201643Mapping3 OBJECT-TYPE
        SYNTAX            INTEGER
        MAX-ACCESS        read-write
        STATUS            current
        DESCRIPTION
                "CMNT: - SMTPE2016 4:3 AFD Mapping
                 TYPE: - Number
                 PAGE: - Utils
                    4:3 Mapping 3  cmdID= 39018
                    min= 0  max= 35  step= 1  format= 0  div_scale= 1  preset= 34
                    Min = 0  Max = 0  Step = 0  Preset = 0  "
        ::= { iqsyn22CmdEntry 39018 }


    iqsyn22UtilsSmpte201643Mapping4 OBJECT-TYPE
        SYNTAX            INTEGER
        MAX-ACCESS        read-write
        STATUS            current
        DESCRIPTION
                "CMNT: - SMTPE2016 4:3 AFD Mapping
                 TYPE: - Number
                 PAGE: - Utils
                    4:3 Mapping 4  cmdID= 39019
                    min= 0  max= 35  step= 1  format= 0  div_scale= 1  preset= 34
                    Min = 0  Max = 0  Step = 0  Preset = 0  "
        ::= { iqsyn22CmdEntry 39019 }


    iqsyn22UtilsSmpte201643Mapping5 OBJECT-TYPE
        SYNTAX            INTEGER
        MAX-ACCESS        read-write
        STATUS            current
        DESCRIPTION
                "CMNT: - SMTPE2016 4:3 AFD Mapping
                 TYPE: - Number
                 PAGE: - Utils
                    4:3 Mapping 5  cmdID= 39020
                    min= 0  max= 35  step= 1  format= 0  div_scale= 1  preset= 34
                    Min = 0  Max = 0  Step = 0  Preset = 0  "
        ::= { iqsyn22CmdEntry 39020 }


    iqsyn22UtilsSmpte201643Mapping6 OBJECT-TYPE
        SYNTAX            INTEGER
        MAX-ACCESS        read-write
        STATUS            current
        DESCRIPTION
                "CMNT: - SMTPE2016 4:3 AFD Mapping
                 TYPE: - Number
                 PAGE: - Utils
                    4:3 Mapping 6  cmdID= 39021
                    min= 0  max= 35  step= 1  format= 0  div_scale= 1  preset= 34
                    Min = 0  Max = 0  Step = 0  Preset = 0  "
        ::= { iqsyn22CmdEntry 39021 }


    iqsyn22UtilsSmpte201643Mapping7 OBJECT-TYPE
        SYNTAX            INTEGER
        MAX-ACCESS        read-write
        STATUS            current
        DESCRIPTION
                "CMNT: - SMTPE2016 4:3 AFD Mapping
                 TYPE: - Number
                 PAGE: - Utils
                    4:3 Mapping 7  cmdID= 39022
                    min= 0  max= 35  step= 1  format= 0  div_scale= 1  preset= 34
                    Min = 0  Max = 0  Step = 0  Preset = 0  "
        ::= { iqsyn22CmdEntry 39022 }


    iqsyn22UtilsSmpte201643Mapping8 OBJECT-TYPE
        SYNTAX            INTEGER
        MAX-ACCESS        read-write
        STATUS            current
        DESCRIPTION
                "CMNT: - SMTPE2016 4:3 AFD Mapping
                 TYPE: - Number
                 PAGE: - Utils
                    4:3 Mapping 8  cmdID= 39023
                    min= 0  max= 35  step= 1  format= 0  div_scale= 1  preset= 34
                    Min = 0  Max = 0  Step = 0  Preset = 0  "
        ::= { iqsyn22CmdEntry 39023 }


    iqsyn22UtilsSmpte201643Mapping9 OBJECT-TYPE
        SYNTAX            INTEGER
        MAX-ACCESS        read-write
        STATUS            current
        DESCRIPTION
                "CMNT: - SMTPE2016 4:3 AFD Mapping
                 TYPE: - Number
                 PAGE: - Utils
                    4:3 Mapping 9  cmdID= 39024
                    min= 0  max= 35  step= 1  format= 0  div_scale= 1  preset= 34
                    Min = 0  Max = 0  Step = 0  Preset = 0  "
        ::= { iqsyn22CmdEntry 39024 }


    iqsyn22UtilsSmpte201643Mapping10 OBJECT-TYPE
        SYNTAX            INTEGER
        MAX-ACCESS        read-write
        STATUS            current
        DESCRIPTION
                "CMNT: - SMTPE2016 4:3 AFD Mapping
                 TYPE: - Number
                 PAGE: - Utils
                    4:3 Mapping 10  cmdID= 39025
                    min= 0  max= 35  step= 1  format= 0  div_scale= 1  preset= 34
                    Min = 0  Max = 0  Step = 0  Preset = 0  "
        ::= { iqsyn22CmdEntry 39025 }


    iqsyn22UtilsSmpte201643Mapping11 OBJECT-TYPE
        SYNTAX            INTEGER
        MAX-ACCESS        read-write
        STATUS            current
        DESCRIPTION
                "CMNT: - SMTPE2016 4:3 AFD Mapping
                 TYPE: - Number
                 PAGE: - Utils
                    4:3 Mapping 11  cmdID= 39026
                    min= 0  max= 35  step= 1  format= 0  div_scale= 1  preset= 34
                    Min = 0  Max = 0  Step = 0  Preset = 0  "
        ::= { iqsyn22CmdEntry 39026 }


    iqsyn22UtilsSmpte201643Mapping12 OBJECT-TYPE
        SYNTAX            INTEGER
        MAX-ACCESS        read-write
        STATUS            current
        DESCRIPTION
                "CMNT: - SMTPE2016 4:3 AFD Mapping
                 TYPE: - Number
                 PAGE: - Utils
                    4:3 Mapping 12  cmdID= 39027
                    min= 0  max= 35  step= 1  format= 0  div_scale= 1  preset= 34
                    Min = 0  Max = 0  Step = 0  Preset = 0  "
        ::= { iqsyn22CmdEntry 39027 }


    iqsyn22UtilsSmpte201643Mapping13 OBJECT-TYPE
        SYNTAX            INTEGER
        MAX-ACCESS        read-write
        STATUS            current
        DESCRIPTION
                "CMNT: - SMTPE2016 4:3 AFD Mapping
                 TYPE: - Number
                 PAGE: - Utils
                    4:3 Mapping 13  cmdID= 39028
                    min= 0  max= 35  step= 1  format= 0  div_scale= 1  preset= 34
                    Min = 0  Max = 0  Step = 0  Preset = 0  "
        ::= { iqsyn22CmdEntry 39028 }


    iqsyn22UtilsSmpte201643Mapping14 OBJECT-TYPE
        SYNTAX            INTEGER
        MAX-ACCESS        read-write
        STATUS            current
        DESCRIPTION
                "CMNT: - SMTPE2016 4:3 AFD Mapping
                 TYPE: - Number
                 PAGE: - Utils
                    4:3 Mapping 14  cmdID= 39029
                    min= 0  max= 35  step= 1  format= 0  div_scale= 1  preset= 34
                    Min = 0  Max = 0  Step = 0  Preset = 0  "
        ::= { iqsyn22CmdEntry 39029 }


    iqsyn22UtilsSmpte201643Mapping15 OBJECT-TYPE
        SYNTAX            INTEGER
        MAX-ACCESS        read-write
        STATUS            current
        DESCRIPTION
                "CMNT: - SMTPE2016 4:3 AFD Mapping
                 TYPE: - Number
                 PAGE: - Utils
                    4:3 Mapping 15  cmdID= 39030
                    min= 0  max= 35  step= 1  format= 0  div_scale= 1  preset= 34
                    Min = 0  Max = 0  Step = 0  Preset = 0  "
        ::= { iqsyn22CmdEntry 39030 }


    iqsyn22UtilsSmpte201643Mapping16 OBJECT-TYPE
        SYNTAX            INTEGER
        MAX-ACCESS        read-write
        STATUS            current
        DESCRIPTION
                "CMNT: - SMTPE2016 4:3 AFD Mapping
                 TYPE: - Number
                 PAGE: - Utils
                    4:3 Mapping 16  cmdID= 39031
                    min= 0  max= 35  step= 1  format= 0  div_scale= 1  preset= 35
                    Min = 0  Max = 0  Step = 0  Preset = 0  "
        ::= { iqsyn22CmdEntry 39031 }


    iqsyn22UtilsSmpte2016169Mapping0 OBJECT-TYPE
        SYNTAX            INTEGER
        MAX-ACCESS        read-write
        STATUS            current
        DESCRIPTION
                "CMNT: - SMTPE2016 16:9 AFD Mapping
                 TYPE: - Number
                 PAGE: - Utils
                    16:9 Mapping 0  cmdID= 39032
                    min= 0  max= 35  step= 1  format= 0  div_scale= 1  preset= 34
                    Min = 0  Max = 0  Step = 0  Preset = 0  "
        ::= { iqsyn22CmdEntry 39032 }


    iqsyn22UtilsSmpte2016169Mapping1 OBJECT-TYPE
        SYNTAX            INTEGER
        MAX-ACCESS        read-write
        STATUS            current
        DESCRIPTION
                "CMNT: - SMTPE2016 16:9 AFD Mapping
                 TYPE: - Number
                 PAGE: - Utils
                    16:9 Mapping 1  cmdID= 39033
                    min= 0  max= 35  step= 1  format= 0  div_scale= 1  preset= 34
                    Min = 0  Max = 0  Step = 0  Preset = 0  "
        ::= { iqsyn22CmdEntry 39033 }


    iqsyn22UtilsSmpte2016169Mapping2 OBJECT-TYPE
        SYNTAX            INTEGER
        MAX-ACCESS        read-write
        STATUS            current
        DESCRIPTION
                "CMNT: - SMTPE2016 16:9 AFD Mapping
                 TYPE: - Number
                 PAGE: - Utils
                    16:9 Mapping 2  cmdID= 39034
                    min= 0  max= 35  step= 1  format= 0  div_scale= 1  preset= 34
                    Min = 0  Max = 0  Step = 0  Preset = 0  "
        ::= { iqsyn22CmdEntry 39034 }


    iqsyn22UtilsSmpte2016169Mapping3 OBJECT-TYPE
        SYNTAX            INTEGER
        MAX-ACCESS        read-write
        STATUS            current
        DESCRIPTION
                "CMNT: - SMTPE2016 16:9 AFD Mapping
                 TYPE: - Number
                 PAGE: - Utils
                    16:9 Mapping 3  cmdID= 39035
                    min= 0  max= 35  step= 1  format= 0  div_scale= 1  preset= 34
                    Min = 0  Max = 0  Step = 0  Preset = 0  "
        ::= { iqsyn22CmdEntry 39035 }


    iqsyn22UtilsSmpte2016169Mapping4 OBJECT-TYPE
        SYNTAX            INTEGER
        MAX-ACCESS        read-write
        STATUS            current
        DESCRIPTION
                "CMNT: - SMTPE2016 16:9 AFD Mapping
                 TYPE: - Number
                 PAGE: - Utils
                    16:9 Mapping 4  cmdID= 39036
                    min= 0  max= 35  step= 1  format= 0  div_scale= 1  preset= 34
                    Min = 0  Max = 0  Step = 0  Preset = 0  "
        ::= { iqsyn22CmdEntry 39036 }


    iqsyn22UtilsSmpte2016169Mapping5 OBJECT-TYPE
        SYNTAX            INTEGER
        MAX-ACCESS        read-write
        STATUS            current
        DESCRIPTION
                "CMNT: - SMTPE2016 16:9 AFD Mapping
                 TYPE: - Number
                 PAGE: - Utils
                    16:9 Mapping 5  cmdID= 39037
                    min= 0  max= 35  step= 1  format= 0  div_scale= 1  preset= 34
                    Min = 0  Max = 0  Step = 0  Preset = 0  "
        ::= { iqsyn22CmdEntry 39037 }


    iqsyn22UtilsSmpte2016169Mapping6 OBJECT-TYPE
        SYNTAX            INTEGER
        MAX-ACCESS        read-write
        STATUS            current
        DESCRIPTION
                "CMNT: - SMTPE2016 16:9 AFD Mapping
                 TYPE: - Number
                 PAGE: - Utils
                    16:9 Mapping 6  cmdID= 39038
                    min= 0  max= 35  step= 1  format= 0  div_scale= 1  preset= 34
                    Min = 0  Max = 0  Step = 0  Preset = 0  "
        ::= { iqsyn22CmdEntry 39038 }


    iqsyn22UtilsSmpte2016169Mapping7 OBJECT-TYPE
        SYNTAX            INTEGER
        MAX-ACCESS        read-write
        STATUS            current
        DESCRIPTION
                "CMNT: - SMTPE2016 16:9 AFD Mapping
                 TYPE: - Number
                 PAGE: - Utils
                    16:9 Mapping 7  cmdID= 39039
                    min= 0  max= 35  step= 1  format= 0  div_scale= 1  preset= 34
                    Min = 0  Max = 0  Step = 0  Preset = 0  "
        ::= { iqsyn22CmdEntry 39039 }


    iqsyn22UtilsSmpte2016169Mapping8 OBJECT-TYPE
        SYNTAX            INTEGER
        MAX-ACCESS        read-write
        STATUS            current
        DESCRIPTION
                "CMNT: - SMTPE2016 16:9 AFD Mapping
                 TYPE: - Number
                 PAGE: - Utils
                    16:9 Mapping 8  cmdID= 39040
                    min= 0  max= 35  step= 1  format= 0  div_scale= 1  preset= 34
                    Min = 0  Max = 0  Step = 0  Preset = 0  "
        ::= { iqsyn22CmdEntry 39040 }


    iqsyn22UtilsSmpte2016169Mapping9 OBJECT-TYPE
        SYNTAX            INTEGER
        MAX-ACCESS        read-write
        STATUS            current
        DESCRIPTION
                "CMNT: - SMTPE2016 16:9 AFD Mapping
                 TYPE: - Number
                 PAGE: - Utils
                    16:9 Mapping 9  cmdID= 39041
                    min= 0  max= 35  step= 1  format= 0  div_scale= 1  preset= 34
                    Min = 0  Max = 0  Step = 0  Preset = 0  "
        ::= { iqsyn22CmdEntry 39041 }


    iqsyn22UtilsSmpte2016169Mapping10 OBJECT-TYPE
        SYNTAX            INTEGER
        MAX-ACCESS        read-write
        STATUS            current
        DESCRIPTION
                "CMNT: - SMTPE2016 16:9 AFD Mapping
                 TYPE: - Number
                 PAGE: - Utils
                    16:9 Mapping 10  cmdID= 39042
                    min= 0  max= 35  step= 1  format= 0  div_scale= 1  preset= 34
                    Min = 0  Max = 0  Step = 0  Preset = 0  "
        ::= { iqsyn22CmdEntry 39042 }


    iqsyn22UtilsSmpte2016169Mapping11 OBJECT-TYPE
        SYNTAX            INTEGER
        MAX-ACCESS        read-write
        STATUS            current
        DESCRIPTION
                "CMNT: - SMTPE2016 16:9 AFD Mapping
                 TYPE: - Number
                 PAGE: - Utils
                    16:9 Mapping 11  cmdID= 39043
                    min= 0  max= 35  step= 1  format= 0  div_scale= 1  preset= 34
                    Min = 0  Max = 0  Step = 0  Preset = 0  "
        ::= { iqsyn22CmdEntry 39043 }


    iqsyn22UtilsSmpte2016169Mapping12 OBJECT-TYPE
        SYNTAX            INTEGER
        MAX-ACCESS        read-write
        STATUS            current
        DESCRIPTION
                "CMNT: - SMTPE2016 16:9 AFD Mapping
                 TYPE: - Number
                 PAGE: - Utils
                    16:9 Mapping 12  cmdID= 39044
                    min= 0  max= 35  step= 1  format= 0  div_scale= 1  preset= 34
                    Min = 0  Max = 0  Step = 0  Preset = 0  "
        ::= { iqsyn22CmdEntry 39044 }


    iqsyn22UtilsSmpte2016169Mapping13 OBJECT-TYPE
        SYNTAX            INTEGER
        MAX-ACCESS        read-write
        STATUS            current
        DESCRIPTION
                "CMNT: - SMTPE2016 16:9 AFD Mapping
                 TYPE: - Number
                 PAGE: - Utils
                    16:9 Mapping 13  cmdID= 39045
                    min= 0  max= 35  step= 1  format= 0  div_scale= 1  preset= 34
                    Min = 0  Max = 0  Step = 0  Preset = 0  "
        ::= { iqsyn22CmdEntry 39045 }


    iqsyn22UtilsSmpte2016169Mapping14 OBJECT-TYPE
        SYNTAX            INTEGER
        MAX-ACCESS        read-write
        STATUS            current
        DESCRIPTION
                "CMNT: - SMTPE2016 16:9 AFD Mapping
                 TYPE: - Number
                 PAGE: - Utils
                    16:9 Mapping 14  cmdID= 39046
                    min= 0  max= 35  step= 1  format= 0  div_scale= 1  preset= 34
                    Min = 0  Max = 0  Step = 0  Preset = 0  "
        ::= { iqsyn22CmdEntry 39046 }


    iqsyn22UtilsSmpte2016169Mapping15 OBJECT-TYPE
        SYNTAX            INTEGER
        MAX-ACCESS        read-write
        STATUS            current
        DESCRIPTION
                "CMNT: - SMTPE2016 16:9 AFD Mapping
                 TYPE: - Number
                 PAGE: - Utils
                    16:9 Mapping 15  cmdID= 39047
                    min= 0  max= 35  step= 1  format= 0  div_scale= 1  preset= 34
                    Min = 0  Max = 0  Step = 0  Preset = 0  "
        ::= { iqsyn22CmdEntry 39047 }


    iqsyn22UtilsSmpte2016ReaderIndex OBJECT-TYPE
        SYNTAX            INTEGER {
                            val43nReserved0(0),
                            val43nReserved1(1),
                            val43nBox169top(2),
                            val43nBox149top(3),
                            val43nBox169ctr(4),
                            val43nReserved5(5),
                            val43nReserved6(6),
                            val43nReserved7(7),
                            val43nCodedFrame(8),
                            val43n43(9),
                            val43n169(10),
                            val43n149(11),
                            val43nReserved12(12),
                            val43n43SP149(13),
                            val43n169SP149(14),
                            val43n169SP43(15),
                            valUnknown(16),
                            val169nReserved0(17),
                            val169nReserved1(18),
                            val169nBox169top(19),
                            val169nBox149top(20),
                            val169nBox169ctr(21),
                            val169nReserved5(22),
                            val169nReserved6(23),
                            val169nReserved7(24),
                            val169nCodedFrame(25),
                            val169n43(26),
                            val169n169(27),
                            val169n149(28),
                            val169nReserved12(29),
                            val169n43SP149(30),
                            val169n169SP149(31),
                            val169n169SP43(32)
                            }
        MAX-ACCESS        read-write
        STATUS            current
        DESCRIPTION
                "CMNT: - SMTPE2016 Reader Index
                 TYPE: - RadiobuttonList
                 PAGE: - Utils
                    Reader Index  cmdID= 39049
                    4:3 - Reserved(0)  value= 0
                    4:3 - Reserved(1)  value= 1
                    4:3 - Box 16:9 top  value= 2
                    4:3 - Box 14:9 top  value= 3
                    4:3 - Box>16:9 ctr  value= 4
                    4:3 - Reserved(5)  value= 5
                    4:3 - Reserved(6)  value= 6
                    4:3 - Reserved(7)  value= 7
                    4:3 - Coded Frame  value= 8
                    4:3 - 4:3  value= 9
                    4:3 - 16:9  value= 10
                    4:3 - 14:9  value= 11
                    4:3 - Reserved(12)  value= 12
                    4:3 - 4:3 SP 14:9  value= 13
                    4:3 - 16:9 SP 14:9  value= 14
                    4:3 - 16:9 SP 4:3  value= 15
                    Unknown  value= 16
                    16:9 - Reserved(0)  value= 17
                    16:9 - Reserved(1)  value= 18
                    16:9 - Box 16:9 top  value= 19
                    16:9 - Box 14:9 top  value= 20
                    16:9 - Box>16:9 ctr  value= 21
                    16:9 - Reserved(5)  value= 22
                    16:9 - Reserved(6)  value= 23
                    16:9 - Reserved(7)  value= 24
                    16:9 - Coded Frame  value= 25
                    16:9 - 4:3  value= 26
                    16:9 - 16:9  value= 27
                    16:9 - 14:9  value= 28
                    16:9 - Reserved(12)  value= 29
                    16:9 - 4:3 SP 14:9  value= 30
                    16:9 - 16:9 SP 14:9  value= 31
                    16:9 - 16:9 SP 4:3  value= 32  "
        ::= { iqsyn22CmdEntry 39049 }


    iqsyn22UtilsSmpte2016WriterIndex OBJECT-TYPE
        SYNTAX            INTEGER {
                            valReader(34),
                            valDelete(35),
                            val43nReserved0(0),
                            val43nReserved1(1),
                            val43nBox169top(2),
                            val43nBox149top(3),
                            val43nBox169ctr(4),
                            val43nReserved5(5),
                            val43nReserved6(6),
                            val43nReserved7(7),
                            val43nCodedFrame(8),
                            val43n43(9),
                            val43n169(10),
                            val43n149(11),
                            val43nReserved12(12),
                            val43n43SP149(13),
                            val43n169SP149(14),
                            val43n169SP43(15),
                            val169nReserved0(17),
                            val169nReserved1(18),
                            val169nBox169top(19),
                            val169nBox149top(20),
                            val169nBox169ctr(21),
                            val169nReserved5(22),
                            val169nReserved6(23),
                            val169nReserved7(24),
                            val169nCodedFrame(25),
                            val169n43(26),
                            val169n169(27),
                            val169n149(28),
                            val169nReserved12(29),
                            val169n43SP149(30),
                            val169n169SP149(31),
                            val169n169SP43(32)
                            }
        MAX-ACCESS        read-write
        STATUS            current
        DESCRIPTION
                "CMNT: - SMTPE2016 Writer Index
                 TYPE: - RadiobuttonList
                 PAGE: - Utils
                    Writer Index  cmdID= 39050
                    Reader  value= 34
                    Delete  value= 35
                    4:3 - Reserved(0)  value= 0
                    4:3 - Reserved(1)  value= 1
                    4:3 - Box 16:9 top  value= 2
                    4:3 - Box 14:9 top  value= 3
                    4:3 - Box>16:9 ctr  value= 4
                    4:3 - Reserved(5)  value= 5
                    4:3 - Reserved(6)  value= 6
                    4:3 - Reserved(7)  value= 7
                    4:3 - Coded Frame  value= 8
                    4:3 - 4:3  value= 9
                    4:3 - 16:9  value= 10
                    4:3 - 14:9  value= 11
                    4:3 - Reserved(12)  value= 12
                    4:3 - 4:3 SP 14:9  value= 13
                    4:3 - 16:9 SP 14:9  value= 14
                    4:3 - 16:9 SP 4:3  value= 15
                    16:9 - Reserved(0)  value= 17
                    16:9 - Reserved(1)  value= 18
                    16:9 - Box 16:9 top  value= 19
                    16:9 - Box 14:9 top  value= 20
                    16:9 - Box>16:9 ctr  value= 21
                    16:9 - Reserved(5)  value= 22
                    16:9 - Reserved(6)  value= 23
                    16:9 - Reserved(7)  value= 24
                    16:9 - Coded Frame  value= 25
                    16:9 - 4:3  value= 26
                    16:9 - 16:9  value= 27
                    16:9 - 14:9  value= 28
                    16:9 - Reserved(12)  value= 29
                    16:9 - 4:3 SP 14:9  value= 30
                    16:9 - 16:9 SP 14:9  value= 31
                    16:9 - 16:9 SP 4:3  value= 32  "
        ::= { iqsyn22CmdEntry 39050 }


    iqsyn22UtilsSmpte2016PresetReader OBJECT-TYPE
        SYNTAX            INTEGER { noAction(0),valPresetReader(1) }
        MAX-ACCESS        read-write
        STATUS            current
        DESCRIPTION
                "CMNT: - 
                 TYPE: - Button
                 PAGE: - Utils
                    Preset Reader  cmdID= 39051
                    value= 1  "
        ::= { iqsyn22CmdEntry 39051 }


    iqsyn22UtilsSmpte2016PresetDelete OBJECT-TYPE
        SYNTAX            INTEGER { noAction(0),valPresetDelete(1) }
        MAX-ACCESS        read-write
        STATUS            current
        DESCRIPTION
                "CMNT: - 
                 TYPE: - Button
                 PAGE: - Utils
                    Preset Delete  cmdID= 39052
                    value= 1  "
        ::= { iqsyn22CmdEntry 39052 }


    iqsyn22GPIGPI1GPIO1Mode OBJECT-TYPE
        SYNTAX            INTEGER {
                            valUnused(0),
                            valInputGPI1(1),
                            valOutputGPO1(2)
                            }
        MAX-ACCESS        read-write
        STATUS            current
        DESCRIPTION
                "CMNT: - GPIO-1 Input/Output
                 TYPE: - RadiobuttonList
                 PAGE: - GPI
                    GPI/O 1 Mode  cmdID= 36120
                    Unused  value= 0
                    Input (GPI1)  value= 1
                    Output (GPO1)  value= 2  "
        ::= { iqsyn22CmdEntry 36120 }


    iqsyn22GPIGPI1GPI1ipSelect OBJECT-TYPE
        SYNTAX            INTEGER {
                            valUnused(-1),
                            valFreeze(0),
                            valPattern(1),
                            valBlack(2),
                            valBlankAncillary(3),
                            valMonoChrmYOnly(4),
                            valMonoChrmCbCrOnly(5),
                            valUseIPRef(6),
                            valUseExtRef(7),
                            valSelectInp1(50),
                            valSelectInp2(51),
                            valSelectInput(8),
                            valSelectBackup(9),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115)
                            }
        MAX-ACCESS        read-write
        STATUS            current
        DESCRIPTION
                "CMNT: - GPI-1 Input action
                 TYPE: - RadiobuttonList
                 PAGE: - GPI
                    GPI 1-i/p Select  cmdID= 36121
                    Unused  value= -1
                    Freeze  value= 0
                    Pattern  value= 1
                    Black  value= 2
                    Blank Ancillary  value= 3
                    MonoChrm Y Only  value= 4
                    MonoChrm CbCr Only  value= 5
                    Use I/P Ref  value= 6
                    Use Ext Ref  value= 7
                    Select Inp 1  value= 50
                    Select Inp 2  value= 51
                    Select Input  value= 8
                    Select Backup  value= 9
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115  "
        ::= { iqsyn22CmdEntry 36121 }


    iqsyn22GPIGPI1GPO1opSelect OBJECT-TYPE
        SYNTAX            INTEGER {
                            valInput1OK(50),
                            valInput2OK(51),
                            valReferenceOK(0),
                            valFreeze(1),
                            valPattern(2),
                            valBlack(3),
                            valMonochrome(4),
                            valInput2Selected(52)
                            }
        MAX-ACCESS        read-write
        STATUS            current
        DESCRIPTION
                "CMNT: - GPI-1 Output action
                 TYPE: - RadiobuttonList
                 PAGE: - GPI
                    GPO 1-o/p Select  cmdID= 36122
                    Input 1 OK  value= 50
                    Input 2 OK  value= 51
                    Reference OK  value= 0
                    Freeze  value= 1
                    Pattern  value= 2
                    Black  value= 3
                    Monochrome  value= 4
                    Input 2 Selected  value= 52  "
        ::= { iqsyn22CmdEntry 36122 }


    iqsyn22GPIGPI1InvertGPIO1 OBJECT-TYPE
        SYNTAX            INTEGER { disable(0), enable(1)  }
        MAX-ACCESS        read-write
        STATUS            current
        DESCRIPTION
                "CMNT: - GPI-1 Port Invert
                 TYPE: - Checkbox
                 PAGE: - GPI
                    Invert GPIO 1  cmdID= 36123  "
        ::= { iqsyn22CmdEntry 36123 }


    iqsyn22GPIGPI2GPIO2Mode OBJECT-TYPE
        SYNTAX            INTEGER {
                            valUnused(0),
                            valInputGPI2(1),
                            valOutputGPO2(2)
                            }
        MAX-ACCESS        read-write
        STATUS            current
        DESCRIPTION
                "CMNT: - GPIO-2 Input/Output
                 TYPE: - RadiobuttonList
                 PAGE: - GPI
                    GPI/O 2 Mode  cmdID= 36130
                    Unused  value= 0
                    Input (GPI2)  value= 1
                    Output (GPO2)  value= 2  "
        ::= { iqsyn22CmdEntry 36130 }


    iqsyn22GPIGPI2GPI2ipSelect OBJECT-TYPE
        SYNTAX            INTEGER {
                            valUnused(-1),
                            valFreeze(0),
                            valPattern(1),
                            valBlack(2),
                            valBlankAncillary(3),
                            valMonoChrmYOnly(4),
                            valMonoChrmCbCrOnly(5),
                            valUseIPRef(6),
                            valUseExtRef(7),
                            valSelectInp1(50),
                            valSelectInp2(51),
                            valSelectInput(8),
                            valSelectBackup(9),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115)
                            }
        MAX-ACCESS        read-write
        STATUS            current
        DESCRIPTION
                "CMNT: - GPI-2 Input action
                 TYPE: - RadiobuttonList
                 PAGE: - GPI
                    GPI 2-i/p Select  cmdID= 36131
                    Unused  value= -1
                    Freeze  value= 0
                    Pattern  value= 1
                    Black  value= 2
                    Blank Ancillary  value= 3
                    MonoChrm Y Only  value= 4
                    MonoChrm CbCr Only  value= 5
                    Use I/P Ref  value= 6
                    Use Ext Ref  value= 7
                    Select Inp 1  value= 50
                    Select Inp 2  value= 51
                    Select Input  value= 8
                    Select Backup  value= 9
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115  "
        ::= { iqsyn22CmdEntry 36131 }


    iqsyn22GPIGPI2GPO2opSelect OBJECT-TYPE
        SYNTAX            INTEGER {
                            valInput1OK(50),
                            valInput2OK(51),
                            valReferenceOK(0),
                            valFreeze(1),
                            valPattern(2),
                            valBlack(3),
                            valMonochrome(4),
                            valInput2Selected(52)
                            }
        MAX-ACCESS        read-write
        STATUS            current
        DESCRIPTION
                "CMNT: - GPI-2 Output action
                 TYPE: - RadiobuttonList
                 PAGE: - GPI
                    GPO 2-o/p Select  cmdID= 36132
                    Input 1 OK  value= 50
                    Input 2 OK  value= 51
                    Reference OK  value= 0
                    Freeze  value= 1
                    Pattern  value= 2
                    Black  value= 3
                    Monochrome  value= 4
                    Input 2 Selected  value= 52  "
        ::= { iqsyn22CmdEntry 36132 }


    iqsyn22GPIGPI2InvertGPIO2 OBJECT-TYPE
        SYNTAX            INTEGER { disable(0), enable(1)  }
        MAX-ACCESS        read-write
        STATUS            current
        DESCRIPTION
                "CMNT: - GPI-2 Port Invert
                 TYPE: - Checkbox
                 PAGE: - GPI
                    Invert GPIO 2  cmdID= 36133  "
        ::= { iqsyn22CmdEntry 36133 }


    iqsyn22GPIGPIPWMDelayTimerTimerSource OBJECT-TYPE
        SYNTAX            INTEGER {
                            valOff(0),
                            valGPI1(1),
                            valGPI2(2)
                            }
        MAX-ACCESS        read-write
        STATUS            current
        DESCRIPTION
                "CMNT: - 
                 TYPE: - RadiobuttonList
                 PAGE: - GPI
                    Timer Source  cmdID= 36124
                    Off  value= 0
                    GPI 1  value= 1
                    GPI 2  value= 2  "
        ::= { iqsyn22CmdEntry 36124 }


    iqsyn22GPIGPIPWMDelayTimerActiveHigh OBJECT-TYPE
        SYNTAX            INTEGER { disable(0), enable(1)  }
        MAX-ACCESS        read-write
        STATUS            current
        DESCRIPTION
                "CMNT: - 
                 TYPE: - Checkbox
                 PAGE: - GPI
                    Active High  cmdID= 36125  "
        ::= { iqsyn22CmdEntry 36125 }


    iqsyn22MemoriesRecallMemory OBJECT-TYPE
        SYNTAX            INTEGER {
                            valNoneSelected(0),
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Recall Memory  cmdID= 37100
                    None Selected  value= 0
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqsyn22CmdEntry 37100 }


    iqsyn22MemoriesSelMemory OBJECT-TYPE
        SYNTAX            INTEGER {
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Sel Memory  cmdID= 37101
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqsyn22CmdEntry 37101 }


    iqsyn22MemoriesSaveMemory OBJECT-TYPE
        SYNTAX            INTEGER { noAction(0),valSaveMemory(1) }
        MAX-ACCESS        read-write
        STATUS            current
        DESCRIPTION
                "CMNT: - 
                 TYPE: - Button
                 PAGE: - Memories
                    Save Memory  cmdID= 37102
                    value= 1  "
        ::= { iqsyn22CmdEntry 37102 }


    iqsyn22MemoriesClearMemory OBJECT-TYPE
        SYNTAX            INTEGER { noAction(0),valClearMemory(1) }
        MAX-ACCESS        read-write
        STATUS            current
        DESCRIPTION
                "CMNT: - Delete User Memory
                 TYPE: - Button
                 PAGE: - Memories
                    Clear Memory  cmdID= 37105
                    value= 1  "
        ::= { iqsyn22CmdEntry 37105 }


    iqsyn22MemoriesMemoryNameChangeName OBJECT-TYPE
        SYNTAX            RollCallString
        MAX-ACCESS        read-write
        STATUS            current
        DESCRIPTION
                "CMNT: - 
                 TYPE: - Editstring
                 PAGE: - Memories
                    Change Name  cmdID= 37103
                    preset= Display Memory"
        ::= { iqsyn22CmdEntry 37103 }


    iqsyn22MemoriesLastUserMemory OBJECT-TYPE
        SYNTAX            RollCallString
        MAX-ACCESS        read-only
        STATUS            current
        DESCRIPTION
                "CMNT: - 
                 TYPE: - Display
                 PAGE: - Memories
                    Last User Memory  cmdID= 37104  "
        ::= { iqsyn22CmdEntry 37104 }


    iqsyn22MemoriesMemoryName1 OBJECT-TYPE
        SYNTAX            RollCallString
        MAX-ACCESS        read-only
        STATUS            current
        DESCRIPTION
                "CMNT: - 
                 TYPE: - Display
                 PAGE: - Memories
                    Memory Name1  cmdID= 37106  "
        ::= { iqsyn22CmdEntry 37106 }


    iqsyn22MemoriesMemoryName2 OBJECT-TYPE
        SYNTAX            RollCallString
        MAX-ACCESS        read-only
        STATUS            current
        DESCRIPTION
                "CMNT: - 
                 TYPE: - Display
                 PAGE: - Memories
                    Memory Name2  cmdID= 37107  "
        ::= { iqsyn22CmdEntry 37107 }


    iqsyn22MemoriesMemoryName3 OBJECT-TYPE
        SYNTAX            RollCallString
        MAX-ACCESS        read-only
        STATUS            current
        DESCRIPTION
                "CMNT: - 
                 TYPE: - Display
                 PAGE: - Memories
                    Memory Name3  cmdID= 37108  "
        ::= { iqsyn22CmdEntry 37108 }


    iqsyn22MemoriesMemoryName4 OBJECT-TYPE
        SYNTAX            RollCallString
        MAX-ACCESS        read-only
        STATUS            current
        DESCRIPTION
                "CMNT: - 
                 TYPE: - Display
                 PAGE: - Memories
                    Memory Name4  cmdID= 37109  "
        ::= { iqsyn22CmdEntry 37109 }


    iqsyn22MemoriesMemoryName5 OBJECT-TYPE
        SYNTAX            RollCallString
        MAX-ACCESS        read-only
        STATUS            current
        DESCRIPTION
                "CMNT: - 
                 TYPE: - Display
                 PAGE: - Memories
                    Memory Name5  cmdID= 37110  "
        ::= { iqsyn22CmdEntry 37110 }


    iqsyn22MemoriesMemoryName6 OBJECT-TYPE
        SYNTAX            RollCallString
        MAX-ACCESS        read-only
        STATUS            current
        DESCRIPTION
                "CMNT: - 
                 TYPE: - Display
                 PAGE: - Memories
                    Memory Name6  cmdID= 37111  "
        ::= { iqsyn22CmdEntry 37111 }


    iqsyn22MemoriesMemoryName7 OBJECT-TYPE
        SYNTAX            RollCallString
        MAX-ACCESS        read-only
        STATUS            current
        DESCRIPTION
                "CMNT: - 
                 TYPE: - Display
                 PAGE: - Memories
                    Memory Name7  cmdID= 37112  "
        ::= { iqsyn22CmdEntry 37112 }


    iqsyn22MemoriesMemoryName8 OBJECT-TYPE
        SYNTAX            RollCallString
        MAX-ACCESS        read-only
        STATUS            current
        DESCRIPTION
                "CMNT: - 
                 TYPE: - Display
                 PAGE: - Memories
                    Memory Name8  cmdID= 37113  "
        ::= { iqsyn22CmdEntry 37113 }


    iqsyn22MemoriesMemoryName9 OBJECT-TYPE
        SYNTAX            RollCallString
        MAX-ACCESS        read-only
        STATUS            current
        DESCRIPTION
                "CMNT: - 
                 TYPE: - Display
                 PAGE: - Memories
                    Memory Name9  cmdID= 37114  "
        ::= { iqsyn22CmdEntry 37114 }


    iqsyn22MemoriesMemoryName10 OBJECT-TYPE
        SYNTAX            RollCallString
        MAX-ACCESS        read-only
        STATUS            current
        DESCRIPTION
                "CMNT: - 
                 TYPE: - Display
                 PAGE: - Memories
                    Memory Name10  cmdID= 37115  "
        ::= { iqsyn22CmdEntry 37115 }


    iqsyn22MemoriesMemoryName11 OBJECT-TYPE
        SYNTAX            RollCallString
        MAX-ACCESS        read-only
        STATUS            current
        DESCRIPTION
                "CMNT: - 
                 TYPE: - Display
                 PAGE: - Memories
                    Memory Name11  cmdID= 37116  "
        ::= { iqsyn22CmdEntry 37116 }


    iqsyn22MemoriesMemoryName12 OBJECT-TYPE
        SYNTAX            RollCallString
        MAX-ACCESS        read-only
        STATUS            current
        DESCRIPTION
                "CMNT: - 
                 TYPE: - Display
                 PAGE: - Memories
                    Memory Name12  cmdID= 37117  "
        ::= { iqsyn22CmdEntry 37117 }


    iqsyn22MemoriesMemoryName13 OBJECT-TYPE
        SYNTAX            RollCallString
        MAX-ACCESS        read-only
        STATUS            current
        DESCRIPTION
                "CMNT: - 
                 TYPE: - Display
                 PAGE: - Memories
                    Memory Name13  cmdID= 37118  "
        ::= { iqsyn22CmdEntry 37118 }


    iqsyn22MemoriesMemoryName14 OBJECT-TYPE
        SYNTAX            RollCallString
        MAX-ACCESS        read-only
        STATUS            current
        DESCRIPTION
                "CMNT: - 
                 TYPE: - Display
                 PAGE: - Memories
                    Memory Name14  cmdID= 37119  "
        ::= { iqsyn22CmdEntry 37119 }


    iqsyn22MemoriesMemoryName15 OBJECT-TYPE
        SYNTAX            RollCallString
        MAX-ACCESS        read-only
        STATUS            current
        DESCRIPTION
                "CMNT: - 
                 TYPE: - Display
                 PAGE: - Memories
                    Memory Name15  cmdID= 37120  "
        ::= { iqsyn22CmdEntry 37120 }


    iqsyn22MemoriesMemoryName16 OBJECT-TYPE
        SYNTAX            RollCallString
        MAX-ACCESS        read-only
        STATUS            current
        DESCRIPTION
                "CMNT: - 
                 TYPE: - Display
                 PAGE: - Memories
                    Memory Name16  cmdID= 37121  "
        ::= { iqsyn22CmdEntry 37121 }


    iqsyn22LoggingVideoInputLogInput1Type OBJECT-TYPE
        SYNTAX            INTEGER { disable(0), enable(1)  }
        MAX-ACCESS        read-write
        STATUS            current
        DESCRIPTION
                "CMNT: - Enable/Disable logging for Input 1 Type
                 TYPE: - Checkbox
                 PAGE: - Logging
                    Log Input 1 Type  cmdID= 35017  "
        ::= { iqsyn22CmdEntry 35017 }


    iqsyn22LoggingVideoInputInput1Type OBJECT-TYPE
        SYNTAX            RollCallString
        MAX-ACCESS        read-only
        STATUS            current
        DESCRIPTION
                "CMNT: - Logging state for Input 1 Type
                 TYPE: - Display
                 PAGE: - Logging
                    Input 1 Type=  cmdID= 36017  "
        ::= { iqsyn22CmdEntry 36017 }


    iqsyn22LoggingVideoInputLogInput1Status OBJECT-TYPE
        SYNTAX            INTEGER { disable(0), enable(1)  }
        MAX-ACCESS        read-write
        STATUS            current
        DESCRIPTION
                "CMNT: - Enable/Disable logging for Input 1 Status
                 TYPE: - Checkbox
                 PAGE: - Logging
                    Log Input 1 Status  cmdID= 35005  "
        ::= { iqsyn22CmdEntry 35005 }


    iqsyn22LoggingVideoInputInput1Status OBJECT-TYPE
        SYNTAX            RollCallString
        MAX-ACCESS        read-only
        STATUS            current
        DESCRIPTION
                "CMNT: - Logging state for Input 1 Status
                 TYPE: - Display
                 PAGE: - Logging
                    Input 1 Status=  cmdID= 36005  "
        ::= { iqsyn22CmdEntry 36005 }


    iqsyn22LoggingVideoInputLogInput1Std OBJECT-TYPE
        SYNTAX            INTEGER { disable(0), enable(1)  }
        MAX-ACCESS        read-write
        STATUS            current
        DESCRIPTION
                "CMNT: - Enable/Disable logging for Input 1 Std.
                 TYPE: - Checkbox
                 PAGE: - Logging
                    Log Input 1 Std.  cmdID= 35016  "
        ::= { iqsyn22CmdEntry 35016 }


    iqsyn22LoggingVideoInputInput1Std OBJECT-TYPE
        SYNTAX            RollCallString
        MAX-ACCESS        read-only
        STATUS            current
        DESCRIPTION
                "CMNT: - Logging state for Input 1 Std.
                 TYPE: - Display
                 PAGE: - Logging
                    Input 1 Std.=  cmdID= 36016  "
        ::= { iqsyn22CmdEntry 36016 }


    iqsyn22LoggingVideoInputLogInput1Errors OBJECT-TYPE
        SYNTAX            INTEGER { disable(0), enable(1)  }
        MAX-ACCESS        read-write
        STATUS            current
        DESCRIPTION
                "CMNT: - Enable/Disable logging for Input 1 Errors
                 TYPE: - Checkbox
                 PAGE: - Logging
                    Log Input 1 Errors  cmdID= 35002  "
        ::= { iqsyn22CmdEntry 35002 }


    iqsyn22LoggingVideoInputInput1Errors OBJECT-TYPE
        SYNTAX            RollCallString
        MAX-ACCESS        read-only
        STATUS            current
        DESCRIPTION
                "CMNT: - Logging state for Input 1 Errors
                 TYPE: - Display
                 PAGE: - Logging
                    Input 1 Errors=  cmdID= 36002  "
        ::= { iqsyn22CmdEntry 36002 }


    iqsyn22LoggingVideoInputLogInput1ErrSecs OBJECT-TYPE
        SYNTAX            INTEGER { disable(0), enable(1)  }
        MAX-ACCESS        read-write
        STATUS            current
        DESCRIPTION
                "CMNT: - Enable/Disable logging for Input 1 ErrSecs
                 TYPE: - Checkbox
                 PAGE: - Logging
                    Log Input 1 ErrSecs  cmdID= 35003  "
        ::= { iqsyn22CmdEntry 35003 }


    iqsyn22LoggingVideoInputInput1ErrSecs OBJECT-TYPE
        SYNTAX            RollCallString
        MAX-ACCESS        read-only
        STATUS            current
        DESCRIPTION
                "CMNT: - Logging state for Input 1 ErrSecs
                 TYPE: - Display
                 PAGE: - Logging
                    Input 1 ErrSecs=  cmdID= 36003  "
        ::= { iqsyn22CmdEntry 36003 }


    iqsyn22LoggingVideoInputLogInput1ANCErr OBJECT-TYPE
        SYNTAX            INTEGER { disable(0), enable(1)  }
        MAX-ACCESS        read-write
        STATUS            current
        DESCRIPTION
                "CMNT: - Enable/Disable logging for Input 1 ANC Errors
                 TYPE: - Checkbox
                 PAGE: - Logging
                    Log Input 1 ANC Errors  cmdID= 35000  "
        ::= { iqsyn22CmdEntry 35000 }


    iqsyn22LoggingVideoInputInput1ANCErrors OBJECT-TYPE
        SYNTAX            RollCallString
        MAX-ACCESS        read-only
        STATUS            current
        DESCRIPTION
                "CMNT: - Logging state for Input 1 ANC Errors
                 TYPE: - Display
                 PAGE: - Logging
                    Input 1 ANC Errors=  cmdID= 36000  "
        ::= { iqsyn22CmdEntry 36000 }


    iqsyn22LoggingVideoInputLogInput1ANCErrSecs OBJECT-TYPE
        SYNTAX            INTEGER { disable(0), enable(1)  }
        MAX-ACCESS        read-write
        STATUS            current
        DESCRIPTION
                "CMNT: - Enable/Disable logging for Input 1 ANC ErrSecs
                 TYPE: - Checkbox
                 PAGE: - Logging
                    Log Input 1 ANC ErrSecs  cmdID= 35001  "
        ::= { iqsyn22CmdEntry 35001 }


    iqsyn22LoggingVideoInputInput1ANCErrSecs OBJECT-TYPE
        SYNTAX            RollCallString
        MAX-ACCESS        read-only
        STATUS            current
        DESCRIPTION
                "CMNT: - Logging state for Input 1 ANC ErrSecs
                 TYPE: - Display
                 PAGE: - Logging
                    Input 1 ANC ErrSecs=  cmdID= 36001  "
        ::= { iqsyn22CmdEntry 36001 }


    iqsyn22LoggingVideoInputLogInput2Type OBJECT-TYPE
        SYNTAX            INTEGER { disable(0), enable(1)  }
        MAX-ACCESS        read-write
        STATUS            current
        DESCRIPTION
                "CMNT: - Enable/Disable logging for Input 2 Type
                 TYPE: - Checkbox
                 PAGE: - Logging
                    Log Input 2 Type  cmdID= 35047  "
        ::= { iqsyn22CmdEntry 35047 }


    iqsyn22LoggingVideoInputInput2Type OBJECT-TYPE
        SYNTAX            RollCallString
        MAX-ACCESS        read-only
        STATUS            current
        DESCRIPTION
                "CMNT: - Logging state for Input 2 Type
                 TYPE: - Display
                 PAGE: - Logging
                    Input 2 Type=  cmdID= 36047  "
        ::= { iqsyn22CmdEntry 36047 }


    iqsyn22LoggingVideoInputLogInput2Status OBJECT-TYPE
        SYNTAX            INTEGER { disable(0), enable(1)  }
        MAX-ACCESS        read-write
        STATUS            current
        DESCRIPTION
                "CMNT: - Enable/Disable logging for Input 2 Status
                 TYPE: - Checkbox
                 PAGE: - Logging
                    Log Input 2 Status  cmdID= 35035  "
        ::= { iqsyn22CmdEntry 35035 }


    iqsyn22LoggingVideoInputInput2Status OBJECT-TYPE
        SYNTAX            RollCallString
        MAX-ACCESS        read-only
        STATUS            current
        DESCRIPTION
                "CMNT: - Logging state for Input 2 Status
                 TYPE: - Display
                 PAGE: - Logging
                    Input 2 Status=  cmdID= 36035  "
        ::= { iqsyn22CmdEntry 36035 }


    iqsyn22LoggingVideoInputLogInput2Std OBJECT-TYPE
        SYNTAX            INTEGER { disable(0), enable(1)  }
        MAX-ACCESS        read-write
        STATUS            current
        DESCRIPTION
                "CMNT: - Enable/Disable logging for Input 2 Std.
                 TYPE: - Checkbox
                 PAGE: - Logging
                    Log Input 2 Std.  cmdID= 35046  "
        ::= { iqsyn22CmdEntry 35046 }


    iqsyn22LoggingVideoInputInput2Std OBJECT-TYPE
        SYNTAX            RollCallString
        MAX-ACCESS        read-only
        STATUS            current
        DESCRIPTION
                "CMNT: - Logging state for Input 2 Std.
                 TYPE: - Display
                 PAGE: - Logging
                    Input 2 Std.=  cmdID= 36046  "
        ::= { iqsyn22CmdEntry 36046 }


    iqsyn22LoggingVideoInputLogInput2Errors OBJECT-TYPE
        SYNTAX            INTEGER { disable(0), enable(1)  }
        MAX-ACCESS        read-write
        STATUS            current
        DESCRIPTION
                "CMNT: - Enable/Disable logging for Input 2 Errors
                 TYPE: - Checkbox
                 PAGE: - Logging
                    Log Input 2 Errors  cmdID= 35032  "
        ::= { iqsyn22CmdEntry 35032 }


    iqsyn22LoggingVideoInputInput2Errors OBJECT-TYPE
        SYNTAX            RollCallString
        MAX-ACCESS        read-only
        STATUS            current
        DESCRIPTION
                "CMNT: - Logging state for Input 2 Errors
                 TYPE: - Display
                 PAGE: - Logging
                    Input 2 Errors=  cmdID= 36032  "
        ::= { iqsyn22CmdEntry 36032 }


    iqsyn22LoggingVideoInputLogInput2ErrSecs OBJECT-TYPE
        SYNTAX            INTEGER { disable(0), enable(1)  }
        MAX-ACCESS        read-write
        STATUS            current
        DESCRIPTION
                "CMNT: - Enable/Disable logging for Input 2 ErrSecs
                 TYPE: - Checkbox
                 PAGE: - Logging
                    Log Input 2 ErrSecs  cmdID= 35033  "
        ::= { iqsyn22CmdEntry 35033 }


    iqsyn22LoggingVideoInputInput2ErrSecs OBJECT-TYPE
        SYNTAX            RollCallString
        MAX-ACCESS        read-only
        STATUS            current
        DESCRIPTION
                "CMNT: - Logging state for Input 2 ErrSecs
                 TYPE: - Display
                 PAGE: - Logging
                    Input 2 ErrSecs=  cmdID= 36033  "
        ::= { iqsyn22CmdEntry 36033 }


    iqsyn22LoggingVideoInputLogInput2ANCErr OBJECT-TYPE
        SYNTAX            INTEGER { disable(0), enable(1)  }
        MAX-ACCESS        read-write
        STATUS            current
        DESCRIPTION
                "CMNT: - Enable/Disable logging for Input 2 ANC Errors
                 TYPE: - Checkbox
                 PAGE: - Logging
                    Log Input 2 ANC Errors  cmdID= 35030  "
        ::= { iqsyn22CmdEntry 35030 }


    iqsyn22LoggingVideoInputInput2ANCErrors OBJECT-TYPE
        SYNTAX            RollCallString
        MAX-ACCESS        read-only
        STATUS            current
        DESCRIPTION
                "CMNT: - Logging state for Input 2 ANC Errors
                 TYPE: - Display
                 PAGE: - Logging
                    Input 2 ANC Errors=  cmdID= 36030  "
        ::= { iqsyn22CmdEntry 36030 }


    iqsyn22LoggingVideoInputLogInput2ANCErrSecs OBJECT-TYPE
        SYNTAX            INTEGER { disable(0), enable(1)  }
        MAX-ACCESS        read-write
        STATUS            current
        DESCRIPTION
                "CMNT: - Enable/Disable logging for Input 2 ANC ErrSecs
                 TYPE: - Checkbox
                 PAGE: - Logging
                    Log Input 2 ANC ErrSecs  cmdID= 35031  "
        ::= { iqsyn22CmdEntry 35031 }


    iqsyn22LoggingVideoInputInput2ANCErrSecs OBJECT-TYPE
        SYNTAX            RollCallString
        MAX-ACCESS        read-only
        STATUS            current
        DESCRIPTION
                "CMNT: - Logging state for Input 2 ANC ErrSecs
                 TYPE: - Display
                 PAGE: - Logging
                    Input 2 ANC ErrSecs=  cmdID= 36031  "
        ::= { iqsyn22CmdEntry 36031 }


    iqsyn22LoggingRefOutputLogOutputState OBJECT-TYPE
        SYNTAX            INTEGER { disable(0), enable(1)  }
        MAX-ACCESS        read-write
        STATUS            current
        DESCRIPTION
                "CMNT: - Enable/Disable logging for Output State
                 TYPE: - Checkbox
                 PAGE: - Logging
                    Log Output State  cmdID= 35941  "
        ::= { iqsyn22CmdEntry 35941 }


    iqsyn22LoggingRefOutputOutputState OBJECT-TYPE
        SYNTAX            RollCallString
        MAX-ACCESS        read-only
        STATUS            current
        DESCRIPTION
                "CMNT: - Logging state for Output State
                 TYPE: - Display
                 PAGE: - Logging
                    Output State=  cmdID= 36941  "
        ::= { iqsyn22CmdEntry 36941 }


    iqsyn22LoggingRefOutputLogOutputType OBJECT-TYPE
        SYNTAX            INTEGER { disable(0), enable(1)  }
        MAX-ACCESS        read-write
        STATUS            current
        DESCRIPTION
                "CMNT: - Enable/Disable logging for Output Type
                 TYPE: - Checkbox
                 PAGE: - Logging
                    Log Output Type  cmdID= 35942  "
        ::= { iqsyn22CmdEntry 35942 }


    iqsyn22LoggingRefOutputOutputType OBJECT-TYPE
        SYNTAX            RollCallString
        MAX-ACCESS        read-only
        STATUS            current
        DESCRIPTION
                "CMNT: - Logging state for Output Type
                 TYPE: - Display
                 PAGE: - Logging
                    Output Type=  cmdID= 36942  "
        ::= { iqsyn22CmdEntry 36942 }


    iqsyn22LoggingRefOutputLogOutputStandard OBJECT-TYPE
        SYNTAX            INTEGER { disable(0), enable(1)  }
        MAX-ACCESS        read-write
        STATUS            current
        DESCRIPTION
                "CMNT: - Enable/Disable logging for Output Standard
                 TYPE: - Checkbox
                 PAGE: - Logging
                    Log Output Standard  cmdID= 35940  "
        ::= { iqsyn22CmdEntry 35940 }


    iqsyn22LoggingRefOutputOutputStandard OBJECT-TYPE
        SYNTAX            RollCallString
        MAX-ACCESS        read-only
        STATUS            current
        DESCRIPTION
                "CMNT: - Logging state for Output Standard
                 TYPE: - Display
                 PAGE: - Logging
                    Output Standard=  cmdID= 36940  "
        ::= { iqsyn22CmdEntry 36940 }


    iqsyn22LoggingVideoOutLoggingLogoutputANCstate OBJECT-TYPE
        SYNTAX            INTEGER { disable(0), enable(1)  }
        MAX-ACCESS        read-write
        STATUS            current
        DESCRIPTION
                "CMNT: - Enable/Disable logging for Output ANC embedder state
                 TYPE: - Checkbox
                 PAGE: - Logging
                    Log output ANC state  cmdID= 35946  "
        ::= { iqsyn22CmdEntry 35946 }


    iqsyn22LoggingVideoOutLoggingOutputANCstate OBJECT-TYPE
        SYNTAX            RollCallString
        MAX-ACCESS        read-only
        STATUS            current
        DESCRIPTION
                "CMNT: - Logging state for Output ANC embedder state
                 TYPE: - Display
                 PAGE: - Logging
                    Output ANC state=  cmdID= 36946  "
        ::= { iqsyn22CmdEntry 36946 }


    iqsyn22LoggingRefOutputLogOutputSource OBJECT-TYPE
        SYNTAX            INTEGER { disable(0), enable(1)  }
        MAX-ACCESS        read-write
        STATUS            current
        DESCRIPTION
                "CMNT: - Enable/Disable logging for Output Source
                 TYPE: - Checkbox
                 PAGE: - Logging
                    Log output Source  cmdID= 35943  "
        ::= { iqsyn22CmdEntry 35943 }


    iqsyn22LoggingRefOutputOutputSource OBJECT-TYPE
        SYNTAX            RollCallString
        MAX-ACCESS        read-only
        STATUS            current
        DESCRIPTION
                "CMNT: - Logging state for Output Source
                 TYPE: - Display
                 PAGE: - Logging
                    Output Source=  cmdID= 36943  "
        ::= { iqsyn22CmdEntry 36943 }


    iqsyn22LoggingIn1AudStateLogInp1Emb1stat OBJECT-TYPE
        SYNTAX            INTEGER { disable(0), enable(1)  }
        MAX-ACCESS        read-write
        STATUS            current
        DESCRIPTION
                "CMNT: - Enable/Disable logging for Input 1 Emb.Pair 1 state
                 TYPE: - Checkbox
                 PAGE: - Logging
                    Log Inp1 Emb.1 state  cmdID= 35006  "
        ::= { iqsyn22CmdEntry 35006 }


    iqsyn22LoggingIn1AudStateInp1Emb1state OBJECT-TYPE
        SYNTAX            RollCallString
        MAX-ACCESS        read-only
        STATUS            current
        DESCRIPTION
                "CMNT: - Logging state for Input 1 Emb.Pair 1 state
                 TYPE: - Display
                 PAGE: - Logging
                    Inp1 Emb.1 state=  cmdID= 36006  "
        ::= { iqsyn22CmdEntry 36006 }


    iqsyn22LoggingIn1AudStateLogInp1Emb2stat OBJECT-TYPE
        SYNTAX            INTEGER { disable(0), enable(1)  }
        MAX-ACCESS        read-write
        STATUS            current
        DESCRIPTION
                "CMNT: - Enable/Disable logging for Input 1 Emb.Pair 2 state
                 TYPE: - Checkbox
                 PAGE: - Logging
                    Log Inp1 Emb.2 state  cmdID= 35007  "
        ::= { iqsyn22CmdEntry 35007 }


    iqsyn22LoggingIn1AudStateInp1Emb2state OBJECT-TYPE
        SYNTAX            RollCallString
        MAX-ACCESS        read-only
        STATUS            current
        DESCRIPTION
                "CMNT: - Logging state for Input 1 Emb.Pair 2 state
                 TYPE: - Display
                 PAGE: - Logging
                    Inp1 Emb.2 state=  cmdID= 36007  "
        ::= { iqsyn22CmdEntry 36007 }


    iqsyn22LoggingIn1AudStateLogInp1Emb3stat OBJECT-TYPE
        SYNTAX            INTEGER { disable(0), enable(1)  }
        MAX-ACCESS        read-write
        STATUS            current
        DESCRIPTION
                "CMNT: - Enable/Disable logging for Input 1 Emb.Pair 3 state
                 TYPE: - Checkbox
                 PAGE: - Logging
                    Log Inp1 Emb.3 state  cmdID= 35008  "
        ::= { iqsyn22CmdEntry 35008 }


    iqsyn22LoggingIn1AudStateInp1Emb3state OBJECT-TYPE
        SYNTAX            RollCallString
        MAX-ACCESS        read-only
        STATUS            current
        DESCRIPTION
                "CMNT: - Logging state for Input 1 Emb.Pair 3 state
                 TYPE: - Display
                 PAGE: - Logging
                    Inp1 Emb.3 state=  cmdID= 36008  "
        ::= { iqsyn22CmdEntry 36008 }


    iqsyn22LoggingIn1AudStateLogInp1Emb4stat OBJECT-TYPE
        SYNTAX            INTEGER { disable(0), enable(1)  }
        MAX-ACCESS        read-write
        STATUS            current
        DESCRIPTION
                "CMNT: - Enable/Disable logging for Input 1 Emb.Pair 4 state
                 TYPE: - Checkbox
                 PAGE: - Logging
                    Log Inp1 Emb.4 state  cmdID= 35009  "
        ::= { iqsyn22CmdEntry 35009 }


    iqsyn22LoggingIn1AudStateInp1Emb4state OBJECT-TYPE
        SYNTAX            RollCallString
        MAX-ACCESS        read-only
        STATUS            current
        DESCRIPTION
                "CMNT: - Logging state for Input 1 Emb.Pair 4 state
                 TYPE: - Display
                 PAGE: - Logging
                    Inp1 Emb.4 state=  cmdID= 36009  "
        ::= { iqsyn22CmdEntry 36009 }


    iqsyn22LoggingIn1AudStateLogInp1Emb5stat OBJECT-TYPE
        SYNTAX            INTEGER { disable(0), enable(1)  }
        MAX-ACCESS        read-write
        STATUS            current
        DESCRIPTION
                "CMNT: - Enable/Disable logging for Input 1 Emb.Pair 5 state
                 TYPE: - Checkbox
                 PAGE: - Logging
                    Log Inp1 Emb.5 state  cmdID= 35010  "
        ::= { iqsyn22CmdEntry 35010 }


    iqsyn22LoggingIn1AudStateInp1Emb5state OBJECT-TYPE
        SYNTAX            RollCallString
        MAX-ACCESS        read-only
        STATUS            current
        DESCRIPTION
                "CMNT: - Logging state for Input 1 Emb.Pair 5 state
                 TYPE: - Display
                 PAGE: - Logging
                    Inp1 Emb.5 state=  cmdID= 36010  "
        ::= { iqsyn22CmdEntry 36010 }


    iqsyn22LoggingIn1AudStateLogInp1Emb6stat OBJECT-TYPE
        SYNTAX            INTEGER { disable(0), enable(1)  }
        MAX-ACCESS        read-write
        STATUS            current
        DESCRIPTION
                "CMNT: - Enable/Disable logging for Input 1 Emb.Pair 6 state
                 TYPE: - Checkbox
                 PAGE: - Logging
                    Log Inp1 Emb.6 state  cmdID= 35011  "
        ::= { iqsyn22CmdEntry 35011 }


    iqsyn22LoggingIn1AudStateInp1Emb6state OBJECT-TYPE
        SYNTAX            RollCallString
        MAX-ACCESS        read-only
        STATUS            current
        DESCRIPTION
                "CMNT: - Logging state for Input 1 Emb.Pair 6 state
                 TYPE: - Display
                 PAGE: - Logging
                    Inp1 Emb.6 state=  cmdID= 36011  "
        ::= { iqsyn22CmdEntry 36011 }


    iqsyn22LoggingIn1AudStateLogInp1Emb7stat OBJECT-TYPE
        SYNTAX            INTEGER { disable(0), enable(1)  }
        MAX-ACCESS        read-write
        STATUS            current
        DESCRIPTION
                "CMNT: - Enable/Disable logging for Input 1 Emb.Pair 7 state
                 TYPE: - Checkbox
                 PAGE: - Logging
                    Log Inp1 Emb.7 state  cmdID= 35012  "
        ::= { iqsyn22CmdEntry 35012 }


    iqsyn22LoggingIn1AudStateInp1Emb7state OBJECT-TYPE
        SYNTAX            RollCallString
        MAX-ACCESS        read-only
        STATUS            current
        DESCRIPTION
                "CMNT: - Logging state for Input 1 Emb.Pair 7 state
                 TYPE: - Display
                 PAGE: - Logging
                    Inp1 Emb.7 state=  cmdID= 36012  "
        ::= { iqsyn22CmdEntry 36012 }


    iqsyn22LoggingIn1AudStateLogInp1Emb8stat OBJECT-TYPE
        SYNTAX            INTEGER { disable(0), enable(1)  }
        MAX-ACCESS        read-write
        STATUS            current
        DESCRIPTION
                "CMNT: - Enable/Disable logging for Input 1 Emb.Pair 8 state
                 TYPE: - Checkbox
                 PAGE: - Logging
                    Log Inp1 Emb.8 state  cmdID= 35013  "
        ::= { iqsyn22CmdEntry 35013 }


    iqsyn22LoggingIn1AudStateInp1Emb8state OBJECT-TYPE
        SYNTAX            RollCallString
        MAX-ACCESS        read-only
        STATUS            current
        DESCRIPTION
                "CMNT: - Logging state for Input 1 Emb.Pair 8 state
                 TYPE: - Display
                 PAGE: - Logging
                    Inp1 Emb.8 state=  cmdID= 36013  "
        ::= { iqsyn22CmdEntry 36013 }


    iqsyn22LoggingIn1AudTypeLogInp1Emb1type OBJECT-TYPE
        SYNTAX            INTEGER { disable(0), enable(1)  }
        MAX-ACCESS        read-write
        STATUS            current
        DESCRIPTION
                "CMNT: - Enable/Disable logging for Input 1 Emb.Pair 1 type
                 TYPE: - Checkbox
                 PAGE: - Logging
                    Log Inp1 Emb.1 type  cmdID= 35018  "
        ::= { iqsyn22CmdEntry 35018 }


    iqsyn22LoggingIn1AudTypeInp1Emb1type OBJECT-TYPE
        SYNTAX            RollCallString
        MAX-ACCESS        read-only
        STATUS            current
        DESCRIPTION
                "CMNT: - Logging state for Input 1 Emb.Pair 1 type
                 TYPE: - Display
                 PAGE: - Logging
                    Inp1 Emb.1 type=  cmdID= 36018  "
        ::= { iqsyn22CmdEntry 36018 }


    iqsyn22LoggingIn1AudTypeLogInp1Emb2type OBJECT-TYPE
        SYNTAX            INTEGER { disable(0), enable(1)  }
        MAX-ACCESS        read-write
        STATUS            current
        DESCRIPTION
                "CMNT: - Enable/Disable logging for Input 1 Emb.Pair 2 type
                 TYPE: - Checkbox
                 PAGE: - Logging
                    Log Inp1 Emb.2 type  cmdID= 35019  "
        ::= { iqsyn22CmdEntry 35019 }


    iqsyn22LoggingIn1AudTypeInp1Emb2type OBJECT-TYPE
        SYNTAX            RollCallString
        MAX-ACCESS        read-only
        STATUS            current
        DESCRIPTION
                "CMNT: - Logging state for Input 1 Emb.Pair 2 type
                 TYPE: - Display
                 PAGE: - Logging
                    Inp1 Emb.2 type=  cmdID= 36019  "
        ::= { iqsyn22CmdEntry 36019 }


    iqsyn22LoggingIn1AudTypeLogInp1Emb3type OBJECT-TYPE
        SYNTAX            INTEGER { disable(0), enable(1)  }
        MAX-ACCESS        read-write
        STATUS            current
        DESCRIPTION
                "CMNT: - Enable/Disable logging for Input 1 Emb.Pair 3 type
                 TYPE: - Checkbox
                 PAGE: - Logging
                    Log Inp1 Emb.3 type  cmdID= 35020  "
        ::= { iqsyn22CmdEntry 35020 }


    iqsyn22LoggingIn1AudTypeInp1Emb3type OBJECT-TYPE
        SYNTAX            RollCallString
        MAX-ACCESS        read-only
        STATUS            current
        DESCRIPTION
                "CMNT: - Logging state for Input 1 Emb.Pair 3 type
                 TYPE: - Display
                 PAGE: - Logging
                    Inp1 Emb.3 type=  cmdID= 36020  "
        ::= { iqsyn22CmdEntry 36020 }


    iqsyn22LoggingIn1AudTypeLogInp1Emb4type OBJECT-TYPE
        SYNTAX            INTEGER { disable(0), enable(1)  }
        MAX-ACCESS        read-write
        STATUS            current
        DESCRIPTION
                "CMNT: - Enable/Disable logging for Input 1 Emb.Pair 4 type
                 TYPE: - Checkbox
                 PAGE: - Logging
                    Log Inp1 Emb.4 type  cmdID= 35021  "
        ::= { iqsyn22CmdEntry 35021 }


    iqsyn22LoggingIn1AudTypeInp1Emb4type OBJECT-TYPE
        SYNTAX            RollCallString
        MAX-ACCESS        read-only
        STATUS            current
        DESCRIPTION
                "CMNT: - Logging state for Input 1 Emb.Pair 4 type
                 TYPE: - Display
                 PAGE: - Logging
                    Inp1 Emb.4 type=  cmdID= 36021  "
        ::= { iqsyn22CmdEntry 36021 }


    iqsyn22LoggingIn1AudTypeLogInp1Emb5type OBJECT-TYPE
        SYNTAX            INTEGER { disable(0), enable(1)  }
        MAX-ACCESS        read-write
        STATUS            current
        DESCRIPTION
                "CMNT: - Enable/Disable logging for Input 1 Emb.Pair 4 type
                 TYPE: - Checkbox
                 PAGE: - Logging
                    Log Inp1 Emb.5 type  cmdID= 35022  "
        ::= { iqsyn22CmdEntry 35022 }


    iqsyn22LoggingIn1AudTypeInp1Emb5type OBJECT-TYPE
        SYNTAX            RollCallString
        MAX-ACCESS        read-only
        STATUS            current
        DESCRIPTION
                "CMNT: - Logging state for Input 1 Emb.Pair 5 type
                 TYPE: - Display
                 PAGE: - Logging
                    Inp1 Emb.5 type=  cmdID= 36022  "
        ::= { iqsyn22CmdEntry 36022 }


    iqsyn22LoggingIn1AudTypeLogInp1Emb6type OBJECT-TYPE
        SYNTAX            INTEGER { disable(0), enable(1)  }
        MAX-ACCESS        read-write
        STATUS            current
        DESCRIPTION
                "CMNT: - Enable/Disable logging for Input 1 Emb.Pair 6 type
                 TYPE: - Checkbox
                 PAGE: - Logging
                    Log Inp1 Emb.6 type  cmdID= 35023  "
        ::= { iqsyn22CmdEntry 35023 }


    iqsyn22LoggingIn1AudTypeInp1Emb6type OBJECT-TYPE
        SYNTAX            RollCallString
        MAX-ACCESS        read-only
        STATUS            current
        DESCRIPTION
                "CMNT: - Logging state for Input 1 Emb.Pair 6 type
                 TYPE: - Display
                 PAGE: - Logging
                    Inp1 Emb.6 type=  cmdID= 36023  "
        ::= { iqsyn22CmdEntry 36023 }


    iqsyn22LoggingIn1AudTypeLogInp1Emb7type OBJECT-TYPE
        SYNTAX            INTEGER { disable(0), enable(1)  }
        MAX-ACCESS        read-write
        STATUS            current
        DESCRIPTION
                "CMNT: - Enable/Disable logging for Input 1 Emb.Pair 7 type
                 TYPE: - Checkbox
                 PAGE: - Logging
                    Log Inp1 Emb.7 type  cmdID= 35024  "
        ::= { iqsyn22CmdEntry 35024 }


    iqsyn22LoggingIn1AudTypeInp1Emb7type OBJECT-TYPE
        SYNTAX            RollCallString
        MAX-ACCESS        read-only
        STATUS            current
        DESCRIPTION
                "CMNT: - Logging state for Input 1 Emb.Pair 7 type
                 TYPE: - Display
                 PAGE: - Logging
                    Inp1 Emb.7 type=  cmdID= 36024  "
        ::= { iqsyn22CmdEntry 36024 }


    iqsyn22LoggingIn1AudTypeLogInp1Emb8type OBJECT-TYPE
        SYNTAX            INTEGER { disable(0), enable(1)  }
        MAX-ACCESS        read-write
        STATUS            current
        DESCRIPTION
                "CMNT: - Enable/Disable logging for Input 1 Emb.Pair 8 type
                 TYPE: - Checkbox
                 PAGE: - Logging
                    Log Inp1 Emb.8 type  cmdID= 35025  "
        ::= { iqsyn22CmdEntry 35025 }


    iqsyn22LoggingIn1AudTypeInp1Emb8type OBJECT-TYPE
        SYNTAX            RollCallString
        MAX-ACCESS        read-only
        STATUS            current
        DESCRIPTION
                "CMNT: - Logging state for Input 1 Emb.Pair 8 type
                 TYPE: - Display
                 PAGE: - Logging
                    Inp1 Emb.8 type=  cmdID= 36025  "
        ::= { iqsyn22CmdEntry 36025 }


    iqsyn22LoggingIn2AudStateLogInp2Emb1stat OBJECT-TYPE
        SYNTAX            INTEGER { disable(0), enable(1)  }
        MAX-ACCESS        read-write
        STATUS            current
        DESCRIPTION
                "CMNT: - Enable/Disable logging for Input 2 Emb.Pair 1 state
                 TYPE: - Checkbox
                 PAGE: - Logging
                    Log Inp2 Emb.1 state  cmdID= 35036  "
        ::= { iqsyn22CmdEntry 35036 }


    iqsyn22LoggingIn2AudStateInp2Emb1state OBJECT-TYPE
        SYNTAX            RollCallString
        MAX-ACCESS        read-only
        STATUS            current
        DESCRIPTION
                "CMNT: - Logging state for Input 2 Emb.Pair 1 state
                 TYPE: - Display
                 PAGE: - Logging
                    Inp2 Emb.1 state=  cmdID= 36036  "
        ::= { iqsyn22CmdEntry 36036 }


    iqsyn22LoggingIn2AudStateLogInp2Emb2stat OBJECT-TYPE
        SYNTAX            INTEGER { disable(0), enable(1)  }
        MAX-ACCESS        read-write
        STATUS            current
        DESCRIPTION
                "CMNT: - Enable/Disable logging for Input 2 Emb.Pair 2 state
                 TYPE: - Checkbox
                 PAGE: - Logging
                    Log Inp2 Emb.2 state  cmdID= 35037  "
        ::= { iqsyn22CmdEntry 35037 }


    iqsyn22LoggingIn2AudStateInp2Emb2state OBJECT-TYPE
        SYNTAX            RollCallString
        MAX-ACCESS        read-only
        STATUS            current
        DESCRIPTION
                "CMNT: - Logging state for Input 2 Emb.Pair 2 state
                 TYPE: - Display
                 PAGE: - Logging
                    Inp2 Emb.2 state=  cmdID= 36037  "
        ::= { iqsyn22CmdEntry 36037 }


    iqsyn22LoggingIn2AudStateLogInp2Emb3stat OBJECT-TYPE
        SYNTAX            INTEGER { disable(0), enable(1)  }
        MAX-ACCESS        read-write
        STATUS            current
        DESCRIPTION
                "CMNT: - Enable/Disable logging for Input 2 Emb.Pair 3 state
                 TYPE: - Checkbox
                 PAGE: - Logging
                    Log Inp2 Emb.3 state  cmdID= 35038  "
        ::= { iqsyn22CmdEntry 35038 }


    iqsyn22LoggingIn2AudStateInp2Emb3state OBJECT-TYPE
        SYNTAX            RollCallString
        MAX-ACCESS        read-only
        STATUS            current
        DESCRIPTION
                "CMNT: - Logging state for Input 2 Emb.Pair 3 state
                 TYPE: - Display
                 PAGE: - Logging
                    Inp2 Emb.3 state=  cmdID= 36038  "
        ::= { iqsyn22CmdEntry 36038 }


    iqsyn22LoggingIn2AudStateLogInp2Emb4stat OBJECT-TYPE
        SYNTAX            INTEGER { disable(0), enable(1)  }
        MAX-ACCESS        read-write
        STATUS            current
        DESCRIPTION
                "CMNT: - Enable/Disable logging for Input 2 Emb.Pair 4 state
                 TYPE: - Checkbox
                 PAGE: - Logging
                    Log Inp2 Emb.4 state  cmdID= 35039  "
        ::= { iqsyn22CmdEntry 35039 }


    iqsyn22LoggingIn2AudStateInp2Emb4state OBJECT-TYPE
        SYNTAX            RollCallString
        MAX-ACCESS        read-only
        STATUS            current
        DESCRIPTION
                "CMNT: - Logging state for Input 2 Emb.Pair 4 state
                 TYPE: - Display
                 PAGE: - Logging
                    Inp2 Emb.4 state=  cmdID= 36039  "
        ::= { iqsyn22CmdEntry 36039 }


    iqsyn22LoggingIn2AudStateLogInp2Emb5stat OBJECT-TYPE
        SYNTAX            INTEGER { disable(0), enable(1)  }
        MAX-ACCESS        read-write
        STATUS            current
        DESCRIPTION
                "CMNT: - Enable/Disable logging for Input 2 Emb.Pair 5 state
                 TYPE: - Checkbox
                 PAGE: - Logging
                    Log Inp2 Emb.5 state  cmdID= 35040  "
        ::= { iqsyn22CmdEntry 35040 }


    iqsyn22LoggingIn2AudStateInp2Emb5state OBJECT-TYPE
        SYNTAX            RollCallString
        MAX-ACCESS        read-only
        STATUS            current
        DESCRIPTION
                "CMNT: - Logging state for Input 2 Emb.Pair 5 state
                 TYPE: - Display
                 PAGE: - Logging
                    Inp2 Emb.5 state=  cmdID= 36040  "
        ::= { iqsyn22CmdEntry 36040 }


    iqsyn22LoggingIn2AudStateLogInp2Emb6stat OBJECT-TYPE
        SYNTAX            INTEGER { disable(0), enable(1)  }
        MAX-ACCESS        read-write
        STATUS            current
        DESCRIPTION
                "CMNT: - Enable/Disable logging for Input 2 Emb.Pair 6 state
                 TYPE: - Checkbox
                 PAGE: - Logging
                    Log Inp2 Emb.6 state  cmdID= 35041  "
        ::= { iqsyn22CmdEntry 35041 }


    iqsyn22LoggingIn2AudStateInp2Emb6state OBJECT-TYPE
        SYNTAX            RollCallString
        MAX-ACCESS        read-only
        STATUS            current
        DESCRIPTION
                "CMNT: - Logging state for Input 2 Emb.Pair 6 state
                 TYPE: - Display
                 PAGE: - Logging
                    Inp2 Emb.6 state=  cmdID= 36041  "
        ::= { iqsyn22CmdEntry 36041 }


    iqsyn22LoggingIn2AudStateLogInp2Emb7stat OBJECT-TYPE
        SYNTAX            INTEGER { disable(0), enable(1)  }
        MAX-ACCESS        read-write
        STATUS            current
        DESCRIPTION
                "CMNT: - Enable/Disable logging for Input 2 Emb.Pair 7 state
                 TYPE: - Checkbox
                 PAGE: - Logging
                    Log Inp2 Emb.7 state  cmdID= 35042  "
        ::= { iqsyn22CmdEntry 35042 }


    iqsyn22LoggingIn2AudStateInp2Emb7state OBJECT-TYPE
        SYNTAX            RollCallString
        MAX-ACCESS        read-only
        STATUS            current
        DESCRIPTION
                "CMNT: - Logging state for Input 2 Emb.Pair 7 state
                 TYPE: - Display
                 PAGE: - Logging
                    Inp2 Emb.7 state=  cmdID= 36042  "
        ::= { iqsyn22CmdEntry 36042 }


    iqsyn22LoggingIn2AudStateLogInp2Emb8stat OBJECT-TYPE
        SYNTAX            INTEGER { disable(0), enable(1)  }
        MAX-ACCESS        read-write
        STATUS            current
        DESCRIPTION
                "CMNT: - Enable/Disable logging for Input 2 Emb.Pair 8 state
                 TYPE: - Checkbox
                 PAGE: - Logging
                    Log Inp2 Emb.8 state  cmdID= 35043  "
        ::= { iqsyn22CmdEntry 35043 }


    iqsyn22LoggingIn2AudStateInp2Emb8state OBJECT-TYPE
        SYNTAX            RollCallString
        MAX-ACCESS        read-only
        STATUS            current
        DESCRIPTION
                "CMNT: - Logging state for Input 2 Emb.Pair 8 state
                 TYPE: - Display
                 PAGE: - Logging
                    Inp2 Emb.8 state=  cmdID= 36043  "
        ::= { iqsyn22CmdEntry 36043 }


    iqsyn22LoggingIn1AudTypeLogInp2Emb1type OBJECT-TYPE
        SYNTAX            INTEGER { disable(0), enable(1)  }
        MAX-ACCESS        read-write
        STATUS            current
        DESCRIPTION
                "CMNT: - Enable/Disable logging for Input 2 Emb.Pair 1 type
                 TYPE: - Checkbox
                 PAGE: - Logging
                    Log Inp2 Emb.1 type  cmdID= 35048  "
        ::= { iqsyn22CmdEntry 35048 }


    iqsyn22LoggingIn1AudTypeInp2Emb1type OBJECT-TYPE
        SYNTAX            RollCallString
        MAX-ACCESS        read-only
        STATUS            current
        DESCRIPTION
                "CMNT: - Logging state for Input 2 Emb.Pair 1 type
                 TYPE: - Display
                 PAGE: - Logging
                    Inp2 Emb.1 type=  cmdID= 36048  "
        ::= { iqsyn22CmdEntry 36048 }


    iqsyn22LoggingIn1AudTypeLogInp2Emb2type OBJECT-TYPE
        SYNTAX            INTEGER { disable(0), enable(1)  }
        MAX-ACCESS        read-write
        STATUS            current
        DESCRIPTION
                "CMNT: - Enable/Disable logging for Input 1 Emb.Pair 2 type
                 TYPE: - Checkbox
                 PAGE: - Logging
                    Log Inp2 Emb.2 type  cmdID= 35049  "
        ::= { iqsyn22CmdEntry 35049 }


    iqsyn22LoggingIn1AudTypeInp2Emb2type OBJECT-TYPE
        SYNTAX            RollCallString
        MAX-ACCESS        read-only
        STATUS            current
        DESCRIPTION
                "CMNT: - Logging state for Input 2 Emb.Pair 2 type
                 TYPE: - Display
                 PAGE: - Logging
                    Inp2 Emb.2 type=  cmdID= 36049  "
        ::= { iqsyn22CmdEntry 36049 }


    iqsyn22LoggingIn1AudTypeLogInp2Emb3type OBJECT-TYPE
        SYNTAX            INTEGER { disable(0), enable(1)  }
        MAX-ACCESS        read-write
        STATUS            current
        DESCRIPTION
                "CMNT: - Enable/Disable logging for Input 2 Emb.Pair 3 type
                 TYPE: - Checkbox
                 PAGE: - Logging
                    Log Inp2 Emb.3 type  cmdID= 35050  "
        ::= { iqsyn22CmdEntry 35050 }


    iqsyn22LoggingIn1AudTypeInp2Emb3type OBJECT-TYPE
        SYNTAX            RollCallString
        MAX-ACCESS        read-only
        STATUS            current
        DESCRIPTION
                "CMNT: - Logging state for Input 2 Emb.Pair 3 type
                 TYPE: - Display
                 PAGE: - Logging
                    Inp2 Emb.3 type=  cmdID= 36050  "
        ::= { iqsyn22CmdEntry 36050 }


    iqsyn22LoggingIn1AudTypeLogInp2Emb4type OBJECT-TYPE
        SYNTAX            INTEGER { disable(0), enable(1)  }
        MAX-ACCESS        read-write
        STATUS            current
        DESCRIPTION
                "CMNT: - Enable/Disable logging for Input 2 Emb.Pair 4 type
                 TYPE: - Checkbox
                 PAGE: - Logging
                    Log Inp2 Emb.4 type  cmdID= 35051  "
        ::= { iqsyn22CmdEntry 35051 }


    iqsyn22LoggingIn1AudTypeInp2Emb4type OBJECT-TYPE
        SYNTAX            RollCallString
        MAX-ACCESS        read-only
        STATUS            current
        DESCRIPTION
                "CMNT: - Logging state for Input 2 Emb.Pair 4 type
                 TYPE: - Display
                 PAGE: - Logging
                    Inp2 Emb.4 type=  cmdID= 36051  "
        ::= { iqsyn22CmdEntry 36051 }


    iqsyn22LoggingIn1AudTypeLogInp2Emb5type OBJECT-TYPE
        SYNTAX            INTEGER { disable(0), enable(1)  }
        MAX-ACCESS        read-write
        STATUS            current
        DESCRIPTION
                "CMNT: - Enable/Disable logging for Input 2 Emb.Pair 5 type
                 TYPE: - Checkbox
                 PAGE: - Logging
                    Log Inp2 Emb.5 type  cmdID= 35052  "
        ::= { iqsyn22CmdEntry 35052 }


    iqsyn22LoggingIn1AudTypeInp2Emb5type OBJECT-TYPE
        SYNTAX            RollCallString
        MAX-ACCESS        read-only
        STATUS            current
        DESCRIPTION
                "CMNT: - Logging state for Input 2 Emb.Pair 5 type
                 TYPE: - Display
                 PAGE: - Logging
                    Inp2 Emb.5 type=  cmdID= 36052  "
        ::= { iqsyn22CmdEntry 36052 }


    iqsyn22LoggingIn1AudTypeLogInp2Emb6type OBJECT-TYPE
        SYNTAX            INTEGER { disable(0), enable(1)  }
        MAX-ACCESS        read-write
        STATUS            current
        DESCRIPTION
                "CMNT: - Enable/Disable logging for Input 2 Emb.Pair 6 type
                 TYPE: - Checkbox
                 PAGE: - Logging
                    Log Inp2 Emb.6 type  cmdID= 35053  "
        ::= { iqsyn22CmdEntry 35053 }


    iqsyn22LoggingIn1AudTypeInp2Emb6type OBJECT-TYPE
        SYNTAX            RollCallString
        MAX-ACCESS        read-only
        STATUS            current
        DESCRIPTION
                "CMNT: - Logging state for Input 2 Emb.Pair 6 type
                 TYPE: - Display
                 PAGE: - Logging
                    Inp2 Emb.6 type=  cmdID= 36053  "
        ::= { iqsyn22CmdEntry 36053 }


    iqsyn22LoggingIn1AudTypeLogInp2Emb7type OBJECT-TYPE
        SYNTAX            INTEGER { disable(0), enable(1)  }
        MAX-ACCESS        read-write
        STATUS            current
        DESCRIPTION
                "CMNT: - Enable/Disable logging for Input 2 Emb.Pair 7 type
                 TYPE: - Checkbox
                 PAGE: - Logging
                    Log Inp2 Emb.7 type  cmdID= 35054  "
        ::= { iqsyn22CmdEntry 35054 }


    iqsyn22LoggingIn1AudTypeInp2Emb7type OBJECT-TYPE
        SYNTAX            RollCallString
        MAX-ACCESS        read-only
        STATUS            current
        DESCRIPTION
                "CMNT: - Logging state for Input 2 Emb.Pair 7 type
                 TYPE: - Display
                 PAGE: - Logging
                    Inp2 Emb.7 type=  cmdID= 36054  "
        ::= { iqsyn22CmdEntry 36054 }


    iqsyn22LoggingIn1AudTypeLogInp2Emb8type OBJECT-TYPE
        SYNTAX            INTEGER { disable(0), enable(1)  }
        MAX-ACCESS        read-write
        STATUS            current
        DESCRIPTION
                "CMNT: - Enable/Disable logging for Input 2 Emb.Pair 8 type
                 TYPE: - Checkbox
                 PAGE: - Logging
                    Log Inp2 Emb.8 type  cmdID= 35055  "
        ::= { iqsyn22CmdEntry 35055 }


    iqsyn22LoggingIn1AudTypeInp2Emb8type OBJECT-TYPE
        SYNTAX            RollCallString
        MAX-ACCESS        read-only
        STATUS            current
        DESCRIPTION
                "CMNT: - Logging state for Input 2 Emb.Pair 8 type
                 TYPE: - Display
                 PAGE: - Logging
                    Inp2 Emb.8 type=  cmdID= 36055  "
        ::= { iqsyn22CmdEntry 36055 }


    iqsyn22LoggingOPAudStateLogOutEmb1state OBJECT-TYPE
        SYNTAX            INTEGER { disable(0), enable(1)  }
        MAX-ACCESS        read-write
        STATUS            current
        DESCRIPTION
                "CMNT: - Enable/Disable logging for Output Emb.Pair 1 state
                 TYPE: - Checkbox
                 PAGE: - Logging
                    Log Out Emb.1 state  cmdID= 35920  "
        ::= { iqsyn22CmdEntry 35920 }


    iqsyn22LoggingOPAudStateOutEmb1state OBJECT-TYPE
        SYNTAX            RollCallString
        MAX-ACCESS        read-only
        STATUS            current
        DESCRIPTION
                "CMNT: - Logging state for Output Emb.Pair 1 state
                 TYPE: - Display
                 PAGE: - Logging
                    Out Emb.1 state=  cmdID= 36920  "
        ::= { iqsyn22CmdEntry 36920 }


    iqsyn22LoggingOPAudStateLogOutEmb2state OBJECT-TYPE
        SYNTAX            INTEGER { disable(0), enable(1)  }
        MAX-ACCESS        read-write
        STATUS            current
        DESCRIPTION
                "CMNT: - Enable/Disable logging for Output Emb.Pair 2 state
                 TYPE: - Checkbox
                 PAGE: - Logging
                    Log Out Emb.2 state  cmdID= 35921  "
        ::= { iqsyn22CmdEntry 35921 }


    iqsyn22LoggingOPAudStateOutEmb2state OBJECT-TYPE
        SYNTAX            RollCallString
        MAX-ACCESS        read-only
        STATUS            current
        DESCRIPTION
                "CMNT: - Logging state for Output Emb.Pair 2 state
                 TYPE: - Display
                 PAGE: - Logging
                    Out Emb.2 state=  cmdID= 36921  "
        ::= { iqsyn22CmdEntry 36921 }


    iqsyn22LoggingOPAudStateLogOutEmb3state OBJECT-TYPE
        SYNTAX            INTEGER { disable(0), enable(1)  }
        MAX-ACCESS        read-write
        STATUS            current
        DESCRIPTION
                "CMNT: - Enable/Disable logging for Output Emb.Pair 3 state
                 TYPE: - Checkbox
                 PAGE: - Logging
                    Log Out Emb.3 state  cmdID= 35922  "
        ::= { iqsyn22CmdEntry 35922 }


    iqsyn22LoggingOPAudStateOutEmb3state OBJECT-TYPE
        SYNTAX            RollCallString
        MAX-ACCESS        read-only
        STATUS            current
        DESCRIPTION
                "CMNT: - Logging state for Output Emb.Pair 3 state
                 TYPE: - Display
                 PAGE: - Logging
                    Out Emb.3 state=  cmdID= 36922  "
        ::= { iqsyn22CmdEntry 36922 }


    iqsyn22LoggingOPAudStateLogOutEmb4state OBJECT-TYPE
        SYNTAX            INTEGER { disable(0), enable(1)  }
        MAX-ACCESS        read-write
        STATUS            current
        DESCRIPTION
                "CMNT: - Enable/Disable logging for Output Emb.Pair 4 state
                 TYPE: - Checkbox
                 PAGE: - Logging
                    Log Out Emb.4 state  cmdID= 35923  "
        ::= { iqsyn22CmdEntry 35923 }


    iqsyn22LoggingOPAudStateOutEmb4state OBJECT-TYPE
        SYNTAX            RollCallString
        MAX-ACCESS        read-only
        STATUS            current
        DESCRIPTION
                "CMNT: - Logging state for Output Emb.Pair 4 state
                 TYPE: - Display
                 PAGE: - Logging
                    Out Emb.4 state=  cmdID= 36923  "
        ::= { iqsyn22CmdEntry 36923 }


    iqsyn22LoggingOPAudStateLogOutEmb5state OBJECT-TYPE
        SYNTAX            INTEGER { disable(0), enable(1)  }
        MAX-ACCESS        read-write
        STATUS            current
        DESCRIPTION
                "CMNT: - Enable/Disable logging for Output Emb.Pair 5 state
                 TYPE: - Checkbox
                 PAGE: - Logging
                    Log Out Emb.5 state  cmdID= 35924  "
        ::= { iqsyn22CmdEntry 35924 }


    iqsyn22LoggingOPAudStateOutEmb5state OBJECT-TYPE
        SYNTAX            RollCallString
        MAX-ACCESS        read-only
        STATUS            current
        DESCRIPTION
                "CMNT: - Logging state for Output Emb.Pair 5 state
                 TYPE: - Display
                 PAGE: - Logging
                    Out Emb.5 state=  cmdID= 36924  "
        ::= { iqsyn22CmdEntry 36924 }


    iqsyn22LoggingOPAudStateLogOutEmb6state OBJECT-TYPE
        SYNTAX            INTEGER { disable(0), enable(1)  }
        MAX-ACCESS        read-write
        STATUS            current
        DESCRIPTION
                "CMNT: - Enable/Disable logging for Output Emb.Pair 6 state
                 TYPE: - Checkbox
                 PAGE: - Logging
                    Log Out Emb.6 state  cmdID= 35925  "
        ::= { iqsyn22CmdEntry 35925 }


    iqsyn22LoggingOPAudStateOutEmb6state OBJECT-TYPE
        SYNTAX            RollCallString
        MAX-ACCESS        read-only
        STATUS            current
        DESCRIPTION
                "CMNT: - Logging state for Output Emb.Pair 6 state
                 TYPE: - Display
                 PAGE: - Logging
                    Out Emb.6 state=  cmdID= 36925  "
        ::= { iqsyn22CmdEntry 36925 }


    iqsyn22LoggingOPAudStateLogOutEmb7state OBJECT-TYPE
        SYNTAX            INTEGER { disable(0), enable(1)  }
        MAX-ACCESS        read-write
        STATUS            current
        DESCRIPTION
                "CMNT: - Enable/Disable logging for Output Emb.Pair 7 state
                 TYPE: - Checkbox
                 PAGE: - Logging
                    Log Out Emb.7 state  cmdID= 35926  "
        ::= { iqsyn22CmdEntry 35926 }


    iqsyn22LoggingOPAudStateOutEmb7state OBJECT-TYPE
        SYNTAX            RollCallString
        MAX-ACCESS        read-only
        STATUS            current
        DESCRIPTION
                "CMNT: - Logging state for Output Emb.Pair 7 state
                 TYPE: - Display
                 PAGE: - Logging
                    Out Emb.7 state=  cmdID= 36926  "
        ::= { iqsyn22CmdEntry 36926 }


    iqsyn22LoggingOPAudStateLogOutEmb8state OBJECT-TYPE
        SYNTAX            INTEGER { disable(0), enable(1)  }
        MAX-ACCESS        read-write
        STATUS            current
        DESCRIPTION
                "CMNT: - Enable/Disable logging for Output Emb.Pair 8 state
                 TYPE: - Checkbox
                 PAGE: - Logging
                    Log Out Emb.8 state  cmdID= 35927  "
        ::= { iqsyn22CmdEntry 35927 }


    iqsyn22LoggingOPAudStateOutEmb8state OBJECT-TYPE
        SYNTAX            RollCallString
        MAX-ACCESS        read-only
        STATUS            current
        DESCRIPTION
                "CMNT: - Logging state for Output Emb.Pair 8 state
                 TYPE: - Display
                 PAGE: - Logging
                    Out Emb.8 state=  cmdID= 36927  "
        ::= { iqsyn22CmdEntry 36927 }


    iqsyn22LoggingOPAudTypeLogOutEmb1type OBJECT-TYPE
        SYNTAX            INTEGER { disable(0), enable(1)  }
        MAX-ACCESS        read-write
        STATUS            current
        DESCRIPTION
                "CMNT: - Enable/Disable logging for Output Emb.Pair 1 type
                 TYPE: - Checkbox
                 PAGE: - Logging
                    Log Out Emb.1 type  cmdID= 35930  "
        ::= { iqsyn22CmdEntry 35930 }


    iqsyn22LoggingOPAudTypeOutEmb1type OBJECT-TYPE
        SYNTAX            RollCallString
        MAX-ACCESS        read-only
        STATUS            current
        DESCRIPTION
                "CMNT: - Logging state for Output Emb.Pair 1 type
                 TYPE: - Display
                 PAGE: - Logging
                    Out Emb.1 type=  cmdID= 36930  "
        ::= { iqsyn22CmdEntry 36930 }


    iqsyn22LoggingOPAudTypeLogOutEmb2type OBJECT-TYPE
        SYNTAX            INTEGER { disable(0), enable(1)  }
        MAX-ACCESS        read-write
        STATUS            current
        DESCRIPTION
                "CMNT: - Enable/Disable logging for Output Emb.Pair 2 type
                 TYPE: - Checkbox
                 PAGE: - Logging
                    Log Out Emb.2 type  cmdID= 35931  "
        ::= { iqsyn22CmdEntry 35931 }


    iqsyn22LoggingOPAudTypeOutEmb2type OBJECT-TYPE
        SYNTAX            RollCallString
        MAX-ACCESS        read-only
        STATUS            current
        DESCRIPTION
                "CMNT: - Logging state for Output Emb.Pair 2 type
                 TYPE: - Display
                 PAGE: - Logging
                    Out Emb.2 type=  cmdID= 36931  "
        ::= { iqsyn22CmdEntry 36931 }


    iqsyn22LoggingOPAudTypeLogOutEmb3type OBJECT-TYPE
        SYNTAX            INTEGER { disable(0), enable(1)  }
        MAX-ACCESS        read-write
        STATUS            current
        DESCRIPTION
                "CMNT: - Enable/Disable logging for Output Emb.Pair 3 type
                 TYPE: - Checkbox
                 PAGE: - Logging
                    Log Out Emb.3 type  cmdID= 35932  "
        ::= { iqsyn22CmdEntry 35932 }


    iqsyn22LoggingOPAudTypeOutEmb3type OBJECT-TYPE
        SYNTAX            RollCallString
        MAX-ACCESS        read-only
        STATUS            current
        DESCRIPTION
                "CMNT: - Logging state for Output Emb.Pair 3 type
                 TYPE: - Display
                 PAGE: - Logging
                    Out Emb.3 type=  cmdID= 36932  "
        ::= { iqsyn22CmdEntry 36932 }


    iqsyn22LoggingOPAudTypeLogOutEmb4type OBJECT-TYPE
        SYNTAX            INTEGER { disable(0), enable(1)  }
        MAX-ACCESS        read-write
        STATUS            current
        DESCRIPTION
                "CMNT: - Enable/Disable logging for Output Emb.Pair 4 type
                 TYPE: - Checkbox
                 PAGE: - Logging
                    Log Out Emb.4 type  cmdID= 35933  "
        ::= { iqsyn22CmdEntry 35933 }


    iqsyn22LoggingOPAudTypeOutEmb4type OBJECT-TYPE
        SYNTAX            RollCallString
        MAX-ACCESS        read-only
        STATUS            current
        DESCRIPTION
                "CMNT: - Logging state for Output Emb.Pair 4 type
                 TYPE: - Display
                 PAGE: - Logging
                    Out Emb.4 type=  cmdID= 36933  "
        ::= { iqsyn22CmdEntry 36933 }


    iqsyn22LoggingOPAudTypeLogOutEmb5type OBJECT-TYPE
        SYNTAX            INTEGER { disable(0), enable(1)  }
        MAX-ACCESS        read-write
        STATUS            current
        DESCRIPTION
                "CMNT: - Enable/Disable logging for Output Emb.Pair 5 type
                 TYPE: - Checkbox
                 PAGE: - Logging
                    Log Out Emb.5 type  cmdID= 35934  "
        ::= { iqsyn22CmdEntry 35934 }


    iqsyn22LoggingOPAudTypeOutEmb5type OBJECT-TYPE
        SYNTAX            RollCallString
        MAX-ACCESS        read-only
        STATUS            current
        DESCRIPTION
                "CMNT: - Logging state for Output Emb.Pair 5 type
                 TYPE: - Display
                 PAGE: - Logging
                    Out Emb.5 type=  cmdID= 36934  "
        ::= { iqsyn22CmdEntry 36934 }


    iqsyn22LoggingOPAudTypeLogOutEmb6type OBJECT-TYPE
        SYNTAX            INTEGER { disable(0), enable(1)  }
        MAX-ACCESS        read-write
        STATUS            current
        DESCRIPTION
                "CMNT: - Enable/Disable logging for Output Emb.Pair 6 type
                 TYPE: - Checkbox
                 PAGE: - Logging
                    Log Out Emb.6 type  cmdID= 35935  "
        ::= { iqsyn22CmdEntry 35935 }


    iqsyn22LoggingOPAudTypeOutEmb6type OBJECT-TYPE
        SYNTAX            RollCallString
        MAX-ACCESS        read-only
        STATUS            current
        DESCRIPTION
                "CMNT: - Logging state for Output Emb.Pair 6 type
                 TYPE: - Display
                 PAGE: - Logging
                    Out Emb.6 type=  cmdID= 36935  "
        ::= { iqsyn22CmdEntry 36935 }


    iqsyn22LoggingOPAudTypeLogOutEmb7type OBJECT-TYPE
        SYNTAX            INTEGER { disable(0), enable(1)  }
        MAX-ACCESS        read-write
        STATUS            current
        DESCRIPTION
                "CMNT: - Enable/Disable logging for Output Emb.Pair 7 type
                 TYPE: - Checkbox
                 PAGE: - Logging
                    Log Out Emb.7 type  cmdID= 35936  "
        ::= { iqsyn22CmdEntry 35936 }


    iqsyn22LoggingOPAudTypeOutEmb7type OBJECT-TYPE
        SYNTAX            RollCallString
        MAX-ACCESS        read-only
        STATUS            current
        DESCRIPTION
                "CMNT: - Logging state for Output Emb.Pair 7 type
                 TYPE: - Display
                 PAGE: - Logging
                    Out Emb.7 type=  cmdID= 36936  "
        ::= { iqsyn22CmdEntry 36936 }


    iqsyn22LoggingOPAudTypeLogOutEmb8type OBJECT-TYPE
        SYNTAX            INTEGER { disable(0), enable(1)  }
        MAX-ACCESS        read-write
        STATUS            current
        DESCRIPTION
                "CMNT: - Enable/Disable logging for Output Emb.Pair 8 type
                 TYPE: - Checkbox
                 PAGE: - Logging
                    Log Out Emb.8 type  cmdID= 35937  "
        ::= { iqsyn22CmdEntry 35937 }


    iqsyn22LoggingOPAudTypeOutEmb8type OBJECT-TYPE
        SYNTAX            RollCallString
        MAX-ACCESS        read-only
        STATUS            current
        DESCRIPTION
                "CMNT: - Logging state for Output Emb.Pair 8 type
                 TYPE: - Display
                 PAGE: - Logging
                    Out Emb.8 type=  cmdID= 36937  "
        ::= { iqsyn22CmdEntry 36937 }


    iqsyn22LoggingOPAudLevelLogOutEmb1LLev OBJECT-TYPE
        SYNTAX            INTEGER { disable(0), enable(1)  }
        MAX-ACCESS        read-write
        STATUS            current
        DESCRIPTION
                "CMNT: - Enable/Disable logging for Output Emb.Audio 1-L Level
                 TYPE: - Checkbox
                 PAGE: - Logging
                    Log Out Emb.1-L Level  cmdID= 35900  "
        ::= { iqsyn22CmdEntry 35900 }


    iqsyn22LoggingOPAudLevelOutEmb1LLevel OBJECT-TYPE
        SYNTAX            RollCallString
        MAX-ACCESS        read-only
        STATUS            current
        DESCRIPTION
                "CMNT: - Logging state for Output Emb.Audio 1-L Level
                 TYPE: - Display
                 PAGE: - Logging
                    Out Emb.1-L Level=  cmdID= 36900  "
        ::= { iqsyn22CmdEntry 36900 }


    iqsyn22LoggingOPAudLevelLogOutEmb1RLev OBJECT-TYPE
        SYNTAX            INTEGER { disable(0), enable(1)  }
        MAX-ACCESS        read-write
        STATUS            current
        DESCRIPTION
                "CMNT: - Enable/Disable logging for Output Emb.Audio 1-R Level
                 TYPE: - Checkbox
                 PAGE: - Logging
                    Log Out Emb.1-R Level  cmdID= 35901  "
        ::= { iqsyn22CmdEntry 35901 }


    iqsyn22LoggingOPAudLevelOutEmb1RLevel OBJECT-TYPE
        SYNTAX            RollCallString
        MAX-ACCESS        read-only
        STATUS            current
        DESCRIPTION
                "CMNT: - Logging state for Output Emb.Audio 1-R Level
                 TYPE: - Display
                 PAGE: - Logging
                    Out Emb.1-R Level=  cmdID= 36901  "
        ::= { iqsyn22CmdEntry 36901 }


    iqsyn22LoggingOPAudLevelLogOutEmb2LLev OBJECT-TYPE
        SYNTAX            INTEGER { disable(0), enable(1)  }
        MAX-ACCESS        read-write
        STATUS            current
        DESCRIPTION
                "CMNT: - Enable/Disable logging for Output Emb.Audio 2-L Level
                 TYPE: - Checkbox
                 PAGE: - Logging
                    Log Out Emb.2-L Level  cmdID= 35902  "
        ::= { iqsyn22CmdEntry 35902 }


    iqsyn22LoggingOPAudLevelOutEmb2LLevel OBJECT-TYPE
        SYNTAX            RollCallString
        MAX-ACCESS        read-only
        STATUS            current
        DESCRIPTION
                "CMNT: - Logging state for Output Emb.Audio 2-L Level
                 TYPE: - Display
                 PAGE: - Logging
                    Out Emb.2-L Level=  cmdID= 36902  "
        ::= { iqsyn22CmdEntry 36902 }


    iqsyn22LoggingOPAudLevelLogOutEmb2RLev OBJECT-TYPE
        SYNTAX            INTEGER { disable(0), enable(1)  }
        MAX-ACCESS        read-write
        STATUS            current
        DESCRIPTION
                "CMNT: - Enable/Disable logging for Output Emb.Audio 2-R Level
                 TYPE: - Checkbox
                 PAGE: - Logging
                    Log Out Emb.2-R Level  cmdID= 35903  "
        ::= { iqsyn22CmdEntry 35903 }


    iqsyn22LoggingOPAudLevelOutEmb2RLevel OBJECT-TYPE
        SYNTAX            RollCallString
        MAX-ACCESS        read-only
        STATUS            current
        DESCRIPTION
                "CMNT: - Logging state for Output Emb.Audio 2-R Level
                 TYPE: - Display
                 PAGE: - Logging
                    Out Emb.2-R Level=  cmdID= 36903  "
        ::= { iqsyn22CmdEntry 36903 }


    iqsyn22LoggingOPAudLevelLogOutEmb3LLev OBJECT-TYPE
        SYNTAX            INTEGER { disable(0), enable(1)  }
        MAX-ACCESS        read-write
        STATUS            current
        DESCRIPTION
                "CMNT: - Enable/Disable logging for Output Emb.Audio 3-L Level
                 TYPE: - Checkbox
                 PAGE: - Logging
                    Log Out Emb.3-L Level  cmdID= 35904  "
        ::= { iqsyn22CmdEntry 35904 }


    iqsyn22LoggingOPAudLevelOutEmb3LLevel OBJECT-TYPE
        SYNTAX            RollCallString
        MAX-ACCESS        read-only
        STATUS            current
        DESCRIPTION
                "CMNT: - Logging state for Output Emb.Audio 3-L Level
                 TYPE: - Display
                 PAGE: - Logging
                    Out Emb.3-L Level=  cmdID= 36904  "
        ::= { iqsyn22CmdEntry 36904 }


    iqsyn22LoggingOPAudLevelLogOutEmb3RLev OBJECT-TYPE
        SYNTAX            INTEGER { disable(0), enable(1)  }
        MAX-ACCESS        read-write
        STATUS            current
        DESCRIPTION
                "CMNT: - Enable/Disable logging for Output Emb.Audio 3-R Level
                 TYPE: - Checkbox
                 PAGE: - Logging
                    Log Out Emb.3-R Level  cmdID= 35905  "
        ::= { iqsyn22CmdEntry 35905 }


    iqsyn22LoggingOPAudLevelOutEmb3RLevel OBJECT-TYPE
        SYNTAX            RollCallString
        MAX-ACCESS        read-only
        STATUS            current
        DESCRIPTION
                "CMNT: - Logging state for Output Emb.Audio 3-R Level
                 TYPE: - Display
                 PAGE: - Logging
                    Out Emb.3-R Level=  cmdID= 36905  "
        ::= { iqsyn22CmdEntry 36905 }


    iqsyn22LoggingOPAudLevelLogOutEmb4LLev OBJECT-TYPE
        SYNTAX            INTEGER { disable(0), enable(1)  }
        MAX-ACCESS        read-write
        STATUS            current
        DESCRIPTION
                "CMNT: - Enable/Disable logging for Output Emb.Audio 4-L Level
                 TYPE: - Checkbox
                 PAGE: - Logging
                    Log Out Emb.4-L Level  cmdID= 35906  "
        ::= { iqsyn22CmdEntry 35906 }


    iqsyn22LoggingOPAudLevelOutEmb4LLevel OBJECT-TYPE
        SYNTAX            RollCallString
        MAX-ACCESS        read-only
        STATUS            current
        DESCRIPTION
                "CMNT: - Logging state for Output Emb.Audio 4-L Level
                 TYPE: - Display
                 PAGE: - Logging
                    Out Emb.4-L Level=  cmdID= 36906  "
        ::= { iqsyn22CmdEntry 36906 }


    iqsyn22LoggingOPAudLevelLogOutEmb4RLev OBJECT-TYPE
        SYNTAX            INTEGER { disable(0), enable(1)  }
        MAX-ACCESS        read-write
        STATUS            current
        DESCRIPTION
                "CMNT: - Enable/Disable logging for Output Emb.Audio 4-R Level
                 TYPE: - Checkbox
                 PAGE: - Logging
                    Log Out Emb.4-R Level  cmdID= 35907  "
        ::= { iqsyn22CmdEntry 35907 }


    iqsyn22LoggingOPAudLevelOutEmb4RLevel OBJECT-TYPE
        SYNTAX            RollCallString
        MAX-ACCESS        read-only
        STATUS            current
        DESCRIPTION
                "CMNT: - Logging state for Output Emb.Audio 4-R Level
                 TYPE: - Display
                 PAGE: - Logging
                    Out Emb.4-R Level=  cmdID= 36907  "
        ::= { iqsyn22CmdEntry 36907 }


    iqsyn22LoggingOPAudLevelLogOutEmb5LLev OBJECT-TYPE
        SYNTAX            INTEGER { disable(0), enable(1)  }
        MAX-ACCESS        read-write
        STATUS            current
        DESCRIPTION
                "CMNT: - Enable/Disable logging for Output Emb.Audio 5-L Level
                 TYPE: - Checkbox
                 PAGE: - Logging
                    Log Out Emb.5-L Level  cmdID= 35908  "
        ::= { iqsyn22CmdEntry 35908 }


    iqsyn22LoggingOPAudLevelOutEmb5LLevel OBJECT-TYPE
        SYNTAX            RollCallString
        MAX-ACCESS        read-only
        STATUS            current
        DESCRIPTION
                "CMNT: - Logging state for Output Emb.Audio 5-L Level
                 TYPE: - Display
                 PAGE: - Logging
                    Out Emb.5-L Level=  cmdID= 36908  "
        ::= { iqsyn22CmdEntry 36908 }


    iqsyn22LoggingOPAudLevelLogOutEmb5RLev OBJECT-TYPE
        SYNTAX            INTEGER { disable(0), enable(1)  }
        MAX-ACCESS        read-write
        STATUS            current
        DESCRIPTION
                "CMNT: - Enable/Disable logging for Output Emb.Audio 5-R Level
                 TYPE: - Checkbox
                 PAGE: - Logging
                    Log Out Emb.5-R Level  cmdID= 35909  "
        ::= { iqsyn22CmdEntry 35909 }


    iqsyn22LoggingOPAudLevelOutEmb5RLevel OBJECT-TYPE
        SYNTAX            RollCallString
        MAX-ACCESS        read-only
        STATUS            current
        DESCRIPTION
                "CMNT: - Logging state for Output Emb.Audio 5-R Level
                 TYPE: - Display
                 PAGE: - Logging
                    Out Emb.5-R Level=  cmdID= 36909  "
        ::= { iqsyn22CmdEntry 36909 }


    iqsyn22LoggingOPAudLevelLogOutEmb6LLev OBJECT-TYPE
        SYNTAX            INTEGER { disable(0), enable(1)  }
        MAX-ACCESS        read-write
        STATUS            current
        DESCRIPTION
                "CMNT: - Enable/Disable logging for Output Emb.Audio 6-L Level
                 TYPE: - Checkbox
                 PAGE: - Logging
                    Log Out Emb.6-L Level  cmdID= 35910  "
        ::= { iqsyn22CmdEntry 35910 }


    iqsyn22LoggingOPAudLevelOutEmb6LLevel OBJECT-TYPE
        SYNTAX            RollCallString
        MAX-ACCESS        read-only
        STATUS            current
        DESCRIPTION
                "CMNT: - Logging state for Output Emb.Audio 6-L Level
                 TYPE: - Display
                 PAGE: - Logging
                    Out Emb.6-L Level=  cmdID= 36910  "
        ::= { iqsyn22CmdEntry 36910 }


    iqsyn22LoggingOPAudLevelLogOutEmb6RLev OBJECT-TYPE
        SYNTAX            INTEGER { disable(0), enable(1)  }
        MAX-ACCESS        read-write
        STATUS            current
        DESCRIPTION
                "CMNT: - Enable/Disable logging for Output Emb.Audio 6-R Level
                 TYPE: - Checkbox
                 PAGE: - Logging
                    Log Out Emb.6-R Level  cmdID= 35911  "
        ::= { iqsyn22CmdEntry 35911 }


    iqsyn22LoggingOPAudLevelOutEmb6RLevel OBJECT-TYPE
        SYNTAX            RollCallString
        MAX-ACCESS        read-only
        STATUS            current
        DESCRIPTION
                "CMNT: - Logging state for Output Emb.Audio 6-R Level
                 TYPE: - Display
                 PAGE: - Logging
                    Out Emb.6-R Level=  cmdID= 36911  "
        ::= { iqsyn22CmdEntry 36911 }


    iqsyn22LoggingOPAudLevelLogOutEmb7LLev OBJECT-TYPE
        SYNTAX            INTEGER { disable(0), enable(1)  }
        MAX-ACCESS        read-write
        STATUS            current
        DESCRIPTION
                "CMNT: - Enable/Disable logging for Output Emb.Audio 7-L Level
                 TYPE: - Checkbox
                 PAGE: - Logging
                    Log Out Emb.7-L Level  cmdID= 35912  "
        ::= { iqsyn22CmdEntry 35912 }


    iqsyn22LoggingOPAudLevelOutEmb7LLevel OBJECT-TYPE
        SYNTAX            RollCallString
        MAX-ACCESS        read-only
        STATUS            current
        DESCRIPTION
                "CMNT: - Logging state for Output Emb.Audio 7-L Level
                 TYPE: - Display
                 PAGE: - Logging
                    Out Emb.7-L Level=  cmdID= 36912  "
        ::= { iqsyn22CmdEntry 36912 }


    iqsyn22LoggingOPAudLevelLogOutEmb7RLev OBJECT-TYPE
        SYNTAX            INTEGER { disable(0), enable(1)  }
        MAX-ACCESS        read-write
        STATUS            current
        DESCRIPTION
                "CMNT: - Enable/Disable logging for Output Emb.Audio 7-R Level
                 TYPE: - Checkbox
                 PAGE: - Logging
                    Log Out Emb.7-R Level  cmdID= 35913  "
        ::= { iqsyn22CmdEntry 35913 }


    iqsyn22LoggingOPAudLevelOutEmb7RLevel OBJECT-TYPE
        SYNTAX            RollCallString
        MAX-ACCESS        read-only
        STATUS            current
        DESCRIPTION
                "CMNT: - Logging state for Output Emb.Audio 7-R Level
                 TYPE: - Display
                 PAGE: - Logging
                    Out Emb.7-R Level=  cmdID= 36913  "
        ::= { iqsyn22CmdEntry 36913 }


    iqsyn22LoggingOPAudLevelLogOutEmb8LLev OBJECT-TYPE
        SYNTAX            INTEGER { disable(0), enable(1)  }
        MAX-ACCESS        read-write
        STATUS            current
        DESCRIPTION
                "CMNT: - Enable/Disable logging for Output Emb.Audio 8-L Level
                 TYPE: - Checkbox
                 PAGE: - Logging
                    Log Out Emb.8-L Level  cmdID= 35914  "
        ::= { iqsyn22CmdEntry 35914 }


    iqsyn22LoggingOPAudLevelOutEmb8LLevel OBJECT-TYPE
        SYNTAX            RollCallString
        MAX-ACCESS        read-only
        STATUS            current
        DESCRIPTION
                "CMNT: - Logging state for Output Emb.Audio 8-L Level
                 TYPE: - Display
                 PAGE: - Logging
                    Out Emb.8-L Level=  cmdID= 36914  "
        ::= { iqsyn22CmdEntry 36914 }


    iqsyn22LoggingOPAudLevelLogOutEmb8RLev OBJECT-TYPE
        SYNTAX            INTEGER { disable(0), enable(1)  }
        MAX-ACCESS        read-write
        STATUS            current
        DESCRIPTION
                "CMNT: - Enable/Disable logging for Output Emb.Audio 8-R Level
                 TYPE: - Checkbox
                 PAGE: - Logging
                    Log Out Emb.8-R Level  cmdID= 35915  "
        ::= { iqsyn22CmdEntry 35915 }


    iqsyn22LoggingOPAudLevelOutEmb8RLevel OBJECT-TYPE
        SYNTAX            RollCallString
        MAX-ACCESS        read-only
        STATUS            current
        DESCRIPTION
                "CMNT: - Logging state for Output Emb.Audio 8-R Level
                 TYPE: - Display
                 PAGE: - Logging
                    Out Emb.8-R Level=  cmdID= 36915  "
        ::= { iqsyn22CmdEntry 36915 }


    iqsyn22LoggingOPDolbyELoggingLogEmbDolbyE1 OBJECT-TYPE
        SYNTAX            INTEGER { disable(0), enable(1)  }
        MAX-ACCESS        read-write
        STATUS            current
        DESCRIPTION
                "CMNT: - Enable/Disable logging for Emb DolbyE 1
                 TYPE: - Checkbox
                 PAGE: - Logging
                    Log Emb DolbyE 1  cmdID= 35950  "
        ::= { iqsyn22CmdEntry 35950 }


    iqsyn22LoggingOPDolbyELoggingEmbDolbyE1 OBJECT-TYPE
        SYNTAX            RollCallString
        MAX-ACCESS        read-only
        STATUS            current
        DESCRIPTION
                "CMNT: - Logging state for Emb DolbyE 1
                 TYPE: - Display
                 PAGE: - Logging
                    Emb DolbyE 1=  cmdID= 36950  "
        ::= { iqsyn22CmdEntry 36950 }


    iqsyn22LoggingOPDolbyELoggingLogEmbDolbyE2 OBJECT-TYPE
        SYNTAX            INTEGER { disable(0), enable(1)  }
        MAX-ACCESS        read-write
        STATUS            current
        DESCRIPTION
                "CMNT: - Enable/Disable logging for Emb DolbyE 2
                 TYPE: - Checkbox
                 PAGE: - Logging
                    Log Emb DolbyE 2  cmdID= 35951  "
        ::= { iqsyn22CmdEntry 35951 }


    iqsyn22LoggingOPDolbyELoggingEmbDolbyE2 OBJECT-TYPE
        SYNTAX            RollCallString
        MAX-ACCESS        read-only
        STATUS            current
        DESCRIPTION
                "CMNT: - Logging state for Emb DolbyE 2
                 TYPE: - Display
                 PAGE: - Logging
                    Emb DolbyE 2=  cmdID= 36951  "
        ::= { iqsyn22CmdEntry 36951 }


    iqsyn22LoggingOPDolbyELoggingLogEmbDolbyE3 OBJECT-TYPE
        SYNTAX            INTEGER { disable(0), enable(1)  }
        MAX-ACCESS        read-write
        STATUS            current
        DESCRIPTION
                "CMNT: - Enable/Disable logging for Emb DolbyE 3
                 TYPE: - Checkbox
                 PAGE: - Logging
                    Log Emb DolbyE 3  cmdID= 35952  "
        ::= { iqsyn22CmdEntry 35952 }


    iqsyn22LoggingOPDolbyELoggingEmbDolbyE3 OBJECT-TYPE
        SYNTAX            RollCallString
        MAX-ACCESS        read-only
        STATUS            current
        DESCRIPTION
                "CMNT: - Logging state for Emb DolbyE 3
                 TYPE: - Display
                 PAGE: - Logging
                    Emb DolbyE 3=  cmdID= 36952  "
        ::= { iqsyn22CmdEntry 36952 }


    iqsyn22LoggingOPDolbyELoggingLogEmbDolbyE4 OBJECT-TYPE
        SYNTAX            INTEGER { disable(0), enable(1)  }
        MAX-ACCESS        read-write
        STATUS            current
        DESCRIPTION
                "CMNT: - Enable/Disable logging for Emb DolbyE 4
                 TYPE: - Checkbox
                 PAGE: - Logging
                    Log Emb DolbyE 4  cmdID= 35953  "
        ::= { iqsyn22CmdEntry 35953 }


    iqsyn22LoggingOPDolbyELoggingEmbDolbyE4 OBJECT-TYPE
        SYNTAX            RollCallString
        MAX-ACCESS        read-only
        STATUS            current
        DESCRIPTION
                "CMNT: - Logging state for Emb DolbyE 4
                 TYPE: - Display
                 PAGE: - Logging
                    Emb DolbyE 4=  cmdID= 36953  "
        ::= { iqsyn22CmdEntry 36953 }


    iqsyn22LoggingOPDolbyELoggingLogEmbDolbyE5 OBJECT-TYPE
        SYNTAX            INTEGER { disable(0), enable(1)  }
        MAX-ACCESS        read-write
        STATUS            current
        DESCRIPTION
                "CMNT: - Enable/Disable logging for Emb DolbyE 5
                 TYPE: - Checkbox
                 PAGE: - Logging
                    Log Emb DolbyE 5  cmdID= 35954  "
        ::= { iqsyn22CmdEntry 35954 }


    iqsyn22LoggingOPDolbyELoggingEmbDolbyE5 OBJECT-TYPE
        SYNTAX            RollCallString
        MAX-ACCESS        read-only
        STATUS            current
        DESCRIPTION
                "CMNT: - Logging state for Emb DolbyE 5
                 TYPE: - Display
                 PAGE: - Logging
                    Emb DolbyE 5=  cmdID= 36954  "
        ::= { iqsyn22CmdEntry 36954 }


    iqsyn22LoggingOPDolbyELoggingLogEmbDolbyE6 OBJECT-TYPE
        SYNTAX            INTEGER { disable(0), enable(1)  }
        MAX-ACCESS        read-write
        STATUS            current
        DESCRIPTION
                "CMNT: - Enable/Disable logging for Emb DolbyE 6
                 TYPE: - Checkbox
                 PAGE: - Logging
                    Log Emb DolbyE 6  cmdID= 35955  "
        ::= { iqsyn22CmdEntry 35955 }


    iqsyn22LoggingOPDolbyELoggingEmbDolbyE6 OBJECT-TYPE
        SYNTAX            RollCallString
        MAX-ACCESS        read-only
        STATUS            current
        DESCRIPTION
                "CMNT: - Logging state for Emb DolbyE 6
                 TYPE: - Display
                 PAGE: - Logging
                    Emb DolbyE 6=  cmdID= 36955  "
        ::= { iqsyn22CmdEntry 36955 }


    iqsyn22LoggingOPDolbyELoggingLogEmbDolbyE7 OBJECT-TYPE
        SYNTAX            INTEGER { disable(0), enable(1)  }
        MAX-ACCESS        read-write
        STATUS            current
        DESCRIPTION
                "CMNT: - Enable/Disable logging for Emb DolbyE 7
                 TYPE: - Checkbox
                 PAGE: - Logging
                    Log Emb DolbyE 7  cmdID= 35956  "
        ::= { iqsyn22CmdEntry 35956 }


    iqsyn22LoggingOPDolbyELoggingEmbDolbyE7 OBJECT-TYPE
        SYNTAX            RollCallString
        MAX-ACCESS        read-only
        STATUS            current
        DESCRIPTION
                "CMNT: - Logging state for Emb DolbyE 7
                 TYPE: - Display
                 PAGE: - Logging
                    Emb DolbyE 7=  cmdID= 36956  "
        ::= { iqsyn22CmdEntry 36956 }


    iqsyn22LoggingOPDolbyELoggingLogEmbDolbyE8 OBJECT-TYPE
        SYNTAX            INTEGER { disable(0), enable(1)  }
        MAX-ACCESS        read-write
        STATUS            current
        DESCRIPTION
                "CMNT: - Enable/Disable logging for Emb DolbyE 8
                 TYPE: - Checkbox
                 PAGE: - Logging
                    Log Emb DolbyE 8  cmdID= 35957  "
        ::= { iqsyn22CmdEntry 35957 }


    iqsyn22LoggingOPDolbyELoggingEmbDolbyE8 OBJECT-TYPE
        SYNTAX            RollCallString
        MAX-ACCESS        read-only
        STATUS            current
        DESCRIPTION
                "CMNT: - Logging state for Emb DolbyE 8
                 TYPE: - Display
                 PAGE: - Logging
                    Emb DolbyE 8=  cmdID= 36957  "
        ::= { iqsyn22CmdEntry 36957 }


    iqsyn22LoggingWideScreenLoggingLogInput1Aspect OBJECT-TYPE
        SYNTAX            INTEGER { disable(0), enable(1)  }
        MAX-ACCESS        read-write
        STATUS            current
        DESCRIPTION
                "CMNT: - Enable/Disable logging for Input 1 Aspect
                 TYPE: - Checkbox
                 PAGE: - Logging
                    Log Input 1 Aspect  cmdID= 35026  "
        ::= { iqsyn22CmdEntry 35026 }


    iqsyn22LoggingWideScreenLoggingInput1Aspect OBJECT-TYPE
        SYNTAX            RollCallString
        MAX-ACCESS        read-only
        STATUS            current
        DESCRIPTION
                "CMNT: - 
                 TYPE: - Display
                 PAGE: - Logging
                    Input 1 Aspect=  cmdID= 36026  "
        ::= { iqsyn22CmdEntry 36026 }


    iqsyn22LoggingWideScreenLoggingLogInput1AFD OBJECT-TYPE
        SYNTAX            INTEGER { disable(0), enable(1)  }
        MAX-ACCESS        read-write
        STATUS            current
        DESCRIPTION
                "CMNT: - Enable/Disable logging for Input 1 AFD
                 TYPE: - Checkbox
                 PAGE: - Logging
                    Log Input 1 AFD  cmdID= 35027  "
        ::= { iqsyn22CmdEntry 35027 }


    iqsyn22LoggingWideScreenLoggingInput1AFD OBJECT-TYPE
        SYNTAX            RollCallString
        MAX-ACCESS        read-only
        STATUS            current
        DESCRIPTION
                "CMNT: - 
                 TYPE: - Display
                 PAGE: - Logging
                    Input 1 AFD=  cmdID= 36027  "
        ::= { iqsyn22CmdEntry 36027 }


    iqsyn22LoggingWideScreenLoggingLogInput2Aspect OBJECT-TYPE
        SYNTAX            INTEGER { disable(0), enable(1)  }
        MAX-ACCESS        read-write
        STATUS            current
        DESCRIPTION
                "CMNT: - 
                 TYPE: - Checkbox
                 PAGE: - Logging
                    Log Input 2 Aspect  cmdID= 35056  "
        ::= { iqsyn22CmdEntry 35056 }


    iqsyn22LoggingWideScreenLoggingInput2Aspect OBJECT-TYPE
        SYNTAX            RollCallString
        MAX-ACCESS        read-only
        STATUS            current
        DESCRIPTION
                "CMNT: - 
                 TYPE: - Display
                 PAGE: - Logging
                    Input 2 Aspect=  cmdID= 36056  "
        ::= { iqsyn22CmdEntry 36056 }


    iqsyn22LoggingWideScreenLoggingLogInput2AFD OBJECT-TYPE
        SYNTAX            INTEGER { disable(0), enable(1)  }
        MAX-ACCESS        read-write
        STATUS            current
        DESCRIPTION
                "CMNT: - 
                 TYPE: - Checkbox
                 PAGE: - Logging
                    Log Input 2 AFD  cmdID= 35057  "
        ::= { iqsyn22CmdEntry 35057 }


    iqsyn22LoggingWideScreenLoggingInput2AFD OBJECT-TYPE
        SYNTAX            RollCallString
        MAX-ACCESS        read-only
        STATUS            current
        DESCRIPTION
                "CMNT: - 
                 TYPE: - Display
                 PAGE: - Logging
                    Input 2 AFD=  cmdID= 36057  "
        ::= { iqsyn22CmdEntry 36057 }


    iqsyn22LoggingWideScreenLoggingLogOutputAFDEnable OBJECT-TYPE
        SYNTAX            INTEGER { disable(0), enable(1)  }
        MAX-ACCESS        read-write
        STATUS            current
        DESCRIPTION
                "CMNT: - 
                 TYPE: - Checkbox
                 PAGE: - Logging
                    Log Output AFD35944  cmdID= 35944  "
        ::= { iqsyn22CmdEntry 35944 }


    iqsyn22LoggingWideScreenLoggingOutputAFD OBJECT-TYPE
        SYNTAX            RollCallString
        MAX-ACCESS        read-only
        STATUS            current
        DESCRIPTION
                "CMNT: - 
                 TYPE: - Display
                 PAGE: - Logging
                    Output AFD=36944  cmdID= 36944  "
        ::= { iqsyn22CmdEntry 36944 }


    iqsyn22LoggingWideScreenLoggingLogOutputAFDEnable OBJECT-TYPE
        SYNTAX            INTEGER { disable(0), enable(1)  }
        MAX-ACCESS        read-write
        STATUS            current
        DESCRIPTION
                "CMNT: - 
                 TYPE: - Checkbox
                 PAGE: - Logging
                    Log Output AFD35945  cmdID= 35945  "
        ::= { iqsyn22CmdEntry 35945 }


    iqsyn22LoggingWideScreenLoggingOutputAFD OBJECT-TYPE
        SYNTAX            RollCallString
        MAX-ACCESS        read-only
        STATUS            current
        DESCRIPTION
                "CMNT: - 
                 TYPE: - Display
                 PAGE: - Logging
                    Output AFD=36945  cmdID= 36945  "
        ::= { iqsyn22CmdEntry 36945 }


    iqsyn22LoggingMiscLogSerialNo OBJECT-TYPE
        SYNTAX            INTEGER { disable(0), enable(1)  }
        MAX-ACCESS        read-write
        STATUS            current
        DESCRIPTION
                "CMNT: - Enable/Disable logging for Serial No.
                 TYPE: - Checkbox
                 PAGE: - Logging
                    Log Serial No.  cmdID= 35015  "
        ::= { iqsyn22CmdEntry 35015 }


    iqsyn22LoggingMiscSerialNo OBJECT-TYPE
        SYNTAX            RollCallString
        MAX-ACCESS        read-only
        STATUS            current
        DESCRIPTION
                "CMNT: - Logging state for Serial No.
                 TYPE: - Display
                 PAGE: - Logging
                    Serial No.=  cmdID= 36015  "
        ::= { iqsyn22CmdEntry 36015 }


    iqsyn22LoggingMiscLogOSVersion OBJECT-TYPE
        SYNTAX            INTEGER { disable(0), enable(1)  }
        MAX-ACCESS        read-write
        STATUS            current
        DESCRIPTION
                "CMNT: - Enable/Disable logging for OS Version
                 TYPE: - Checkbox
                 PAGE: - Logging
                    Log OS Version  cmdID= 35993  "
        ::= { iqsyn22CmdEntry 35993 }


    iqsyn22LoggingMiscOSVersion OBJECT-TYPE
        SYNTAX            RollCallString
        MAX-ACCESS        read-only
        STATUS            current
        DESCRIPTION
                "CMNT: - Logging state for OS Version
                 TYPE: - Display
                 PAGE: - Logging
                    OS Version=  cmdID= 36993  "
        ::= { iqsyn22CmdEntry 36993 }


    iqsyn22LoggingMiscLogBuildNo OBJECT-TYPE
        SYNTAX            INTEGER { disable(0), enable(1)  }
        MAX-ACCESS        read-write
        STATUS            current
        DESCRIPTION
                "CMNT: - Enable/Disable logging for Build No.
                 TYPE: - Checkbox
                 PAGE: - Logging
                    Log Build No.  cmdID= 35990  "
        ::= { iqsyn22CmdEntry 35990 }


    iqsyn22LoggingMiscBuildNo OBJECT-TYPE
        SYNTAX            RollCallString
        MAX-ACCESS        read-only
        STATUS            current
        DESCRIPTION
                "CMNT: - Logging state for Build No.
                 TYPE: - Display
                 PAGE: - Logging
                    Build No.=  cmdID= 36990  "
        ::= { iqsyn22CmdEntry 36990 }


    iqsyn22LoggingMiscLogHardwareVer OBJECT-TYPE
        SYNTAX            INTEGER { disable(0), enable(1)  }
        MAX-ACCESS        read-write
        STATUS            current
        DESCRIPTION
                "CMNT: - Enable/Disable logging for Hardware Ver.
                 TYPE: - Checkbox
                 PAGE: - Logging
                    Log Hardware Ver.  cmdID= 35992  "
        ::= { iqsyn22CmdEntry 35992 }


    iqsyn22LoggingMiscHardwareVer OBJECT-TYPE
        SYNTAX            RollCallString
        MAX-ACCESS        read-only
        STATUS            current
        DESCRIPTION
                "CMNT: - Logging state for Hardware Ver.
                 TYPE: - Display
                 PAGE: - Logging
                    Hardware Ver.=  cmdID= 36992  "
        ::= { iqsyn22CmdEntry 36992 }


    iqsyn22LoggingMiscLogFirmwareVer OBJECT-TYPE
        SYNTAX            INTEGER { disable(0), enable(1)  }
        MAX-ACCESS        read-write
        STATUS            current
        DESCRIPTION
                "CMNT: - Enable/Disable logging for Firmware Ver.
                 TYPE: - Checkbox
                 PAGE: - Logging
                    Log Firmware Ver.  cmdID= 35991  "
        ::= { iqsyn22CmdEntry 35991 }


    iqsyn22LoggingMiscFirmwareVer OBJECT-TYPE
        SYNTAX            RollCallString
        MAX-ACCESS        read-only
        STATUS            current
        DESCRIPTION
                "CMNT: - Logging state for Firmware Ver.
                 TYPE: - Display
                 PAGE: - Logging
                    Firmware Ver.=  cmdID= 36991  "
        ::= { iqsyn22CmdEntry 36991 }


    iqsyn22LoggingMiscLogUpTime OBJECT-TYPE
        SYNTAX            INTEGER { disable(0), enable(1)  }
        MAX-ACCESS        read-write
        STATUS            current
        DESCRIPTION
                "CMNT: - Enable/Disable logging for Up Time
                 TYPE: - Checkbox
                 PAGE: - Logging
                    Log Up Time  cmdID= 35994  "
        ::= { iqsyn22CmdEntry 35994 }


    iqsyn22LoggingMiscUpTime OBJECT-TYPE
        SYNTAX            RollCallString
        MAX-ACCESS        read-only
        STATUS            current
        DESCRIPTION
                "CMNT: - Logging state for Up Time
                 TYPE: - Display
                 PAGE: - Logging
                    Up Time=  cmdID= 36994  "
        ::= { iqsyn22CmdEntry 36994 }


    iqsyn22LoggingRefOutputLogReferenceType OBJECT-TYPE
        SYNTAX            INTEGER { disable(0), enable(1)  }
        MAX-ACCESS        read-write
        STATUS            current
        DESCRIPTION
                "CMNT: - Enable/Disable logging for Reference Type
                 TYPE: - Checkbox
                 PAGE: - Logging
                    Log Reference Type  cmdID= 35995  "
        ::= { iqsyn22CmdEntry 35995 }


    iqsyn22LoggingRefOutputReferenceType OBJECT-TYPE
        SYNTAX            RollCallString
        MAX-ACCESS        read-only
        STATUS            current
        DESCRIPTION
                "CMNT: - Logging state for Reference Type
                 TYPE: - Display
                 PAGE: - Logging
                    Reference Type=  cmdID= 36995  "
        ::= { iqsyn22CmdEntry 36995 }


    iqsyn22LoggingRefOutputLogReferenceState OBJECT-TYPE
        SYNTAX            INTEGER { disable(0), enable(1)  }
        MAX-ACCESS        read-write
        STATUS            current
        DESCRIPTION
                "CMNT: - Enable/Disable logging for Reference State
                 TYPE: - Checkbox
                 PAGE: - Logging
                    Log Reference State  cmdID= 35004  "
        ::= { iqsyn22CmdEntry 35004 }


    iqsyn22LoggingRefOutputReferenceState OBJECT-TYPE
        SYNTAX            RollCallString
        MAX-ACCESS        read-only
        STATUS            current
        DESCRIPTION
                "CMNT: - Logging state for Reference State
                 TYPE: - Display
                 PAGE: - Logging
                    Reference State=  cmdID= 36004  "
        ::= { iqsyn22CmdEntry 36004 }


    iqsyn22LoggingRefOutputLogReferenceStand OBJECT-TYPE
        SYNTAX            INTEGER { disable(0), enable(1)  }
        MAX-ACCESS        read-write
        STATUS            current
        DESCRIPTION
                "CMNT: - Enable/Disable logging for Reference Standard
                 TYPE: - Checkbox
                 PAGE: - Logging
                    Log Reference Standard  cmdID= 35014  "
        ::= { iqsyn22CmdEntry 35014 }


    iqsyn22LoggingRefOutputReferenceStandard OBJECT-TYPE
        SYNTAX            RollCallString
        MAX-ACCESS        read-only
        STATUS            current
        DESCRIPTION
                "CMNT: - Logging state for Reference Standard
                 TYPE: - Display
                 PAGE: - Logging
                    Reference Standard=  cmdID= 36014  "
        ::= { iqsyn22CmdEntry 36014 }


    iqsyn22RollCallRollTrackDisableAll OBJECT-TYPE
        SYNTAX            INTEGER { disable(0), enable(1)  }
        MAX-ACCESS        read-write
        STATUS            current
        DESCRIPTION
                "CMNT: - Disable all rolltrack outputs
                 TYPE: - Checkbox
                 PAGE: - RollTrack
                    Disable All  cmdID= 36104  "
        ::= { iqsyn22CmdEntry 36104 }


    iqsyn22RollCallRollTrackIndex OBJECT-TYPE
        SYNTAX            INTEGER
        MAX-ACCESS        read-write
        STATUS            current
        DESCRIPTION
                "CMNT: - Select rolltrack to edit
                 TYPE: - BarGraph
                 PAGE: - RollTrack
                    Index  cmdID= 36100
                    min= 1  max= 16  step= 1  format= %0.0f  div_scale= 1  preset= 1
                    Min = 1  Max = 16  Step = 1  Preset = 1  "
        ::= { iqsyn22CmdEntry 36100 }


    iqsyn22RollCallRollTrackSource OBJECT-TYPE
        SYNTAX            INTEGER {
                            valUnused(-1),
                            valVideoDelay(0),
                            valInputPresent(1),
                            valInputLoss(2),
                            valReferenceOK(3),
                            valReferenceLost(4),
                            valOpFreeze(5),
                            valOpUnFreeze(6),
                            valINP1Select(54),
                            valINP2Select(55),
                            valGPI1High(32),
                            valGPI1Low(33),
                            valGPI1InActive(31),
                            valGPI2High(35),
                            valGPI2Low(36),
                            valGPI2InActive(34),
                            valDenembed1Data(7),
                            valDenembed1Pcm(8),
                            valDenembed1Lost(9),
                            valDenembed2Data(10),
                            valDenembed2Pcm(11),
                            valDenembed2Lost(12),
                            valDenembed3Data(13),
                            valDenembed3Pcm(14),
                            valDenembed3Lost(15),
                            valDenembed4Data(16),
                            valDenembed4Pcm(17),
                            valDenembed4Lost(18),
                            valDenembed5Data(19),
                            valDenembed5Pcm(20),
                            valDenembed5Lost(21),
                            valDenembed6Data(22),
                            valDenembed6Pcm(23),
                            valDenembed6Lost(24),
                            valDenembed7Data(25),
                            valDenembed7Pcm(26),
                            valDenembed7Lost(27),
                            valDenembed8Data(28),
                            valDenembed8Pcm(29),
                            valDenembed8Lost(30),
                            valOut1125108030i(37),
                            valOut1125108030p(38),
                            valOut1125108029i(39),
                            valOut1125108029p(40),
                            valOut1125108025i(41),
                            valOut1125108025p(42),
                            valOut1125108024p(43),
                            valOut1125108024sf(44),
                            valOut1125108023p(45),
                            valOut1125108023sf(46),
                            valOut1125103530i(47),
                            valOut1125103529i(48),
                            valOut75072060p(49),
                            valOut75072059p(50),
                            valOut75072050p(51),
                            valOut52548029i(52),
                            valOut62557625i(53)
                            }
        MAX-ACCESS        read-write
        STATUS            current
        DESCRIPTION
                "CMNT: - Source for Rolltrack
                 TYPE: - RadiobuttonList
                 PAGE: - RollTrack
                    Source  cmdID= 36101
                    Unused  value= -1
                    Video Delay  value= 0
                    Input Present  value= 1
                    Input Loss  value= 2
                    Reference OK  value= 3
                    Reference Lost  value= 4
                    O/p Freeze  value= 5
                    O/p UnFreeze  value= 6
                    INP1 Select  value= 54
                    INP2 Select  value= 55
                    GPI 1 High  value= 32
                    GPI 1 Low  value= 33
                    GPI 1 InActive  value= 31
                    GPI 2 High  value= 35
                    GPI 2 Low  value= 36
                    GPI 2 InActive  value= 34
                    De-embed 1 Data  value= 7
                    De-embed 1 Pcm  value= 8
                    De-embed 1 Lost  value= 9
                    De-embed 2 Data  value= 10
                    De-embed 2 Pcm  value= 11
                    De-embed 2 Lost  value= 12
                    De-embed 3 Data  value= 13
                    De-embed 3 Pcm  value= 14
                    De-embed 3 Lost  value= 15
                    De-embed 4 Data  value= 16
                    De-embed 4 Pcm  value= 17
                    De-embed 4 Lost  value= 18
                    De-embed 5 Data  value= 19
                    De-embed 5 Pcm  value= 20
                    De-embed 5 Lost  value= 21
                    De-embed 6 Data  value= 22
                    De-embed 6 Pcm  value= 23
                    De-embed 6 Lost  value= 24
                    De-embed 7 Data  value= 25
                    De-embed 7 Pcm  value= 26
                    De-embed 7 Lost  value= 27
                    De-embed 8 Data  value= 28
                    De-embed 8 Pcm  value= 29
                    De-embed 8 Lost  value= 30
                    Out 1125(1080)/30i  value= 37
                    Out 1125(1080)/30p  value= 38
                    Out 1125(1080)/29i  value= 39
                    Out 1125(1080)/29p  value= 40
                    Out 1125(1080)/25i  value= 41
                    Out 1125(1080)/25p  value= 42
                    Out 1125(1080)/24p  value= 43
                    Out 1125(1080)/24sf  value= 44
                    Out 1125(1080)/23p  value= 45
                    Out 1125(1080)/23sf  value= 46
                    Out 1125(1035)/30i  value= 47
                    Out 1125(1035)/29i  value= 48
                    Out 750(720)/60p  value= 49
                    Out 750(720)/59p  value= 50
                    Out 750(720)/50p  value= 51
                    Out 525(480)/29i  value= 52
                    Out 625(576)/25i  value= 53  "
        ::= { iqsyn22CmdEntry 36101 }


    iqsyn22RollCallRollTrackAddress OBJECT-TYPE
        SYNTAX            RollCallString
        MAX-ACCESS        read-write
        STATUS            current
        DESCRIPTION
                "CMNT: - Unit address for Rolltrack message
                 TYPE: - Editstring
                 PAGE: - RollTrack
                    Address  cmdID= 36102
                    preset= 0000:00:00*0\0*"
        ::= { iqsyn22CmdEntry 36102 }


    iqsyn22RollCallRollTrackCommand OBJECT-TYPE
        SYNTAX            RollCallString
        MAX-ACCESS        read-write
        STATUS            current
        DESCRIPTION
                "CMNT: - Command to send for Rolltrack message
                 TYPE: - Editstring
                 PAGE: - RollTrack
                    Command  cmdID= 36103
                    preset= 000:000\0"
        ::= { iqsyn22CmdEntry 36103 }


    iqsyn22RollCallRollTrackStatus OBJECT-TYPE
        SYNTAX            RollCallString
        MAX-ACCESS        read-only
        STATUS            current
        DESCRIPTION
                "CMNT: - Rolltrack status
                 TYPE: - Display
                 PAGE: - RollTrack
                    Status  cmdID= 36105  "
        ::= { iqsyn22CmdEntry 36105 }


    iqsyn22RollCallRollTrackSending OBJECT-TYPE
        SYNTAX            RollCallString
        MAX-ACCESS        read-only
        STATUS            current
        DESCRIPTION
                "CMNT: - Rolltrack sending status: true/false
                 TYPE: - Display
                 PAGE: - RollTrack
                    Sending  cmdID= 36106  "
        ::= { iqsyn22CmdEntry 36106 }


    iqsyn22SetupProduct OBJECT-TYPE
        SYNTAX            RollCallString
        MAX-ACCESS        read-only
        STATUS            current
        DESCRIPTION
                "CMNT: - 
                 TYPE: - Display
                 PAGE: - Setup
                    Product  cmdID= 32771  "
        ::= { iqsyn22CmdEntry 32771 }


    iqsyn22SetupRelease OBJECT-TYPE
        SYNTAX            RollCallString
        MAX-ACCESS        read-only
        STATUS            current
        DESCRIPTION
                "CMNT: - Unit version number
                 TYPE: - Display
                 PAGE: - Setup
                    Release  cmdID= 2  "
        ::= { iqsyn22CmdEntry 2 }


    iqsyn22SetupBuild OBJECT-TYPE
        SYNTAX            RollCallString
        MAX-ACCESS        read-only
        STATUS            current
        DESCRIPTION
                "CMNT: - Unit build number
                 TYPE: - Display
                 PAGE: - Setup
                    Build  cmdID= 5  "
        ::= { iqsyn22CmdEntry 5 }


    iqsyn22SetupKOS OBJECT-TYPE
        SYNTAX            RollCallString
        MAX-ACCESS        read-only
        STATUS            current
        DESCRIPTION
                "CMNT: - 
                 TYPE: - Display
                 PAGE: - Setup
                    KOS  cmdID= 32772  "
        ::= { iqsyn22CmdEntry 32772 }


    iqsyn22SetupSerial OBJECT-TYPE
        SYNTAX            RollCallString
        MAX-ACCESS        read-only
        STATUS            current
        DESCRIPTION
                "CMNT: - Unit serial number
                 TYPE: - Display
                 PAGE: - Setup
                    Serial No.  cmdID= 1  "
        ::= { iqsyn22CmdEntry 1 }


    iqsyn22SetupFirmware OBJECT-TYPE
        SYNTAX            RollCallString
        MAX-ACCESS        read-only
        STATUS            current
        DESCRIPTION
                "CMNT: - Display firmware version
                 TYPE: - Display
                 PAGE: - Setup
                    Firmware  cmdID= 32769  "
        ::= { iqsyn22CmdEntry 32769 }


    iqsyn22SetupPCB OBJECT-TYPE
        SYNTAX            RollCallString
        MAX-ACCESS        read-only
        STATUS            current
        DESCRIPTION
                "CMNT: - Display PCB revision
                 TYPE: - Display
                 PAGE: - Setup
                    PCB  cmdID= 32770  "
        ::= { iqsyn22CmdEntry 32770 }


    iqsyn22SetupFactoryDefault OBJECT-TYPE
        SYNTAX            INTEGER { noAction(0),valFactoryDefault(1) }
        MAX-ACCESS        read-write
        STATUS            current
        DESCRIPTION
                "CMNT: - Recall factory defaults
                 TYPE: - Button
                 PAGE: - Setup
                    Factory Default  cmdID= 37002
                    value= 1  "
        ::= { iqsyn22CmdEntry 37002 }


    iqsyn22SetupRestart OBJECT-TYPE
        SYNTAX            INTEGER { noAction(0),valRestart(1) }
        MAX-ACCESS        read-write
        STATUS            current
        DESCRIPTION
                "CMNT: - Restart unit
                 TYPE: - Button
                 PAGE: - Setup
                    Restart  cmdID= 4
                    value= 1  "
        ::= { iqsyn22CmdEntry 4 }


    iqsyn22MemoriesMemorySave OBJECT-TYPE
        SYNTAX            INTEGER { noAction(0),valDefaultSettings(1) }
        MAX-ACCESS        read-write
        STATUS            current
        DESCRIPTION
                "CMNT: - Recall factory defaults-KeepMemories
                 TYPE: - Button
                 PAGE: - Setup
                    Default Settings  cmdID= 37001
                    value= 1  "
        ::= { iqsyn22CmdEntry 37001 }


    iqsyn22SetupDisplay OBJECT-TYPE
        SYNTAX            INTEGER {
                            valVideoStatus(0),
                            valAudioStatus(1),
                            valMetadataStatus(2)
                            }
        MAX-ACCESS        read-write
        STATUS            current
        DESCRIPTION
                "CMNT: - Select Info display to show
                 TYPE: - RadiobuttonList
                 PAGE: - Setup
                    Display  cmdID= 32773
                    Video Status  value= 0
                    Audio Status  value= 1
                    Metadata Status  value= 2  "
        ::= { iqsyn22CmdEntry 32773 }


    iqsyn22SetupSerialNumber OBJECT-TYPE
        SYNTAX            RollCallString
        MAX-ACCESS        read-write
        STATUS            current
        DESCRIPTION
                "CMNT: - Edit serial number (On Factory Test Only)
                 TYPE: - Editstring
                 PAGE: - Setup
                    Serial Number  cmdID= 32774
                    preset= unknown"
        ::= { iqsyn22CmdEntry 32774 }


    iqsyn22SetupBoardID OBJECT-TYPE
        SYNTAX            INTEGER {
                            valIQSYN20(344),
                            valIQSYN21(387),
                            valIQSYN22(538)
                            }
        MAX-ACCESS        read-write
        STATUS            current
        DESCRIPTION
                "CMNT: - Edit product type (On Factory Test Only)
                 TYPE: - RadiobuttonList
                 PAGE: - Setup
                    BoardID  cmdID= 32776
                    IQSYN20  value= 344
                    IQSYN21  value= 387
                    IQSYN22  value= 538  "
        ::= { iqsyn22CmdEntry 32776 }


    iqsyn22SetupSaveID OBJECT-TYPE
        SYNTAX            INTEGER { noAction(0),valSaveID(1) }
        MAX-ACCESS        read-write
        STATUS            current
        DESCRIPTION
                "CMNT: - Save serial number/board type (On Factory Test Only)
                 TYPE: - Button
                 PAGE: - Setup
                    Save ID  cmdID= 32775
                    value= 1  "
        ::= { iqsyn22CmdEntry 32775 }


    iqsyn22EngineerPassword OBJECT-TYPE
        SYNTAX            RollCallString
        MAX-ACCESS        read-write
        STATUS            current
        DESCRIPTION
                "CMNT: - 
                 TYPE: - Editstring
                 PAGE: - Engineer
                    Engineer Password  cmdID= 34011
                    preset= -"
        ::= { iqsyn22CmdEntry 34011 }


    iqsyn22EngineerShowEngineer OBJECT-TYPE
        SYNTAX            INTEGER { disable(0), enable(1)  }
        MAX-ACCESS        read-write
        STATUS            current
        DESCRIPTION
                "CMNT: - 
                 TYPE: - Checkbox
                 PAGE: - Engineer
                    Show Engineer  cmdID= 34012  "
        ::= { iqsyn22CmdEntry 34012 }


    iqsyn22EngineerPageUndoChanges OBJECT-TYPE
        SYNTAX            INTEGER { noAction(0),valUndoChanges(1) }
        MAX-ACCESS        read-write
        STATUS            current
        DESCRIPTION
                "CMNT: - 
                 TYPE: - Button
                 PAGE: - Engineer
                    Undo Changes  cmdID= 34013
                    value= 1  "
        ::= { iqsyn22CmdEntry 34013 }


    iqsyn22EngineerShowEngineer2 OBJECT-TYPE
        SYNTAX            INTEGER { disable(0), enable(1)  }
        MAX-ACCESS        read-write
        STATUS            current
        DESCRIPTION
                "CMNT: - 
                 TYPE: - Checkbox
                 PAGE: - Engineer
                    Show Engineer2  cmdID= 34050  "
        ::= { iqsyn22CmdEntry 34050 }


    iqsyn22EngineerShowEngineer3 OBJECT-TYPE
        SYNTAX            INTEGER { disable(0), enable(1)  }
        MAX-ACCESS        read-write
        STATUS            current
        DESCRIPTION
                "CMNT: - 
                 TYPE: - Checkbox
                 PAGE: - Engineer
                    Show Engineer3  cmdID= 34051  "
        ::= { iqsyn22CmdEntry 34051 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: S34091041
-- Comments		: Runtime string Serial Number of unit
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 00-00-00 01:30Z
-- Comments		: Uptime in formated date-time string
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
--
-- Value(s)		: INP 1
--				: INP 2
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: K_OS: V115 Release
-- Comments		: String
--
---------------------------------------------------------------------------------------------------
-- Header		: INPUT_1_AFD
--
-- MIB ref		: swCardEventLogSlotXX       .11.73.78.80.85.84.95.49.95.65.70.68
-- absolute OID	: 1.3.6.1.4.1.7995.2.6.1.1.XX.11.73.78.80.85.84.95.49.95.65.70.68
--
-- Value(s)		: Reserved(0)
--				: Reserved(1)
--				: Box 16:9 top
--				: Box 14:9 top
--				: Box>16:9 ctr
--				: Reserved(5)
--				: Reserved(6)
--				: Reserved(7)
--				: Coded Frame
--				: 4:3 center
--				: 16:9 center
--				: 14:9 center
--				: Reserved(12)
--				: 4:3 SP 14:9
--				: 16:9 SP 14:9
--				: 16:9 SP 4:3
--				: Unknown
--				: Delete
-- Comments		:
--
---------------------------------------------------------------------------------------------------
-- Header		: INPUT_2_AFD
--
-- MIB ref		: swCardEventLogSlotXX       .11.73.78.80.85.84.95.50.95.65.70.68
-- absolute OID	: 1.3.6.1.4.1.7995.2.6.1.1.XX.11.73.78.80.85.84.95.50.95.65.70.68
--
-- Value(s)		: Reserved(0)
--				: Reserved(1)
--				: Box 16:9 top
--				: Box 14:9 top
--				: Box>16:9 ctr
--				: Reserved(5)
--				: Reserved(6)
--				: Reserved(7)
--				: Coded Frame
--				: 4:3 center
--				: 16:9 center
--				: 14:9 center
--				: Reserved(12)
--				: 4:3 SP 14:9
--				: 16:9 SP 14:9
--				: 16:9 SP 4:3
--				: Unknown
--				: Delete
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 0003102405
-- Comments		: String of current Software build number
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD / SD SDI
-- Comments		:
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
--
-- Value(s)		: HD / SD SDI
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: FAIL:Lost
--				: OK
--				: FAIL:Error
-- Comments		:
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
--
-- Value(s)		: FAIL:Lost
--				: OK
--				: FAIL:Error
-- Comments		:
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
--
-- Value(s)		: HD / SD SDI
-- Comments		:
--
---------------------------------------------------------------------------------------------------
-- Header		: INPUT_1_ASPECT
--
-- MIB ref		: swCardEventLogSlotXX       .14.73.78.80.85.84.95.49.95.65.83.80.69.67.84
-- absolute OID	: 1.3.6.1.4.1.7995.2.6.1.1.XX.14.73.78.80.85.84.95.49.95.65.83.80.69.67.84
--
-- Value(s)		: 4:3
--				: 16:9
--				: Unknown
-- Comments		:
--
---------------------------------------------------------------------------------------------------
-- Header		: INPUT_2_ASPECT
--
-- MIB ref		: swCardEventLogSlotXX       .14.73.78.80.85.84.95.50.95.65.83.80.69.67.84
-- absolute OID	: 1.3.6.1.4.1.7995.2.6.1.1.XX.14.73.78.80.85.84.95.50.95.65.83.80.69.67.84
--
-- Value(s)		: 4:3
--				: 16:9
--				: Unknown
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
--
-- Value(s)		: OK
-- Comments		:
--
---------------------------------------------------------------------------------------------------
-- Header		: OUTPUT_1_ASPECT
--
-- MIB ref		: swCardEventLogSlotXX       .15.79.85.84.80.85.84.95.49.95.65.83.80.69.67.84
-- absolute OID	: 1.3.6.1.4.1.7995.2.6.1.1.XX.15.79.85.84.80.85.84.95.49.95.65.83.80.69.67.84
--
-- Value(s)		: 4:3
--				: 16:9
--				: Unknown
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: 2.122
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: 1
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
--
-- Value(s)		: OK
--				: NONE
--				: WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
--
-- Value(s)		: OK
--				: NONE
--				: WARN
-- Comments		:
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
--
-- Value(s)		: Tri/Bi-Level
--				: TriLevel
--				: BiLevel
--				: BlackBurst
--				: Analog
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
--
-- Value(s)		: OK
--				: FAIL:Lost
--				: FAIL:Error
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
--
-- Value(s)		: 0
-- Comments		: Number
--
---------------------------------------------------------------------------------------------------
-- Header		: INPUT_2_SDI_ERRSEC
--
-- MIB ref		: swCardEventLogSlotXX       .18.73.78.80.85.84.95.50.95.83.68.73.95.69.82.82.83.69.67
-- absolute OID	: 1.3.6.1.4.1.7995.2.6.1.1.XX.18.73.78.80.85.84.95.50.95.83.68.73.95.69.82.82.83.69.67
--
-- Value(s)		: 0
-- Comments		: Number
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
--
-- Value(s)		: OK
--				: NONE
--				: WARN
-- Comments		:
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
--
-- Value(s)		: OK
--				: NONE
--				: WARN
-- Comments		:
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
--
-- Value(s)		: 0
-- Comments		: Number
--
---------------------------------------------------------------------------------------------------
-- Header		: INPUT_2_SDI_ANC_ERRSECS
--
-- MIB ref		: swCardEventLogSlotXX       .23.73.78.80.85.84.95.50.95.83.68.73.95.65.78.67.95.69.82.82.83.69.67.83
-- absolute OID	: 1.3.6.1.4.1.7995.2.6.1.1.XX.23.73.78.80.85.84.95.50.95.83.68.73.95.65.78.67.95.69.82.82.83.69.67.83
--
-- Value(s)		: 0
-- Comments		: Number
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
--
-- Value(s)		: WARN: No Input
--				: PCM
--				: NONPCM
--				: Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
--
-- Value(s)		: WARN: No Input
--				: PCM
--				: NONPCM
--				: Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
--
-- Value(s)		: WARN: No Input
--				: PCM
--				: NONPCM
--				: Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
--
-- Value(s)		: WARN: No Input
--				: PCM
--				: NONPCM
--				: Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
--
-- Value(s)		: WARN: No Input
--				: PCM
--				: NONPCM
--				: Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
--
-- Value(s)		: WARN: No Input
--				: PCM
--				: NONPCM
--				: Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
--
-- Value(s)		: WARN: No Input
--				: PCM
--				: NONPCM
--				: Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
--
-- Value(s)		: WARN: No Input
--				: PCM
--				: NONPCM
--				: Unknown
-- Comments		:
--
---------------------------------------------------------------------------------------------------
-- Header		: INPUT_2_EMBEDDED_AUDIO_1_TYPE
--
-- MIB ref		: swCardEventLogSlotXX       .29.73.78.80.85.84.95.50.95.69.77.66.69.68.68.69.68.95.65.85.68.73.79.95.49.95.84.89.80.69
-- absolute OID	: 1.3.6.1.4.1.7995.2.6.1.1.XX.29.73.78.80.85.84.95.50.95.69.77.66.69.68.68.69.68.95.65.85.68.73.79.95.49.95.84.89.80.69
--
-- Value(s)		: WARN: No Input
--				: PCM
--				: NONPCM
--				: Unknown
-- Comments		:
--
---------------------------------------------------------------------------------------------------
-- Header		: INPUT_2_EMBEDDED_AUDIO_2_TYPE
--
-- MIB ref		: swCardEventLogSlotXX       .29.73.78.80.85.84.95.50.95.69.77.66.69.68.68.69.68.95.65.85.68.73.79.95.50.95.84.89.80.69
-- absolute OID	: 1.3.6.1.4.1.7995.2.6.1.1.XX.29.73.78.80.85.84.95.50.95.69.77.66.69.68.68.69.68.95.65.85.68.73.79.95.50.95.84.89.80.69
--
-- Value(s)		: WARN: No Input
--				: PCM
--				: NONPCM
--				: Unknown
-- Comments		:
--
---------------------------------------------------------------------------------------------------
-- Header		: INPUT_2_EMBEDDED_AUDIO_3_TYPE
--
-- MIB ref		: swCardEventLogSlotXX       .29.73.78.80.85.84.95.50.95.69.77.66.69.68.68.69.68.95.65.85.68.73.79.95.51.95.84.89.80.69
-- absolute OID	: 1.3.6.1.4.1.7995.2.6.1.1.XX.29.73.78.80.85.84.95.50.95.69.77.66.69.68.68.69.68.95.65.85.68.73.79.95.51.95.84.89.80.69
--
-- Value(s)		: WARN: No Input
--				: PCM
--				: NONPCM
--				: Unknown
-- Comments		:
--
---------------------------------------------------------------------------------------------------
-- Header		: INPUT_2_EMBEDDED_AUDIO_4_TYPE
--
-- MIB ref		: swCardEventLogSlotXX       .29.73.78.80.85.84.95.50.95.69.77.66.69.68.68.69.68.95.65.85.68.73.79.95.52.95.84.89.80.69
-- absolute OID	: 1.3.6.1.4.1.7995.2.6.1.1.XX.29.73.78.80.85.84.95.50.95.69.77.66.69.68.68.69.68.95.65.85.68.73.79.95.52.95.84.89.80.69
--
-- Value(s)		: WARN: No Input
--				: PCM
--				: NONPCM
--				: Unknown
-- Comments		:
--
---------------------------------------------------------------------------------------------------
-- Header		: INPUT_2_EMBEDDED_AUDIO_5_TYPE
--
-- MIB ref		: swCardEventLogSlotXX       .29.73.78.80.85.84.95.50.95.69.77.66.69.68.68.69.68.95.65.85.68.73.79.95.53.95.84.89.80.69
-- absolute OID	: 1.3.6.1.4.1.7995.2.6.1.1.XX.29.73.78.80.85.84.95.50.95.69.77.66.69.68.68.69.68.95.65.85.68.73.79.95.53.95.84.89.80.69
--
-- Value(s)		: WARN: No Input
--				: PCM
--				: NONPCM
--				: Unknown
-- Comments		:
--
---------------------------------------------------------------------------------------------------
-- Header		: INPUT_2_EMBEDDED_AUDIO_6_TYPE
--
-- MIB ref		: swCardEventLogSlotXX       .29.73.78.80.85.84.95.50.95.69.77.66.69.68.68.69.68.95.65.85.68.73.79.95.54.95.84.89.80.69
-- absolute OID	: 1.3.6.1.4.1.7995.2.6.1.1.XX.29.73.78.80.85.84.95.50.95.69.77.66.69.68.68.69.68.95.65.85.68.73.79.95.54.95.84.89.80.69
--
-- Value(s)		: WARN: No Input
--				: PCM
--				: NONPCM
--				: Unknown
-- Comments		:
--
---------------------------------------------------------------------------------------------------
-- Header		: INPUT_2_EMBEDDED_AUDIO_7_TYPE
--
-- MIB ref		: swCardEventLogSlotXX       .29.73.78.80.85.84.95.50.95.69.77.66.69.68.68.69.68.95.65.85.68.73.79.95.55.95.84.89.80.69
-- absolute OID	: 1.3.6.1.4.1.7995.2.6.1.1.XX.29.73.78.80.85.84.95.50.95.69.77.66.69.68.68.69.68.95.65.85.68.73.79.95.55.95.84.89.80.69
--
-- Value(s)		: WARN: No Input
--				: PCM
--				: NONPCM
--				: Unknown
-- Comments		:
--
---------------------------------------------------------------------------------------------------
-- Header		: INPUT_2_EMBEDDED_AUDIO_8_TYPE
--
-- MIB ref		: swCardEventLogSlotXX       .29.73.78.80.85.84.95.50.95.69.77.66.69.68.68.69.68.95.65.85.68.73.79.95.56.95.84.89.80.69
-- absolute OID	: 1.3.6.1.4.1.7995.2.6.1.1.XX.29.73.78.80.85.84.95.50.95.69.77.66.69.68.68.69.68.95.65.85.68.73.79.95.56.95.84.89.80.69
--
-- Value(s)		: WARN: No Input
--				: PCM
--				: NONPCM
--				: Unknown
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
--
-- Value(s)		: LOST
--				: FAIL:Lost
--				: OK
--				: Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
--
-- Value(s)		: LOST
--				: FAIL:Lost
--				: OK
--				: Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
--
-- Value(s)		: LOST
--				: FAIL:Lost
--				: OK
--				: Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
--
-- Value(s)		: LOST
--				: FAIL:Lost
--				: OK
--				: Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
--
-- Value(s)		: LOST
--				: FAIL:Lost
--				: OK
--				: Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
--
-- Value(s)		: LOST
--				: FAIL:Lost
--				: OK
--				: Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
--
-- Value(s)		: LOST
--				: FAIL:Lost
--				: OK
--				: Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
--
-- Value(s)		: LOST
--				: FAIL:Lost
--				: OK
--				: Unknown
-- Comments		:
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
--
-- Value(s)		: LOST
--				: FAIL:Lost
--				: OK
--				: Unknown
-- Comments		:
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
--
-- Value(s)		: LOST
--				: FAIL:Lost
--				: OK
--				: Unknown
-- Comments		:
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
--
-- Value(s)		: LOST
--				: FAIL:Lost
--				: OK
--				: Unknown
-- Comments		:
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
--
-- Value(s)		: LOST
--				: FAIL:Lost
--				: OK
--				: Unknown
-- Comments		:
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
--
-- Value(s)		: LOST
--				: FAIL:Lost
--				: OK
--				: Unknown
-- Comments		:
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
--
-- Value(s)		: LOST
--				: FAIL:Lost
--				: OK
--				: Unknown
-- Comments		:
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
--
-- Value(s)		: LOST
--				: FAIL:Lost
--				: OK
--				: Unknown
-- Comments		:
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
--
-- Value(s)		: LOST
--				: FAIL:Lost
--				: OK
--				: Unknown
-- Comments		:
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
--
-- Value(s)		: WARN: No Input
--				: PCM
--				: NONPCM
--				: Unknown
-- Comments		:
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
--
-- Value(s)		: WARN: No Input
--				: PCM
--				: NONPCM
--				: Unknown
-- Comments		:
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
--
-- Value(s)		: WARN: No Input
--				: PCM
--				: NONPCM
--				: Unknown
-- Comments		:
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
--
-- Value(s)		: WARN: No Input
--				: PCM
--				: NONPCM
--				: Unknown
-- Comments		:
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
--
-- Value(s)		: WARN: No Input
--				: PCM
--				: NONPCM
--				: Unknown
-- Comments		:
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
--
-- Value(s)		: WARN: No Input
--				: PCM
--				: NONPCM
--				: Unknown
-- Comments		:
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
--
-- Value(s)		: WARN: No Input
--				: PCM
--				: NONPCM
--				: Unknown
-- Comments		:
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
--
-- Value(s)		: WARN: No Input
--				: PCM
--				: NONPCM
--				: Unknown
-- Comments		:
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
--
-- Value(s)		: LOST
--				: FAIL:Lost
--				: OK
--				: Unknown
-- Comments		:
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
--
-- Value(s)		: LOST
--				: FAIL:Lost
--				: OK
--				: Unknown
-- Comments		:
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
--
-- Value(s)		: LOST
--				: FAIL:Lost
--				: OK
--				: Unknown
-- Comments		:
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
--
-- Value(s)		: LOST
--				: FAIL:Lost
--				: OK
--				: Unknown
-- Comments		:
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
--
-- Value(s)		: LOST
--				: FAIL:Lost
--				: OK
--				: Unknown
-- Comments		:
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
--
-- Value(s)		: LOST
--				: FAIL:Lost
--				: OK
--				: Unknown
-- Comments		:
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
--
-- Value(s)		: LOST
--				: FAIL:Lost
--				: OK
--				: Unknown
-- Comments		:
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
--
-- Value(s)		: LOST
--				: FAIL:Lost
--				: OK
--				: Unknown
-- Comments		:
--
---------------------------------------------------------------------------------------------------
-- Header		: OUTPUT_1_EMBEDDED_AUDIO_1_1_LEVEL
--
-- MIB ref		: swCardEventLogSlotXX       .33.79.85.84.80.85.84.95.49.95.69.77.66.69.68.68.69.68.95.65.85.68.73.79.95.49.95.49.95.76.69.86.69.76
-- absolute OID	: 1.3.6.1.4.1.7995.2.6.1.1.XX.33.79.85.84.80.85.84.95.49.95.69.77.66.69.68.68.69.68.95.65.85.68.73.79.95.49.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_1_2_LEVEL
--
-- MIB ref		: swCardEventLogSlotXX       .33.79.85.84.80.85.84.95.49.95.69.77.66.69.68.68.69.68.95.65.85.68.73.79.95.49.95.50.95.76.69.86.69.76
-- absolute OID	: 1.3.6.1.4.1.7995.2.6.1.1.XX.33.79.85.84.80.85.84.95.49.95.69.77.66.69.68.68.69.68.95.65.85.68.73.79.95.49.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_2_1_LEVEL
--
-- MIB ref		: swCardEventLogSlotXX       .33.79.85.84.80.85.84.95.49.95.69.77.66.69.68.68.69.68.95.65.85.68.73.79.95.50.95.49.95.76.69.86.69.76
-- absolute OID	: 1.3.6.1.4.1.7995.2.6.1.1.XX.33.79.85.84.80.85.84.95.49.95.69.77.66.69.68.68.69.68.95.65.85.68.73.79.95.50.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_2_2_LEVEL
--
-- MIB ref		: swCardEventLogSlotXX       .33.79.85.84.80.85.84.95.49.95.69.77.66.69.68.68.69.68.95.65.85.68.73.79.95.50.95.50.95.76.69.86.69.76
-- absolute OID	: 1.3.6.1.4.1.7995.2.6.1.1.XX.33.79.85.84.80.85.84.95.49.95.69.77.66.69.68.68.69.68.95.65.85.68.73.79.95.50.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_3_1_LEVEL
--
-- MIB ref		: swCardEventLogSlotXX       .33.79.85.84.80.85.84.95.49.95.69.77.66.69.68.68.69.68.95.65.85.68.73.79.95.51.95.49.95.76.69.86.69.76
-- absolute OID	: 1.3.6.1.4.1.7995.2.6.1.1.XX.33.79.85.84.80.85.84.95.49.95.69.77.66.69.68.68.69.68.95.65.85.68.73.79.95.51.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_3_2_LEVEL
--
-- MIB ref		: swCardEventLogSlotXX       .33.79.85.84.80.85.84.95.49.95.69.77.66.69.68.68.69.68.95.65.85.68.73.79.95.51.95.50.95.76.69.86.69.76
-- absolute OID	: 1.3.6.1.4.1.7995.2.6.1.1.XX.33.79.85.84.80.85.84.95.49.95.69.77.66.69.68.68.69.68.95.65.85.68.73.79.95.51.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_4_1_LEVEL
--
-- MIB ref		: swCardEventLogSlotXX       .33.79.85.84.80.85.84.95.49.95.69.77.66.69.68.68.69.68.95.65.85.68.73.79.95.52.95.49.95.76.69.86.69.76
-- absolute OID	: 1.3.6.1.4.1.7995.2.6.1.1.XX.33.79.85.84.80.85.84.95.49.95.69.77.66.69.68.68.69.68.95.65.85.68.73.79.95.52.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_4_2_LEVEL
--
-- MIB ref		: swCardEventLogSlotXX       .33.79.85.84.80.85.84.95.49.95.69.77.66.69.68.68.69.68.95.65.85.68.73.79.95.52.95.50.95.76.69.86.69.76
-- absolute OID	: 1.3.6.1.4.1.7995.2.6.1.1.XX.33.79.85.84.80.85.84.95.49.95.69.77.66.69.68.68.69.68.95.65.85.68.73.79.95.52.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_5_1_LEVEL
--
-- MIB ref		: swCardEventLogSlotXX       .33.79.85.84.80.85.84.95.49.95.69.77.66.69.68.68.69.68.95.65.85.68.73.79.95.53.95.49.95.76.69.86.69.76
-- absolute OID	: 1.3.6.1.4.1.7995.2.6.1.1.XX.33.79.85.84.80.85.84.95.49.95.69.77.66.69.68.68.69.68.95.65.85.68.73.79.95.53.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_5_2_LEVEL
--
-- MIB ref		: swCardEventLogSlotXX       .33.79.85.84.80.85.84.95.49.95.69.77.66.69.68.68.69.68.95.65.85.68.73.79.95.53.95.50.95.76.69.86.69.76
-- absolute OID	: 1.3.6.1.4.1.7995.2.6.1.1.XX.33.79.85.84.80.85.84.95.49.95.69.77.66.69.68.68.69.68.95.65.85.68.73.79.95.53.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_6_1_LEVEL
--
-- MIB ref		: swCardEventLogSlotXX       .33.79.85.84.80.85.84.95.49.95.69.77.66.69.68.68.69.68.95.65.85.68.73.79.95.54.95.49.95.76.69.86.69.76
-- absolute OID	: 1.3.6.1.4.1.7995.2.6.1.1.XX.33.79.85.84.80.85.84.95.49.95.69.77.66.69.68.68.69.68.95.65.85.68.73.79.95.54.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_6_2_LEVEL
--
-- MIB ref		: swCardEventLogSlotXX       .33.79.85.84.80.85.84.95.49.95.69.77.66.69.68.68.69.68.95.65.85.68.73.79.95.54.95.50.95.76.69.86.69.76
-- absolute OID	: 1.3.6.1.4.1.7995.2.6.1.1.XX.33.79.85.84.80.85.84.95.49.95.69.77.66.69.68.68.69.68.95.65.85.68.73.79.95.54.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_7_1_LEVEL
--
-- MIB ref		: swCardEventLogSlotXX       .33.79.85.84.80.85.84.95.49.95.69.77.66.69.68.68.69.68.95.65.85.68.73.79.95.55.95.49.95.76.69.86.69.76
-- absolute OID	: 1.3.6.1.4.1.7995.2.6.1.1.XX.33.79.85.84.80.85.84.95.49.95.69.77.66.69.68.68.69.68.95.65.85.68.73.79.95.55.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_7_2_LEVEL
--
-- MIB ref		: swCardEventLogSlotXX       .33.79.85.84.80.85.84.95.49.95.69.77.66.69.68.68.69.68.95.65.85.68.73.79.95.55.95.50.95.76.69.86.69.76
-- absolute OID	: 1.3.6.1.4.1.7995.2.6.1.1.XX.33.79.85.84.80.85.84.95.49.95.69.77.66.69.68.68.69.68.95.65.85.68.73.79.95.55.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_8_1_LEVEL
--
-- MIB ref		: swCardEventLogSlotXX       .33.79.85.84.80.85.84.95.49.95.69.77.66.69.68.68.69.68.95.65.85.68.73.79.95.56.95.49.95.76.69.86.69.76
-- absolute OID	: 1.3.6.1.4.1.7995.2.6.1.1.XX.33.79.85.84.80.85.84.95.49.95.69.77.66.69.68.68.69.68.95.65.85.68.73.79.95.56.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_8_2_LEVEL
--
-- MIB ref		: swCardEventLogSlotXX       .33.79.85.84.80.85.84.95.49.95.69.77.66.69.68.68.69.68.95.65.85.68.73.79.95.56.95.50.95.76.69.86.69.76
-- absolute OID	: 1.3.6.1.4.1.7995.2.6.1.1.XX.33.79.85.84.80.85.84.95.49.95.69.77.66.69.68.68.69.68.95.65.85.68.73.79.95.56.95.50.95.76.69.86.69.76
--
-- Value(s)		: OK
--				: WARN:Overflow
--				: WARN:Silent
--				: WARN:Quiet
--				: WARN:Loud
-- Comments		:
--
---------------------------------------------------------------------------------------------------
