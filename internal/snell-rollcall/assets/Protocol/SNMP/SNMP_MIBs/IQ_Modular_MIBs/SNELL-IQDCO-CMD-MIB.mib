-- ************************************************************************************
-- Snell&Wilcox Card:IQDCO
--        Module Id#:208
--       Command Set:6
--          Filename:SNELL-IQDCO-CMD-MIB.mib
--            Author:Jonathan Riches
--              Date:13/06/2005
--              Time:09:22
--
-- Copyright (c) 2005 Snell & Wilcox Ltd
-- All rights reserved.
--
-- ************************************************************************************

SNELL-IQDCO-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDCO,
    moduleIQDCOMIB
        FROM SNELL-WILCOX-PRODUCT-REG;

 moduleIQDCOCmdMi MODULE-IDENTITY
    LAST-UPDATED "0506130922Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDCOMIB 1 }




--********************************************************************************
--*
--*  Snell Wilcox Card:
--*  command set:
--*  list commands/menus:
--*
--******************************************************************************
	iqdcoCmdTable OBJECT-TYPE
		SYNTAX			SEQUENCE OF IqdcoCmdEntry
		MAX-ACCESS		not-accessible
		STATUS			current
		DESCRIPTION
				"Note the instance of this table is relected in the command set Version"
		::= { moduleIQDCO 1 }

	iqdcoCmdEntry OBJECT-TYPE
		SYNTAX		IqdcoCmdEntry
		MAX-ACCESS		not-accessible
		STATUS			current
		DESCRIPTION
				"Entry in command table."
		INDEX	{ iqdcoSlotIndex }
		::= { iqdcoCmdTable 1 }

	IqdcoCmdEntry ::=
		SEQUENCE {
			iqdcoSlotIndex
				Unsigned32,
			iqdcoForceA
				INTEGER,
			iqdcoForceB
				INTEGER,
			iqdcoRulesDefineipAOkInputPresent
				INTEGER,
			iqdcoDefineIPAokInputStandardStdis525
				INTEGER,
			iqdcoDefineIPAokInputStandardStdis625
				INTEGER,
			iqdcoDefineIPAokEmbeddedAudioPair1
				INTEGER,
			iqdcoDefineIPAokEmbeddedAudioPair2
				INTEGER,
			iqdcoDefineIPAokEmbeddedAudioPair3
				INTEGER,
			iqdcoDefineIPAokEmbeddedAudioPair4
				INTEGER,
			iqdcoDefineIPAokEmbeddedAudioPair5
				INTEGER,
			iqdcoDefineIPAokEmbeddedAudioPair6
				INTEGER,
			iqdcoDefineIPAokEmbeddedAudioPair7
				INTEGER,
			iqdcoDefineIPAokEmbeddedAudioPair8
				INTEGER,
			iqdcoRulesDefineipAOkEDHOk
				INTEGER,
			iqdcoRulesDefineipBOkInputPresent
				INTEGER,
			iqdcoDefineIPBokInputStandardStdis525
				INTEGER,
			iqdcoDefineIPBokInputStandardStdis625
				INTEGER,
			iqdcoDefineIPBokEmbeddedAudioPair1
				INTEGER,
			iqdcoDefineIPBokEmbeddedAudioPair2
				INTEGER,
			iqdcoDefineIPBokEmbeddedAudioPair3
				INTEGER,
			iqdcoDefineIPBokEmbeddedAudioPair4
				INTEGER,
			iqdcoDefineIPBokEmbeddedAudioPair5
				INTEGER,
			iqdcoDefineIPBokEmbeddedAudioPair6
				INTEGER,
			iqdcoDefineIPBokEmbeddedAudioPair7
				INTEGER,
			iqdcoDefineIPBokEmbeddedAudioPair8
				INTEGER,
			iqdcoRulesDefineipBOkEDHOk
				INTEGER,
			iqdcoRulesRule1SetRule1
				INTEGER,
			iqdcoRulesRule1Select
				INTEGER,
			iqdcoRulesRule1TimeDelay
				INTEGER,
			iqdcoRulesRule2SetRule2
				INTEGER,
			iqdcoRulesRule2Select
				INTEGER,
			iqdcoRulesRule2TimeDelay
				INTEGER,
			iqdcoRulesRule3SetRule3
				INTEGER,
			iqdcoRulesRule3Select
				INTEGER,
			iqdcoRulesRule3TimeDelay
				INTEGER,
			iqdcoRulesRule4SetRule4
				INTEGER,
			iqdcoRulesRule4Select
				INTEGER,
			iqdcoRulesRule4TimeDelay
				INTEGER,
			iqdcoRulesRule5SetRule5
				INTEGER,
			iqdcoRulesRule5Select
				INTEGER,
			iqdcoRulesRule5TimeDelay
				INTEGER,
			iqdcoGPIOCtrl1DefineipOkUseRulesDefinition
				INTEGER,
			iqdcoDefineipOkDefineIPGPI1okInputPresent
				INTEGER,
			iqdcoDefineIPGPI1okInputStandardStdis525
				INTEGER,
			iqdcoDefineIPGPI1okInputStandardStdis625
				INTEGER,
			iqdcoDefineIPGPI1okEmbeddedAudioPair1
				INTEGER,
			iqdcoDefineIPGPI1okEmbeddedAudioPair2
				INTEGER,
			iqdcoDefineIPGPI1okEmbeddedAudioPair3
				INTEGER,
			iqdcoDefineIPGPI1okEmbeddedAudioPair4
				INTEGER,
			iqdcoDefineIPGPI1okEmbeddedAudioPair5
				INTEGER,
			iqdcoDefineIPGPI1okEmbeddedAudioPair6
				INTEGER,
			iqdcoDefineIPGPI1okEmbeddedAudioPair7
				INTEGER,
			iqdcoDefineIPGPI1okEmbeddedAudioPair8
				INTEGER,
			iqdcoDefineipOkDefineIPGPI1okEDHOk
				INTEGER,
			iqdcoGPIOCtrlsGPIOCtrl1
				INTEGER,
			iqdcoGPIOCtrl2DefineipOkUseRulesDefinition
				INTEGER,
			iqdcoDefineipOkDefineIPGPI2okInputPresent
				INTEGER,
			iqdcoDefineIPGPI2okInputStandardStdis525
				INTEGER,
			iqdcoDefineIPGPI2okInputStandardStdis625
				INTEGER,
			iqdcoDefineIPGPI2okEmbeddedAudioPair1
				INTEGER,
			iqdcoDefineIPGPI2okEmbeddedAudioPair2
				INTEGER,
			iqdcoDefineIPGPI2okEmbeddedAudioPair3
				INTEGER,
			iqdcoDefineIPGPI2okEmbeddedAudioPair4
				INTEGER,
			iqdcoDefineIPGPI2okEmbeddedAudioPair5
				INTEGER,
			iqdcoDefineIPGPI2okEmbeddedAudioPair6
				INTEGER,
			iqdcoDefineIPGPI2okEmbeddedAudioPair7
				INTEGER,
			iqdcoDefineIPGPI2okEmbeddedAudioPair8
				INTEGER,
			iqdcoDefineipOkDefineIPGPI2okEDHOk
				INTEGER,
			iqdcoGPIOCtrlsGPIOCtrl2
				INTEGER,
			iqdcoGPIOCtrl3DefineipOkUseRulesDefinition
				INTEGER,
			iqdcoDefineipOkDefineIPGPI3okInputPresent
				INTEGER,
			iqdcoDefineIPGPI3okInputStandardStdis525
				INTEGER,
			iqdcoDefineIPGPI3okInputStandardStdis625
				INTEGER,
			iqdcoDefineIPGPI3okEmbeddedAudioPair1
				INTEGER,
			iqdcoDefineIPGPI3okEmbeddedAudioPair2
				INTEGER,
			iqdcoDefineIPGPI3okEmbeddedAudioPair3
				INTEGER,
			iqdcoDefineIPGPI3okEmbeddedAudioPair4
				INTEGER,
			iqdcoDefineIPGPI3okEmbeddedAudioPair5
				INTEGER,
			iqdcoDefineIPGPI3okEmbeddedAudioPair6
				INTEGER,
			iqdcoDefineIPGPI3okEmbeddedAudioPair7
				INTEGER,
			iqdcoDefineIPGPI3okEmbeddedAudioPair8
				INTEGER,
			iqdcoDefineipOkDefineIPGPI3okEDHOk
				INTEGER,
			iqdcoGPIOCtrlsGPIOCtrl3
				INTEGER,
			iqdcoRollTracksRTrk1RollTrack1Mode
				INTEGER,
			iqdcoRollTracksRTrk1RollTrack1Add
				RollCallString,
			iqdcoRollTracksRTrk1RollTrack1Data
				RollCallString,
			iqdcoRollTracksRTrk2RollTrack2Mode
				INTEGER,
			iqdcoRollTracksRTrk2RollTrack2Add
				RollCallString,
			iqdcoRollTracksRTrk2RollTrack2Data
				RollCallString,
			iqdcoRollTracksRTrk3RollTrack3Mode
				INTEGER,
			iqdcoRollTracksRTrk3RollTrack3Add
				RollCallString,
			iqdcoRollTracksRTrk3RollTrack3Data
				RollCallString,
			iqdcoRollTracksRTrk4RollTrack4Mode
				INTEGER,
			iqdcoRollTracksRTrk4RollTrack4Add
				RollCallString,
			iqdcoRollTracksRTrk4RollTrack4Data
				RollCallString,
			iqdcoRollTracksRTrk5RollTrack5Mode
				INTEGER,
			iqdcoRollTracksRTrk5RollTrack5Add
				RollCallString,
			iqdcoRollTracksRTrk5RollTrack5Data
				RollCallString,
			iqdcoRollTracksRTrk6RollTrack6Mode
				INTEGER,
			iqdcoRollTracksRTrk6RollTrack6Add
				RollCallString,
			iqdcoRollTracksRTrk6RollTrack6Data
				RollCallString,
			iqdcoSetupEDHShowStats
				INTEGER,
			iqdcoSetupEDHResetStats
				INTEGER,
			iqdcoSetupLoggingLogInputA
				INTEGER,
			iqdcoSetupLoggingLogInputB
				INTEGER,
			iqdcoSetupLoggingOutput
				INTEGER,
			iqdcoSetupPresetUnit
				INTEGER,
			iqdcoSetupSoftwareVersion
				RollCallString,
			iqdcoSetupSerialNo
				RollCallString,
			iqdcoSetupBuildNo
				RollCallString
		}

	iqdcoSlotIndex OBJECT-TYPE
		SYNTAX		Unsigned32
		MAX-ACCESS		not-accessible
		STATUS			current
		DESCRIPTION
				"The unique Index value for each slot.  Its value
					ranges between 1 and the value of slotNumber."
		::= { iqdcoCmdEntry 0 }


	iqdcoForceA OBJECT-TYPE
		SYNTAX		INTEGER { disable(0), enable(1) }
		MAX-ACCESS		read-write
		STATUS			current
		DESCRIPTION
				"TYPE: - Checkbox
					Force_A  cmdID= 12 "
		::= { iqdcoCmdEntry 12 }


	iqdcoForceB OBJECT-TYPE
		SYNTAX		INTEGER { disable(0), enable(1) }
		MAX-ACCESS		read-write
		STATUS			current
		DESCRIPTION
				"TYPE: - Checkbox
					Force_B  cmdID= 13 "
		::= { iqdcoCmdEntry 13 }


	iqdcoRulesDefineipAOkInputPresent OBJECT-TYPE
		SYNTAX		INTEGER { disable(0), enable(1) }
		MAX-ACCESS		read-write
		STATUS			current
		DESCRIPTION
				"TYPE: - Checkbox
				 PAGE: - Rules- Define_i/p_A_Ok
					Input_Present  cmdID= 32 "
		::= { iqdcoCmdEntry 32 }


	iqdcoDefineIPAokInputStandardStdis525 OBJECT-TYPE
		SYNTAX		INTEGER { disable(0), enable(1) }
		MAX-ACCESS		read-write
		STATUS			current
		DESCRIPTION
				"TYPE: - Checkbox
				 PAGE: - Rules- Define_i/p_A_Ok
					Std_is_525  cmdID= 33 "
		::= { iqdcoCmdEntry 33 }


	iqdcoDefineIPAokInputStandardStdis625 OBJECT-TYPE
		SYNTAX		INTEGER { disable(0), enable(1) }
		MAX-ACCESS		read-write
		STATUS			current
		DESCRIPTION
				"TYPE: - Checkbox
				 PAGE: - Rules- Define_i/p_A_Ok
					Std_is_625  cmdID= 34 "
		::= { iqdcoCmdEntry 34 }


	iqdcoDefineIPAokEmbeddedAudioPair1 OBJECT-TYPE
		SYNTAX		INTEGER { disable(0), enable(1) }
		MAX-ACCESS		read-write
		STATUS			current
		DESCRIPTION
				"TYPE: - Checkbox
				 PAGE: - Rules- Define_i/p_A_Ok
					Pair1  cmdID= 35 "
		::= { iqdcoCmdEntry 35 }


	iqdcoDefineIPAokEmbeddedAudioPair2 OBJECT-TYPE
		SYNTAX		INTEGER { disable(0), enable(1) }
		MAX-ACCESS		read-write
		STATUS			current
		DESCRIPTION
				"TYPE: - Checkbox
				 PAGE: - Rules- Define_i/p_A_Ok
					Pair2  cmdID= 36 "
		::= { iqdcoCmdEntry 36 }


	iqdcoDefineIPAokEmbeddedAudioPair3 OBJECT-TYPE
		SYNTAX		INTEGER { disable(0), enable(1) }
		MAX-ACCESS		read-write
		STATUS			current
		DESCRIPTION
				"TYPE: - Checkbox
				 PAGE: - Rules- Define_i/p_A_Ok
					Pair3  cmdID= 37 "
		::= { iqdcoCmdEntry 37 }


	iqdcoDefineIPAokEmbeddedAudioPair4 OBJECT-TYPE
		SYNTAX		INTEGER { disable(0), enable(1) }
		MAX-ACCESS		read-write
		STATUS			current
		DESCRIPTION
				"TYPE: - Checkbox
				 PAGE: - Rules- Define_i/p_A_Ok
					Pair4  cmdID= 38 "
		::= { iqdcoCmdEntry 38 }


	iqdcoDefineIPAokEmbeddedAudioPair5 OBJECT-TYPE
		SYNTAX		INTEGER { disable(0), enable(1) }
		MAX-ACCESS		read-write
		STATUS			current
		DESCRIPTION
				"TYPE: - Checkbox
				 PAGE: - Rules- Define_i/p_A_Ok
					Pair5  cmdID= 39 "
		::= { iqdcoCmdEntry 39 }


	iqdcoDefineIPAokEmbeddedAudioPair6 OBJECT-TYPE
		SYNTAX		INTEGER { disable(0), enable(1) }
		MAX-ACCESS		read-write
		STATUS			current
		DESCRIPTION
				"TYPE: - Checkbox
				 PAGE: - Rules- Define_i/p_A_Ok
					Pair6  cmdID= 40 "
		::= { iqdcoCmdEntry 40 }


	iqdcoDefineIPAokEmbeddedAudioPair7 OBJECT-TYPE
		SYNTAX		INTEGER { disable(0), enable(1) }
		MAX-ACCESS		read-write
		STATUS			current
		DESCRIPTION
				"TYPE: - Checkbox
				 PAGE: - Rules- Define_i/p_A_Ok
					Pair7  cmdID= 41 "
		::= { iqdcoCmdEntry 41 }


	iqdcoDefineIPAokEmbeddedAudioPair8 OBJECT-TYPE
		SYNTAX		INTEGER { disable(0), enable(1) }
		MAX-ACCESS		read-write
		STATUS			current
		DESCRIPTION
				"TYPE: - Checkbox
				 PAGE: - Rules- Define_i/p_A_Ok
					Pair8  cmdID= 42 "
		::= { iqdcoCmdEntry 42 }


	iqdcoRulesDefineipAOkEDHOk OBJECT-TYPE
		SYNTAX		INTEGER { disable(0), enable(1) }
		MAX-ACCESS		read-write
		STATUS			current
		DESCRIPTION
				"TYPE: - Checkbox
				 PAGE: - Rules- Define_i/p_A_Ok
					EDH_Ok  cmdID= 43 "
		::= { iqdcoCmdEntry 43 }


	iqdcoRulesDefineipBOkInputPresent OBJECT-TYPE
		SYNTAX		INTEGER { disable(0), enable(1) }
		MAX-ACCESS		read-write
		STATUS			current
		DESCRIPTION
				"TYPE: - Checkbox
				 PAGE: - Rules- Define_i/p_B_Ok
					Input_Present  cmdID= 44 "
		::= { iqdcoCmdEntry 44 }


	iqdcoDefineIPBokInputStandardStdis525 OBJECT-TYPE
		SYNTAX		INTEGER { disable(0), enable(1) }
		MAX-ACCESS		read-write
		STATUS			current
		DESCRIPTION
				"TYPE: - Checkbox
				 PAGE: - Rules- Define_i/p_B_Ok
					Std_is_525  cmdID= 45 "
		::= { iqdcoCmdEntry 45 }


	iqdcoDefineIPBokInputStandardStdis625 OBJECT-TYPE
		SYNTAX		INTEGER { disable(0), enable(1) }
		MAX-ACCESS		read-write
		STATUS			current
		DESCRIPTION
				"TYPE: - Checkbox
				 PAGE: - Rules- Define_i/p_B_Ok
					Std_is_625  cmdID= 46 "
		::= { iqdcoCmdEntry 46 }


	iqdcoDefineIPBokEmbeddedAudioPair1 OBJECT-TYPE
		SYNTAX		INTEGER { disable(0), enable(1) }
		MAX-ACCESS		read-write
		STATUS			current
		DESCRIPTION
				"TYPE: - Checkbox
				 PAGE: - Rules- Define_i/p_B_Ok
					Pair1  cmdID= 47 "
		::= { iqdcoCmdEntry 47 }


	iqdcoDefineIPBokEmbeddedAudioPair2 OBJECT-TYPE
		SYNTAX		INTEGER { disable(0), enable(1) }
		MAX-ACCESS		read-write
		STATUS			current
		DESCRIPTION
				"TYPE: - Checkbox
				 PAGE: - Rules- Define_i/p_B_Ok
					Pair2  cmdID= 48 "
		::= { iqdcoCmdEntry 48 }


	iqdcoDefineIPBokEmbeddedAudioPair3 OBJECT-TYPE
		SYNTAX		INTEGER { disable(0), enable(1) }
		MAX-ACCESS		read-write
		STATUS			current
		DESCRIPTION
				"TYPE: - Checkbox
				 PAGE: - Rules- Define_i/p_B_Ok
					Pair3  cmdID= 49 "
		::= { iqdcoCmdEntry 49 }


	iqdcoDefineIPBokEmbeddedAudioPair4 OBJECT-TYPE
		SYNTAX		INTEGER { disable(0), enable(1) }
		MAX-ACCESS		read-write
		STATUS			current
		DESCRIPTION
				"TYPE: - Checkbox
				 PAGE: - Rules- Define_i/p_B_Ok
					Pair4  cmdID= 50 "
		::= { iqdcoCmdEntry 50 }


	iqdcoDefineIPBokEmbeddedAudioPair5 OBJECT-TYPE
		SYNTAX		INTEGER { disable(0), enable(1) }
		MAX-ACCESS		read-write
		STATUS			current
		DESCRIPTION
				"TYPE: - Checkbox
				 PAGE: - Rules- Define_i/p_B_Ok
					Pair5  cmdID= 51 "
		::= { iqdcoCmdEntry 51 }


	iqdcoDefineIPBokEmbeddedAudioPair6 OBJECT-TYPE
		SYNTAX		INTEGER { disable(0), enable(1) }
		MAX-ACCESS		read-write
		STATUS			current
		DESCRIPTION
				"TYPE: - Checkbox
				 PAGE: - Rules- Define_i/p_B_Ok
					Pair6  cmdID= 52 "
		::= { iqdcoCmdEntry 52 }


	iqdcoDefineIPBokEmbeddedAudioPair7 OBJECT-TYPE
		SYNTAX		INTEGER { disable(0), enable(1) }
		MAX-ACCESS		read-write
		STATUS			current
		DESCRIPTION
				"TYPE: - Checkbox
				 PAGE: - Rules- Define_i/p_B_Ok
					Pair7  cmdID= 53 "
		::= { iqdcoCmdEntry 53 }


	iqdcoDefineIPBokEmbeddedAudioPair8 OBJECT-TYPE
		SYNTAX		INTEGER { disable(0), enable(1) }
		MAX-ACCESS		read-write
		STATUS			current
		DESCRIPTION
				"TYPE: - Checkbox
				 PAGE: - Rules- Define_i/p_B_Ok
					Pair8  cmdID= 54 "
		::= { iqdcoCmdEntry 54 }


	iqdcoRulesDefineipBOkEDHOk OBJECT-TYPE
		SYNTAX		INTEGER { disable(0), enable(1) }
		MAX-ACCESS		read-write
		STATUS			current
		DESCRIPTION
				"TYPE: - Checkbox
				 PAGE: - Rules- Define_i/p_B_Ok
					EDH_Ok  cmdID= 55 "
		::= { iqdcoCmdEntry 55 }


	iqdcoRulesRule1SetRule1 OBJECT-TYPE
		SYNTAX		INTEGER {
							val_Off(0),
							val_A_is_Ok(1),
							val_B_is_Ok(5),
							val_A_in_Error(3),
							val_B_in_Error(7),
							val_GPI_1_Open(9),
							val_GPI_1_Closed(11),
							val_GPI_2_Open(13),
							val_GPI_2_Closed(15),
							val_GPI_3_Open(17),
							val_GPI_3_Closed(19)
							}
		MAX-ACCESS		read-write
		STATUS			current
		DESCRIPTION
				"TYPE: - RadiobuttonList
				 PAGE: - Rules- Rule_1
					Set_Rule_1  cmdID= 99 
					Off  value= 0  
					A_is_Ok  value= 1  
					B_is_Ok  value= 5  
					A_in_Error  value= 3  
					B_in_Error  value= 7  
					GPI_1_Open  value= 9  
					GPI_1_Closed  value= 11  
					GPI_2_Open  value= 13  
					GPI_2_Closed  value= 15  
					GPI_3_Open  value= 17  
					GPI_3_Closed  value= 19  "
		::= { iqdcoCmdEntry 99 }


	iqdcoRulesRule1Select OBJECT-TYPE
		SYNTAX		INTEGER {
							val_Select_A(0),
							val_Select_B(1)
							}
		MAX-ACCESS		read-write
		STATUS			current
		DESCRIPTION
				"TYPE: - Button
				 PAGE: - Rules- Rule_1
					Select A  cmdID= 104  value= 0  
					Select B  cmdID= 104  value= 1  "
		::= { iqdcoCmdEntry 104 }


	iqdcoRulesRule1TimeDelay OBJECT-TYPE
		SYNTAX		INTEGER
		MAX-ACCESS		read-write
		STATUS			current
		DESCRIPTION
				"TYPE: - Number
				 PAGE: - Rules- Rule_1
					Time Delay  cmdID= 7  min= 0  max= 10000  step= 20  format= %.0fms  div_scale= 1 
					Min = 0ms  Max = 10000ms  Step = 20ms "
		::= { iqdcoCmdEntry 7 }


	iqdcoRulesRule2SetRule2 OBJECT-TYPE
		SYNTAX		INTEGER {
							val_Off(0),
							val_A_is_Ok(1),
							val_B_is_Ok(5),
							val_A_in_Error(3),
							val_B_in_Error(7),
							val_GPI_1_Open(9),
							val_GPI_1_Closed(11),
							val_GPI_2_Open(13),
							val_GPI_2_Closed(15),
							val_GPI_3_Open(17),
							val_GPI_3_Closed(19)
							}
		MAX-ACCESS		read-write
		STATUS			current
		DESCRIPTION
				"TYPE: - RadiobuttonList
				 PAGE: - Rules- Rule_2
					Set_Rule_2  cmdID= 100 
					Off  value= 0  
					A_is_Ok  value= 1  
					B_is_Ok  value= 5  
					A_in_Error  value= 3  
					B_in_Error  value= 7  
					GPI_1_Open  value= 9  
					GPI_1_Closed  value= 11  
					GPI_2_Open  value= 13  
					GPI_2_Closed  value= 15  
					GPI_3_Open  value= 17  
					GPI_3_Closed  value= 19  "
		::= { iqdcoCmdEntry 100 }


	iqdcoRulesRule2Select OBJECT-TYPE
		SYNTAX		INTEGER {
							val_Select_A(0),
							val_Select_B(1)
							}
		MAX-ACCESS		read-write
		STATUS			current
		DESCRIPTION
				"TYPE: - Button
				 PAGE: - Rules- Rule_2
					Select A  cmdID= 105  value= 0  
					Select B  cmdID= 105  value= 1  "
		::= { iqdcoCmdEntry 105 }


	iqdcoRulesRule2TimeDelay OBJECT-TYPE
		SYNTAX		INTEGER
		MAX-ACCESS		read-write
		STATUS			current
		DESCRIPTION
				"TYPE: - Number
				 PAGE: - Rules- Rule_2
					Time Delay  cmdID= 8  min= 0  max= 10000  step= 20  format= %.0fms  div_scale= 1 
					Min = 0ms  Max = 10000ms  Step = 20ms "
		::= { iqdcoCmdEntry 8 }


	iqdcoRulesRule3SetRule3 OBJECT-TYPE
		SYNTAX		INTEGER {
							val_Off(0),
							val_A_is_Ok(1),
							val_B_is_Ok(5),
							val_A_in_Error(3),
							val_B_in_Error(7),
							val_GPI_1_Open(9),
							val_GPI_1_Closed(11),
							val_GPI_2_Open(13),
							val_GPI_2_Closed(15),
							val_GPI_3_Open(17),
							val_GPI_3_Closed(19)
							}
		MAX-ACCESS		read-write
		STATUS			current
		DESCRIPTION
				"TYPE: - RadiobuttonList
				 PAGE: - Rules- Rule_3
					Set_Rule_3  cmdID= 101 
					Off  value= 0  
					A_is_Ok  value= 1  
					B_is_Ok  value= 5  
					A_in_Error  value= 3  
					B_in_Error  value= 7  
					GPI_1_Open  value= 9  
					GPI_1_Closed  value= 11  
					GPI_2_Open  value= 13  
					GPI_2_Closed  value= 15  
					GPI_3_Open  value= 17  
					GPI_3_Closed  value= 19  "
		::= { iqdcoCmdEntry 101 }


	iqdcoRulesRule3Select OBJECT-TYPE
		SYNTAX		INTEGER {
							val_Select_A(0),
							val_Select_B(1)
							}
		MAX-ACCESS		read-write
		STATUS			current
		DESCRIPTION
				"TYPE: - Button
				 PAGE: - Rules- Rule_3
					Select A  cmdID= 106  value= 0  
					Select B  cmdID= 106  value= 1  "
		::= { iqdcoCmdEntry 106 }


	iqdcoRulesRule3TimeDelay OBJECT-TYPE
		SYNTAX		INTEGER
		MAX-ACCESS		read-write
		STATUS			current
		DESCRIPTION
				"TYPE: - Number
				 PAGE: - Rules- Rule_3
					Time Delay  cmdID= 9  min= 0  max= 10000  step= 20  format= %.0fms  div_scale= 1 
					Min = 0ms  Max = 10000ms  Step = 20ms "
		::= { iqdcoCmdEntry 9 }


	iqdcoRulesRule4SetRule4 OBJECT-TYPE
		SYNTAX		INTEGER {
							val_Off(0),
							val_A_is_Ok(1),
							val_B_is_Ok(5),
							val_A_in_Error(3),
							val_B_in_Error(7),
							val_GPI_1_Open(9),
							val_GPI_1_Closed(11),
							val_GPI_2_Open(13),
							val_GPI_2_Closed(15),
							val_GPI_3_Open(17),
							val_GPI_3_Closed(19)
							}
		MAX-ACCESS		read-write
		STATUS			current
		DESCRIPTION
				"TYPE: - RadiobuttonList
				 PAGE: - Rules- Rule_4
					Set_Rule_4  cmdID= 102 
					Off  value= 0  
					A_is_Ok  value= 1  
					B_is_Ok  value= 5  
					A_in_Error  value= 3  
					B_in_Error  value= 7  
					GPI_1_Open  value= 9  
					GPI_1_Closed  value= 11  
					GPI_2_Open  value= 13  
					GPI_2_Closed  value= 15  
					GPI_3_Open  value= 17  
					GPI_3_Closed  value= 19  "
		::= { iqdcoCmdEntry 102 }


	iqdcoRulesRule4Select OBJECT-TYPE
		SYNTAX		INTEGER {
							val_Select_A(0),
							val_Select_B(1)
							}
		MAX-ACCESS		read-write
		STATUS			current
		DESCRIPTION
				"TYPE: - Button
				 PAGE: - Rules- Rule_4
					Select A  cmdID= 107  value= 0  
					Select B  cmdID= 107  value= 1  "
		::= { iqdcoCmdEntry 107 }


	iqdcoRulesRule4TimeDelay OBJECT-TYPE
		SYNTAX		INTEGER
		MAX-ACCESS		read-write
		STATUS			current
		DESCRIPTION
				"TYPE: - Number
				 PAGE: - Rules- Rule_4
					Time Delay  cmdID= 10  min= 0  max= 10000  step= 20  format= %.0fms  div_scale= 1 
					Min = 0ms  Max = 10000ms  Step = 20ms "
		::= { iqdcoCmdEntry 10 }


	iqdcoRulesRule5SetRule5 OBJECT-TYPE
		SYNTAX		INTEGER {
							val_Off(0),
							val_A_is_Ok(1),
							val_B_is_Ok(5),
							val_A_in_Error(3),
							val_B_in_Error(7),
							val_GPI_1_Open(9),
							val_GPI_1_Closed(11),
							val_GPI_2_Open(13),
							val_GPI_2_Closed(15),
							val_GPI_3_Open(17),
							val_GPI_3_Closed(19)
							}
		MAX-ACCESS		read-write
		STATUS			current
		DESCRIPTION
				"TYPE: - RadiobuttonList
				 PAGE: - Rules- Rule_5
					Set_Rule_5  cmdID= 103 
					Off  value= 0  
					A_is_Ok  value= 1  
					B_is_Ok  value= 5  
					A_in_Error  value= 3  
					B_in_Error  value= 7  
					GPI_1_Open  value= 9  
					GPI_1_Closed  value= 11  
					GPI_2_Open  value= 13  
					GPI_2_Closed  value= 15  
					GPI_3_Open  value= 17  
					GPI_3_Closed  value= 19  "
		::= { iqdcoCmdEntry 103 }


	iqdcoRulesRule5Select OBJECT-TYPE
		SYNTAX		INTEGER {
							val_Select_A(0),
							val_Select_B(1)
							}
		MAX-ACCESS		read-write
		STATUS			current
		DESCRIPTION
				"TYPE: - Button
				 PAGE: - Rules- Rule_5
					Select A  cmdID= 108  value= 0  
					Select B  cmdID= 108  value= 1  "
		::= { iqdcoCmdEntry 108 }


	iqdcoRulesRule5TimeDelay OBJECT-TYPE
		SYNTAX		INTEGER
		MAX-ACCESS		read-write
		STATUS			current
		DESCRIPTION
				"TYPE: - Number
				 PAGE: - Rules- Rule_5
					Time Delay  cmdID= 11  min= 0  max= 10000  step= 20  format= %.0fms  div_scale= 1 
					Min = 0ms  Max = 10000ms  Step = 20ms "
		::= { iqdcoCmdEntry 11 }


	iqdcoGPIOCtrl1DefineipOkUseRulesDefinition OBJECT-TYPE
		SYNTAX		INTEGER { disable(0), enable(1) }
		MAX-ACCESS		read-write
		STATUS			current
		DESCRIPTION
				"TYPE: - Checkbox
				 PAGE: - GPI_Setup
					Use Rules Definition  cmdID= 95 "
		::= { iqdcoCmdEntry 95 }


	iqdcoDefineipOkDefineIPGPI1okInputPresent OBJECT-TYPE
		SYNTAX		INTEGER { disable(0), enable(1) }
		MAX-ACCESS		read-write
		STATUS			current
		DESCRIPTION
				"TYPE: - Checkbox
				 PAGE: - GPI_Setup- Define_i/p_Ok
					Input_Present  cmdID= 56 "
		::= { iqdcoCmdEntry 56 }


	iqdcoDefineIPGPI1okInputStandardStdis525 OBJECT-TYPE
		SYNTAX		INTEGER { disable(0), enable(1) }
		MAX-ACCESS		read-write
		STATUS			current
		DESCRIPTION
				"TYPE: - Checkbox
				 PAGE: - GPI_Setup- Define_i/p_Ok
					Std_is_525  cmdID= 57 "
		::= { iqdcoCmdEntry 57 }


	iqdcoDefineIPGPI1okInputStandardStdis625 OBJECT-TYPE
		SYNTAX		INTEGER { disable(0), enable(1) }
		MAX-ACCESS		read-write
		STATUS			current
		DESCRIPTION
				"TYPE: - Checkbox
				 PAGE: - GPI_Setup- Define_i/p_Ok
					Std_is_625  cmdID= 58 "
		::= { iqdcoCmdEntry 58 }


	iqdcoDefineIPGPI1okEmbeddedAudioPair1 OBJECT-TYPE
		SYNTAX		INTEGER { disable(0), enable(1) }
		MAX-ACCESS		read-write
		STATUS			current
		DESCRIPTION
				"TYPE: - Checkbox
				 PAGE: - GPI_Setup- Define_i/p_Ok
					Pair1  cmdID= 59 "
		::= { iqdcoCmdEntry 59 }


	iqdcoDefineIPGPI1okEmbeddedAudioPair2 OBJECT-TYPE
		SYNTAX		INTEGER { disable(0), enable(1) }
		MAX-ACCESS		read-write
		STATUS			current
		DESCRIPTION
				"TYPE: - Checkbox
				 PAGE: - GPI_Setup- Define_i/p_Ok
					Pair2  cmdID= 60 "
		::= { iqdcoCmdEntry 60 }


	iqdcoDefineIPGPI1okEmbeddedAudioPair3 OBJECT-TYPE
		SYNTAX		INTEGER { disable(0), enable(1) }
		MAX-ACCESS		read-write
		STATUS			current
		DESCRIPTION
				"TYPE: - Checkbox
				 PAGE: - GPI_Setup- Define_i/p_Ok
					Pair3  cmdID= 61 "
		::= { iqdcoCmdEntry 61 }


	iqdcoDefineIPGPI1okEmbeddedAudioPair4 OBJECT-TYPE
		SYNTAX		INTEGER { disable(0), enable(1) }
		MAX-ACCESS		read-write
		STATUS			current
		DESCRIPTION
				"TYPE: - Checkbox
				 PAGE: - GPI_Setup- Define_i/p_Ok
					Pair4  cmdID= 62 "
		::= { iqdcoCmdEntry 62 }


	iqdcoDefineIPGPI1okEmbeddedAudioPair5 OBJECT-TYPE
		SYNTAX		INTEGER { disable(0), enable(1) }
		MAX-ACCESS		read-write
		STATUS			current
		DESCRIPTION
				"TYPE: - Checkbox
				 PAGE: - GPI_Setup- Define_i/p_Ok
					Pair5  cmdID= 63 "
		::= { iqdcoCmdEntry 63 }


	iqdcoDefineIPGPI1okEmbeddedAudioPair6 OBJECT-TYPE
		SYNTAX		INTEGER { disable(0), enable(1) }
		MAX-ACCESS		read-write
		STATUS			current
		DESCRIPTION
				"TYPE: - Checkbox
				 PAGE: - GPI_Setup- Define_i/p_Ok
					Pair6  cmdID= 64 "
		::= { iqdcoCmdEntry 64 }


	iqdcoDefineIPGPI1okEmbeddedAudioPair7 OBJECT-TYPE
		SYNTAX		INTEGER { disable(0), enable(1) }
		MAX-ACCESS		read-write
		STATUS			current
		DESCRIPTION
				"TYPE: - Checkbox
				 PAGE: - GPI_Setup- Define_i/p_Ok
					Pair7  cmdID= 65 "
		::= { iqdcoCmdEntry 65 }


	iqdcoDefineIPGPI1okEmbeddedAudioPair8 OBJECT-TYPE
		SYNTAX		INTEGER { disable(0), enable(1) }
		MAX-ACCESS		read-write
		STATUS			current
		DESCRIPTION
				"TYPE: - Checkbox
				 PAGE: - GPI_Setup- Define_i/p_Ok
					Pair8  cmdID= 66 "
		::= { iqdcoCmdEntry 66 }


	iqdcoDefineipOkDefineIPGPI1okEDHOk OBJECT-TYPE
		SYNTAX		INTEGER { disable(0), enable(1) }
		MAX-ACCESS		read-write
		STATUS			current
		DESCRIPTION
				"TYPE: - Checkbox
				 PAGE: - GPI_Setup- Define_i/p_Ok
					EDH_Ok  cmdID= 67 "
		::= { iqdcoCmdEntry 67 }


	iqdcoGPIOCtrlsGPIOCtrl1 OBJECT-TYPE
		SYNTAX		INTEGER {
							val_Input_To_Rules(1),
							val_Output_A_Selected(2),
							val_Output_B_Selected(5),
							val_Output_A_Ok(3),
							val_Output_B_Ok(6),
							val_Output_A_Error(4),
							val_Output_B_Error(7)
							}
		MAX-ACCESS		read-write
		STATUS			current
		DESCRIPTION
				"TYPE: - Button
				 PAGE: - GPI_Setup
					(Input)_To_Rules  cmdID= 92  value= 1  
					(Output)_A_Selected  cmdID= 92  value= 2  
					(Output)_B_Selected  cmdID= 92  value= 5  
					(Output)_A_Ok  cmdID= 92  value= 3  
					(Output)_B_Ok  cmdID= 92  value= 6  
					(Output)_A_Error  cmdID= 92  value= 4  
					(Output)_B_Error  cmdID= 92  value= 7  "
		::= { iqdcoCmdEntry 92 }


	iqdcoGPIOCtrl2DefineipOkUseRulesDefinition OBJECT-TYPE
		SYNTAX		INTEGER { disable(0), enable(1) }
		MAX-ACCESS		read-write
		STATUS			current
		DESCRIPTION
				"TYPE: - Checkbox
				 PAGE: - GPI_Setup
					Use Rules Definition  cmdID= 96 "
		::= { iqdcoCmdEntry 96 }


	iqdcoDefineipOkDefineIPGPI2okInputPresent OBJECT-TYPE
		SYNTAX		INTEGER { disable(0), enable(1) }
		MAX-ACCESS		read-write
		STATUS			current
		DESCRIPTION
				"TYPE: - Checkbox
				 PAGE: - GPI_Setup- Define_i/p_Ok
					Input_Present  cmdID= 68 "
		::= { iqdcoCmdEntry 68 }


	iqdcoDefineIPGPI2okInputStandardStdis525 OBJECT-TYPE
		SYNTAX		INTEGER { disable(0), enable(1) }
		MAX-ACCESS		read-write
		STATUS			current
		DESCRIPTION
				"TYPE: - Checkbox
				 PAGE: - GPI_Setup- Define_i/p_Ok
					Std_is_525  cmdID= 69 "
		::= { iqdcoCmdEntry 69 }


	iqdcoDefineIPGPI2okInputStandardStdis625 OBJECT-TYPE
		SYNTAX		INTEGER { disable(0), enable(1) }
		MAX-ACCESS		read-write
		STATUS			current
		DESCRIPTION
				"TYPE: - Checkbox
				 PAGE: - GPI_Setup- Define_i/p_Ok
					Std_is_625  cmdID= 70 "
		::= { iqdcoCmdEntry 70 }


	iqdcoDefineIPGPI2okEmbeddedAudioPair1 OBJECT-TYPE
		SYNTAX		INTEGER { disable(0), enable(1) }
		MAX-ACCESS		read-write
		STATUS			current
		DESCRIPTION
				"TYPE: - Checkbox
				 PAGE: - GPI_Setup- Define_i/p_Ok
					Pair1  cmdID= 71 "
		::= { iqdcoCmdEntry 71 }


	iqdcoDefineIPGPI2okEmbeddedAudioPair2 OBJECT-TYPE
		SYNTAX		INTEGER { disable(0), enable(1) }
		MAX-ACCESS		read-write
		STATUS			current
		DESCRIPTION
				"TYPE: - Checkbox
				 PAGE: - GPI_Setup- Define_i/p_Ok
					Pair2  cmdID= 72 "
		::= { iqdcoCmdEntry 72 }


	iqdcoDefineIPGPI2okEmbeddedAudioPair3 OBJECT-TYPE
		SYNTAX		INTEGER { disable(0), enable(1) }
		MAX-ACCESS		read-write
		STATUS			current
		DESCRIPTION
				"TYPE: - Checkbox
				 PAGE: - GPI_Setup- Define_i/p_Ok
					Pair3  cmdID= 73 "
		::= { iqdcoCmdEntry 73 }


	iqdcoDefineIPGPI2okEmbeddedAudioPair4 OBJECT-TYPE
		SYNTAX		INTEGER { disable(0), enable(1) }
		MAX-ACCESS		read-write
		STATUS			current
		DESCRIPTION
				"TYPE: - Checkbox
				 PAGE: - GPI_Setup- Define_i/p_Ok
					Pair4  cmdID= 74 "
		::= { iqdcoCmdEntry 74 }


	iqdcoDefineIPGPI2okEmbeddedAudioPair5 OBJECT-TYPE
		SYNTAX		INTEGER { disable(0), enable(1) }
		MAX-ACCESS		read-write
		STATUS			current
		DESCRIPTION
				"TYPE: - Checkbox
				 PAGE: - GPI_Setup- Define_i/p_Ok
					Pair5  cmdID= 75 "
		::= { iqdcoCmdEntry 75 }


	iqdcoDefineIPGPI2okEmbeddedAudioPair6 OBJECT-TYPE
		SYNTAX		INTEGER { disable(0), enable(1) }
		MAX-ACCESS		read-write
		STATUS			current
		DESCRIPTION
				"TYPE: - Checkbox
				 PAGE: - GPI_Setup- Define_i/p_Ok
					Pair6  cmdID= 76 "
		::= { iqdcoCmdEntry 76 }


	iqdcoDefineIPGPI2okEmbeddedAudioPair7 OBJECT-TYPE
		SYNTAX		INTEGER { disable(0), enable(1) }
		MAX-ACCESS		read-write
		STATUS			current
		DESCRIPTION
				"TYPE: - Checkbox
				 PAGE: - GPI_Setup- Define_i/p_Ok
					Pair7  cmdID= 77 "
		::= { iqdcoCmdEntry 77 }


	iqdcoDefineIPGPI2okEmbeddedAudioPair8 OBJECT-TYPE
		SYNTAX		INTEGER { disable(0), enable(1) }
		MAX-ACCESS		read-write
		STATUS			current
		DESCRIPTION
				"TYPE: - Checkbox
				 PAGE: - GPI_Setup- Define_i/p_Ok
					Pair8  cmdID= 78 "
		::= { iqdcoCmdEntry 78 }


	iqdcoDefineipOkDefineIPGPI2okEDHOk OBJECT-TYPE
		SYNTAX		INTEGER { disable(0), enable(1) }
		MAX-ACCESS		read-write
		STATUS			current
		DESCRIPTION
				"TYPE: - Checkbox
				 PAGE: - GPI_Setup- Define_i/p_Ok
					EDH_Ok  cmdID= 79 "
		::= { iqdcoCmdEntry 79 }


	iqdcoGPIOCtrlsGPIOCtrl2 OBJECT-TYPE
		SYNTAX		INTEGER {
							val_Input_To_Rules(1),
							val_Output_A_Selected(2),
							val_Output_B_Selected(5),
							val_Output_A_Ok(3),
							val_Output_B_Ok(6),
							val_Output_A_Error(4),
							val_Output_B_Error(7)
							}
		MAX-ACCESS		read-write
		STATUS			current
		DESCRIPTION
				"TYPE: - Button
				 PAGE: - GPI_Setup
					(Input)_To_Rules  cmdID= 93  value= 1  
					(Output)_A_Selected  cmdID= 93  value= 2  
					(Output)_B_Selected  cmdID= 93  value= 5  
					(Output)_A_Ok  cmdID= 93  value= 3  
					(Output)_B_Ok  cmdID= 93  value= 6  
					(Output)_A_Error  cmdID= 93  value= 4  
					(Output)_B_Error  cmdID= 93  value= 7  "
		::= { iqdcoCmdEntry 93 }


	iqdcoGPIOCtrl3DefineipOkUseRulesDefinition OBJECT-TYPE
		SYNTAX		INTEGER { disable(0), enable(1) }
		MAX-ACCESS		read-write
		STATUS			current
		DESCRIPTION
				"TYPE: - Checkbox
				 PAGE: - GPI_Setup
					Use Rules Definition  cmdID= 97 "
		::= { iqdcoCmdEntry 97 }


	iqdcoDefineipOkDefineIPGPI3okInputPresent OBJECT-TYPE
		SYNTAX		INTEGER { disable(0), enable(1) }
		MAX-ACCESS		read-write
		STATUS			current
		DESCRIPTION
				"TYPE: - Checkbox
				 PAGE: - GPI_Setup- Define_i/p_Ok
					Input_Present  cmdID= 80 "
		::= { iqdcoCmdEntry 80 }


	iqdcoDefineIPGPI3okInputStandardStdis525 OBJECT-TYPE
		SYNTAX		INTEGER { disable(0), enable(1) }
		MAX-ACCESS		read-write
		STATUS			current
		DESCRIPTION
				"TYPE: - Checkbox
				 PAGE: - GPI_Setup- Define_i/p_Ok
					Std_is_525  cmdID= 81 "
		::= { iqdcoCmdEntry 81 }


	iqdcoDefineIPGPI3okInputStandardStdis625 OBJECT-TYPE
		SYNTAX		INTEGER { disable(0), enable(1) }
		MAX-ACCESS		read-write
		STATUS			current
		DESCRIPTION
				"TYPE: - Checkbox
				 PAGE: - GPI_Setup- Define_i/p_Ok
					Std_is_625  cmdID= 82 "
		::= { iqdcoCmdEntry 82 }


	iqdcoDefineIPGPI3okEmbeddedAudioPair1 OBJECT-TYPE
		SYNTAX		INTEGER { disable(0), enable(1) }
		MAX-ACCESS		read-write
		STATUS			current
		DESCRIPTION
				"TYPE: - Checkbox
				 PAGE: - GPI_Setup- Define_i/p_Ok
					Pair1  cmdID= 83 "
		::= { iqdcoCmdEntry 83 }


	iqdcoDefineIPGPI3okEmbeddedAudioPair2 OBJECT-TYPE
		SYNTAX		INTEGER { disable(0), enable(1) }
		MAX-ACCESS		read-write
		STATUS			current
		DESCRIPTION
				"TYPE: - Checkbox
				 PAGE: - GPI_Setup- Define_i/p_Ok
					Pair2  cmdID= 84 "
		::= { iqdcoCmdEntry 84 }


	iqdcoDefineIPGPI3okEmbeddedAudioPair3 OBJECT-TYPE
		SYNTAX		INTEGER { disable(0), enable(1) }
		MAX-ACCESS		read-write
		STATUS			current
		DESCRIPTION
				"TYPE: - Checkbox
				 PAGE: - GPI_Setup- Define_i/p_Ok
					Pair3  cmdID= 85 "
		::= { iqdcoCmdEntry 85 }


	iqdcoDefineIPGPI3okEmbeddedAudioPair4 OBJECT-TYPE
		SYNTAX		INTEGER { disable(0), enable(1) }
		MAX-ACCESS		read-write
		STATUS			current
		DESCRIPTION
				"TYPE: - Checkbox
				 PAGE: - GPI_Setup- Define_i/p_Ok
					Pair4  cmdID= 86 "
		::= { iqdcoCmdEntry 86 }


	iqdcoDefineIPGPI3okEmbeddedAudioPair5 OBJECT-TYPE
		SYNTAX		INTEGER { disable(0), enable(1) }
		MAX-ACCESS		read-write
		STATUS			current
		DESCRIPTION
				"TYPE: - Checkbox
				 PAGE: - GPI_Setup- Define_i/p_Ok
					Pair5  cmdID= 87 "
		::= { iqdcoCmdEntry 87 }


	iqdcoDefineIPGPI3okEmbeddedAudioPair6 OBJECT-TYPE
		SYNTAX		INTEGER { disable(0), enable(1) }
		MAX-ACCESS		read-write
		STATUS			current
		DESCRIPTION
				"TYPE: - Checkbox
				 PAGE: - GPI_Setup- Define_i/p_Ok
					Pair6  cmdID= 88 "
		::= { iqdcoCmdEntry 88 }


	iqdcoDefineIPGPI3okEmbeddedAudioPair7 OBJECT-TYPE
		SYNTAX		INTEGER { disable(0), enable(1) }
		MAX-ACCESS		read-write
		STATUS			current
		DESCRIPTION
				"TYPE: - Checkbox
				 PAGE: - GPI_Setup- Define_i/p_Ok
					Pair7  cmdID= 89 "
		::= { iqdcoCmdEntry 89 }


	iqdcoDefineIPGPI3okEmbeddedAudioPair8 OBJECT-TYPE
		SYNTAX		INTEGER { disable(0), enable(1) }
		MAX-ACCESS		read-write
		STATUS			current
		DESCRIPTION
				"TYPE: - Checkbox
				 PAGE: - GPI_Setup- Define_i/p_Ok
					Pair8  cmdID= 90 "
		::= { iqdcoCmdEntry 90 }


	iqdcoDefineipOkDefineIPGPI3okEDHOk OBJECT-TYPE
		SYNTAX		INTEGER { disable(0), enable(1) }
		MAX-ACCESS		read-write
		STATUS			current
		DESCRIPTION
				"TYPE: - Checkbox
				 PAGE: - GPI_Setup- Define_i/p_Ok
					EDH_Ok  cmdID= 91 "
		::= { iqdcoCmdEntry 91 }


	iqdcoGPIOCtrlsGPIOCtrl3 OBJECT-TYPE
		SYNTAX		INTEGER {
							val_Input_To_Rules(1),
							val_Output_A_Selected(2),
							val_Output_B_Selected(5),
							val_Output_A_Ok(3),
							val_Output_B_Ok(6),
							val_Output_A_Error(4),
							val_Output_B_Error(7)
							}
		MAX-ACCESS		read-write
		STATUS			current
		DESCRIPTION
				"TYPE: - Button
				 PAGE: - GPI_Setup
					(Input)_To_Rules  cmdID= 94  value= 1  
					(Output)_A_Selected  cmdID= 94  value= 2  
					(Output)_B_Selected  cmdID= 94  value= 5  
					(Output)_A_Ok  cmdID= 94  value= 3  
					(Output)_B_Ok  cmdID= 94  value= 6  
					(Output)_A_Error  cmdID= 94  value= 4  
					(Output)_B_Error  cmdID= 94  value= 7  "
		::= { iqdcoCmdEntry 94 }


	iqdcoRollTracksRTrk1RollTrack1Mode OBJECT-TYPE
		SYNTAX		INTEGER {
							val_Off(0),
							val_A_Ok(1),
							val_A_in_Error(2),
							val_B_Ok(3),
							val_B_in_Error(4),
							val_Using_A(5),
							val_Using_B(6)
							}
		MAX-ACCESS		read-write
		STATUS			current
		DESCRIPTION
				"TYPE: - RadiobuttonList
				 PAGE: - RollTracks
					RollTrack_1 Mode  cmdID= 111 
					Off  value= 0  
					A Ok  value= 1  
					A in Error  value= 2  
					B Ok  value= 3  
					B in Error  value= 4  
					Using A  value= 5  
					Using B  value= 6  "
		::= { iqdcoCmdEntry 111 }


	iqdcoRollTracksRTrk1RollTrack1Add OBJECT-TYPE
		SYNTAX		RollCallString
		MAX-ACCESS		read-write
		STATUS			current
		DESCRIPTION
				"TYPE: - Editstring
				 PAGE: - RollTracks
					RollTrack_1 Add  cmdID= 109  "
		::= { iqdcoCmdEntry 109 }


	iqdcoRollTracksRTrk1RollTrack1Data OBJECT-TYPE
		SYNTAX		RollCallString
		MAX-ACCESS		read-write
		STATUS			current
		DESCRIPTION
				"TYPE: - Editstring
				 PAGE: - RollTracks
					RollTrack_1 Data  cmdID= 110  "
		::= { iqdcoCmdEntry 110 }


	iqdcoRollTracksRTrk2RollTrack2Mode OBJECT-TYPE
		SYNTAX		INTEGER {
							val_Off(0),
							val_A_Ok(1),
							val_A_in_Error(2),
							val_B_Ok(3),
							val_B_in_Error(4),
							val_Using_A(5),
							val_Using_B(6)
							}
		MAX-ACCESS		read-write
		STATUS			current
		DESCRIPTION
				"TYPE: - RadiobuttonList
				 PAGE: - RollTracks
					RollTrack_2 Mode  cmdID= 114 
					Off  value= 0  
					A Ok  value= 1  
					A in Error  value= 2  
					B Ok  value= 3  
					B in Error  value= 4  
					Using A  value= 5  
					Using B  value= 6  "
		::= { iqdcoCmdEntry 114 }


	iqdcoRollTracksRTrk2RollTrack2Add OBJECT-TYPE
		SYNTAX		RollCallString
		MAX-ACCESS		read-write
		STATUS			current
		DESCRIPTION
				"TYPE: - Editstring
				 PAGE: - RollTracks
					RollTrack_2 Add  cmdID= 112  "
		::= { iqdcoCmdEntry 112 }


	iqdcoRollTracksRTrk2RollTrack2Data OBJECT-TYPE
		SYNTAX		RollCallString
		MAX-ACCESS		read-write
		STATUS			current
		DESCRIPTION
				"TYPE: - Editstring
				 PAGE: - RollTracks
					RollTrack_2 Data  cmdID= 113  "
		::= { iqdcoCmdEntry 113 }


	iqdcoRollTracksRTrk3RollTrack3Mode OBJECT-TYPE
		SYNTAX		INTEGER {
							val_Off(0),
							val_A_Ok(1),
							val_A_in_Error(2),
							val_B_Ok(3),
							val_B_in_Error(4),
							val_Using_A(5),
							val_Using_B(6)
							}
		MAX-ACCESS		read-write
		STATUS			current
		DESCRIPTION
				"TYPE: - RadiobuttonList
				 PAGE: - RollTracks
					RollTrack_3 Mode  cmdID= 117 
					Off  value= 0  
					A Ok  value= 1  
					A in Error  value= 2  
					B Ok  value= 3  
					B in Error  value= 4  
					Using A  value= 5  
					Using B  value= 6  "
		::= { iqdcoCmdEntry 117 }


	iqdcoRollTracksRTrk3RollTrack3Add OBJECT-TYPE
		SYNTAX		RollCallString
		MAX-ACCESS		read-write
		STATUS			current
		DESCRIPTION
				"TYPE: - Editstring
				 PAGE: - RollTracks
					RollTrack_3 Add  cmdID= 115  "
		::= { iqdcoCmdEntry 115 }


	iqdcoRollTracksRTrk3RollTrack3Data OBJECT-TYPE
		SYNTAX		RollCallString
		MAX-ACCESS		read-write
		STATUS			current
		DESCRIPTION
				"TYPE: - Editstring
				 PAGE: - RollTracks
					RollTrack_3 Data  cmdID= 116  "
		::= { iqdcoCmdEntry 116 }


	iqdcoRollTracksRTrk4RollTrack4Mode OBJECT-TYPE
		SYNTAX		INTEGER {
							val_Off(0),
							val_A_Ok(1),
							val_A_in_Error(2),
							val_B_Ok(3),
							val_B_in_Error(4),
							val_Using_A(5),
							val_Using_B(6)
							}
		MAX-ACCESS		read-write
		STATUS			current
		DESCRIPTION
				"TYPE: - RadiobuttonList
				 PAGE: - RollTracks
					RollTrack_4 Mode  cmdID= 120 
					Off  value= 0  
					A Ok  value= 1  
					A in Error  value= 2  
					B Ok  value= 3  
					B in Error  value= 4  
					Using A  value= 5  
					Using B  value= 6  "
		::= { iqdcoCmdEntry 120 }


	iqdcoRollTracksRTrk4RollTrack4Add OBJECT-TYPE
		SYNTAX		RollCallString
		MAX-ACCESS		read-write
		STATUS			current
		DESCRIPTION
				"TYPE: - Editstring
				 PAGE: - RollTracks
					RollTrack_4 Add  cmdID= 118  "
		::= { iqdcoCmdEntry 118 }


	iqdcoRollTracksRTrk4RollTrack4Data OBJECT-TYPE
		SYNTAX		RollCallString
		MAX-ACCESS		read-write
		STATUS			current
		DESCRIPTION
				"TYPE: - Editstring
				 PAGE: - RollTracks
					RollTrack_4 Data  cmdID= 119  "
		::= { iqdcoCmdEntry 119 }


	iqdcoRollTracksRTrk5RollTrack5Mode OBJECT-TYPE
		SYNTAX		INTEGER {
							val_Off(0),
							val_A_Ok(1),
							val_A_in_Error(2),
							val_B_Ok(3),
							val_B_in_Error(4),
							val_Using_A(5),
							val_Using_B(6)
							}
		MAX-ACCESS		read-write
		STATUS			current
		DESCRIPTION
				"TYPE: - RadiobuttonList
				 PAGE: - RollTracks
					RollTrack_5 Mode  cmdID= 123 
					Off  value= 0  
					A Ok  value= 1  
					A in Error  value= 2  
					B Ok  value= 3  
					B in Error  value= 4  
					Using A  value= 5  
					Using B  value= 6  "
		::= { iqdcoCmdEntry 123 }


	iqdcoRollTracksRTrk5RollTrack5Add OBJECT-TYPE
		SYNTAX		RollCallString
		MAX-ACCESS		read-write
		STATUS			current
		DESCRIPTION
				"TYPE: - Editstring
				 PAGE: - RollTracks
					RollTrack_5 Add  cmdID= 121  "
		::= { iqdcoCmdEntry 121 }


	iqdcoRollTracksRTrk5RollTrack5Data OBJECT-TYPE
		SYNTAX		RollCallString
		MAX-ACCESS		read-write
		STATUS			current
		DESCRIPTION
				"TYPE: - Editstring
				 PAGE: - RollTracks
					RollTrack_5 Data  cmdID= 122  "
		::= { iqdcoCmdEntry 122 }


	iqdcoRollTracksRTrk6RollTrack6Mode OBJECT-TYPE
		SYNTAX		INTEGER {
							val_Off(0),
							val_A_Ok(1),
							val_A_in_Error(2),
							val_B_Ok(3),
							val_B_in_Error(4),
							val_Using_A(5),
							val_Using_B(6)
							}
		MAX-ACCESS		read-write
		STATUS			current
		DESCRIPTION
				"TYPE: - RadiobuttonList
				 PAGE: - RollTracks
					RollTrack_6 Mode  cmdID= 126 
					Off  value= 0  
					A Ok  value= 1  
					A in Error  value= 2  
					B Ok  value= 3  
					B in Error  value= 4  
					Using A  value= 5  
					Using B  value= 6  "
		::= { iqdcoCmdEntry 126 }


	iqdcoRollTracksRTrk6RollTrack6Add OBJECT-TYPE
		SYNTAX		RollCallString
		MAX-ACCESS		read-write
		STATUS			current
		DESCRIPTION
				"TYPE: - Editstring
				 PAGE: - RollTracks
					RollTrack_6 Add  cmdID= 124  "
		::= { iqdcoCmdEntry 124 }


	iqdcoRollTracksRTrk6RollTrack6Data OBJECT-TYPE
		SYNTAX		RollCallString
		MAX-ACCESS		read-write
		STATUS			current
		DESCRIPTION
				"TYPE: - Editstring
				 PAGE: - RollTracks
					RollTrack_6 Data  cmdID= 125  "
		::= { iqdcoCmdEntry 125 }


	iqdcoSetupEDHShowStats OBJECT-TYPE
		SYNTAX		INTEGER {
							val_Off(0),
							val_Input_A(1),
							val_Input_B(2)
							}
		MAX-ACCESS		read-write
		STATUS			current
		DESCRIPTION
				"TYPE: - RadiobuttonList
					Show_Stats  cmdID= 5 
					Off  value= 0  
					Input_A  value= 1  
					Input_B  value= 2  "
		::= { iqdcoCmdEntry 5 }


	iqdcoSetupEDHResetStats OBJECT-TYPE
		SYNTAX		INTEGER { noAction(0),val_Reset_Stats(1) }
		MAX-ACCESS		read-write
		STATUS			current
		DESCRIPTION
				"TYPE: - Button
					Reset_Stats  cmdID= 6  value= 1  "
		::= { iqdcoCmdEntry 6 }


	iqdcoSetupLoggingLogInputA OBJECT-TYPE
		SYNTAX		INTEGER { disable(0), enable(1) }
		MAX-ACCESS		read-write
		STATUS			current
		DESCRIPTION
				"TYPE: - Checkbox
					Log Input A  cmdID= 14 "
		::= { iqdcoCmdEntry 14 }


	iqdcoSetupLoggingLogInputB OBJECT-TYPE
		SYNTAX		INTEGER { disable(0), enable(1) }
		MAX-ACCESS		read-write
		STATUS			current
		DESCRIPTION
				"TYPE: - Checkbox
					Log Input B  cmdID= 15 "
		::= { iqdcoCmdEntry 15 }


	iqdcoSetupLoggingOutput OBJECT-TYPE
		SYNTAX		INTEGER { disable(0), enable(1) }
		MAX-ACCESS		read-write
		STATUS			current
		DESCRIPTION
				"TYPE: - Checkbox
					Output  cmdID= 16 "
		::= { iqdcoCmdEntry 16 }


	iqdcoSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqdcoCmdEntry 3 }


	iqdcoSetupSoftwareVersion OBJECT-TYPE
		SYNTAX		RollCallString
		MAX-ACCESS		read-only
		STATUS			current
		DESCRIPTION
				"TYPE: - Display
					Software_Version  cmdID= 2  format=   "
		::= { iqdcoCmdEntry 2 }


	iqdcoSetupSerialNo OBJECT-TYPE
		SYNTAX		RollCallString
		MAX-ACCESS		read-only
		STATUS			current
		DESCRIPTION
				"TYPE: - Display
					Serial_No  cmdID= 1  format=   "
		::= { iqdcoCmdEntry 1 }


	iqdcoSetupBuildNo OBJECT-TYPE
		SYNTAX		RollCallString
		MAX-ACCESS		read-only
		STATUS			current
		DESCRIPTION
				"TYPE: - Display
					Build_No  cmdID= 98  format=   "
		::= { iqdcoCmdEntry 98 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUTA
--
-- MIB ref		: swCardEventLogSlotXX       .6.73.78.80.85.84.65
-- absolute OID	: 1.3.6.1.4.1.7995.2.6.1.1.XX.6.73.78.80.85.84.65
-- Vary			: YES
--
-- Value(s)		: LOST
--				: OK
--				: FAIL;STD525
--				: FAIL;STD625
--				: FAIL;EDH
-- 				: FAIL;----------------
--				: FAIL;1---------------
--				: FAIL;1-2-------------
--				: FAIL;1-2-3-----------
--				: FAIL;1-2-3-4---------
--				: FAIL;1-2-3-4-5-------
--				: FAIL;1-2-3-4-5-6-----
--				: FAIL;1-2-3-4-5-6-7---
--				: FAIL;1-2-3-4-5-6-7-8-
--				: FAIL;1-2-3-4-5-6---8-
--				: FAIL;1-2-3-4-5---7---
--				: FAIL;1-2-3-4-5---7-8-
--				: FAIL;1-2-3-4-5-----8-
--				: FAIL;1-2-3-4---6-----
--				: FAIL;1-2-3-4---6-7---
--				: FAIL;1-2-3-4---6-7-8-
--				: FAIL;1-2-3-4---6---8-
--				: FAIL;1-2-3-4-----7---
--				: FAIL;1-2-3-4-----7-8-
--				: FAIL;1-2-3-4-------8-
--				: FAIL;1-2-3---5-------
--				: FAIL;1-2-3---5-6-----
--				: FAIL;1-2-3---5-6-7---
--				: FAIL;1-2-3---5-6-7-8-
--				: FAIL;1-2-3---5-6---8-
--				: FAIL;1-2-3---5---7---
--				: FAIL;1-2-3---5---7-8-
--				: FAIL;1-2-3---5-----8-
--				: FAIL;1-2-3-----6-----
--				: FAIL;1-2-3-----6-7---
--				: FAIL;1-2-3-----6-7-8-
--				: FAIL;1-2-3-----6---8-
--				: FAIL;1-2-3-------7---
--				: FAIL;1-2-3-------7-8-
--				: FAIL;1-2-3---------8-
--				: FAIL;1-2---4---------
--				: FAIL;1-2---4-5-------
--				: FAIL;1-2---4-5-6-----
--				: FAIL;1-2---4-5-6-7---
--				: FAIL;1-2---4-5-6-7-8-
--				: FAIL;1-2---4-5-6---8-
--				: FAIL;1-2---4-5---7---
--				: FAIL;1-2---4-5---7-8-
--				: FAIL;1-2---4-5-----8-
--				: FAIL;1-2---4---6-----
--				: FAIL;1-2---4---6-7---
--				: FAIL;1-2---4---6-7-8-
--				: FAIL;1-2---4---6---8-
--				: FAIL;1-2---4-----7---
--				: FAIL;1-2---4-----7-8-
--				: FAIL;1-2---4-------8-
--				: FAIL;1-2-----5-------
--				: FAIL;1-2-----5-6-----
--				: FAIL;1-2-----5-6-7---
--				: FAIL;1-2-----5-6-7-8-
--				: FAIL;1-2-----5-6---8-
--				: FAIL;1-2-----5---7---
--				: FAIL;1-2-----5---7-8-
--				: FAIL;1-2-----5-----8-
--				: FAIL;1-2-------6-----
--				: FAIL;1-2-------6-7---
--				: FAIL;1-2-------6-7-8-
--				: FAIL;1-2-------6---8-
--				: FAIL;1-2---------7---
--				: FAIL;1-2---------7-8-
--				: FAIL;1-2-----------8-
--				: FAIL;1---3-----------
--				: FAIL;1---3-4---------
--				: FAIL;1---3-4-5-------
--				: FAIL;1---3-4-5-6-----
--				: FAIL;1---3-4-5-6-7---
--				: FAIL;1---3-4-5-6-7-8-
--				: FAIL;1---3-4-5-6---8-
--				: FAIL;1---3-4-5---7---
--				: FAIL;1---3-4-5---7-8-
--				: FAIL;1---3-4-5-----8-
--				: FAIL;1---3-4---6-----
--				: FAIL;1---3-4---6-7---
--				: FAIL;1---3-4---6-7-8-
--				: FAIL;1---3-4---6---8-
--				: FAIL;1---3-4-----7---
--				: FAIL;1---3-4-----7-8-
--				: FAIL;1---3-4-------8-
--				: FAIL;1---3---5-------
--				: FAIL;1---3---5-6-----
--				: FAIL;1---3---5-6-7---
--				: FAIL;1---3---5-6-7-8-
--				: FAIL;1---3---5-6---8-
--				: FAIL;1---3---5---7---
--				: FAIL;1---3---5---7-8-
--				: FAIL;1---3---5-----8-
--				: FAIL;1---3-----6-----
--				: FAIL;1---3-----6-7---
--				: FAIL;1---3-----6-7-8-
--				: FAIL;1---3-----6---8-
--				: FAIL;1---3-------7---
--				: FAIL;1---3-------7-8-
--				: FAIL;1---3---------8-
--				: FAIL;1-----4---------
--				: FAIL;1-----4-5-------
--				: FAIL;1-----4-5-6-----
--				: FAIL;1-----4-5-6-7---
--				: FAIL;1-----4-5-6-7-8-
--				: FAIL;1-----4-5-6---8-
--				: FAIL;1-----4-5---7---
--				: FAIL;1-----4-5---7-8-
--				: FAIL;1-----4-5-----8-
--				: FAIL;1-----4---6-----
--				: FAIL;1-----4---6-7---
--				: FAIL;1-----4---6-7-8-
--				: FAIL;1-----4---6---8-
--				: FAIL;1-----4-----7---
--				: FAIL;1-----4-----7-8-
--				: FAIL;1-----4-------8-
--				: FAIL;1-------5-------
--				: FAIL;1-------5-6-----
--				: FAIL;1-------5-6-7---
--				: FAIL;1-------5-6-7-8-
--				: FAIL;1-------5-6---8-
--				: FAIL;1-------5---7---
--				: FAIL;1-------5---7-8-
--				: FAIL;1-------5-----8-
--				: FAIL;1---------6-----
--				: FAIL;1---------6-7---
--				: FAIL;1---------6-7-8-
--				: FAIL;1---------6---8-
--				: FAIL;1-----------7---
--				: FAIL;1-----------7-8-
--				: FAIL;1-------------8-
--				: FAIL;--2-------------
--				: FAIL;--2-3-----------
--				: FAIL;--2-3-4---------
--				: FAIL;--2-3-4-5-------
--				: FAIL;--2-3-4-5-6-----
--				: FAIL;--2-3-4-5-6-7---
--				: FAIL;--2-3-4-5-6-7-8-
--				: FAIL;--2-3-4-5-6---8-
--				: FAIL;--2-3-4-5---7---
--				: FAIL;--2-3-4-5---7-8-
--				: FAIL;--2-3-4-5-----8-
--				: FAIL;--2-3-4---6-----
--				: FAIL;--2-3-4---6-7---
--				: FAIL;--2-3-4---6-7-8-
--				: FAIL;--2-3-4---6---8-
--				: FAIL;--2-3-4-----7---
--				: FAIL;--2-3-4-----7-8-
--				: FAIL;--2-3-4-------8-
--				: FAIL;--2-3---5-------
--				: FAIL;--2-3---5-6-----
--				: FAIL;--2-3---5-6-7---
--				: FAIL;--2-3---5-6-7-8-
--				: FAIL;--2-3---5-6---8-
--				: FAIL;--2-3---5---7---
--				: FAIL;--2-3---5---7-8-
--				: FAIL;--2-3---5-----8-
--				: FAIL;--2-3-----6-----
--				: FAIL;--2-3-----6-7---
--				: FAIL;--2-3-----6-7-8-
--				: FAIL;--2-3-----6---8-
--				: FAIL;--2-3-------7---
--				: FAIL;--2-3-------7-8-
--				: FAIL;--2-3---------8-
--				: FAIL;--2---4---------
--				: FAIL;--2---4-5-------
--				: FAIL;--2---4-5-6-----
--				: FAIL;--2---4-5-6-7---
--				: FAIL;--2---4-5-6-7-8-
--				: FAIL;--2---4-5-6---8-
--				: FAIL;--2---4-5---7---
--				: FAIL;--2---4-5---7-8-
--				: FAIL;--2---4-5-----8-
--				: FAIL;--2---4---6-----
--				: FAIL;--2---4---6-7---
--				: FAIL;--2---4---6-7-8-
--				: FAIL;--2---4---6---8-
--				: FAIL;--2---4-----7---
--				: FAIL;--2---4-----7-8-
--				: FAIL;--2---4-------8-
--				: FAIL;--2-----5-------
--				: FAIL;--2-----5-6-----
--				: FAIL;--2-----5-6-7---
--				: FAIL;--2-----5-6-7-8-
--				: FAIL;--2-----5-6---8-
--				: FAIL;--2-----5---7---
--				: FAIL;--2-----5---7-8-
--				: FAIL;--2-----5-----8-
--				: FAIL;--2-------6-----
--				: FAIL;--2-------6-7---
--				: FAIL;--2-------6-7-8-
--				: FAIL;--2-------6---8-
--				: FAIL;--2---------7---
--				: FAIL;--2---------7-8-
--				: FAIL;--2-----------8-
--				: FAIL;----3-----------
--				: FAIL;----3-4---------
--				: FAIL;----3-4-5-------
--				: FAIL;----3-4-5-6-----
--				: FAIL;----3-4-5-6-7---
--				: FAIL;----3-4-5-6-7-8-
--				: FAIL;----3-4-5-6---8-
--				: FAIL;----3-4-5---7---
--				: FAIL;----3-4-5---7-8-
--				: FAIL;----3-4-5-----8-
--				: FAIL;----3-4---6-----
--				: FAIL;----3-4---6-7---
--				: FAIL;----3-4---6-7-8-
--				: FAIL;----3-4---6---8-
--				: FAIL;----3-4-----7---
--				: FAIL;----3-4-----7-8-
--				: FAIL;----3-4-------8-
--				: FAIL;----3---5-------
--				: FAIL;----3---5-6-----
--				: FAIL;----3---5-6-7---
--				: FAIL;----3---5-6-7-8-
--				: FAIL;----3---5-6---8-
--				: FAIL;----3---5---7---
--				: FAIL;----3---5---7-8-
--				: FAIL;----3---5-----8-
--				: FAIL;----3-----6-----
--				: FAIL;----3-----6-7---
--				: FAIL;----3-----6-7-8-
--				: FAIL;----3-----6---8-
--				: FAIL;----3-------7---
--				: FAIL;----3-------7-8-
--				: FAIL;----3---------8-
--				: FAIL;------4---------
--				: FAIL;------4-5-------
--				: FAIL;------4-5-6-----
--				: FAIL;------4-5-6-7---
--				: FAIL;------4-5-6-7-8-
--				: FAIL;------4-5-6---8-
--				: FAIL;------4-5---7---
--				: FAIL;------4-5---7-8-
--				: FAIL;------4-5-----8-
--				: FAIL;------4---6-----
--				: FAIL;------4---6-7---
--				: FAIL;------4---6-7-8-
--				: FAIL;------4---6---8-
--				: FAIL;------4-----7---
--				: FAIL;------4-----7-8-
--				: FAIL;------4-------8-
--				: FAIL;--------5-------
--				: FAIL;--------5-6-----
--				: FAIL;--------5-6-7---
--				: FAIL;--------5-6-7-8-
--				: FAIL;--------5-6---8-
--				: FAIL;--------5---7---
--				: FAIL;--------5---7-8-
--				: FAIL;--------5-----8-
--				: FAIL;----------6-----
--				: FAIL;----------6-7---
--				: FAIL;----------6-7-8-
--				: FAIL;----------6---8-
--				: FAIL;------------7---
--				: FAIL;------------7-8-
--				: FAIL;--------------8-
-- Comments		: 
--
---------------------------------------------------------------------------------------------------
-- Header		: INPUTB
--
-- MIB ref		: swCardEventLogSlotXX       .6.73.78.80.85.84.66
-- absolute OID	: 1.3.6.1.4.1.7995.2.6.1.1.XX.6.73.78.80.85.84.66
-- Vary			: YES
--
-- Value(s)		: LOST
--				: OK
--				: FAIL;STD525
--				: FAIL;STD625
--				: FAIL;EDH
-- 				: FAIL;----------------
--				: FAIL;1---------------
--				: FAIL;1-2-------------
--				: FAIL;1-2-3-----------
--				: FAIL;1-2-3-4---------
--				: FAIL;1-2-3-4-5-------
--				: FAIL;1-2-3-4-5-6-----
--				: FAIL;1-2-3-4-5-6-7---
--				: FAIL;1-2-3-4-5-6-7-8-
--				: FAIL;1-2-3-4-5-6---8-
--				: FAIL;1-2-3-4-5---7---
--				: FAIL;1-2-3-4-5---7-8-
--				: FAIL;1-2-3-4-5-----8-
--				: FAIL;1-2-3-4---6-----
--				: FAIL;1-2-3-4---6-7---
--				: FAIL;1-2-3-4---6-7-8-
--				: FAIL;1-2-3-4---6---8-
--				: FAIL;1-2-3-4-----7---
--				: FAIL;1-2-3-4-----7-8-
--				: FAIL;1-2-3-4-------8-
--				: FAIL;1-2-3---5-------
--				: FAIL;1-2-3---5-6-----
--				: FAIL;1-2-3---5-6-7---
--				: FAIL;1-2-3---5-6-7-8-
--				: FAIL;1-2-3---5-6---8-
--				: FAIL;1-2-3---5---7---
--				: FAIL;1-2-3---5---7-8-
--				: FAIL;1-2-3---5-----8-
--				: FAIL;1-2-3-----6-----
--				: FAIL;1-2-3-----6-7---
--				: FAIL;1-2-3-----6-7-8-
--				: FAIL;1-2-3-----6---8-
--				: FAIL;1-2-3-------7---
--				: FAIL;1-2-3-------7-8-
--				: FAIL;1-2-3---------8-
--				: FAIL;1-2---4---------
--				: FAIL;1-2---4-5-------
--				: FAIL;1-2---4-5-6-----
--				: FAIL;1-2---4-5-6-7---
--				: FAIL;1-2---4-5-6-7-8-
--				: FAIL;1-2---4-5-6---8-
--				: FAIL;1-2---4-5---7---
--				: FAIL;1-2---4-5---7-8-
--				: FAIL;1-2---4-5-----8-
--				: FAIL;1-2---4---6-----
--				: FAIL;1-2---4---6-7---
--				: FAIL;1-2---4---6-7-8-
--				: FAIL;1-2---4---6---8-
--				: FAIL;1-2---4-----7---
--				: FAIL;1-2---4-----7-8-
--				: FAIL;1-2---4-------8-
--				: FAIL;1-2-----5-------
--				: FAIL;1-2-----5-6-----
--				: FAIL;1-2-----5-6-7---
--				: FAIL;1-2-----5-6-7-8-
--				: FAIL;1-2-----5-6---8-
--				: FAIL;1-2-----5---7---
--				: FAIL;1-2-----5---7-8-
--				: FAIL;1-2-----5-----8-
--				: FAIL;1-2-------6-----
--				: FAIL;1-2-------6-7---
--				: FAIL;1-2-------6-7-8-
--				: FAIL;1-2-------6---8-
--				: FAIL;1-2---------7---
--				: FAIL;1-2---------7-8-
--				: FAIL;1-2-----------8-
--				: FAIL;1---3-----------
--				: FAIL;1---3-4---------
--				: FAIL;1---3-4-5-------
--				: FAIL;1---3-4-5-6-----
--				: FAIL;1---3-4-5-6-7---
--				: FAIL;1---3-4-5-6-7-8-
--				: FAIL;1---3-4-5-6---8-
--				: FAIL;1---3-4-5---7---
--				: FAIL;1---3-4-5---7-8-
--				: FAIL;1---3-4-5-----8-
--				: FAIL;1---3-4---6-----
--				: FAIL;1---3-4---6-7---
--				: FAIL;1---3-4---6-7-8-
--				: FAIL;1---3-4---6---8-
--				: FAIL;1---3-4-----7---
--				: FAIL;1---3-4-----7-8-
--				: FAIL;1---3-4-------8-
--				: FAIL;1---3---5-------
--				: FAIL;1---3---5-6-----
--				: FAIL;1---3---5-6-7---
--				: FAIL;1---3---5-6-7-8-
--				: FAIL;1---3---5-6---8-
--				: FAIL;1---3---5---7---
--				: FAIL;1---3---5---7-8-
--				: FAIL;1---3---5-----8-
--				: FAIL;1---3-----6-----
--				: FAIL;1---3-----6-7---
--				: FAIL;1---3-----6-7-8-
--				: FAIL;1---3-----6---8-
--				: FAIL;1---3-------7---
--				: FAIL;1---3-------7-8-
--				: FAIL;1---3---------8-
--				: FAIL;1-----4---------
--				: FAIL;1-----4-5-------
--				: FAIL;1-----4-5-6-----
--				: FAIL;1-----4-5-6-7---
--				: FAIL;1-----4-5-6-7-8-
--				: FAIL;1-----4-5-6---8-
--				: FAIL;1-----4-5---7---
--				: FAIL;1-----4-5---7-8-
--				: FAIL;1-----4-5-----8-
--				: FAIL;1-----4---6-----
--				: FAIL;1-----4---6-7---
--				: FAIL;1-----4---6-7-8-
--				: FAIL;1-----4---6---8-
--				: FAIL;1-----4-----7---
--				: FAIL;1-----4-----7-8-
--				: FAIL;1-----4-------8-
--				: FAIL;1-------5-------
--				: FAIL;1-------5-6-----
--				: FAIL;1-------5-6-7---
--				: FAIL;1-------5-6-7-8-
--				: FAIL;1-------5-6---8-
--				: FAIL;1-------5---7---
--				: FAIL;1-------5---7-8-
--				: FAIL;1-------5-----8-
--				: FAIL;1---------6-----
--				: FAIL;1---------6-7---
--				: FAIL;1---------6-7-8-
--				: FAIL;1---------6---8-
--				: FAIL;1-----------7---
--				: FAIL;1-----------7-8-
--				: FAIL;1-------------8-
--				: FAIL;--2-------------
--				: FAIL;--2-3-----------
--				: FAIL;--2-3-4---------
--				: FAIL;--2-3-4-5-------
--				: FAIL;--2-3-4-5-6-----
--				: FAIL;--2-3-4-5-6-7---
--				: FAIL;--2-3-4-5-6-7-8-
--				: FAIL;--2-3-4-5-6---8-
--				: FAIL;--2-3-4-5---7---
--				: FAIL;--2-3-4-5---7-8-
--				: FAIL;--2-3-4-5-----8-
--				: FAIL;--2-3-4---6-----
--				: FAIL;--2-3-4---6-7---
--				: FAIL;--2-3-4---6-7-8-
--				: FAIL;--2-3-4---6---8-
--				: FAIL;--2-3-4-----7---
--				: FAIL;--2-3-4-----7-8-
--				: FAIL;--2-3-4-------8-
--				: FAIL;--2-3---5-------
--				: FAIL;--2-3---5-6-----
--				: FAIL;--2-3---5-6-7---
--				: FAIL;--2-3---5-6-7-8-
--				: FAIL;--2-3---5-6---8-
--				: FAIL;--2-3---5---7---
--				: FAIL;--2-3---5---7-8-
--				: FAIL;--2-3---5-----8-
--				: FAIL;--2-3-----6-----
--				: FAIL;--2-3-----6-7---
--				: FAIL;--2-3-----6-7-8-
--				: FAIL;--2-3-----6---8-
--				: FAIL;--2-3-------7---
--				: FAIL;--2-3-------7-8-
--				: FAIL;--2-3---------8-
--				: FAIL;--2---4---------
--				: FAIL;--2---4-5-------
--				: FAIL;--2---4-5-6-----
--				: FAIL;--2---4-5-6-7---
--				: FAIL;--2---4-5-6-7-8-
--				: FAIL;--2---4-5-6---8-
--				: FAIL;--2---4-5---7---
--				: FAIL;--2---4-5---7-8-
--				: FAIL;--2---4-5-----8-
--				: FAIL;--2---4---6-----
--				: FAIL;--2---4---6-7---
--				: FAIL;--2---4---6-7-8-
--				: FAIL;--2---4---6---8-
--				: FAIL;--2---4-----7---
--				: FAIL;--2---4-----7-8-
--				: FAIL;--2---4-------8-
--				: FAIL;--2-----5-------
--				: FAIL;--2-----5-6-----
--				: FAIL;--2-----5-6-7---
--				: FAIL;--2-----5-6-7-8-
--				: FAIL;--2-----5-6---8-
--				: FAIL;--2-----5---7---
--				: FAIL;--2-----5---7-8-
--				: FAIL;--2-----5-----8-
--				: FAIL;--2-------6-----
--				: FAIL;--2-------6-7---
--				: FAIL;--2-------6-7-8-
--				: FAIL;--2-------6---8-
--				: FAIL;--2---------7---
--				: FAIL;--2---------7-8-
--				: FAIL;--2-----------8-
--				: FAIL;----3-----------
--				: FAIL;----3-4---------
--				: FAIL;----3-4-5-------
--				: FAIL;----3-4-5-6-----
--				: FAIL;----3-4-5-6-7---
--				: FAIL;----3-4-5-6-7-8-
--				: FAIL;----3-4-5-6---8-
--				: FAIL;----3-4-5---7---
--				: FAIL;----3-4-5---7-8-
--				: FAIL;----3-4-5-----8-
--				: FAIL;----3-4---6-----
--				: FAIL;----3-4---6-7---
--				: FAIL;----3-4---6-7-8-
--				: FAIL;----3-4---6---8-
--				: FAIL;----3-4-----7---
--				: FAIL;----3-4-----7-8-
--				: FAIL;----3-4-------8-
--				: FAIL;----3---5-------
--				: FAIL;----3---5-6-----
--				: FAIL;----3---5-6-7---
--				: FAIL;----3---5-6-7-8-
--				: FAIL;----3---5-6---8-
--				: FAIL;----3---5---7---
--				: FAIL;----3---5---7-8-
--				: FAIL;----3---5-----8-
--				: FAIL;----3-----6-----
--				: FAIL;----3-----6-7---
--				: FAIL;----3-----6-7-8-
--				: FAIL;----3-----6---8-
--				: FAIL;----3-------7---
--				: FAIL;----3-------7-8-
--				: FAIL;----3---------8-
--				: FAIL;------4---------
--				: FAIL;------4-5-------
--				: FAIL;------4-5-6-----
--				: FAIL;------4-5-6-7---
--				: FAIL;------4-5-6-7-8-
--				: FAIL;------4-5-6---8-
--				: FAIL;------4-5---7---
--				: FAIL;------4-5---7-8-
--				: FAIL;------4-5-----8-
--				: FAIL;------4---6-----
--				: FAIL;------4---6-7---
--				: FAIL;------4---6-7-8-
--				: FAIL;------4---6---8-
--				: FAIL;------4-----7---
--				: FAIL;------4-----7-8-
--				: FAIL;------4-------8-
--				: FAIL;--------5-------
--				: FAIL;--------5-6-----
--				: FAIL;--------5-6-7---
--				: FAIL;--------5-6-7-8-
--				: FAIL;--------5-6---8-
--				: FAIL;--------5---7---
--				: FAIL;--------5---7-8-
--				: FAIL;--------5-----8-
--				: FAIL;----------6-----
--				: FAIL;----------6-7---
--				: FAIL;----------6-7-8-
--				: FAIL;----------6---8-
--				: FAIL;------------7---
--				: FAIL;------------7-8-
--				: FAIL;--------------8-
-- Comments		: 
--
---------------------------------------------------------------------------------------------------
-- Header		: OUTPUT
--
-- MIB ref		: swCardEventLogSlotXX       .6.79.85.84.80.85.84
-- absolute OID	: 1.3.6.1.4.1.7995.2.6.1.1.XX.6.79.85.84.80.85.84
-- Vary			: YES
--
-- Value(s)		: A
--				: B
-- Comments		: 
--
---------------------------------------------------------------------------------------------------
