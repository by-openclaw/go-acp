-- ************************************************************************************
-- Snell&Wilcox Card:IQBAIR
--        Module Id#:100
--       Command Set:8
--          Filename:SNELL-IQBAIR-CMD-MIB.mib
--            Author:Jonathan Riches
--              Date:17/06/2005
--              Time:14:46
-- Last Modification:Logging comments added
--   Version Control:CVS $Id: SNELL-IQBAIR-CMD-MIB.mib 227 2006-12-22 13:14:20Z nikolaoskatsampekis $
-- Copyright (c) 2006 Snell & Wilcox Ltd
-- All rights reserved.
--
-- ************************************************************************************

SNELL-IQBAIR-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQBAIR,
    moduleIQBAIRMIB
        FROM SNELL-WILCOX-PRODUCT-REG;

 moduleIQBAIRCmdMi MODULE-IDENTITY
    LAST-UPDATED "0506171446Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQBAIRMIB 1 }




--********************************************************************************
--*
--*  Snell Wilcox Card:
--*  command set:
--*  list commands/menus:
--*
--******************************************************************************
	iqbairCmdTable OBJECT-TYPE
		SYNTAX			SEQUENCE OF IqbairCmdEntry
		MAX-ACCESS		not-accessible
		STATUS			current
		DESCRIPTION
				"Note the instance of this table is relected in the command set Version"
		::= { moduleIQBAIR 1 }

	iqbairCmdEntry OBJECT-TYPE
		SYNTAX		IqbairCmdEntry
		MAX-ACCESS		not-accessible
		STATUS			current
		DESCRIPTION
				"Entry in command table."
		INDEX	{ iqbairSlotIndex }
		::= { iqbairCmdTable 1 }

	IqbairCmdEntry ::=
		SEQUENCE {
			iqbairSlotIndex
				Unsigned32,
			iqbairAssignInserterA
				INTEGER,
			iqbairAssignInserterB
				INTEGER,
			iqbairInserterInserterA
				INTEGER,
			iqbairInserterInserterB
				INTEGER,
			iqbairInputsInput1InvertL
				INTEGER,
			iqbairInputsInput1InvertR
				INTEGER,
			iqbairInputsInput1Embed
				INTEGER,
			iqbairInputsInput2InvertL
				INTEGER,
			iqbairInputsInput2InvertR
				INTEGER,
			iqbairInputsInput2Embed
				INTEGER,
			iqbairDisplay
				INTEGER,
			iqbairEDHShowStats
				INTEGER,
			iqbairEDHResetStats
				INTEGER,
			iqbairEDHEDHOutEnable
				INTEGER,
			iqbairSetupAncDataStrip
				INTEGER,
			iqbairSetupSetDefaultOutput
				INTEGER,
			iqbairNamesAESInputNamesInput1
				RollCallString,
			iqbairNamesAESInputNamesInput2
				RollCallString,
			iqbairNamesOutputNamesOutput1
				RollCallString,
			iqbairNamesOutputNamesOutput2
				RollCallString,
			iqbairNamesOutputNamesOutput3
				RollCallString,
			iqbairNamesOutputNamesOutput4
				RollCallString,
			iqbairNamesOutputNamesOutput5
				RollCallString,
			iqbairNamesOutputNamesOutput6
				RollCallString,
			iqbairNamesOutputNamesOutput7
				RollCallString,
			iqbairNamesOutputNamesOutput8
				RollCallString,
			iqbairSetupNamesPresetNames
				INTEGER,
			iqbairInputRemappingRemapPairs12To
				INTEGER,
			iqbairInputRemappingRemapPairs12ToTagPairs12
				INTEGER,
			iqbairInputRemappingRemapPairs34To
				INTEGER,
			iqbairInputRemappingRemapPairs34ToTagPairs34
				INTEGER,
			iqbairInputRemappingRemapPairs56To
				INTEGER,
			iqbairInputRemappingRemapPairs56ToTagPairs56
				INTEGER,
			iqbairInputRemappingRemapPairs78To
				INTEGER,
			iqbairInputRemappingRemapPairs78ToTagPairs78
				INTEGER,
			iqbairSetupSampleDist
				INTEGER,
			iqbairSetupLoggingVideoInputChange
				INTEGER,
			iqbairSetupLoggingD1AudioChange
				INTEGER,
			iqbairSetupLoggingAudioInputChange
				INTEGER,
			iqbairSetupLoggingEDHErrors
				INTEGER,
			iqbairSetupPresetUnit
				INTEGER,
			iqbairSetupSoftwareVersion
				RollCallString,
			iqbairSetupSerialNo
				RollCallString
		}

	iqbairSlotIndex OBJECT-TYPE
		SYNTAX		Unsigned32
		MAX-ACCESS		not-accessible
		STATUS			current
		DESCRIPTION
				"The unique Index value for each slot.  Its value
					ranges between 1 and the value of slotNumber."
		::= { iqbairCmdEntry 0 }


	iqbairAssignInserterA OBJECT-TYPE
		SYNTAX		INTEGER {
							val_1_Pair_1(0),
							val_2_Pair_2(1),
							val_3_Pair_3(2),
							val_4_Pair_4(3),
							val_5_Pair_5(4),
							val_6_Pair_6(5),
							val_7_Pair_7(6),
							val_8_Pair_8(7)
							}
		MAX-ACCESS		read-write
		STATUS			current
		DESCRIPTION
				"TYPE: - RadiobuttonList
					Inserter_A  cmdID= 5 
					1:Pair_1  value= 0  
					2:Pair_2  value= 1  
					3:Pair_3  value= 2  
					4:Pair_4  value= 3  
					5:Pair_5  value= 4  
					6:Pair_6  value= 5  
					7:Pair_7  value= 6  
					8:Pair_8  value= 7  "
		::= { iqbairCmdEntry 5 }


	iqbairAssignInserterB OBJECT-TYPE
		SYNTAX		INTEGER {
							val_1_Pair_1(0),
							val_2_Pair_2(1),
							val_3_Pair_3(2),
							val_4_Pair_4(3),
							val_5_Pair_5(4),
							val_6_Pair_6(5),
							val_7_Pair_7(6),
							val_8_Pair_8(7)
							}
		MAX-ACCESS		read-write
		STATUS			current
		DESCRIPTION
				"TYPE: - RadiobuttonList
					Inserter_B  cmdID= 6 
					1:Pair_1  value= 0  
					2:Pair_2  value= 1  
					3:Pair_3  value= 2  
					4:Pair_4  value= 3  
					5:Pair_5  value= 4  
					6:Pair_6  value= 5  
					7:Pair_7  value= 6  
					8:Pair_8  value= 7  "
		::= { iqbairCmdEntry 6 }


	iqbairInserterInserterA OBJECT-TYPE
		SYNTAX		INTEGER {
							val_No_Insert(0),
							val_Default_Insertion(1),
							val_Input_1(2)
							}
		MAX-ACCESS		read-write
		STATUS			current
		DESCRIPTION
				"TYPE: - RadiobuttonList
					Inserter_A  cmdID= 28 
					No_Insert  value= 0  
					Default_Insertion  value= 1  
					Input_1  value= 2  "
		::= { iqbairCmdEntry 28 }


	iqbairInserterInserterB OBJECT-TYPE
		SYNTAX		INTEGER {
							val_No_Insert(0),
							val_Default_Insertion(1),
							val_Input_2(2)
							}
		MAX-ACCESS		read-write
		STATUS			current
		DESCRIPTION
				"TYPE: - RadiobuttonList
					Inserter_B  cmdID= 29 
					No_Insert  value= 0  
					Default_Insertion  value= 1  
					Input_2  value= 2  "
		::= { iqbairCmdEntry 29 }


	iqbairInputsInput1InvertL OBJECT-TYPE
		SYNTAX		INTEGER { disable(0), enable(1) }
		MAX-ACCESS		read-write
		STATUS			current
		DESCRIPTION
				"TYPE: - Checkbox
					Invert_L  cmdID= 44 "
		::= { iqbairCmdEntry 44 }


	iqbairInputsInput1InvertR OBJECT-TYPE
		SYNTAX		INTEGER { disable(0), enable(1) }
		MAX-ACCESS		read-write
		STATUS			current
		DESCRIPTION
				"TYPE: - Checkbox
					Invert_R  cmdID= 45 "
		::= { iqbairCmdEntry 45 }


	iqbairInputsInput1Embed OBJECT-TYPE
		SYNTAX		INTEGER {
							val_Input_1_Left_Right(0),
							val_Input_1_Right_Left(1),
							val_Input_1_Left_Left(2),
							val_Input_1_Right_Right(3)
							}
		MAX-ACCESS		read-write
		STATUS			current
		DESCRIPTION
				"TYPE: - RadiobuttonList
					Embed  cmdID= 41 
					Input_1_Left/Right  value= 0  
					Input_1_Right/Left  value= 1  
					Input_1_Left/Left  value= 2  
					Input_1_Right/Right  value= 3  "
		::= { iqbairCmdEntry 41 }


	iqbairInputsInput2InvertL OBJECT-TYPE
		SYNTAX		INTEGER { disable(0), enable(1) }
		MAX-ACCESS		read-write
		STATUS			current
		DESCRIPTION
				"TYPE: - Checkbox
					Invert_L  cmdID= 46 "
		::= { iqbairCmdEntry 46 }


	iqbairInputsInput2InvertR OBJECT-TYPE
		SYNTAX		INTEGER { disable(0), enable(1) }
		MAX-ACCESS		read-write
		STATUS			current
		DESCRIPTION
				"TYPE: - Checkbox
					Invert_R  cmdID= 47 "
		::= { iqbairCmdEntry 47 }


	iqbairInputsInput2Embed OBJECT-TYPE
		SYNTAX		INTEGER {
							val_Input_2_Left_Right(0),
							val_Input_2_Right_Left(1),
							val_Input_2_Left_Left(2),
							val_Input_2_Right_Right(3)
							}
		MAX-ACCESS		read-write
		STATUS			current
		DESCRIPTION
				"TYPE: - RadiobuttonList
					Embed  cmdID= 42 
					Input_2_Left/Right  value= 0  
					Input_2_Right/Left  value= 1  
					Input_2_Left/Left  value= 2  
					Input_2_Right/Right  value= 3  "
		::= { iqbairCmdEntry 42 }


	iqbairDisplay OBJECT-TYPE
		SYNTAX		INTEGER {
							val_Embedded_D1(4),
							val_AES_Inputs(5)
							}
		MAX-ACCESS		read-write
		STATUS			current
		DESCRIPTION
				"TYPE: - RadiobuttonList
					Display  cmdID= 7 
					Embedded_D1  value= 4  
					AES_Inputs  value= 5  "
		::= { iqbairCmdEntry 7 }


	iqbairEDHShowStats OBJECT-TYPE
		SYNTAX		INTEGER { disable(0), enable(1) }
		MAX-ACCESS		read-write
		STATUS			current
		DESCRIPTION
				"TYPE: - Checkbox
					Show_Stats  cmdID= 43 "
		::= { iqbairCmdEntry 43 }


	iqbairEDHResetStats OBJECT-TYPE
		SYNTAX		INTEGER { noAction(0),val_Reset_Stats(1) }
		MAX-ACCESS		read-write
		STATUS			current
		DESCRIPTION
				"TYPE: - Button
					Reset_Stats  cmdID= 8  value= 1  "
		::= { iqbairCmdEntry 8 }


	iqbairEDHEDHOutEnable OBJECT-TYPE
		SYNTAX		INTEGER { disable(0), enable(1) }
		MAX-ACCESS		read-write
		STATUS			current
		DESCRIPTION
				"TYPE: - Checkbox
					EDH_Out_Enable  cmdID= 9 "
		::= { iqbairCmdEntry 9 }


	iqbairSetupAncDataStrip OBJECT-TYPE
		SYNTAX		INTEGER { disable(0), enable(1) }
		MAX-ACCESS		read-write
		STATUS			current
		DESCRIPTION
				"TYPE: - Checkbox
					Anc_Data_Strip  cmdID= 26 "
		::= { iqbairCmdEntry 26 }


	iqbairSetupSetDefaultOutput OBJECT-TYPE
		SYNTAX		INTEGER {
							val_No_Insert(2),
							val_Tone(0),
							val_Silence(1)
							}
		MAX-ACCESS		read-write
		STATUS			current
		DESCRIPTION
				"TYPE: - RadiobuttonList
					Set_Default_Output  cmdID= 27 
					No_Insert  value= 2  
					Tone  value= 0  
					Silence  value= 1  "
		::= { iqbairCmdEntry 27 }


	iqbairNamesAESInputNamesInput1 OBJECT-TYPE
		SYNTAX		RollCallString
		MAX-ACCESS		read-write
		STATUS			current
		DESCRIPTION
				"TYPE: - Editstring
					Input_1  cmdID= 18  "
		::= { iqbairCmdEntry 18 }


	iqbairNamesAESInputNamesInput2 OBJECT-TYPE
		SYNTAX		RollCallString
		MAX-ACCESS		read-write
		STATUS			current
		DESCRIPTION
				"TYPE: - Editstring
					Input_2  cmdID= 19  "
		::= { iqbairCmdEntry 19 }


	iqbairNamesOutputNamesOutput1 OBJECT-TYPE
		SYNTAX		RollCallString
		MAX-ACCESS		read-write
		STATUS			current
		DESCRIPTION
				"TYPE: - Editstring
					Output_1  cmdID= 10  "
		::= { iqbairCmdEntry 10 }


	iqbairNamesOutputNamesOutput2 OBJECT-TYPE
		SYNTAX		RollCallString
		MAX-ACCESS		read-write
		STATUS			current
		DESCRIPTION
				"TYPE: - Editstring
					Output_2  cmdID= 11  "
		::= { iqbairCmdEntry 11 }


	iqbairNamesOutputNamesOutput3 OBJECT-TYPE
		SYNTAX		RollCallString
		MAX-ACCESS		read-write
		STATUS			current
		DESCRIPTION
				"TYPE: - Editstring
					Output_3  cmdID= 12  "
		::= { iqbairCmdEntry 12 }


	iqbairNamesOutputNamesOutput4 OBJECT-TYPE
		SYNTAX		RollCallString
		MAX-ACCESS		read-write
		STATUS			current
		DESCRIPTION
				"TYPE: - Editstring
					Output_4  cmdID= 13  "
		::= { iqbairCmdEntry 13 }


	iqbairNamesOutputNamesOutput5 OBJECT-TYPE
		SYNTAX		RollCallString
		MAX-ACCESS		read-write
		STATUS			current
		DESCRIPTION
				"TYPE: - Editstring
					Output_5  cmdID= 14  "
		::= { iqbairCmdEntry 14 }


	iqbairNamesOutputNamesOutput6 OBJECT-TYPE
		SYNTAX		RollCallString
		MAX-ACCESS		read-write
		STATUS			current
		DESCRIPTION
				"TYPE: - Editstring
					Output_6  cmdID= 15  "
		::= { iqbairCmdEntry 15 }


	iqbairNamesOutputNamesOutput7 OBJECT-TYPE
		SYNTAX		RollCallString
		MAX-ACCESS		read-write
		STATUS			current
		DESCRIPTION
				"TYPE: - Editstring
					Output_7  cmdID= 16  "
		::= { iqbairCmdEntry 16 }


	iqbairNamesOutputNamesOutput8 OBJECT-TYPE
		SYNTAX		RollCallString
		MAX-ACCESS		read-write
		STATUS			current
		DESCRIPTION
				"TYPE: - Editstring
					Output_8  cmdID= 17  "
		::= { iqbairCmdEntry 17 }


	iqbairSetupNamesPresetNames OBJECT-TYPE
		SYNTAX		INTEGER {
							val_Preset_Names(1)
							}
		MAX-ACCESS		read-write
		STATUS			current
		DESCRIPTION
				"TYPE: - RadiobuttonList
					Preset_Names  cmdID= 25 
					Preset_Names  value= 1  "
		::= { iqbairCmdEntry 25 }


	iqbairInputRemappingRemapPairs12To OBJECT-TYPE
		SYNTAX		INTEGER {
							val_Pairs_1_2(0),
							val_Pairs_3_4(1),
							val_Pairs_5_6(2),
							val_Pairs_7_8(3)
							}
		MAX-ACCESS		read-write
		STATUS			current
		DESCRIPTION
				"TYPE: - Button
					Pairs_1&2  cmdID= 33  value= 0  
					Pairs_3&4  cmdID= 33  value= 1  
					Pairs_5&6  cmdID= 33  value= 2  
					Pairs_7&8  cmdID= 33  value= 3  "
		::= { iqbairCmdEntry 33 }


	iqbairInputRemappingRemapPairs12ToTagPairs12 OBJECT-TYPE
		SYNTAX		INTEGER { disable(0), enable(1) }
		MAX-ACCESS		read-write
		STATUS			current
		DESCRIPTION
				"TYPE: - Checkbox
					Tag_Pairs_1&2  cmdID= 37 "
		::= { iqbairCmdEntry 37 }


	iqbairInputRemappingRemapPairs34To OBJECT-TYPE
		SYNTAX		INTEGER {
							val_Pairs_1_2(0),
							val_Pairs_3_4(1),
							val_Pairs_5_6(2),
							val_Pairs_7_8(3)
							}
		MAX-ACCESS		read-write
		STATUS			current
		DESCRIPTION
				"TYPE: - Button
					Pairs_1&2  cmdID= 34  value= 0  
					Pairs_3&4  cmdID= 34  value= 1  
					Pairs_5&6  cmdID= 34  value= 2  
					Pairs_7&8  cmdID= 34  value= 3  "
		::= { iqbairCmdEntry 34 }


	iqbairInputRemappingRemapPairs34ToTagPairs34 OBJECT-TYPE
		SYNTAX		INTEGER { disable(0), enable(1) }
		MAX-ACCESS		read-write
		STATUS			current
		DESCRIPTION
				"TYPE: - Checkbox
					Tag_Pairs_3&4  cmdID= 38 "
		::= { iqbairCmdEntry 38 }


	iqbairInputRemappingRemapPairs56To OBJECT-TYPE
		SYNTAX		INTEGER {
							val_Pairs_1_2(0),
							val_Pairs_3_4(1),
							val_Pairs_5_6(2),
							val_Pairs_7_8(3)
							}
		MAX-ACCESS		read-write
		STATUS			current
		DESCRIPTION
				"TYPE: - Button
					Pairs_1&2  cmdID= 35  value= 0  
					Pairs_3&4  cmdID= 35  value= 1  
					Pairs_5&6  cmdID= 35  value= 2  
					Pairs_7&8  cmdID= 35  value= 3  "
		::= { iqbairCmdEntry 35 }


	iqbairInputRemappingRemapPairs56ToTagPairs56 OBJECT-TYPE
		SYNTAX		INTEGER { disable(0), enable(1) }
		MAX-ACCESS		read-write
		STATUS			current
		DESCRIPTION
				"TYPE: - Checkbox
					Tag_Pairs_5&6  cmdID= 39 "
		::= { iqbairCmdEntry 39 }


	iqbairInputRemappingRemapPairs78To OBJECT-TYPE
		SYNTAX		INTEGER {
							val_Pairs_1_2(0),
							val_Pairs_3_4(1),
							val_Pairs_5_6(2),
							val_Pairs_7_8(3)
							}
		MAX-ACCESS		read-write
		STATUS			current
		DESCRIPTION
				"TYPE: - Button
					Pairs_1&2  cmdID= 36  value= 0  
					Pairs_3&4  cmdID= 36  value= 1  
					Pairs_5&6  cmdID= 36  value= 2  
					Pairs_7&8  cmdID= 36  value= 3  "
		::= { iqbairCmdEntry 36 }


	iqbairInputRemappingRemapPairs78ToTagPairs78 OBJECT-TYPE
		SYNTAX		INTEGER { disable(0), enable(1) }
		MAX-ACCESS		read-write
		STATUS			current
		DESCRIPTION
				"TYPE: - Checkbox
					Tag_Pairs_7&8  cmdID= 40 "
		::= { iqbairCmdEntry 40 }


	iqbairSetupSampleDist OBJECT-TYPE
		SYNTAX		INTEGER {
							val_Standard(0),
							val_Alternative(1)
							}
		MAX-ACCESS		read-write
		STATUS			current
		DESCRIPTION
				"TYPE: - RadiobuttonList
					Sample_Dist  cmdID= 48 
					Standard  value= 0  
					Alternative  value= 1  "
		::= { iqbairCmdEntry 48 }


	iqbairSetupLoggingVideoInputChange OBJECT-TYPE
		SYNTAX		INTEGER { disable(0), enable(1) }
		MAX-ACCESS		read-write
		STATUS			current
		DESCRIPTION
				"TYPE: - Checkbox
					Video_Input_Change  cmdID= 22 "
		::= { iqbairCmdEntry 22 }


	iqbairSetupLoggingD1AudioChange OBJECT-TYPE
		SYNTAX		INTEGER { disable(0), enable(1) }
		MAX-ACCESS		read-write
		STATUS			current
		DESCRIPTION
				"TYPE: - Checkbox
					D1_Audio_Change  cmdID= 49 "
		::= { iqbairCmdEntry 49 }


	iqbairSetupLoggingAudioInputChange OBJECT-TYPE
		SYNTAX		INTEGER { disable(0), enable(1) }
		MAX-ACCESS		read-write
		STATUS			current
		DESCRIPTION
				"TYPE: - Checkbox
					Audio_Input_Change  cmdID= 24 "
		::= { iqbairCmdEntry 24 }


	iqbairSetupLoggingEDHErrors OBJECT-TYPE
		SYNTAX		INTEGER { disable(0), enable(1) }
		MAX-ACCESS		read-write
		STATUS			current
		DESCRIPTION
				"TYPE: - Checkbox
					EDH_Errors  cmdID= 23 "
		::= { iqbairCmdEntry 23 }


	iqbairSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqbairCmdEntry 3 }


	iqbairSetupSoftwareVersion OBJECT-TYPE
		SYNTAX		RollCallString
		MAX-ACCESS		read-only
		STATUS			current
		DESCRIPTION
				"TYPE: - Display
					Software_Version  cmdID= 2  format=   "
		::= { iqbairCmdEntry 2 }


	iqbairSetupSerialNo OBJECT-TYPE
		SYNTAX		RollCallString
		MAX-ACCESS		read-only
		STATUS			current
		DESCRIPTION
				"TYPE: - Display
					Serial_No  cmdID= 1  format=   "
		::= { iqbairCmdEntry 1 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: This log field shows the unique S&W serial number for this
--				: board instance. 
--
---------------------------------------------------------------------------------------------------
-- Header		: AES
--
-- MIB ref		: swCardEventLogSlotXX       .3.65.69.83
-- absolute OID	: 1.3.6.1.4.1.7995.2.6.1.1.XX.3.65.69.83
-- Vary			: YES
--
-- Value(s)		: LOST:CHAN 1
--				: OK:CHAN 1
--				: LOST:CHAN 2
--				: OK:CHAN 2
-- Comments		: This log field shows the detected digital audio input state. 
--				: LOST:CHAN 1: Indicates that Channel 1 AES pairs are not present.
--				: OK:CHAN 1: Indicates that Channel 1 AES pairs are present.
--				: LOST:CHAN 2: Indicates that Channel 2 AES pairs are not present.
--				: OK:CHAN 2: Indicates that Channel 2 AES pairs are present.
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE
--				: OK
--				: FAIL
--				: RESET
-- Comments		: This log field shows the EDH status of the SDI
--				: input.
--				: EDH (Error Detection Handling) as specified by
--				: SMPTE RP 165-1994 and by the ITU standard ITU-R BT.1304.
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: This log field shows whether the IQ frame gateway card
--				: can communicate with this module.
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: UNKNOWN
--				: 625
--				: 525
-- Comments		: This log field shows the detected video standard of the detected SDI input.
--
---------------------------------------------------------------------------------------------------
-- Header		: AUDIO
--
-- MIB ref		: swCardEventLogSlotXX       .5.65.85.68.73.79
-- absolute OID	: 1.3.6.1.4.1.7995.2.6.1.1.XX.5.65.85.68.73.79
-- Vary			: YES
--
-- Value(s)		: ---------------
--				: 
-- Value(s)		: ----------------
--				: 1---------------
--				: 1-2-------------
--				: 1-2-3-----------
--				: 1-2-3-4---------
--				: 1-2-3-4-5-------
--				: 1-2-3-4-5-6-----
--				: 1-2-3-4-5-6-7---
--				: 1-2-3-4-5-6-7-8-
--				: 1-2-3-4-5-6---8-
--				: 1-2-3-4-5---7---
--				: 1-2-3-4-5---7-8-
--				: 1-2-3-4-5-----8-
--				: 1-2-3-4---6-----
--				: 1-2-3-4---6-7---
--				: 1-2-3-4---6-7-8-
--				: 1-2-3-4---6---8-
--				: 1-2-3-4-----7---
--				: 1-2-3-4-----7-8-
--				: 1-2-3-4-------8-
--				: 1-2-3---5-------
--				: 1-2-3---5-6-----
--				: 1-2-3---5-6-7---
--				: 1-2-3---5-6-7-8-
--				: 1-2-3---5-6---8-
--				: 1-2-3---5---7---
--				: 1-2-3---5---7-8-
--				: 1-2-3---5-----8-
--				: 1-2-3-----6-----
--				: 1-2-3-----6-7---
--				: 1-2-3-----6-7-8-
--				: 1-2-3-----6---8-
--				: 1-2-3-------7---
--				: 1-2-3-------7-8-
--				: 1-2-3---------8-
--				: 1-2---4---------
--				: 1-2---4-5-------
--				: 1-2---4-5-6-----
--				: 1-2---4-5-6-7---
--				: 1-2---4-5-6-7-8-
--				: 1-2---4-5-6---8-
--				: 1-2---4-5---7---
--				: 1-2---4-5---7-8-
--				: 1-2---4-5-----8-
--				: 1-2---4---6-----
--				: 1-2---4---6-7---
--				: 1-2---4---6-7-8-
--				: 1-2---4---6---8-
--				: 1-2---4-----7---
--				: 1-2---4-----7-8-
--				: 1-2---4-------8-
--				: 1-2-----5-------
--				: 1-2-----5-6-----
--				: 1-2-----5-6-7---
--				: 1-2-----5-6-7-8-
--				: 1-2-----5-6---8-
--				: 1-2-----5---7---
--				: 1-2-----5---7-8-
--				: 1-2-----5-----8-
--				: 1-2-------6-----
--				: 1-2-------6-7---
--				: 1-2-------6-7-8-
--				: 1-2-------6---8-
--				: 1-2---------7---
--				: 1-2---------7-8-
--				: 1-2-----------8-
--				: 1---3-----------
--				: 1---3-4---------
--				: 1---3-4-5-------
--				: 1---3-4-5-6-----
--				: 1---3-4-5-6-7---
--				: 1---3-4-5-6-7-8-
--				: 1---3-4-5-6---8-
--				: 1---3-4-5---7---
--				: 1---3-4-5---7-8-
--				: 1---3-4-5-----8-
--				: 1---3-4---6-----
--				: 1---3-4---6-7---
--				: 1---3-4---6-7-8-
--				: 1---3-4---6---8-
--				: 1---3-4-----7---
--				: 1---3-4-----7-8-
--				: 1---3-4-------8-
--				: 1---3---5-------
--				: 1---3---5-6-----
--				: 1---3---5-6-7---
--				: 1---3---5-6-7-8-
--				: 1---3---5-6---8-
--				: 1---3---5---7---
--				: 1---3---5---7-8-
--				: 1---3---5-----8-
--				: 1---3-----6-----
--				: 1---3-----6-7---
--				: 1---3-----6-7-8-
--				: 1---3-----6---8-
--				: 1---3-------7---
--				: 1---3-------7-8-
--				: 1---3---------8-
--				: 1-----4---------
--				: 1-----4-5-------
--				: 1-----4-5-6-----
--				: 1-----4-5-6-7---
--				: 1-----4-5-6-7-8-
--				: 1-----4-5-6---8-
--				: 1-----4-5---7---
--				: 1-----4-5---7-8-
--				: 1-----4-5-----8-
--				: 1-----4---6-----
--				: 1-----4---6-7---
--				: 1-----4---6-7-8-
--				: 1-----4---6---8-
--				: 1-----4-----7---
--				: 1-----4-----7-8-
--				: 1-----4-------8-
--				: 1-------5-------
--				: 1-------5-6-----
--				: 1-------5-6-7---
--				: 1-------5-6-7-8-
--				: 1-------5-6---8-
--				: 1-------5---7---
--				: 1-------5---7-8-
--				: 1-------5-----8-
--				: 1---------6-----
--				: 1---------6-7---
--				: 1---------6-7-8-
--				: 1---------6---8-
--				: 1-----------7---
--				: 1-----------7-8-
--				: 1-------------8-
--				: --2-------------
--				: --2-3-----------
--				: --2-3-4---------
--				: --2-3-4-5-------
--				: --2-3-4-5-6-----
--				: --2-3-4-5-6-7---
--				: --2-3-4-5-6-7-8-
--				: --2-3-4-5-6---8-
--				: --2-3-4-5---7---
--				: --2-3-4-5---7-8-
--				: --2-3-4-5-----8-
--				: --2-3-4---6-----
--				: --2-3-4---6-7---
--				: --2-3-4---6-7-8-
--				: --2-3-4---6---8-
--				: --2-3-4-----7---
--				: --2-3-4-----7-8-
--				: --2-3-4-------8-
--				: --2-3---5-------
--				: --2-3---5-6-----
--				: --2-3---5-6-7---
--				: --2-3---5-6-7-8-
--				: --2-3---5-6---8-
--				: --2-3---5---7---
--				: --2-3---5---7-8-
--				: --2-3---5-----8-
--				: --2-3-----6-----
--				: --2-3-----6-7---
--				: --2-3-----6-7-8-
--				: --2-3-----6---8-
--				: --2-3-------7---
--				: --2-3-------7-8-
--				: --2-3---------8-
--				: --2---4---------
--				: --2---4-5-------
--				: --2---4-5-6-----
--				: --2---4-5-6-7---
--				: --2---4-5-6-7-8-
--				: --2---4-5-6---8-
--				: --2---4-5---7---
--				: --2---4-5---7-8-
--				: --2---4-5-----8-
--				: --2---4---6-----
--				: --2---4---6-7---
--				: --2---4---6-7-8-
--				: --2---4---6---8-
--				: --2---4-----7---
--				: --2---4-----7-8-
--				: --2---4-------8-
--				: --2-----5-------
--				: --2-----5-6-----
--				: --2-----5-6-7---
--				: --2-----5-6-7-8-
--				: --2-----5-6---8-
--				: --2-----5---7---
--				: --2-----5---7-8-
--				: --2-----5-----8-
--				: --2-------6-----
--				: --2-------6-7---
--				: --2-------6-7-8-
--				: --2-------6---8-
--				: --2---------7---
--				: --2---------7-8-
--				: --2-----------8-
--				: ----3-----------
--				: ----3-4---------
--				: ----3-4-5-------
--				: ----3-4-5-6-----
--				: ----3-4-5-6-7---
--				: ----3-4-5-6-7-8-
--				: ----3-4-5-6---8-
--				: ----3-4-5---7---
--				: ----3-4-5---7-8-
--				: ----3-4-5-----8-
--				: ----3-4---6-----
--				: ----3-4---6-7---
--				: ----3-4---6-7-8-
--				: ----3-4---6---8-
--				: ----3-4-----7---
--				: ----3-4-----7-8-
--				: ----3-4-------8-
--				: ----3---5-------
--				: ----3---5-6-----
--				: ----3---5-6-7---
--				: ----3---5-6-7-8-
--				: ----3---5-6---8-
--				: ----3---5---7---
--				: ----3---5---7-8-
--				: ----3---5-----8-
--				: ----3-----6-----
--				: ----3-----6-7---
--				: ----3-----6-7-8-
--				: ----3-----6---8-
--				: ----3-------7---
--				: ----3-------7-8-
--				: ----3---------8-
--				: ------4---------
--				: ------4-5-------
--				: ------4-5-6-----
--				: ------4-5-6-7---
--				: ------4-5-6-7-8-
--				: ------4-5-6---8-
--				: ------4-5---7---
--				: ------4-5---7-8-
--				: ------4-5-----8-
--				: ------4---6-----
--				: ------4---6-7---
--				: ------4---6-7-8-
--				: ------4---6---8-
--				: ------4-----7---
--				: ------4-----7-8-
--				: ------4-------8-
--				: --------5-------
--				: --------5-6-----
--				: --------5-6-7---
--				: --------5-6-7-8-
--				: --------5-6---8-
--				: --------5---7---
--				: --------5---7-8-
--				: --------5-----8-
--				: ----------6-----
--				: ----------6-7---
--				: ----------6-7-8-
--				: ----------6---8-
--				: ------------7---
--				: ------------7-8-
--				: --------------8-
-- Comments		: This log field reports the detected state of embedded audio pairs in the input SDI stream.
--				: Each digit represents presence of that pair and a ( - ) the absence of that pair.
--
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
-- Comments		: This log field shows the detected state of the SDI input signal.
--				: LOST indicates no input detected. 
--				: ERROR indicates that the detected input is not valid. 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
-- Vary Number  : YES
-- Value(s)		: 0
--				: 
-- Comments		: The number of EDH errors raised since initialization or the last EDH stats reset.
--
---------------------------------------------------------------------------------------------------
