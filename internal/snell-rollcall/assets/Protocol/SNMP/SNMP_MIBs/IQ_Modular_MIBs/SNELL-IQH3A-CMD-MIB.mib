-- ************************************************************************************
--        Snell Card:IQH3A
--        Module Id#:429
--       Command Set:21
--          Filename:SNELL-IQH3A-CMD-MIB.mib
--            Author:Jonathan Riches
--              Date:26/02/2014
--              Time:11:48
--
-- Copyright (c) 2014 Snell Ltd
-- All rights reserved.
--
-- ************************************************************************************

SNELL-IQH3A-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQH3A,
    moduleIQH3AMIB
        FROM SNELL-WILCOX-PRODUCT-REG;

 moduleIQH3ACmdMi MODULE-IDENTITY
    LAST-UPDATED "1402261148Z"
    ORGANIZATION "Snell Ltd"
    CONTACT-INFO
        "Primary Author:Jonathan Riches

         postal:    Southleigh Park House
                    Eastleigh Road
                    Havant, Hants
                    PO9 2PE
         phone:     +44 (0)23 92489000
         email:     snmp.support@snellgroup.com"
    DESCRIPTION
        "This file defines the Snell card, command set  translations."
    ::= { moduleIQH3AMIB 1 }




--********************************************************************************
--*
--*  Snell Card:
--*  command set:
--*  list commands/menus:
--*
--******************************************************************************
	iqh3aCmdTable OBJECT-TYPE
		SYNTAX			SEQUENCE OF Iqh3aCmdEntry
		MAX-ACCESS		not-accessible
		STATUS			current
		DESCRIPTION
				"Note the instance of this table is relected in the command set Version"
		::= { moduleIQH3A 1 }

	iqh3aCmdEntry OBJECT-TYPE
		SYNTAX		Iqh3aCmdEntry
		MAX-ACCESS		not-accessible
		STATUS			current
		DESCRIPTION
				"Entry in command table."
		INDEX	{ iqh3aSlotIndex }
		::= { iqh3aCmdTable 1 }

	Iqh3aCmdEntry ::=
		SEQUENCE {
			iqh3aSlotIndex
				Unsigned32,
			iqh3aSlot1InstalledType
				RollCallString,
			iqh3aSlot1InstalledUnit
				RollCallString,
			iqh3aSlot1Name
				RollCallString,
			iqh3aSlot1BoundType
				INTEGER,
			iqh3aSlot1Information1
				RollCallString,
			iqh3aSlot1Information2
				RollCallString,
			iqh3aSlot1NonRollCallSlot
				INTEGER,
			iqh3aSlot1IdName
				RollCallString,
			iqh3aSlot1PowerUsage
				INTEGER,
			iqh3aSlot1PowerDisplay
				RollCallString,
			iqh3aSlot2InstalledType
				RollCallString,
			iqh3aSlot2InstalledUnit
				RollCallString,
			iqh3aSlot2Name
				RollCallString,
			iqh3aSlot2BoundType
				INTEGER,
			iqh3aSlot2Information1
				RollCallString,
			iqh3aSlot2Information2
				RollCallString,
			iqh3aSlot2NonRollCallSlot
				INTEGER,
			iqh3aSlot2IdName
				RollCallString,
			iqh3aSlot2PowerUsage
				INTEGER,
			iqh3aSlot2PowerDisplay
				RollCallString,
			iqh3aSlot3InstalledType
				RollCallString,
			iqh3aSlot3InstalledUnit
				RollCallString,
			iqh3aSlot3Name
				RollCallString,
			iqh3aSlot3BoundType
				INTEGER,
			iqh3aSlot3Information1
				RollCallString,
			iqh3aSlot3Information2
				RollCallString,
			iqh3aSlot3NonRollCallSlot
				INTEGER,
			iqh3aSlot3IdName
				RollCallString,
			iqh3aSlot3PowerUsage
				INTEGER,
			iqh3aSlot3PowerDisplay
				RollCallString,
			iqh3aSlot4InstalledType
				RollCallString,
			iqh3aSlot4InstalledUnit
				RollCallString,
			iqh3aSlot4Name
				RollCallString,
			iqh3aSlot4BoundType
				INTEGER,
			iqh3aSlot4Information1
				RollCallString,
			iqh3aSlot4Information2
				RollCallString,
			iqh3aSlot4NonRollCallSlot
				INTEGER,
			iqh3aSlot4IdName
				RollCallString,
			iqh3aSlot4PowerUsage
				INTEGER,
			iqh3aSlot4PowerDisplay
				RollCallString,
			iqh3aSlot5InstalledType
				RollCallString,
			iqh3aSlot5InstalledUnit
				RollCallString,
			iqh3aSlot5Name
				RollCallString,
			iqh3aSlot5BoundType
				INTEGER,
			iqh3aSlot5Information1
				RollCallString,
			iqh3aSlot5Information2
				RollCallString,
			iqh3aSlot5NonRollCallSlot
				INTEGER,
			iqh3aSlot5IdName
				RollCallString,
			iqh3aSlot5PowerUsage
				INTEGER,
			iqh3aSlot5PowerDisplay
				RollCallString,
			iqh3aSlot6InstalledType
				RollCallString,
			iqh3aSlot6InstalledUnit
				RollCallString,
			iqh3aSlot6Name
				RollCallString,
			iqh3aSlot6BoundType
				INTEGER,
			iqh3aSlot6Information1
				RollCallString,
			iqh3aSlot6Information2
				RollCallString,
			iqh3aSlot6NonRollCallSlot
				INTEGER,
			iqh3aSlot6IdName
				RollCallString,
			iqh3aSlot6PowerUsage
				INTEGER,
			iqh3aSlot6PowerDisplay
				RollCallString,
			iqh3aSlot7InstalledType
				RollCallString,
			iqh3aSlot7InstalledUnit
				RollCallString,
			iqh3aSlot7Name
				RollCallString,
			iqh3aSlot7BoundType
				INTEGER,
			iqh3aSlot7Information1
				RollCallString,
			iqh3aSlot7Information2
				RollCallString,
			iqh3aSlot7NonRollCallSlot
				INTEGER,
			iqh3aSlot7IdName
				RollCallString,
			iqh3aSlot7PowerUsage
				INTEGER,
			iqh3aSlot7PowerDisplay
				RollCallString,
			iqh3aSlot8InstalledType
				RollCallString,
			iqh3aSlot8InstalledUnit
				RollCallString,
			iqh3aSlot8Name
				RollCallString,
			iqh3aSlot8BoundType
				INTEGER,
			iqh3aSlot8Information1
				RollCallString,
			iqh3aSlot8Information2
				RollCallString,
			iqh3aSlot8NonRollCallSlot
				INTEGER,
			iqh3aSlot8IdName
				RollCallString,
			iqh3aSlot8PowerUsage
				INTEGER,
			iqh3aSlot8PowerDisplay
				RollCallString,
			iqh3aSlot9InstalledType
				RollCallString,
			iqh3aSlot9InstalledUnit
				RollCallString,
			iqh3aSlot9Name
				RollCallString,
			iqh3aSlot9BoundType
				INTEGER,
			iqh3aSlot9Information1
				RollCallString,
			iqh3aSlot9Information2
				RollCallString,
			iqh3aSlot9NonRollCallSlot
				INTEGER,
			iqh3aSlot9IdName
				RollCallString,
			iqh3aSlot9PowerUsage
				INTEGER,
			iqh3aSlot9PowerDisplay
				RollCallString,
			iqh3aSlot10InstalledType
				RollCallString,
			iqh3aSlot10InstalledUnit
				RollCallString,
			iqh3aSlot10Name
				RollCallString,
			iqh3aSlot10BoundType
				INTEGER,
			iqh3aSlot10Information1
				RollCallString,
			iqh3aSlot10Information2
				RollCallString,
			iqh3aSlot10NonRollCallSlot
				INTEGER,
			iqh3aSlot10IdName
				RollCallString,
			iqh3aSlot10PowerUsage
				INTEGER,
			iqh3aSlot10PowerDisplay
				RollCallString,
			iqh3aSlot11InstalledType
				RollCallString,
			iqh3aSlot11InstalledUnit
				RollCallString,
			iqh3aSlot11Name
				RollCallString,
			iqh3aSlot11BoundType
				INTEGER,
			iqh3aSlot11Information1
				RollCallString,
			iqh3aSlot11Information2
				RollCallString,
			iqh3aSlot11NonRollCallSlot
				INTEGER,
			iqh3aSlot11IdName
				RollCallString,
			iqh3aSlot11PowerUsage
				INTEGER,
			iqh3aSlot11PowerDisplay
				RollCallString,
			iqh3aSlot12InstalledType
				RollCallString,
			iqh3aSlot12InstalledUnit
				RollCallString,
			iqh3aSlot12Name
				RollCallString,
			iqh3aSlot12BoundType
				INTEGER,
			iqh3aSlot12Information1
				RollCallString,
			iqh3aSlot12Information2
				RollCallString,
			iqh3aSlot12NonRollCallSlot
				INTEGER,
			iqh3aSlot12IdName
				RollCallString,
			iqh3aSlot12PowerUsage
				INTEGER,
			iqh3aSlot12PowerDisplay
				RollCallString,
			iqh3aSlot13InstalledType
				RollCallString,
			iqh3aSlot13InstalledUnit
				RollCallString,
			iqh3aSlot13Name
				RollCallString,
			iqh3aSlot13BoundType
				INTEGER,
			iqh3aSlot13Information1
				RollCallString,
			iqh3aSlot13Information2
				RollCallString,
			iqh3aSlot13NonRollCallSlot
				INTEGER,
			iqh3aSlot13IdName
				RollCallString,
			iqh3aSlot13PowerUsage
				INTEGER,
			iqh3aSlot13PowerDisplay
				RollCallString,
			iqh3aSlot14InstalledType
				RollCallString,
			iqh3aSlot14InstalledUnit
				RollCallString,
			iqh3aSlot14Name
				RollCallString,
			iqh3aSlot14BoundType
				INTEGER,
			iqh3aSlot14Information1
				RollCallString,
			iqh3aSlot14Information2
				RollCallString,
			iqh3aSlot14NonRollCallSlot
				INTEGER,
			iqh3aSlot14IdName
				RollCallString,
			iqh3aSlot14PowerUsage
				INTEGER,
			iqh3aSlot14PowerDisplay
				RollCallString,
			iqh3aSlot15InstalledType
				RollCallString,
			iqh3aSlot15InstalledUnit
				RollCallString,
			iqh3aSlot15Name
				RollCallString,
			iqh3aSlot15BoundType
				INTEGER,
			iqh3aSlot15Information1
				RollCallString,
			iqh3aSlot15Information2
				RollCallString,
			iqh3aSlot15NonRollCallSlot
				INTEGER,
			iqh3aSlot15IdName
				RollCallString,
			iqh3aSlot15PowerUsage
				INTEGER,
			iqh3aSlot15PowerDisplay
				RollCallString,
			iqh3aSlot16InstalledType
				RollCallString,
			iqh3aSlot16InstalledUnit
				RollCallString,
			iqh3aSlot16Name
				RollCallString,
			iqh3aSlot16BoundType
				INTEGER,
			iqh3aSlot16Information1
				RollCallString,
			iqh3aSlot16Information2
				RollCallString,
			iqh3aSlot16NonRollCallSlot
				INTEGER,
			iqh3aSlot16IdName
				RollCallString,
			iqh3aSlot16PowerUsage
				INTEGER,
			iqh3aSlot16PowerDisplay
				RollCallString,
			iqh3aSystemSetupHardwareVersion
				RollCallString,
			iqh3aSystemSetupUnitName
				RollCallString,
			iqh3aSystemSetupSerialNumber
				RollCallString,
			iqh3aSystemSetupSoftwareVersion
				RollCallString,
			iqh3aSystemSetupBuildNumber
				RollCallString,
			iqh3aSystemSetupLoaderVersion
				RollCallString,
			iqh3aSystemSetupJavaAppletVersion
				RollCallString,
			iqh3aSystemSetupNetShow
				INTEGER,
			iqh3aSystemSetupAllowBlindControl
				INTEGER,
			iqh3aSystemSetupWhereAmI
				INTEGER,
			iqh3aSystemSetupSerialSpeed
				INTEGER,
			iqh3aSystemSetupSerialMode
				RollCallString,
			iqh3aSystemSetupPassIAMSerial
				INTEGER,
			iqh3aSystemSetupPassTIMESerial
				INTEGER,
			iqh3aSetupMonitorPSUsLeftPSU
				INTEGER,
			iqh3aSetupMonitorPSUsRightPSU
				INTEGER,
			iqh3aSystemSetupEnablecom200LongPacket
				INTEGER,
			iqh3aSystemSetupRestartUnit
				INTEGER,
			iqh3aSystemSetupFormatMenuCache
				INTEGER,
			iqh3aSystemSetupEnableMenuCache
				INTEGER,
			iqh3aSystemSetupStartTime
				RollCallString,
			iqh3aSystemSetupInformation1
				RollCallString,
			iqh3aSystemSetupInformation2
				RollCallString,
			iqh3aSystemSetupEnableWebServer
				INTEGER,
			iqh3aSystemSetupWebIPPort
				RollCallString,
			iqh3aSystemSetupModuleUpgradeTime
				INTEGER,
			iqh3aSystemSetupEnableModuleUpgra
				INTEGER,
			iqh3aSystemSetupLm80fanspeed
				INTEGER,
			iqh3aSystemSetupEnclosureType
				INTEGER,
			iqh3aStatisticsResetNetStats
				INTEGER,
			iqh3aStatisticsEnableNetStats
				INTEGER,
			iqh3aStatisticsLengthErrs
				RollCallString,
			iqh3aStatisticsRecons
				RollCallString,
			iqh3aStatisticsModuleCommsErrors
				RollCallString,
			iqh3aStatisticsBadPacketErrs
				RollCallString,
			iqh3aStatisticsRoutingErrs
				RollCallString,
			iqh3aStatisticsPacketDrops
				RollCallString,
			iqh3aStatisticsDestinationErrs
				RollCallString,
			iqh3aStatisticsSourceErrs
				RollCallString,
			iqh3aStatisticsModCommsRxBytes
				RollCallString,
			iqh3aStatisticsModCommsTxBytes
				RollCallString,
			iqh3aStatisticsHyperionRxBytes
				RollCallString,
			iqh3aStatisticsProcessorUse
				RollCallString,
			iqh3aControlSlot1AllowBlindControl
				INTEGER,
			iqh3aControlSlot1SingleSessionOnly
				INTEGER,
			iqh3aControlSlot1Controller
				RollCallString,
			iqh3aControlSlot1ControllerName
				RollCallString,
			iqh3aControlSlot1LastBlindUser
				RollCallString,
			iqh3aControlSlot1ConPktCount
				RollCallString,
			iqh3aControlSlot1ConPktTotal
				RollCallString,
			iqh3aControlSlot1BlindPktCount
				RollCallString,
			iqh3aControlSlotDisconnectSession
				INTEGER,
			iqh3aControlSlot2AllowBlindControl
				INTEGER,
			iqh3aControlSlot2SingleSessionOnly
				INTEGER,
			iqh3aControlSlot2Controller
				RollCallString,
			iqh3aControlSlot2ControllerName
				RollCallString,
			iqh3aControlSlot2LastBlindUser
				RollCallString,
			iqh3aControlSlot2ConPktCount
				RollCallString,
			iqh3aControlSlot2ConPktTotal
				RollCallString,
			iqh3aControlSlot2BlindPktCount
				RollCallString,
			iqh3aControlSlot3AllowBlindControl
				INTEGER,
			iqh3aControlSlot3SingleSessionOnly
				INTEGER,
			iqh3aControlSlot3Controller
				RollCallString,
			iqh3aControlSlot3ControllerName
				RollCallString,
			iqh3aControlSlot3LastBlindUser
				RollCallString,
			iqh3aControlSlot3ConPktCount
				RollCallString,
			iqh3aControlSlot3ConPktTotal
				RollCallString,
			iqh3aControlSlot3BlindPktCount
				RollCallString,
			iqh3aControlSlot4AllowBlindControl
				INTEGER,
			iqh3aControlSlot4SingleSessionOnly
				INTEGER,
			iqh3aControlSlot4Controller
				RollCallString,
			iqh3aControlSlot4ControllerName
				RollCallString,
			iqh3aControlSlot4LastBlindUser
				RollCallString,
			iqh3aControlSlot4ConPktCount
				RollCallString,
			iqh3aControlSlot4ConPktTotal
				RollCallString,
			iqh3aControlSlot4BlindPktCount
				RollCallString,
			iqh3aControlSlot5AllowBlindControl
				INTEGER,
			iqh3aControlSlot5SingleSessionOnly
				INTEGER,
			iqh3aControlSlot5Controller
				RollCallString,
			iqh3aControlSlot5ControllerName
				RollCallString,
			iqh3aControlSlot5LastBlindUser
				RollCallString,
			iqh3aControlSlot5ConPktCount
				RollCallString,
			iqh3aControlSlot5ConPktTotal
				RollCallString,
			iqh3aControlSlot5BlindPktCount
				RollCallString,
			iqh3aControlSlot6AllowBlindControl
				INTEGER,
			iqh3aControlSlot6SingleSessionOnly
				INTEGER,
			iqh3aControlSlot6Controller
				RollCallString,
			iqh3aControlSlot6ControllerName
				RollCallString,
			iqh3aControlSlot6LastBlindUser
				RollCallString,
			iqh3aControlSlot6ConPktCount
				RollCallString,
			iqh3aControlSlot6ConPktTotal
				RollCallString,
			iqh3aControlSlot6BlindPktCount
				RollCallString,
			iqh3aControlSlot7AllowBlindControl
				INTEGER,
			iqh3aControlSlot7SingleSessionOnly
				INTEGER,
			iqh3aControlSlot7Controller
				RollCallString,
			iqh3aControlSlot7ControllerName
				RollCallString,
			iqh3aControlSlot7LastBlindUser
				RollCallString,
			iqh3aControlSlot7ConPktCount
				RollCallString,
			iqh3aControlSlot7ConPktTotal
				RollCallString,
			iqh3aControlSlot7BlindPktCount
				RollCallString,
			iqh3aControlSlot8AllowBlindControl
				INTEGER,
			iqh3aControlSlot8SingleSessionOnly
				INTEGER,
			iqh3aControlSlot8Controller
				RollCallString,
			iqh3aControlSlot8ControllerName
				RollCallString,
			iqh3aControlSlot8LastBlindUser
				RollCallString,
			iqh3aControlSlot8ConPktCount
				RollCallString,
			iqh3aControlSlot8ConPktTotal
				RollCallString,
			iqh3aControlSlot8BlindPktCount
				RollCallString,
			iqh3aControlSlot9AllowBlindControl
				INTEGER,
			iqh3aControlSlot9SingleSessionOnly
				INTEGER,
			iqh3aControlSlot9Controller
				RollCallString,
			iqh3aControlSlot9ControllerName
				RollCallString,
			iqh3aControlSlot9LastBlindUser
				RollCallString,
			iqh3aControlSlot9ConPktCount
				RollCallString,
			iqh3aControlSlot9ConPktTotal
				RollCallString,
			iqh3aControlSlot9BlindPktCount
				RollCallString,
			iqh3aControlSlot10AllowBlindControl
				INTEGER,
			iqh3aControlSlot10SingleSessionOnly
				INTEGER,
			iqh3aControlSlot10Controller
				RollCallString,
			iqh3aControlSlot10ControllerName
				RollCallString,
			iqh3aControlSlot10LastBlindUser
				RollCallString,
			iqh3aControlSlot10ConPktCount
				RollCallString,
			iqh3aControlSlot10ConPktTotal
				RollCallString,
			iqh3aControlSlot10BlindPktCount
				RollCallString,
			iqh3aControlSlot11AllowBlindControl
				INTEGER,
			iqh3aControlSlot11SingleSessionOnly
				INTEGER,
			iqh3aControlSlot11Controller
				RollCallString,
			iqh3aControlSlot11ControllerName
				RollCallString,
			iqh3aControlSlot11LastBlindUser
				RollCallString,
			iqh3aControlSlot11ConPktCount
				RollCallString,
			iqh3aControlSlot11ConPktTotal
				RollCallString,
			iqh3aControlSlot11BlindPktCount
				RollCallString,
			iqh3aControlSlot12AllowBlindControl
				INTEGER,
			iqh3aControlSlot12SingleSessionOnly
				INTEGER,
			iqh3aControlSlot12Controller
				RollCallString,
			iqh3aControlSlot12ControllerName
				RollCallString,
			iqh3aControlSlot12LastBlindUser
				RollCallString,
			iqh3aControlSlot12ConPktCount
				RollCallString,
			iqh3aControlSlot12ConPktTotal
				RollCallString,
			iqh3aControlSlot12BlindPktCount
				RollCallString,
			iqh3aControlSlot13AllowBlindControl
				INTEGER,
			iqh3aControlSlot13SingleSessionOnly
				INTEGER,
			iqh3aControlSlot13Controller
				RollCallString,
			iqh3aControlSlot13ControllerName
				RollCallString,
			iqh3aControlSlot13LastBlindUser
				RollCallString,
			iqh3aControlSlot13ConPktCount
				RollCallString,
			iqh3aControlSlot13ConPktTotal
				RollCallString,
			iqh3aControlSlot13BlindPktCount
				RollCallString,
			iqh3aControlSlot14AllowBlindControl
				INTEGER,
			iqh3aControlSlot14SingleSessionOnly
				INTEGER,
			iqh3aControlSlot14Controller
				RollCallString,
			iqh3aControlSlot14ControllerName
				RollCallString,
			iqh3aControlSlot14LastBlindUser
				RollCallString,
			iqh3aControlSlot14ConPktCount
				RollCallString,
			iqh3aControlSlot14ConPktTotal
				RollCallString,
			iqh3aControlSlot14BlindPktCount
				RollCallString,
			iqh3aControlSlot15AllowBlindControl
				INTEGER,
			iqh3aControlSlot15SingleSessionOnly
				INTEGER,
			iqh3aControlSlot15Controller
				RollCallString,
			iqh3aControlSlot15ControllerName
				RollCallString,
			iqh3aControlSlot15LastBlindUser
				RollCallString,
			iqh3aControlSlot15ConPktCount
				RollCallString,
			iqh3aControlSlot15ConPktTotal
				RollCallString,
			iqh3aControlSlot15BlindPktCount
				RollCallString,
			iqh3aControlSlot16AllowBlindControl
				INTEGER,
			iqh3aControlSlot16SingleSessionOnly
				INTEGER,
			iqh3aControlSlot16Controller
				RollCallString,
			iqh3aControlSlot16ControllerName
				RollCallString,
			iqh3aControlSlot16LastBlindUser
				RollCallString,
			iqh3aControlSlot16ConPktCount
				RollCallString,
			iqh3aControlSlot16ConPktTotal
				RollCallString,
			iqh3aControlSlot16BlindPktCount
				RollCallString,
			iqh3aControlShowSession
				INTEGER,
			iqh3aControlPktStatsUpdatePacketStats
				INTEGER,
			iqh3aControlPktStatsClearPacketCounts
				INTEGER,
			iqh3aControlGatewayControllerName
				RollCallString,
			iqh3aControlGatewayControllerAddr
				RollCallString,
			iqh3aControlGatewayConPktCount
				RollCallString,
			iqh3aControlGatewayConPktTotal
				RollCallString,
			iqh3aControlGatewayLastBlindAddr
				RollCallString,
			iqh3aControlGatewayBlindPktCount
				RollCallString,
			iqh3aControlGatewayDisconnectSession
				INTEGER,
			iqh3aControlGatewayShowSession
				INTEGER,
			iqh3aLoggingLogServerLogto
				INTEGER,
			iqh3aLoggingLogServerLogServerName
				RollCallString,
			iqh3aLoggingLogServerCurLogger
				RollCallString,
			iqh3aLoggingLogServerCurLoggerAddr
				RollCallString,
			iqh3aLoggingLogServerLastTimeaddr
				RollCallString,
			iqh3aLoggingLogServerTimefromLogger
				INTEGER,
			iqh3aLoggingLogServerAcceptviaIP
				INTEGER,
			iqh3aLoggingLogServerAcceptviaSerial
				INTEGER,
			iqh3aLoggingLogServerAcceptviaRollNet
				INTEGER,
			iqh3aLoggingLogServerAcceptviaBridge
				INTEGER,
			iqh3aLoggingSN
				RollCallString,
			iqh3aLoggingVERSION
				RollCallString,
			iqh3aLoggingLogOSVersion
				INTEGER,
			iqh3aLoggingOSVERSION
				RollCallString,
			iqh3aLoggingLogBuildNumber
				INTEGER,
			iqh3aLoggingBUILDNUMBER
				RollCallString,
			iqh3aLoggingLogHardwareVer
				INTEGER,
			iqh3aLoggingHARDWAREVERSION
				RollCallString,
			iqh3aLoggingLogLoaderVersion
				INTEGER,
			iqh3aLoggingLOADERVERSION
				RollCallString,
			iqh3aLoggingLogModuleStatus
				INTEGER,
			iqh3aLoggingMODULESTATUS
				RollCallString,
			iqh3aLoggingLogGwayCtrlSess
				INTEGER,
			iqh3aLoggingSESSIONS
				RollCallString,
			iqh3aLoggingLogLastModified
				INTEGER,
			iqh3aLoggingLASTMODIFIED
				RollCallString,
			iqh3aLoggingLogIPAddress
				INTEGER,
			iqh3aLoggingIPADDRESS
				RollCallString,
			iqh3aLoggingLogPSU1Name
				INTEGER,
			iqh3aLoggingPSU1NAME
				RollCallString,
			iqh3aLoggingLogPSU1State
				INTEGER,
			iqh3aLoggingPSU1STATE
				RollCallString,
			iqh3aLoggingLogPSU2Name
				INTEGER,
			iqh3aLoggingPSU2NAME
				RollCallString,
			iqh3aLoggingLogPSU2State
				INTEGER,
			iqh3aLoggingPSU2STATE
				RollCallString,
			iqh3aLoggingLogReconState
				INTEGER,
			iqh3aLoggingRECONSTATE
				RollCallString,
			iqh3aLoggingLogLanPort1Name
				INTEGER,
			iqh3aLoggingLANPORT1NAME
				RollCallString,
			iqh3aLoggingLogLanPort1State
				INTEGER,
			iqh3aLoggingLANPORT1STATE
				RollCallString,
			iqh3aLoggingLogLanPort1Speed
				INTEGER,
			iqh3aLoggingLANPORT1SPEED
				RollCallString,
			iqh3aLoggingLogLanPort1LastChange
				INTEGER,
			iqh3aLoggingLANPORT1LASTCHANGE
				RollCallString,
			iqh3aLoggingLogLanPort1Errors
				INTEGER,
			iqh3aLoggingLANPORT1ERRORS
				RollCallString,
			iqh3aLoggingLogLanPort1InTraffic
				INTEGER,
			iqh3aLoggingLANPORT1TRAFFICIN
				RollCallString,
			iqh3aLoggingLogLanPort1OutTraffic
				INTEGER,
			iqh3aLoggingLANPORT1TRAFFICOUT
				RollCallString,
			iqh3aLoggingLogIpEvent
				INTEGER,
			iqh3aLoggingIPEVENT
				RollCallString,
			iqh3aLoggingLogUptime
				INTEGER,
			iqh3aLoggingUPTIME
				RollCallString,
			iqh3aLoggingLogRestartedAt
				INTEGER,
			iqh3aLoggingRESTARTEDAT
				RollCallString,
			iqh3aLoggingLogThumbIpPort
				INTEGER,
			iqh3aLoggingTHUMBIPPORT
				RollCallString,
			iqh3aLoggingLogTemp1Name
				INTEGER,
			iqh3aLoggingTEMP1NAME
				RollCallString,
			iqh3aLoggingLogTemp1State
				INTEGER,
			iqh3aLoggingTEMP1STATE
				RollCallString,
			iqh3aLoggingLogTemp1Celsius
				INTEGER,
			iqh3aLoggingTEMP1CELSIUS
				RollCallString,
			iqh3aLoggingLogTemp2Name
				INTEGER,
			iqh3aLoggingTEMP2NAME
				RollCallString,
			iqh3aLoggingLogTemp2State
				INTEGER,
			iqh3aLoggingTEMP2STATE
				RollCallString,
			iqh3aLoggingLogTemp2Celsius
				INTEGER,
			iqh3aLoggingTEMP2CELSIUS
				RollCallString,
			iqh3aLoggingLogFan1Name
				INTEGER,
			iqh3aLoggingFAN1NAME
				RollCallString,
			iqh3aLoggingLogFan1State
				INTEGER,
			iqh3aLoggingFAN1STATE
				RollCallString,
			iqh3aLoggingLogFan2Name
				INTEGER,
			iqh3aLoggingFAN2NAME
				RollCallString,
			iqh3aLoggingLogFan2State
				INTEGER,
			iqh3aLoggingFAN2STATE
				RollCallString,
			iqh3aLoggingLogFan3Name
				INTEGER,
			iqh3aLoggingFAN3NAME
				RollCallString,
			iqh3aLoggingLogFan3State
				INTEGER,
			iqh3aLoggingFAN3STATE
				RollCallString,
			iqh3aLoggingLogFan4Name
				INTEGER,
			iqh3aLoggingFAN4NAME
				RollCallString,
			iqh3aLoggingLogFan4State
				INTEGER,
			iqh3aLoggingFAN4STATE
				RollCallString,
			iqh3aLoggingLogEnclosure
				INTEGER,
			iqh3aLoggingENCLOSURE
				RollCallString,
			iqh3aLoggingLogVoltage1Name
				INTEGER,
			iqh3aLoggingVOLTAGE1NAME
				RollCallString,
			iqh3aLoggingLogVoltage1State
				INTEGER,
			iqh3aLoggingVOLTAGE1STATE
				RollCallString,
			iqh3aLoggingLogVoltage1Value
				INTEGER,
			iqh3aLoggingVOLTAGE1VALUE
				RollCallString,
			iqh3aLoggingLogVoltage2Name
				INTEGER,
			iqh3aLoggingVOLTAGE2NAME
				RollCallString,
			iqh3aLoggingLogVoltage2State
				INTEGER,
			iqh3aLoggingVOLTAGE2STATE
				RollCallString,
			iqh3aLoggingLogVoltage2Value
				INTEGER,
			iqh3aLoggingVOLTAGE2VALUE
				RollCallString,
			iqh3aLoggingLogInformation1
				INTEGER,
			iqh3aLoggingINFORMATION1
				RollCallString,
			iqh3aLoggingLogInformation2
				INTEGER,
			iqh3aLoggingINFORMATION2
				RollCallString,
			iqh3aLoggingLogFaults
				INTEGER,
			iqh3aLoggingFAULT
				RollCallString,
			iqh3aLoggingLogModuleComms
				INTEGER,
			iqh3aLoggingMODULECOMMS
				RollCallString,
			iqh3aLoggingFanStatus
				RollCallString,
			iqh3aLoggingLogSnmpName
				INTEGER,
			iqh3aLoggingSNMPNAME
				RollCallString,
			iqh3aLoggingLogLocation
				INTEGER,
			iqh3aLoggingLOCATION
				RollCallString,
			iqh3aLoggingLogSysContact
				INTEGER,
			iqh3aLoggingSYSTEMCONTACT
				RollCallString,
			iqh3aLoggingLogSysDescription
				INTEGER,
			iqh3aLoggingSYSTEMDESCRIPTION
				RollCallString,
			iqh3aLoggingLoggingState
				INTEGER,
			iqh3aLoggingLOGGINGSTATE
				RollCallString,
			iqh3aLoggingPowerMaxEnable
				INTEGER,
			iqh3aLoggingPOWERMAX
				RollCallString,
			iqh3aLoggingPowerUsageEnable
				INTEGER,
			iqh3aLoggingPOWERUSAGE
				RollCallString,
			iqh3aLoggingPowerCheckEnable
				INTEGER,
			iqh3aLoggingPOWERCHECK
				RollCallString,
			iqh3aLoggingIPBridgeStatEnab
				INTEGER,
			iqh3aLoggingIPBRIDGESTATUS
				RollCallString,
			iqh3aEthernetIPaddress
				RollCallString,
			iqh3aEthernetSubnetmask
				RollCallString,
			iqh3aEthernetDefaultIPgateway
				RollCallString,
			iqh3aEthernetTakeIPChange
				INTEGER,
			iqh3aEthernetIPSharePort
				RollCallString,
			iqh3aEthernetIPSharePortLocal
				RollCallString,
			iqh3aEthernetLinkspeed
				INTEGER,
			iqh3aEthernetLinkState
				RollCallString,
			iqh3aEthernetMACaddress
				RollCallString,
			iqh3aEthernetIPRouting
				RollCallString,
			iqh3aEthernetIgnorebcastpkts
				INTEGER,
			iqh3aEthernetCheckclientIP
				INTEGER,
			iqh3aEthernetIPThumbPort
				RollCallString,
			iqh3aEthernetClientIPRangesMin1
				RollCallString,
			iqh3aEthernetClientIPRangesMax1
				RollCallString,
			iqh3aEthernetClientIPRangesMin2
				RollCallString,
			iqh3aEthernetClientIPRangesMax2
				RollCallString,
			iqh3aEthernetClientIPRangesMin3
				RollCallString,
			iqh3aEthernetClientIPRangesMax3
				RollCallString,
			iqh3aEthernetClientIPRangesMin4
				RollCallString,
			iqh3aEthernetClientIPRangesMax4
				RollCallString,
			iqh3aEthernetClientIPRangesMin5
				RollCallString,
			iqh3aEthernetClientIPRangesMax5
				RollCallString,
			iqh3aEthernetClientIPRangesMin6
				RollCallString,
			iqh3aEthernetClientIPRangesMax6
				RollCallString,
			iqh3aEthernetClientIPRangesMin7
				RollCallString,
			iqh3aEthernetClientIPRangesMax7
				RollCallString,
			iqh3aEthernetClientIPRangesMin8
				RollCallString,
			iqh3aEthernetClientIPRangesMax8
				RollCallString,
			iqh3aEthernetPassIAMIP
				INTEGER,
			iqh3aEthernetPassTimeIP
				INTEGER,
			iqh3aEthernetRollCallIPStatsRejectCount
				RollCallString,
			iqh3aEthernetRollCallIPStatsLastRejectClient
				RollCallString,
			iqh3aEthernetRollCallIPStatsClosedCount
				RollCallString,
			iqh3aEthernetRollCallIPStatsLastClosedClient
				RollCallString,
			iqh3aEthernetRollCallIPStatsConnection
				INTEGER,
			iqh3aEthernetRollCallIPStatsRollCallPort
				RollCallString,
			iqh3aEthernetRollCallIPStatsName
				RollCallString,
			iqh3aEthernetRollCallTCPStatsRemotePort
				RollCallString,
			iqh3aEthernetRollCallIPStatsAddr
				RollCallString,
			iqh3aEthernetRollCallIPStatsPacketsReceived
				RollCallString,
			iqh3aEthernetRollCallIPStatsPacketsSent
				RollCallString,
			iqh3aEthernetRollCallIPStatsEverSentTime
				RollCallString,
			iqh3aEthernetRollCallIPStatsFullNetworkMap
				RollCallString,
			iqh3aEthernetRollCallIPStatsStartTime
				RollCallString,
			iqh3aEthernetSNMPEnableSNMP
				INTEGER,
			iqh3aEthernetSNMPEnableLegacySNMP
				INTEGER,
			iqh3aEthernetSNMPReadcommunity
				RollCallString,
			iqh3aEthernetSNMPWritecommunity
				RollCallString,
			iqh3aEthernetSNMPMIB2sysContact
				RollCallString,
			iqh3aEthernetSNMPMIB2sysName
				RollCallString,
			iqh3aEthernetSNMPMIB2sysLocation
				RollCallString,
			iqh3aEthernetSNMPReadWritePort
				RollCallString,
			iqh3aEthernetSNMPResendTraps
				INTEGER,
			iqh3aSnmpTrapDest1IPaddr
				RollCallString,
			iqh3aSnmpTrapDest1Port
				RollCallString,
			iqh3aSnmpTrapDest1Community
				RollCallString,
			iqh3aSnmpTrapDest2IPaddr
				RollCallString,
			iqh3aSnmpTrapDest2Port
				RollCallString,
			iqh3aSnmpTrapDest2Community
				RollCallString,
			iqh3aSnmpTrapDest2EnableTrap
				INTEGER,
			iqh3aSnmpTrapDest3IPaddr
				RollCallString,
			iqh3aSnmpTrapDest3Port
				RollCallString,
			iqh3aSnmpTrapDest3Community
				RollCallString,
			iqh3aSnmpTrapDest3EnableTrap
				INTEGER,
			iqh3aSnmpTrapDest4IPaddr
				RollCallString,
			iqh3aSnmpTrapDest4Port
				RollCallString,
			iqh3aSnmpTrapDest4Community
				RollCallString,
			iqh3aSnmpTrapDest4EnableTrap
				INTEGER,
			iqh3aSnmpTrapDest5IPaddr
				RollCallString,
			iqh3aSnmpTrapDest5Port
				RollCallString,
			iqh3aSnmpTrapDest5Community
				RollCallString,
			iqh3aSnmpTrapDest5EnableTrap
				INTEGER,
			iqh3aSnmpTrapDest6IPaddr
				RollCallString,
			iqh3aSnmpTrapDest6Port
				RollCallString,
			iqh3aSnmpTrapDest6Community
				RollCallString,
			iqh3aSnmpTrapDest6EnableTrap
				INTEGER,
			iqh3aSnmpTrapDest7IPaddr
				RollCallString,
			iqh3aSnmpTrapDest7Port
				RollCallString,
			iqh3aSnmpTrapDest7Community
				RollCallString,
			iqh3aSnmpTrapDest7EnableTrap
				INTEGER,
			iqh3aSnmpTrapDest8IPaddr
				RollCallString,
			iqh3aSnmpTrapDest8Port
				RollCallString,
			iqh3aSnmpTrapDest8Community
				RollCallString,
			iqh3aSnmpTrapDest8EnableTrap
				INTEGER,
			iqh3aTrapsSlotFilter0
				INTEGER,
			iqh3aTrapsSlotFilter1
				INTEGER,
			iqh3aTrapsSlotFilter2
				INTEGER,
			iqh3aTrapsSlotFilter3
				INTEGER,
			iqh3aTrapsSlotFilter4
				INTEGER,
			iqh3aTrapsSlotFilter5
				INTEGER,
			iqh3aTrapsSlotFilter6
				INTEGER,
			iqh3aTrapsSlotFilter7
				INTEGER,
			iqh3aTrapsSlotFilter8
				INTEGER,
			iqh3aTrapsSlotFilter9
				INTEGER,
			iqh3aTrapsSlotFilter10
				INTEGER,
			iqh3aTrapsSlotFilter11
				INTEGER,
			iqh3aTrapsSlotFilter12
				INTEGER,
			iqh3aTrapsSlotFilter13
				INTEGER,
			iqh3aTrapsSlotFilter14
				INTEGER,
			iqh3aTrapsSlotFilter15
				INTEGER,
			iqh3aTrapsSlotFilter16
				INTEGER,
			iqh3aTrapsControlSlot0
				INTEGER,
			iqh3aTrapsControlSlot1
				INTEGER,
			iqh3aTrapsControlSlot2
				INTEGER,
			iqh3aTrapsControlSlot3
				INTEGER,
			iqh3aTrapsControlSlot4
				INTEGER,
			iqh3aTrapsControlSlot5
				INTEGER,
			iqh3aTrapsControlSlot6
				INTEGER,
			iqh3aTrapsControlSlot7
				INTEGER,
			iqh3aTrapsControlSlot8
				INTEGER,
			iqh3aTrapsControlSlot9
				INTEGER,
			iqh3aTrapsControlSlot10
				INTEGER,
			iqh3aTrapsControlSlot11
				INTEGER,
			iqh3aTrapsControlSlot12
				INTEGER,
			iqh3aTrapsControlSlot13
				INTEGER,
			iqh3aTrapsControlSlot14
				INTEGER,
			iqh3aTrapsControlSlot15
				INTEGER,
			iqh3aTrapsControlSlot16
				INTEGER,
			iqh3aEthernetIPBridgeIPAddr
				RollCallString,
			iqh3aEthernetIPBridgeIPAddrAlt
				RollCallString,
			iqh3aEthernetIPBridgeAltBridge
				INTEGER,
			iqh3aEthernetIPBridgeIPPort
				RollCallString,
			iqh3aEthernetIPBridgeOnlythisAddr
				INTEGER,
			iqh3aEthernetIPBridgePriority
				INTEGER,
			iqh3aEthernetIPBridgePassIAMBridge
				INTEGER,
			iqh3aEthernetIPBridgePassTimeBridge
				INTEGER,
			iqh3aEthernetIPBridgeCtrlOnlyBridge
				INTEGER,
			iqh3aEthernetIPBridgeConnect
				INTEGER,
			iqh3aEthernetIPBridgeDisconnect
				INTEGER,
			iqh3aEthernetIPBridgeAutoConnect
				INTEGER,
			iqh3aEthernetIPBridgeAddr
				RollCallString,
			iqh3aEthernetIPBridgePacketsReceived
				RollCallString,
			iqh3aEthernetIPBridgePacketsSent
				RollCallString,
			iqh3aEthernetIPBridgeStartTime
				RollCallString,
			iqh3aEthernetIPBridgeStartedBy
				RollCallString,
			iqh3aEthernetIPBridgeLogging
				INTEGER
		}

	iqh3aSlotIndex OBJECT-TYPE
		SYNTAX		Unsigned32
		MAX-ACCESS		not-accessible
		STATUS			current
		DESCRIPTION
				"The unique Index value for each slot.  Its value
					ranges between 1 and the value of slotNumber."
		::= { iqh3aCmdEntry 0 }


	iqh3aSlot1InstalledType OBJECT-TYPE
		SYNTAX		RollCallString
		MAX-ACCESS		read-only
		STATUS			current
		DESCRIPTION
				"TYPE: - Display
				 PAGE: - Slots
					Installed Type  cmdID= 16510  format=   "
		::= { iqh3aCmdEntry 16510 }


	iqh3aSlot1InstalledUnit OBJECT-TYPE
		SYNTAX		RollCallString
		MAX-ACCESS		read-only
		STATUS			current
		DESCRIPTION
				"TYPE: - Display
				 PAGE: - Slots
					Installed Unit  cmdID= 16530  format=   "
		::= { iqh3aCmdEntry 16530 }


	iqh3aSlot1Name OBJECT-TYPE
		SYNTAX		RollCallString
		MAX-ACCESS		read-write
		STATUS			current
		DESCRIPTION
				"TYPE: - Editstring
				 PAGE: - Slots
					Name  cmdID= 16389  "
		::= { iqh3aCmdEntry 16389 }


	iqh3aSlot1BoundType OBJECT-TYPE
		SYNTAX		INTEGER
		MAX-ACCESS		read-write
		STATUS			current
		DESCRIPTION
				"TYPE: - Number
				 PAGE: - Slots
					Bound Type  cmdID= 16437  min= 0  max= 65536  step= 1  format= %.0f  div_scale= 1
					Min = 0  Max = 65536  Step = 1 "
		::= { iqh3aCmdEntry 16437 }


	iqh3aSlot1Information1 OBJECT-TYPE
		SYNTAX		RollCallString
		MAX-ACCESS		read-write
		STATUS			current
		DESCRIPTION
				"TYPE: - Editstring
				 PAGE: - Slots
				 Generic Information field 1, to hold User defined Information
					Information 1  cmdID= 17101  "
		::= { iqh3aCmdEntry 17101 }


	iqh3aSlot1Information2 OBJECT-TYPE
		SYNTAX		RollCallString
		MAX-ACCESS		read-write
		STATUS			current
		DESCRIPTION
				"TYPE: - Editstring
				 PAGE: - Slots
				 Generic Information field2, to hold User defined Information
					Information 2  cmdID= 17121  "
		::= { iqh3aCmdEntry 17121 }


	iqh3aSlot1NonRollCallSlot OBJECT-TYPE
		SYNTAX		INTEGER { disable(0), enable(1) }
		MAX-ACCESS		read-write
		STATUS			current
		DESCRIPTION
				"TYPE: - Checkbox
				 PAGE: - Slots
					NonRollCallSlot  cmdID= 17201 "
		::= { iqh3aCmdEntry 17201 }


	iqh3aSlot1IdName OBJECT-TYPE
		SYNTAX		RollCallString
		MAX-ACCESS		read-write
		STATUS			current
		DESCRIPTION
				"TYPE: - Editstring
				 PAGE: - Slots
					IdName  cmdID= 17221  "
		::= { iqh3aCmdEntry 17221 }


	iqh3aSlot1PowerUsage OBJECT-TYPE
		SYNTAX		INTEGER
		MAX-ACCESS		read-write
		STATUS			current
		DESCRIPTION
				"TYPE: - Number
				 PAGE: - Slots
					Power Usage  cmdID= 17250  min= 0  max= 500  step= 1  format= %0.1f  div_scale= 10 
					Min = 0.0  Max = 50.0  Step = 0.1 "
		::= { iqh3aCmdEntry 17250 }


	iqh3aSlot1PowerDisplay OBJECT-TYPE
		SYNTAX		RollCallString
		MAX-ACCESS		read-only
		STATUS			current
		DESCRIPTION
				"TYPE: - Display
				 PAGE: - Slots
					Power Display  cmdID= 17270  format=   "
		::= { iqh3aCmdEntry 17270 }


	iqh3aSlot2InstalledType OBJECT-TYPE
		SYNTAX		RollCallString
		MAX-ACCESS		read-only
		STATUS			current
		DESCRIPTION
				"TYPE: - Display
				 PAGE: - Slots
					Installed Type  cmdID= 16511  format=   "
		::= { iqh3aCmdEntry 16511 }


	iqh3aSlot2InstalledUnit OBJECT-TYPE
		SYNTAX		RollCallString
		MAX-ACCESS		read-only
		STATUS			current
		DESCRIPTION
				"TYPE: - Display
				 PAGE: - Slots
					Installed Unit  cmdID= 16531  format=   "
		::= { iqh3aCmdEntry 16531 }


	iqh3aSlot2Name OBJECT-TYPE
		SYNTAX		RollCallString
		MAX-ACCESS		read-write
		STATUS			current
		DESCRIPTION
				"TYPE: - Editstring
				 PAGE: - Slots
					Name  cmdID= 16390  "
		::= { iqh3aCmdEntry 16390 }


	iqh3aSlot2BoundType OBJECT-TYPE
		SYNTAX		INTEGER
		MAX-ACCESS		read-write
		STATUS			current
		DESCRIPTION
				"TYPE: - Number
				 PAGE: - Slots
					Bound Type  cmdID= 16438  min= 0  max= 65536  step= 1  format= %.0f  div_scale= 1
					Min = 0  Max = 65536  Step = 1 "
		::= { iqh3aCmdEntry 16438 }


	iqh3aSlot2Information1 OBJECT-TYPE
		SYNTAX		RollCallString
		MAX-ACCESS		read-write
		STATUS			current
		DESCRIPTION
				"TYPE: - Editstring
				 PAGE: - Slots
				 Generic Information field 1, to hold User defined Information
					Information 1  cmdID= 17102  "
		::= { iqh3aCmdEntry 17102 }


	iqh3aSlot2Information2 OBJECT-TYPE
		SYNTAX		RollCallString
		MAX-ACCESS		read-write
		STATUS			current
		DESCRIPTION
				"TYPE: - Editstring
				 PAGE: - Slots
				 Generic Information field2, to hold User defined Information
					Information 2  cmdID= 17122  "
		::= { iqh3aCmdEntry 17122 }


	iqh3aSlot2NonRollCallSlot OBJECT-TYPE
		SYNTAX		INTEGER { disable(0), enable(1) }
		MAX-ACCESS		read-write
		STATUS			current
		DESCRIPTION
				"TYPE: - Checkbox
				 PAGE: - Slots
					NonRollCallSlot  cmdID= 17202 "
		::= { iqh3aCmdEntry 17202 }


	iqh3aSlot2IdName OBJECT-TYPE
		SYNTAX		RollCallString
		MAX-ACCESS		read-write
		STATUS			current
		DESCRIPTION
				"TYPE: - Editstring
				 PAGE: - Slots
					IdName  cmdID= 17222  "
		::= { iqh3aCmdEntry 17222 }


	iqh3aSlot2PowerUsage OBJECT-TYPE
		SYNTAX		INTEGER
		MAX-ACCESS		read-write
		STATUS			current
		DESCRIPTION
				"TYPE: - Number
				 PAGE: - Slots
					Power Usage  cmdID= 17251  min= 0  max= 500  step= 1  format= %0.1f  div_scale= 10 
					Min = 0.0  Max = 50.0  Step = 0.1 "
		::= { iqh3aCmdEntry 17251 }


	iqh3aSlot2PowerDisplay OBJECT-TYPE
		SYNTAX		RollCallString
		MAX-ACCESS		read-only
		STATUS			current
		DESCRIPTION
				"TYPE: - Display
				 PAGE: - Slots
					Power Display  cmdID= 17271  format=   "
		::= { iqh3aCmdEntry 17271 }


	iqh3aSlot3InstalledType OBJECT-TYPE
		SYNTAX		RollCallString
		MAX-ACCESS		read-only
		STATUS			current
		DESCRIPTION
				"TYPE: - Display
				 PAGE: - Slots
					Installed Type  cmdID= 16512  format=   "
		::= { iqh3aCmdEntry 16512 }


	iqh3aSlot3InstalledUnit OBJECT-TYPE
		SYNTAX		RollCallString
		MAX-ACCESS		read-only
		STATUS			current
		DESCRIPTION
				"TYPE: - Display
				 PAGE: - Slots
					Installed Unit  cmdID= 16532  format=   "
		::= { iqh3aCmdEntry 16532 }


	iqh3aSlot3Name OBJECT-TYPE
		SYNTAX		RollCallString
		MAX-ACCESS		read-write
		STATUS			current
		DESCRIPTION
				"TYPE: - Editstring
				 PAGE: - Slots
					Name  cmdID= 16391  "
		::= { iqh3aCmdEntry 16391 }


	iqh3aSlot3BoundType OBJECT-TYPE
		SYNTAX		INTEGER
		MAX-ACCESS		read-write
		STATUS			current
		DESCRIPTION
				"TYPE: - Number
				 PAGE: - Slots
					Bound Type  cmdID= 16439  min= 0  max= 65536  step= 1  format= %.0f  div_scale= 1
					Min = 0  Max = 65536  Step = 1 "
		::= { iqh3aCmdEntry 16439 }


	iqh3aSlot3Information1 OBJECT-TYPE
		SYNTAX		RollCallString
		MAX-ACCESS		read-write
		STATUS			current
		DESCRIPTION
				"TYPE: - Editstring
				 PAGE: - Slots
				 Generic Information field 1, to hold User defined Information
					Information 1  cmdID= 17103  "
		::= { iqh3aCmdEntry 17103 }


	iqh3aSlot3Information2 OBJECT-TYPE
		SYNTAX		RollCallString
		MAX-ACCESS		read-write
		STATUS			current
		DESCRIPTION
				"TYPE: - Editstring
				 PAGE: - Slots
				 Generic Information field2, to hold User defined Information
					Information 2  cmdID= 17123  "
		::= { iqh3aCmdEntry 17123 }


	iqh3aSlot3NonRollCallSlot OBJECT-TYPE
		SYNTAX		INTEGER { disable(0), enable(1) }
		MAX-ACCESS		read-write
		STATUS			current
		DESCRIPTION
				"TYPE: - Checkbox
				 PAGE: - Slots
					NonRollCallSlot  cmdID= 17203 "
		::= { iqh3aCmdEntry 17203 }


	iqh3aSlot3IdName OBJECT-TYPE
		SYNTAX		RollCallString
		MAX-ACCESS		read-write
		STATUS			current
		DESCRIPTION
				"TYPE: - Editstring
				 PAGE: - Slots
					IdName  cmdID= 17223  "
		::= { iqh3aCmdEntry 17223 }


	iqh3aSlot3PowerUsage OBJECT-TYPE
		SYNTAX		INTEGER
		MAX-ACCESS		read-write
		STATUS			current
		DESCRIPTION
				"TYPE: - Number
				 PAGE: - Slots
					Power Usage  cmdID= 17252  min= 0  max= 500  step= 1  format= %0.1f  div_scale= 10 
					Min = 0.0  Max = 50.0  Step = 0.1 "
		::= { iqh3aCmdEntry 17252 }


	iqh3aSlot3PowerDisplay OBJECT-TYPE
		SYNTAX		RollCallString
		MAX-ACCESS		read-only
		STATUS			current
		DESCRIPTION
				"TYPE: - Display
				 PAGE: - Slots
					Power Display  cmdID= 17272  format=   "
		::= { iqh3aCmdEntry 17272 }


	iqh3aSlot4InstalledType OBJECT-TYPE
		SYNTAX		RollCallString
		MAX-ACCESS		read-only
		STATUS			current
		DESCRIPTION
				"TYPE: - Display
				 PAGE: - Slots
					Installed Type  cmdID= 16513  format=   "
		::= { iqh3aCmdEntry 16513 }


	iqh3aSlot4InstalledUnit OBJECT-TYPE
		SYNTAX		RollCallString
		MAX-ACCESS		read-only
		STATUS			current
		DESCRIPTION
				"TYPE: - Display
				 PAGE: - Slots
					Installed Unit  cmdID= 16533  format=   "
		::= { iqh3aCmdEntry 16533 }


	iqh3aSlot4Name OBJECT-TYPE
		SYNTAX		RollCallString
		MAX-ACCESS		read-write
		STATUS			current
		DESCRIPTION
				"TYPE: - Editstring
				 PAGE: - Slots
					Name  cmdID= 16392  "
		::= { iqh3aCmdEntry 16392 }


	iqh3aSlot4BoundType OBJECT-TYPE
		SYNTAX		INTEGER
		MAX-ACCESS		read-write
		STATUS			current
		DESCRIPTION
				"TYPE: - Number
				 PAGE: - Slots
					Bound Type  cmdID= 16440  min= 0  max= 65536  step= 1  format= %.0f  div_scale= 1
					Min = 0  Max = 65536  Step = 1 "
		::= { iqh3aCmdEntry 16440 }


	iqh3aSlot4Information1 OBJECT-TYPE
		SYNTAX		RollCallString
		MAX-ACCESS		read-write
		STATUS			current
		DESCRIPTION
				"TYPE: - Editstring
				 PAGE: - Slots
				 Generic Information field 1, to hold User defined Information
					Information 1  cmdID= 17104  "
		::= { iqh3aCmdEntry 17104 }


	iqh3aSlot4Information2 OBJECT-TYPE
		SYNTAX		RollCallString
		MAX-ACCESS		read-write
		STATUS			current
		DESCRIPTION
				"TYPE: - Editstring
				 PAGE: - Slots
				 Generic Information field2, to hold User defined Information
					Information 2  cmdID= 17124  "
		::= { iqh3aCmdEntry 17124 }


	iqh3aSlot4NonRollCallSlot OBJECT-TYPE
		SYNTAX		INTEGER { disable(0), enable(1) }
		MAX-ACCESS		read-write
		STATUS			current
		DESCRIPTION
				"TYPE: - Checkbox
				 PAGE: - Slots
					NonRollCallSlot  cmdID= 17204 "
		::= { iqh3aCmdEntry 17204 }


	iqh3aSlot4IdName OBJECT-TYPE
		SYNTAX		RollCallString
		MAX-ACCESS		read-write
		STATUS			current
		DESCRIPTION
				"TYPE: - Editstring
				 PAGE: - Slots
					IdName  cmdID= 17224  "
		::= { iqh3aCmdEntry 17224 }


	iqh3aSlot4PowerUsage OBJECT-TYPE
		SYNTAX		INTEGER
		MAX-ACCESS		read-write
		STATUS			current
		DESCRIPTION
				"TYPE: - Number
				 PAGE: - Slots
					Power Usage  cmdID= 17253  min= 0  max= 500  step= 1  format= %0.1f  div_scale= 10 
					Min = 0.0  Max = 50.0  Step = 0.1 "
		::= { iqh3aCmdEntry 17253 }


	iqh3aSlot4PowerDisplay OBJECT-TYPE
		SYNTAX		RollCallString
		MAX-ACCESS		read-only
		STATUS			current
		DESCRIPTION
				"TYPE: - Display
				 PAGE: - Slots
					Power Display  cmdID= 17273  format=   "
		::= { iqh3aCmdEntry 17273 }


	iqh3aSlot5InstalledType OBJECT-TYPE
		SYNTAX		RollCallString
		MAX-ACCESS		read-only
		STATUS			current
		DESCRIPTION
				"TYPE: - Display
				 PAGE: - Slots
					Installed Type  cmdID= 16514  format=   "
		::= { iqh3aCmdEntry 16514 }


	iqh3aSlot5InstalledUnit OBJECT-TYPE
		SYNTAX		RollCallString
		MAX-ACCESS		read-only
		STATUS			current
		DESCRIPTION
				"TYPE: - Display
				 PAGE: - Slots
					Installed Unit  cmdID= 16534  format=   "
		::= { iqh3aCmdEntry 16534 }


	iqh3aSlot5Name OBJECT-TYPE
		SYNTAX		RollCallString
		MAX-ACCESS		read-write
		STATUS			current
		DESCRIPTION
				"TYPE: - Editstring
				 PAGE: - Slots
					Name  cmdID= 16393  "
		::= { iqh3aCmdEntry 16393 }


	iqh3aSlot5BoundType OBJECT-TYPE
		SYNTAX		INTEGER
		MAX-ACCESS		read-write
		STATUS			current
		DESCRIPTION
				"TYPE: - Number
				 PAGE: - Slots
					Bound Type  cmdID= 16441  min= 0  max= 65536  step= 1  format= %.0f  div_scale= 1
					Min = 0  Max = 65536  Step = 1 "
		::= { iqh3aCmdEntry 16441 }


	iqh3aSlot5Information1 OBJECT-TYPE
		SYNTAX		RollCallString
		MAX-ACCESS		read-write
		STATUS			current
		DESCRIPTION
				"TYPE: - Editstring
				 PAGE: - Slots
				 Generic Information field 1, to hold User defined Information
					Information 1  cmdID= 17105  "
		::= { iqh3aCmdEntry 17105 }


	iqh3aSlot5Information2 OBJECT-TYPE
		SYNTAX		RollCallString
		MAX-ACCESS		read-write
		STATUS			current
		DESCRIPTION
				"TYPE: - Editstring
				 PAGE: - Slots
				 Generic Information field2, to hold User defined Information
					Information 2  cmdID= 17125  "
		::= { iqh3aCmdEntry 17125 }


	iqh3aSlot5NonRollCallSlot OBJECT-TYPE
		SYNTAX		INTEGER { disable(0), enable(1) }
		MAX-ACCESS		read-write
		STATUS			current
		DESCRIPTION
				"TYPE: - Checkbox
				 PAGE: - Slots
					NonRollCallSlot  cmdID= 17205 "
		::= { iqh3aCmdEntry 17205 }


	iqh3aSlot5IdName OBJECT-TYPE
		SYNTAX		RollCallString
		MAX-ACCESS		read-write
		STATUS			current
		DESCRIPTION
				"TYPE: - Editstring
				 PAGE: - Slots
					IdName  cmdID= 17225  "
		::= { iqh3aCmdEntry 17225 }


	iqh3aSlot5PowerUsage OBJECT-TYPE
		SYNTAX		INTEGER
		MAX-ACCESS		read-write
		STATUS			current
		DESCRIPTION
				"TYPE: - Number
				 PAGE: - Slots
					Power Usage  cmdID= 17254  min= 0  max= 500  step= 1  format= %0.1f  div_scale= 10 
					Min = 0.0  Max = 50.0  Step = 0.1 "
		::= { iqh3aCmdEntry 17254 }


	iqh3aSlot5PowerDisplay OBJECT-TYPE
		SYNTAX		RollCallString
		MAX-ACCESS		read-only
		STATUS			current
		DESCRIPTION
				"TYPE: - Display
				 PAGE: - Slots
					Power Display  cmdID= 17274  format=   "
		::= { iqh3aCmdEntry 17274 }


	iqh3aSlot6InstalledType OBJECT-TYPE
		SYNTAX		RollCallString
		MAX-ACCESS		read-only
		STATUS			current
		DESCRIPTION
				"TYPE: - Display
				 PAGE: - Slots
					Installed Type  cmdID= 16515  format=   "
		::= { iqh3aCmdEntry 16515 }


	iqh3aSlot6InstalledUnit OBJECT-TYPE
		SYNTAX		RollCallString
		MAX-ACCESS		read-only
		STATUS			current
		DESCRIPTION
				"TYPE: - Display
				 PAGE: - Slots
					Installed Unit  cmdID= 16535  format=   "
		::= { iqh3aCmdEntry 16535 }


	iqh3aSlot6Name OBJECT-TYPE
		SYNTAX		RollCallString
		MAX-ACCESS		read-write
		STATUS			current
		DESCRIPTION
				"TYPE: - Editstring
				 PAGE: - Slots
					Name  cmdID= 16394  "
		::= { iqh3aCmdEntry 16394 }


	iqh3aSlot6BoundType OBJECT-TYPE
		SYNTAX		INTEGER
		MAX-ACCESS		read-write
		STATUS			current
		DESCRIPTION
				"TYPE: - Number
				 PAGE: - Slots
					Bound Type  cmdID= 16442  min= 0  max= 65536  step= 1  format= %.0f  div_scale= 1
					Min = 0  Max = 65536  Step = 1 "
		::= { iqh3aCmdEntry 16442 }


	iqh3aSlot6Information1 OBJECT-TYPE
		SYNTAX		RollCallString
		MAX-ACCESS		read-write
		STATUS			current
		DESCRIPTION
				"TYPE: - Editstring
				 PAGE: - Slots
				 Generic Information field 1, to hold User defined Information
					Information 1  cmdID= 17106  "
		::= { iqh3aCmdEntry 17106 }


	iqh3aSlot6Information2 OBJECT-TYPE
		SYNTAX		RollCallString
		MAX-ACCESS		read-write
		STATUS			current
		DESCRIPTION
				"TYPE: - Editstring
				 PAGE: - Slots
				 Generic Information field2, to hold User defined Information
					Information 2  cmdID= 17126  "
		::= { iqh3aCmdEntry 17126 }


	iqh3aSlot6NonRollCallSlot OBJECT-TYPE
		SYNTAX		INTEGER { disable(0), enable(1) }
		MAX-ACCESS		read-write
		STATUS			current
		DESCRIPTION
				"TYPE: - Checkbox
				 PAGE: - Slots
					NonRollCallSlot  cmdID= 17206 "
		::= { iqh3aCmdEntry 17206 }


	iqh3aSlot6IdName OBJECT-TYPE
		SYNTAX		RollCallString
		MAX-ACCESS		read-write
		STATUS			current
		DESCRIPTION
				"TYPE: - Editstring
				 PAGE: - Slots
					IdName  cmdID= 17226  "
		::= { iqh3aCmdEntry 17226 }


	iqh3aSlot6PowerUsage OBJECT-TYPE
		SYNTAX		INTEGER
		MAX-ACCESS		read-write
		STATUS			current
		DESCRIPTION
				"TYPE: - Number
				 PAGE: - Slots
					Power Usage  cmdID= 17255  min= 0  max= 500  step= 1  format= %0.1f  div_scale= 10 
					Min = 0.0  Max = 50.0  Step = 0.1 "
		::= { iqh3aCmdEntry 17255 }


	iqh3aSlot6PowerDisplay OBJECT-TYPE
		SYNTAX		RollCallString
		MAX-ACCESS		read-only
		STATUS			current
		DESCRIPTION
				"TYPE: - Display
				 PAGE: - Slots
					Power Display  cmdID= 17275  format=   "
		::= { iqh3aCmdEntry 17275 }


	iqh3aSlot7InstalledType OBJECT-TYPE
		SYNTAX		RollCallString
		MAX-ACCESS		read-only
		STATUS			current
		DESCRIPTION
				"TYPE: - Display
				 PAGE: - Slots
					Installed Type  cmdID= 16516  format=   "
		::= { iqh3aCmdEntry 16516 }


	iqh3aSlot7InstalledUnit OBJECT-TYPE
		SYNTAX		RollCallString
		MAX-ACCESS		read-only
		STATUS			current
		DESCRIPTION
				"TYPE: - Display
				 PAGE: - Slots
					Installed Unit  cmdID= 16536  format=   "
		::= { iqh3aCmdEntry 16536 }


	iqh3aSlot7Name OBJECT-TYPE
		SYNTAX		RollCallString
		MAX-ACCESS		read-write
		STATUS			current
		DESCRIPTION
				"TYPE: - Editstring
				 PAGE: - Slots
					Name  cmdID= 16395  "
		::= { iqh3aCmdEntry 16395 }


	iqh3aSlot7BoundType OBJECT-TYPE
		SYNTAX		INTEGER
		MAX-ACCESS		read-write
		STATUS			current
		DESCRIPTION
				"TYPE: - Number
				 PAGE: - Slots
					Bound Type  cmdID= 16443  min= 0  max= 65536  step= 1  format= %.0f  div_scale= 1
					Min = 0  Max = 65536  Step = 1 "
		::= { iqh3aCmdEntry 16443 }


	iqh3aSlot7Information1 OBJECT-TYPE
		SYNTAX		RollCallString
		MAX-ACCESS		read-write
		STATUS			current
		DESCRIPTION
				"TYPE: - Editstring
				 PAGE: - Slots
				 Generic Information field 1, to hold User defined Information
					Information 1  cmdID= 17107  "
		::= { iqh3aCmdEntry 17107 }


	iqh3aSlot7Information2 OBJECT-TYPE
		SYNTAX		RollCallString
		MAX-ACCESS		read-write
		STATUS			current
		DESCRIPTION
				"TYPE: - Editstring
				 PAGE: - Slots
				 Generic Information field2, to hold User defined Information
					Information 2  cmdID= 17127  "
		::= { iqh3aCmdEntry 17127 }


	iqh3aSlot7NonRollCallSlot OBJECT-TYPE
		SYNTAX		INTEGER { disable(0), enable(1) }
		MAX-ACCESS		read-write
		STATUS			current
		DESCRIPTION
				"TYPE: - Checkbox
				 PAGE: - Slots
					NonRollCallSlot  cmdID= 17207 "
		::= { iqh3aCmdEntry 17207 }


	iqh3aSlot7IdName OBJECT-TYPE
		SYNTAX		RollCallString
		MAX-ACCESS		read-write
		STATUS			current
		DESCRIPTION
				"TYPE: - Editstring
				 PAGE: - Slots
					IdName  cmdID= 17227  "
		::= { iqh3aCmdEntry 17227 }


	iqh3aSlot7PowerUsage OBJECT-TYPE
		SYNTAX		INTEGER
		MAX-ACCESS		read-write
		STATUS			current
		DESCRIPTION
				"TYPE: - Number
				 PAGE: - Slots
					Power Usage  cmdID= 17256  min= 0  max= 500  step= 1  format= %0.1f  div_scale= 10 
					Min = 0.0  Max = 50.0  Step = 0.1 "
		::= { iqh3aCmdEntry 17256 }


	iqh3aSlot7PowerDisplay OBJECT-TYPE
		SYNTAX		RollCallString
		MAX-ACCESS		read-only
		STATUS			current
		DESCRIPTION
				"TYPE: - Display
				 PAGE: - Slots
					Power Display  cmdID= 17276  format=   "
		::= { iqh3aCmdEntry 17276 }


	iqh3aSlot8InstalledType OBJECT-TYPE
		SYNTAX		RollCallString
		MAX-ACCESS		read-only
		STATUS			current
		DESCRIPTION
				"TYPE: - Display
				 PAGE: - Slots
					Installed Type  cmdID= 16517  format=   "
		::= { iqh3aCmdEntry 16517 }


	iqh3aSlot8InstalledUnit OBJECT-TYPE
		SYNTAX		RollCallString
		MAX-ACCESS		read-only
		STATUS			current
		DESCRIPTION
				"TYPE: - Display
				 PAGE: - Slots
					Installed Unit  cmdID= 16537  format=   "
		::= { iqh3aCmdEntry 16537 }


	iqh3aSlot8Name OBJECT-TYPE
		SYNTAX		RollCallString
		MAX-ACCESS		read-write
		STATUS			current
		DESCRIPTION
				"TYPE: - Editstring
				 PAGE: - Slots
					Name  cmdID= 16396  "
		::= { iqh3aCmdEntry 16396 }


	iqh3aSlot8BoundType OBJECT-TYPE
		SYNTAX		INTEGER
		MAX-ACCESS		read-write
		STATUS			current
		DESCRIPTION
				"TYPE: - Number
				 PAGE: - Slots
					Bound Type  cmdID= 16444  min= 0  max= 65536  step= 1  format= %.0f  div_scale= 1
					Min = 0  Max = 65536  Step = 1 "
		::= { iqh3aCmdEntry 16444 }


	iqh3aSlot8Information1 OBJECT-TYPE
		SYNTAX		RollCallString
		MAX-ACCESS		read-write
		STATUS			current
		DESCRIPTION
				"TYPE: - Editstring
				 PAGE: - Slots
				 Generic Information field 1, to hold User defined Information
					Information 1  cmdID= 17108  "
		::= { iqh3aCmdEntry 17108 }


	iqh3aSlot8Information2 OBJECT-TYPE
		SYNTAX		RollCallString
		MAX-ACCESS		read-write
		STATUS			current
		DESCRIPTION
				"TYPE: - Editstring
				 PAGE: - Slots
				 Generic Information field2, to hold User defined Information
					Information 2  cmdID= 17128  "
		::= { iqh3aCmdEntry 17128 }

	iqh3aSlot8NonRollCallSlot OBJECT-TYPE
		SYNTAX		INTEGER { disable(0), enable(1) }
		MAX-ACCESS		read-write
		STATUS			current
		DESCRIPTION
				"TYPE: - Checkbox
				 PAGE: - Slots
					NonRollCallSlot  cmdID= 17208 "
		::= { iqh3aCmdEntry 17208 }


	iqh3aSlot8IdName OBJECT-TYPE
		SYNTAX		RollCallString
		MAX-ACCESS		read-write
		STATUS			current
		DESCRIPTION
				"TYPE: - Editstring
				 PAGE: - Slots
					IdName  cmdID= 17228  "
		::= { iqh3aCmdEntry 17228 }


	iqh3aSlot8PowerUsage OBJECT-TYPE
		SYNTAX		INTEGER
		MAX-ACCESS		read-write
		STATUS			current
		DESCRIPTION
				"TYPE: - Number
				 PAGE: - Slots
					Power Usage  cmdID= 17257  min= 0  max= 500  step= 1  format= %0.1f  div_scale= 10 
					Min = 0.0  Max = 50.0  Step = 0.1 "
		::= { iqh3aCmdEntry 17257 }


	iqh3aSlot8PowerDisplay OBJECT-TYPE
		SYNTAX		RollCallString
		MAX-ACCESS		read-only
		STATUS			current
		DESCRIPTION
				"TYPE: - Display
				 PAGE: - Slots
					Power Display  cmdID= 17277  format=   "
		::= { iqh3aCmdEntry 17277 }


	iqh3aSlot9InstalledType OBJECT-TYPE
		SYNTAX		RollCallString
		MAX-ACCESS		read-only
		STATUS			current
		DESCRIPTION
				"TYPE: - Display
				 PAGE: - Slots
					Installed Type  cmdID= 16518  format=   "
		::= { iqh3aCmdEntry 16518 }


	iqh3aSlot9InstalledUnit OBJECT-TYPE
		SYNTAX		RollCallString
		MAX-ACCESS		read-only
		STATUS			current
		DESCRIPTION
				"TYPE: - Display
				 PAGE: - Slots
					Installed Unit  cmdID= 16538  format=   "
		::= { iqh3aCmdEntry 16538 }


	iqh3aSlot9Name OBJECT-TYPE
		SYNTAX		RollCallString
		MAX-ACCESS		read-write
		STATUS			current
		DESCRIPTION
				"TYPE: - Editstring
				 PAGE: - Slots
					Name  cmdID= 16397  "
		::= { iqh3aCmdEntry 16397 }


	iqh3aSlot9BoundType OBJECT-TYPE
		SYNTAX		INTEGER
		MAX-ACCESS		read-write
		STATUS			current
		DESCRIPTION
				"TYPE: - Number
				 PAGE: - Slots
					Bound Type  cmdID= 16445  min= 0  max= 65536  step= 1  format= %.0f  div_scale= 1
					Min = 0  Max = 65536  Step = 1 "
		::= { iqh3aCmdEntry 16445 }


	iqh3aSlot9Information1 OBJECT-TYPE
		SYNTAX		RollCallString
		MAX-ACCESS		read-write
		STATUS			current
		DESCRIPTION
				"TYPE: - Editstring
				 PAGE: - Slots
				 Generic Information field 1, to hold User defined Information
					Information 1  cmdID= 17109  "
		::= { iqh3aCmdEntry 17109 }


	iqh3aSlot9Information2 OBJECT-TYPE
		SYNTAX		RollCallString
		MAX-ACCESS		read-write
		STATUS			current
		DESCRIPTION
				"TYPE: - Editstring
				 PAGE: - Slots
				 Generic Information field2, to hold User defined Information
					Information 2  cmdID= 17129  "
		::= { iqh3aCmdEntry 17129 }


	iqh3aSlot9NonRollCallSlot OBJECT-TYPE
		SYNTAX		INTEGER { disable(0), enable(1) }
		MAX-ACCESS		read-write
		STATUS			current
		DESCRIPTION
				"TYPE: - Checkbox
				 PAGE: - Slots
					NonRollCallSlot  cmdID= 17209 "
		::= { iqh3aCmdEntry 17209 }


	iqh3aSlot9IdName OBJECT-TYPE
		SYNTAX		RollCallString
		MAX-ACCESS		read-write
		STATUS			current
		DESCRIPTION
				"TYPE: - Editstring
				 PAGE: - Slots
					IdName  cmdID= 17229  "
		::= { iqh3aCmdEntry 17229 }


	iqh3aSlot9PowerUsage OBJECT-TYPE
		SYNTAX		INTEGER
		MAX-ACCESS		read-write
		STATUS			current
		DESCRIPTION
				"TYPE: - Number
				 PAGE: - Slots
					Power Usage  cmdID= 17258  min= 0  max= 500  step= 1  format= %0.1f  div_scale= 10 
					Min = 0.0  Max = 50.0  Step = 0.1 "
		::= { iqh3aCmdEntry 17258 }


	iqh3aSlot9PowerDisplay OBJECT-TYPE
		SYNTAX		RollCallString
		MAX-ACCESS		read-only
		STATUS			current
		DESCRIPTION
				"TYPE: - Display
				 PAGE: - Slots
					Power Display  cmdID= 17278  format=   "
		::= { iqh3aCmdEntry 17278 }


	iqh3aSlot10InstalledType OBJECT-TYPE
		SYNTAX		RollCallString
		MAX-ACCESS		read-only
		STATUS			current
		DESCRIPTION
				"TYPE: - Display
				 PAGE: - Slots
					Installed Type  cmdID= 16519  format=   "
		::= { iqh3aCmdEntry 16519 }


	iqh3aSlot10InstalledUnit OBJECT-TYPE
		SYNTAX		RollCallString
		MAX-ACCESS		read-only
		STATUS			current
		DESCRIPTION
				"TYPE: - Display
				 PAGE: - Slots
					Installed Unit  cmdID= 16539  format=   "
		::= { iqh3aCmdEntry 16539 }


	iqh3aSlot10Name OBJECT-TYPE
		SYNTAX		RollCallString
		MAX-ACCESS		read-write
		STATUS			current
		DESCRIPTION
				"TYPE: - Editstring
				 PAGE: - Slots
					Name  cmdID= 16398  "
		::= { iqh3aCmdEntry 16398 }


	iqh3aSlot10BoundType OBJECT-TYPE
		SYNTAX		INTEGER
		MAX-ACCESS		read-write
		STATUS			current
		DESCRIPTION
				"TYPE: - Number
				 PAGE: - Slots
					Bound Type  cmdID= 16446  min= 0  max= 65536  step= 1  format= %.0f  div_scale= 1
					Min = 0  Max = 65536  Step = 1 "
		::= { iqh3aCmdEntry 16446 }


	iqh3aSlot10Information1 OBJECT-TYPE
		SYNTAX		RollCallString
		MAX-ACCESS		read-write
		STATUS			current
		DESCRIPTION
				"TYPE: - Editstring
				 PAGE: - Slots
				 Generic Information field 1, to hold User defined Information
					Information 1  cmdID= 17110  "
		::= { iqh3aCmdEntry 17110 }


	iqh3aSlot10Information2 OBJECT-TYPE
		SYNTAX		RollCallString
		MAX-ACCESS		read-write
		STATUS			current
		DESCRIPTION
				"TYPE: - Editstring
				 PAGE: - Slots
				 Generic Information field2, to hold User defined Information
					Information 2  cmdID= 17130  "
		::= { iqh3aCmdEntry 17130 }


	iqh3aSlot10NonRollCallSlot OBJECT-TYPE
		SYNTAX		INTEGER { disable(0), enable(1) }
		MAX-ACCESS		read-write
		STATUS			current
		DESCRIPTION
				"TYPE: - Checkbox
				 PAGE: - Slots
					NonRollCallSlot  cmdID= 17210 "
		::= { iqh3aCmdEntry 17210 }


	iqh3aSlot10IdName OBJECT-TYPE
		SYNTAX		RollCallString
		MAX-ACCESS		read-write
		STATUS			current
		DESCRIPTION
				"TYPE: - Editstring
				 PAGE: - Slots
					IdName  cmdID= 17230  "
		::= { iqh3aCmdEntry 17230 }


	iqh3aSlot10PowerUsage OBJECT-TYPE
		SYNTAX		INTEGER
		MAX-ACCESS		read-write
		STATUS			current
		DESCRIPTION
				"TYPE: - Number
				 PAGE: - Slots
					Power Usage  cmdID= 17259  min= 0  max= 500  step= 1  format= %0.1f  div_scale= 10 
					Min = 0.0  Max = 50.0  Step = 0.1 "
		::= { iqh3aCmdEntry 17259 }


	iqh3aSlot10PowerDisplay OBJECT-TYPE
		SYNTAX		RollCallString
		MAX-ACCESS		read-only
		STATUS			current
		DESCRIPTION
				"TYPE: - Display
				 PAGE: - Slots
					Power Display  cmdID= 17279  format=   "
		::= { iqh3aCmdEntry 17279 }


	iqh3aSlot11InstalledType OBJECT-TYPE
		SYNTAX		RollCallString
		MAX-ACCESS		read-only
		STATUS			current
		DESCRIPTION
				"TYPE: - Display
				 PAGE: - Slots
					Installed Type  cmdID= 16520  format=   "
		::= { iqh3aCmdEntry 16520 }


	iqh3aSlot11InstalledUnit OBJECT-TYPE
		SYNTAX		RollCallString
		MAX-ACCESS		read-only
		STATUS			current
		DESCRIPTION
				"TYPE: - Display
				 PAGE: - Slots
					Installed Unit  cmdID= 16540  format=   "
		::= { iqh3aCmdEntry 16540 }


	iqh3aSlot11Name OBJECT-TYPE
		SYNTAX		RollCallString
		MAX-ACCESS		read-write
		STATUS			current
		DESCRIPTION
				"TYPE: - Editstring
				 PAGE: - Slots
					Name  cmdID= 16399  "
		::= { iqh3aCmdEntry 16399 }


	iqh3aSlot11BoundType OBJECT-TYPE
		SYNTAX		INTEGER
		MAX-ACCESS		read-write
		STATUS			current
		DESCRIPTION
				"TYPE: - Number
				 PAGE: - Slots
					Bound Type  cmdID= 16447  min= 0  max= 65536  step= 1  format= %.0f  div_scale= 1
					Min = 0  Max = 65536  Step = 1 "
		::= { iqh3aCmdEntry 16447 }


	iqh3aSlot11Information1 OBJECT-TYPE
		SYNTAX		RollCallString
		MAX-ACCESS		read-write
		STATUS			current
		DESCRIPTION
				"TYPE: - Editstring
				 PAGE: - Slots
				 Generic Information field 1, to hold User defined Information
					Information 1  cmdID= 17111  "
		::= { iqh3aCmdEntry 17111 }


	iqh3aSlot11Information2 OBJECT-TYPE
		SYNTAX		RollCallString
		MAX-ACCESS		read-write
		STATUS			current
		DESCRIPTION
				"TYPE: - Editstring
				 PAGE: - Slots
				 Generic Information field2, to hold User defined Information
					Information 2  cmdID= 17131  "
		::= { iqh3aCmdEntry 17131 }


	iqh3aSlot11NonRollCallSlot OBJECT-TYPE
		SYNTAX		INTEGER { disable(0), enable(1) }
		MAX-ACCESS		read-write
		STATUS			current
		DESCRIPTION
				"TYPE: - Checkbox
				 PAGE: - Slots
					NonRollCallSlot  cmdID= 17211 "
		::= { iqh3aCmdEntry 17211 }


	iqh3aSlot11IdName OBJECT-TYPE
		SYNTAX		RollCallString
		MAX-ACCESS		read-write
		STATUS			current
		DESCRIPTION
				"TYPE: - Editstring
				 PAGE: - Slots
					IdName  cmdID= 17231  "
		::= { iqh3aCmdEntry 17231 }


	iqh3aSlot11PowerUsage OBJECT-TYPE
		SYNTAX		INTEGER
		MAX-ACCESS		read-write
		STATUS			current
		DESCRIPTION
				"TYPE: - Number
				 PAGE: - Slots
					Power Usage  cmdID= 17260  min= 0  max= 500  step= 1  format= %0.1f  div_scale= 10 
					Min = 0.0  Max = 50.0  Step = 0.1 "
		::= { iqh3aCmdEntry 17260 }


	iqh3aSlot11PowerDisplay OBJECT-TYPE
		SYNTAX		RollCallString
		MAX-ACCESS		read-only
		STATUS			current
		DESCRIPTION
				"TYPE: - Display
				 PAGE: - Slots
					Power Display  cmdID= 17280  format=   "
		::= { iqh3aCmdEntry 17280 }


	iqh3aSlot12InstalledType OBJECT-TYPE
		SYNTAX		RollCallString
		MAX-ACCESS		read-only
		STATUS			current
		DESCRIPTION
				"TYPE: - Display
				 PAGE: - Slots
					Installed Type  cmdID= 16521  format=   "
		::= { iqh3aCmdEntry 16521 }


	iqh3aSlot12InstalledUnit OBJECT-TYPE
		SYNTAX		RollCallString
		MAX-ACCESS		read-only
		STATUS			current
		DESCRIPTION
				"TYPE: - Display
				 PAGE: - Slots
					Installed Unit  cmdID= 16541  format=   "
		::= { iqh3aCmdEntry 16541 }


	iqh3aSlot12Name OBJECT-TYPE
		SYNTAX		RollCallString
		MAX-ACCESS		read-write
		STATUS			current
		DESCRIPTION
				"TYPE: - Editstring
				 PAGE: - Slots
					Name  cmdID= 16400  "
		::= { iqh3aCmdEntry 16400 }


	iqh3aSlot12BoundType OBJECT-TYPE
		SYNTAX		INTEGER
		MAX-ACCESS		read-write
		STATUS			current
		DESCRIPTION
				"TYPE: - Number
				 PAGE: - Slots
					Bound Type  cmdID= 16448  min= 0  max= 65536  step= 1  format= %.0f  div_scale= 1
					Min = 0  Max = 65536  Step = 1 "
		::= { iqh3aCmdEntry 16448 }


	iqh3aSlot12Information1 OBJECT-TYPE
		SYNTAX		RollCallString
		MAX-ACCESS		read-write
		STATUS			current
		DESCRIPTION
				"TYPE: - Editstring
				 PAGE: - Slots
				 Generic Information field 1, to hold User defined Information
					Information 1  cmdID= 17112  "
		::= { iqh3aCmdEntry 17112 }


	iqh3aSlot12Information2 OBJECT-TYPE
		SYNTAX		RollCallString
		MAX-ACCESS		read-write
		STATUS			current
		DESCRIPTION
				"TYPE: - Editstring
				 PAGE: - Slots
				 Generic Information field2, to hold User defined Information
					Information 2  cmdID= 17132  "
		::= { iqh3aCmdEntry 17132 }


	iqh3aSlot12NonRollCallSlot OBJECT-TYPE
		SYNTAX		INTEGER { disable(0), enable(1) }
		MAX-ACCESS		read-write
		STATUS			current
		DESCRIPTION
				"TYPE: - Checkbox
				 PAGE: - Slots
					NonRollCallSlot  cmdID= 17212 "
		::= { iqh3aCmdEntry 17212 }


	iqh3aSlot12IdName OBJECT-TYPE
		SYNTAX		RollCallString
		MAX-ACCESS		read-write
		STATUS			current
		DESCRIPTION
				"TYPE: - Editstring
				 PAGE: - Slots
					IdName  cmdID= 17232  "
		::= { iqh3aCmdEntry 17232 }


	iqh3aSlot12PowerUsage OBJECT-TYPE
		SYNTAX		INTEGER
		MAX-ACCESS		read-write
		STATUS			current
		DESCRIPTION
				"TYPE: - Number
				 PAGE: - Slots
					Power Usage  cmdID= 17261  min= 0  max= 500  step= 1  format= %0.1f  div_scale= 10 
					Min = 0.0  Max = 50.0  Step = 0.1 "
		::= { iqh3aCmdEntry 17261 }


	iqh3aSlot12PowerDisplay OBJECT-TYPE
		SYNTAX		RollCallString
		MAX-ACCESS		read-only
		STATUS			current
		DESCRIPTION
				"TYPE: - Display
				 PAGE: - Slots
					Power Display  cmdID= 17281  format=   "
		::= { iqh3aCmdEntry 17281 }


	iqh3aSlot13InstalledType OBJECT-TYPE
		SYNTAX		RollCallString
		MAX-ACCESS		read-only
		STATUS			current
		DESCRIPTION
				"TYPE: - Display
				 PAGE: - Slots
					Installed Type  cmdID= 16522  format=   "
		::= { iqh3aCmdEntry 16522 }


	iqh3aSlot13InstalledUnit OBJECT-TYPE
		SYNTAX		RollCallString
		MAX-ACCESS		read-only
		STATUS			current
		DESCRIPTION
				"TYPE: - Display
				 PAGE: - Slots
					Installed Unit  cmdID= 16542  format=   "
		::= { iqh3aCmdEntry 16542 }


	iqh3aSlot13Name OBJECT-TYPE
		SYNTAX		RollCallString
		MAX-ACCESS		read-write
		STATUS			current
		DESCRIPTION
				"TYPE: - Editstring
				 PAGE: - Slots
					Name  cmdID= 16401  "
		::= { iqh3aCmdEntry 16401 }


	iqh3aSlot13BoundType OBJECT-TYPE
		SYNTAX		INTEGER
		MAX-ACCESS		read-write
		STATUS			current
		DESCRIPTION
				"TYPE: - Number
				 PAGE: - Slots
					Bound Type  cmdID= 16449  min= 0  max= 65536  step= 1  format= %.0f  div_scale= 1
					Min = 0  Max = 65536  Step = 1 "
		::= { iqh3aCmdEntry 16449 }


	iqh3aSlot13Information1 OBJECT-TYPE
		SYNTAX		RollCallString
		MAX-ACCESS		read-write
		STATUS			current
		DESCRIPTION
				"TYPE: - Editstring
				 PAGE: - Slots
				 Generic Information field 1, to hold User defined Information
					Information 1  cmdID= 17113  "
		::= { iqh3aCmdEntry 17113 }


	iqh3aSlot13Information2 OBJECT-TYPE
		SYNTAX		RollCallString
		MAX-ACCESS		read-write
		STATUS			current
		DESCRIPTION
				"TYPE: - Editstring
				 PAGE: - Slots
				 Generic Information field2, to hold User defined Information
					Information 2  cmdID= 17133  "
		::= { iqh3aCmdEntry 17133 }


	iqh3aSlot13NonRollCallSlot OBJECT-TYPE
		SYNTAX		INTEGER { disable(0), enable(1) }
		MAX-ACCESS		read-write
		STATUS			current
		DESCRIPTION
				"TYPE: - Checkbox
				 PAGE: - Slots
					NonRollCallSlot  cmdID= 17213 "
		::= { iqh3aCmdEntry 17213 }


	iqh3aSlot13IdName OBJECT-TYPE
		SYNTAX		RollCallString
		MAX-ACCESS		read-write
		STATUS			current
		DESCRIPTION
				"TYPE: - Editstring
				 PAGE: - Slots
					IdName  cmdID= 17233  "
		::= { iqh3aCmdEntry 17233 }


	iqh3aSlot13PowerUsage OBJECT-TYPE
		SYNTAX		INTEGER
		MAX-ACCESS		read-write
		STATUS			current
		DESCRIPTION
				"TYPE: - Number
				 PAGE: - Slots
					Power Usage  cmdID= 17262  min= 0  max= 500  step= 1  format= %0.1f  div_scale= 10 
					Min = 0.0  Max = 50.0  Step = 0.1 "
		::= { iqh3aCmdEntry 17262 }


	iqh3aSlot13PowerDisplay OBJECT-TYPE
		SYNTAX		RollCallString
		MAX-ACCESS		read-only
		STATUS			current
		DESCRIPTION
				"TYPE: - Display
				 PAGE: - Slots
					Power Display  cmdID= 17282  format=   "
		::= { iqh3aCmdEntry 17282 }


	iqh3aSlot14InstalledType OBJECT-TYPE
		SYNTAX		RollCallString
		MAX-ACCESS		read-only
		STATUS			current
		DESCRIPTION
				"TYPE: - Display
				 PAGE: - Slots
					Installed Type  cmdID= 16523  format=   "
		::= { iqh3aCmdEntry 16523 }


	iqh3aSlot14InstalledUnit OBJECT-TYPE
		SYNTAX		RollCallString
		MAX-ACCESS		read-only
		STATUS			current
		DESCRIPTION
				"TYPE: - Display
				 PAGE: - Slots
					Installed Unit  cmdID= 16543  format=   "
		::= { iqh3aCmdEntry 16543 }


	iqh3aSlot14Name OBJECT-TYPE
		SYNTAX		RollCallString
		MAX-ACCESS		read-write
		STATUS			current
		DESCRIPTION
				"TYPE: - Editstring
				 PAGE: - Slots
					Name  cmdID= 16402  "
		::= { iqh3aCmdEntry 16402 }


	iqh3aSlot14BoundType OBJECT-TYPE
		SYNTAX		INTEGER
		MAX-ACCESS		read-write
		STATUS			current
		DESCRIPTION
				"TYPE: - Number
				 PAGE: - Slots
					Bound Type  cmdID= 16450  min= 0  max= 65536  step= 1  format= %.0f  div_scale= 1
					Min = 0  Max = 65536  Step = 1 "
		::= { iqh3aCmdEntry 16450 }


	iqh3aSlot14Information1 OBJECT-TYPE
		SYNTAX		RollCallString
		MAX-ACCESS		read-write
		STATUS			current
		DESCRIPTION
				"TYPE: - Editstring
				 PAGE: - Slots
				 Generic Information field 1, to hold User defined Information
					Information 1  cmdID= 17114  "
		::= { iqh3aCmdEntry 17114 }


	iqh3aSlot14Information2 OBJECT-TYPE
		SYNTAX		RollCallString
		MAX-ACCESS		read-write
		STATUS			current
		DESCRIPTION
				"TYPE: - Editstring
				 PAGE: - Slots
				 Generic Information field2, to hold User defined Information
					Information 2  cmdID= 17134  "
		::= { iqh3aCmdEntry 17134 }


	iqh3aSlot14NonRollCallSlot OBJECT-TYPE
		SYNTAX		INTEGER { disable(0), enable(1) }
		MAX-ACCESS		read-write
		STATUS			current
		DESCRIPTION
				"TYPE: - Checkbox
				 PAGE: - Slots
					NonRollCallSlot  cmdID= 17214 "
		::= { iqh3aCmdEntry 17214 }


	iqh3aSlot14IdName OBJECT-TYPE
		SYNTAX		RollCallString
		MAX-ACCESS		read-write
		STATUS			current
		DESCRIPTION
				"TYPE: - Editstring
				 PAGE: - Slots
					IdName  cmdID= 17234  "
		::= { iqh3aCmdEntry 17234 }


	iqh3aSlot14PowerUsage OBJECT-TYPE
		SYNTAX		INTEGER
		MAX-ACCESS		read-write
		STATUS			current
		DESCRIPTION
				"TYPE: - Number
				 PAGE: - Slots
					Power Usage  cmdID= 17263  min= 0  max= 500  step= 1  format= %0.1f  div_scale= 10 
					Min = 0.0  Max = 50.0  Step = 0.1 "
		::= { iqh3aCmdEntry 17263 }


	iqh3aSlot14PowerDisplay OBJECT-TYPE
		SYNTAX		RollCallString
		MAX-ACCESS		read-only
		STATUS			current
		DESCRIPTION
				"TYPE: - Display
				 PAGE: - Slots
					Power Display  cmdID= 17283  format=   "
		::= { iqh3aCmdEntry 17283 }


	iqh3aSlot15InstalledType OBJECT-TYPE
		SYNTAX		RollCallString
		MAX-ACCESS		read-only
		STATUS			current
		DESCRIPTION
				"TYPE: - Display
				 PAGE: - Slots
					Installed Type  cmdID= 16524  format=   "
		::= { iqh3aCmdEntry 16524 }


	iqh3aSlot15InstalledUnit OBJECT-TYPE
		SYNTAX		RollCallString
		MAX-ACCESS		read-only
		STATUS			current
		DESCRIPTION
				"TYPE: - Display
				 PAGE: - Slots
					Installed Unit  cmdID= 16544  format=   "
		::= { iqh3aCmdEntry 16544 }


	iqh3aSlot15Name OBJECT-TYPE
		SYNTAX		RollCallString
		MAX-ACCESS		read-write
		STATUS			current
		DESCRIPTION
				"TYPE: - Editstring
				 PAGE: - Slots
					Name  cmdID= 16403  "
		::= { iqh3aCmdEntry 16403 }


	iqh3aSlot15BoundType OBJECT-TYPE
		SYNTAX		INTEGER
		MAX-ACCESS		read-write
		STATUS			current
		DESCRIPTION
				"TYPE: - Number
				 PAGE: - Slots
					Bound Type  cmdID= 16451  min= 0  max= 65536  step= 1  format= %.0f  div_scale= 1
					Min = 0  Max = 65536  Step = 1 "
		::= { iqh3aCmdEntry 16451 }


	iqh3aSlot15Information1 OBJECT-TYPE
		SYNTAX		RollCallString
		MAX-ACCESS		read-write
		STATUS			current
		DESCRIPTION
				"TYPE: - Editstring
				 PAGE: - Slots
				 Generic Information field 1, to hold User defined Information
					Information 1  cmdID= 17115  "
		::= { iqh3aCmdEntry 17115 }


	iqh3aSlot15Information2 OBJECT-TYPE
		SYNTAX		RollCallString
		MAX-ACCESS		read-write
		STATUS			current
		DESCRIPTION
				"TYPE: - Editstring
				 PAGE: - Slots
				 Generic Information field2, to hold User defined Information
					Information 2  cmdID= 17135  "
		::= { iqh3aCmdEntry 17135 }


	iqh3aSlot15NonRollCallSlot OBJECT-TYPE
		SYNTAX		INTEGER { disable(0), enable(1) }
		MAX-ACCESS		read-write
		STATUS			current
		DESCRIPTION
				"TYPE: - Checkbox
				 PAGE: - Slots
					NonRollCallSlot  cmdID= 17215 "
		::= { iqh3aCmdEntry 17215 }


	iqh3aSlot15IdName OBJECT-TYPE
		SYNTAX		RollCallString
		MAX-ACCESS		read-write
		STATUS			current
		DESCRIPTION
				"TYPE: - Editstring
				 PAGE: - Slots
					IdName  cmdID= 17235  "
		::= { iqh3aCmdEntry 17235 }


	iqh3aSlot15PowerUsage OBJECT-TYPE
		SYNTAX		INTEGER
		MAX-ACCESS		read-write
		STATUS			current
		DESCRIPTION
				"TYPE: - Number
				 PAGE: - Slots
					Power Usage  cmdID= 17264  min= 0  max= 500  step= 1  format= %0.1f  div_scale= 10 
					Min = 0.0  Max = 50.0  Step = 0.1 "
		::= { iqh3aCmdEntry 17264 }


	iqh3aSlot15PowerDisplay OBJECT-TYPE
		SYNTAX		RollCallString
		MAX-ACCESS		read-only
		STATUS			current
		DESCRIPTION
				"TYPE: - Display
				 PAGE: - Slots
					Power Display  cmdID= 17284  format=   "
		::= { iqh3aCmdEntry 17284 }


	iqh3aSlot16InstalledType OBJECT-TYPE
		SYNTAX		RollCallString
		MAX-ACCESS		read-only
		STATUS			current
		DESCRIPTION
				"TYPE: - Display
				 PAGE: - Slots
					Installed Type  cmdID= 16525  format=   "
		::= { iqh3aCmdEntry 16525 }


	iqh3aSlot16InstalledUnit OBJECT-TYPE
		SYNTAX		RollCallString
		MAX-ACCESS		read-only
		STATUS			current
		DESCRIPTION
				"TYPE: - Display
				 PAGE: - Slots
					Installed Unit  cmdID= 16545  format=   "
		::= { iqh3aCmdEntry 16545 }


	iqh3aSlot16Name OBJECT-TYPE
		SYNTAX		RollCallString
		MAX-ACCESS		read-write
		STATUS			current
		DESCRIPTION
				"TYPE: - Editstring
				 PAGE: - Slots
					Name  cmdID= 16404  "
		::= { iqh3aCmdEntry 16404 }


	iqh3aSlot16BoundType OBJECT-TYPE
		SYNTAX		INTEGER
		MAX-ACCESS		read-write
		STATUS			current
		DESCRIPTION
				"TYPE: - Number
				 PAGE: - Slots
					Bound Type  cmdID= 16452  min= 0  max= 65536  step= 1  format= %.0f  div_scale= 1
					Min = 0  Max = 65536  Step = 1 "
		::= { iqh3aCmdEntry 16452 }


	iqh3aSlot16Information1 OBJECT-TYPE
		SYNTAX		RollCallString
		MAX-ACCESS		read-write
		STATUS			current
		DESCRIPTION
				"TYPE: - Editstring
				 PAGE: - Slots
				 Generic Information field 1, to hold User defined Information
					Information 1  cmdID= 17116  "
		::= { iqh3aCmdEntry 17116 }


	iqh3aSlot16Information2 OBJECT-TYPE
		SYNTAX		RollCallString
		MAX-ACCESS		read-write
		STATUS			current
		DESCRIPTION
				"TYPE: - Editstring
				 PAGE: - Slots
				 Generic Information field2, to hold User defined Information
					Information 2  cmdID= 17136  "
		::= { iqh3aCmdEntry 17136 }


	iqh3aSlot16NonRollCallSlot OBJECT-TYPE
		SYNTAX		INTEGER { disable(0), enable(1) }
		MAX-ACCESS		read-write
		STATUS			current
		DESCRIPTION
				"TYPE: - Checkbox
				 PAGE: - Slots
					NonRollCallSlot  cmdID= 17216 "
		::= { iqh3aCmdEntry 17216 }


	iqh3aSlot16IdName OBJECT-TYPE
		SYNTAX		RollCallString
		MAX-ACCESS		read-write
		STATUS			current
		DESCRIPTION
				"TYPE: - Editstring
				 PAGE: - Slots
					IdName  cmdID= 17236  "
		::= { iqh3aCmdEntry 17236 }


	iqh3aSlot16PowerUsage OBJECT-TYPE
		SYNTAX		INTEGER
		MAX-ACCESS		read-write
		STATUS			current
		DESCRIPTION
				"TYPE: - Number
				 PAGE: - Slots
					Power Usage  cmdID= 17265  min= 0  max= 500  step= 1  format= %0.1f  div_scale= 10 
					Min = 0.0  Max = 50.0  Step = 0.1 "
		::= { iqh3aCmdEntry 17265 }


	iqh3aSlot16PowerDisplay OBJECT-TYPE
		SYNTAX		RollCallString
		MAX-ACCESS		read-only
		STATUS			current
		DESCRIPTION
				"TYPE: - Display
				 PAGE: - Slots
					Power Display  cmdID= 17285  format=   "
		::= { iqh3aCmdEntry 17285 }


	iqh3aSystemSetupHardwareVersion OBJECT-TYPE
		SYNTAX		RollCallString
		MAX-ACCESS		read-only
		STATUS			current
		DESCRIPTION
				"TYPE: - Display
				 PAGE: - System
					Hardware Version  cmdID= 16614  format=   "
		::= { iqh3aCmdEntry 16614 }


	iqh3aSystemSetupUnitName OBJECT-TYPE
		SYNTAX		RollCallString
		MAX-ACCESS		read-write
		STATUS			current
		DESCRIPTION
				"TYPE: - Editstring
				 PAGE: - System
					Unit Name  cmdID= 16388  "
		::= { iqh3aCmdEntry 16388 }


	iqh3aSystemSetupSerialNumber OBJECT-TYPE
		SYNTAX		RollCallString
		MAX-ACCESS		read-only
		STATUS			current
		DESCRIPTION
				"TYPE: - Display
				 PAGE: - System
					Serial Number  cmdID= 16461  format=   "
		::= { iqh3aCmdEntry 16461 }


	iqh3aSystemSetupSoftwareVersion OBJECT-TYPE
		SYNTAX		RollCallString
		MAX-ACCESS		read-only
		STATUS			current
		DESCRIPTION
				"TYPE: - Display
				 PAGE: - System
					Software Version  cmdID= 16410  format=   "
		::= { iqh3aCmdEntry 16410 }


	iqh3aSystemSetupBuildNumber OBJECT-TYPE
		SYNTAX		RollCallString
		MAX-ACCESS		read-only
		STATUS			current
		DESCRIPTION
				"TYPE: - Display
				 PAGE: - System
					Build Number  cmdID= 16616  format=   "
		::= { iqh3aCmdEntry 16616 }


	iqh3aSystemSetupLoaderVersion OBJECT-TYPE
		SYNTAX		RollCallString
		MAX-ACCESS		read-only
		STATUS			current
		DESCRIPTION
				"TYPE: - Display
				 PAGE: - System
					Loader Version  cmdID= 16619  format=   "
		::= { iqh3aCmdEntry 16619 }


	iqh3aSystemSetupJavaAppletVersion OBJECT-TYPE
		SYNTAX		RollCallString
		MAX-ACCESS		read-only
		STATUS			current
		DESCRIPTION
				"TYPE: - Display
				 PAGE: - System
					Java Applet Version  cmdID= 16618  format=   "
		::= { iqh3aCmdEntry 16618 }


	iqh3aSystemSetupNetShow OBJECT-TYPE
		SYNTAX		INTEGER { disable(0), enable(1) }
		MAX-ACCESS		read-write
		STATUS			current
		DESCRIPTION
				"TYPE: - Checkbox
				 PAGE: - System
					NetShow  cmdID= 16432 "
		::= { iqh3aCmdEntry 16432 }


	iqh3aSystemSetupAllowBlindControl OBJECT-TYPE
		SYNTAX		INTEGER { disable(0), enable(1) }
		MAX-ACCESS		read-write
		STATUS			current
		DESCRIPTION
				"TYPE: - Checkbox
				 PAGE: - System
					Allow Blind Control  cmdID= 16703 "
		::= { iqh3aCmdEntry 16703 }


	iqh3aSystemSetupWhereAmI OBJECT-TYPE
		SYNTAX		INTEGER { disable(0), enable(1) }
		MAX-ACCESS		read-write
		STATUS			current
		DESCRIPTION
				"TYPE: - Checkbox
				 PAGE: - System
					Where Am I?  cmdID= 16469 "
		::= { iqh3aCmdEntry 16469 }


	iqh3aSystemSetupSerialSpeed OBJECT-TYPE
		SYNTAX		INTEGER {
							val-115200-bps(6),
							val-57600-bps(5),
							val-38400-bps(4),
							val-19200-bps(3),
							val-9600-bps(2),
							val-4800-bps(1),
							val-2400-bps(0)
							}
		MAX-ACCESS		read-write
		STATUS			current
		DESCRIPTION
				"TYPE: - RadiobuttonList
				 PAGE: - System
					Serial Speed  cmdID= 16386
					115200 bps  value= 6
					57600 bps  value= 5
					38400 bps  value= 4
					19200 bps  value= 3
					9600 bps  value= 2
					4800 bps  value= 1
					2400 bps  value= 0  "
		::= { iqh3aCmdEntry 16386 }


	iqh3aSystemSetupSerialMode OBJECT-TYPE
		SYNTAX		RollCallString
		MAX-ACCESS		read-only
		STATUS			current
		DESCRIPTION
				"TYPE: - Display
				 PAGE: - System
					Serial Mode  cmdID= 16704  format=   "
		::= { iqh3aCmdEntry 16704 }


	iqh3aSystemSetupPassIAMSerial OBJECT-TYPE
		SYNTAX		INTEGER { disable(0), enable(1) }
		MAX-ACCESS		read-write
		STATUS			current
		DESCRIPTION
				"TYPE: - Checkbox
				 PAGE: - System
					Pass I_AM (Serial)  cmdID= 17053 "
		::= { iqh3aCmdEntry 17053 }


	iqh3aSystemSetupPassTIMESerial OBJECT-TYPE
		SYNTAX		INTEGER { disable(0), enable(1) }
		MAX-ACCESS		read-write
		STATUS			current
		DESCRIPTION
				"TYPE: - Checkbox
				 PAGE: - System
					Pass TIME (Serial)  cmdID= 17054 "
		::= { iqh3aCmdEntry 17054 }


	iqh3aSetupMonitorPSUsLeftPSU OBJECT-TYPE
		SYNTAX		INTEGER { disable(0), enable(1) }
		MAX-ACCESS		read-write
		STATUS			current
		DESCRIPTION
				"TYPE: - Checkbox
				 PAGE: - System
					Left PSU  cmdID= 16900 "
		::= { iqh3aCmdEntry 16900 }


	iqh3aSetupMonitorPSUsRightPSU OBJECT-TYPE
		SYNTAX		INTEGER { disable(0), enable(1) }
		MAX-ACCESS		read-write
		STATUS			current
		DESCRIPTION
				"TYPE: - Checkbox
				 PAGE: - System
					Right PSU  cmdID= 16901 "
		::= { iqh3aCmdEntry 16901 }


	iqh3aSystemSetupEnablecom200LongPacket OBJECT-TYPE
		SYNTAX		INTEGER { disable(0), enable(1) }
		MAX-ACCESS		read-write
		STATUS			current
		DESCRIPTION
				"TYPE: - Checkbox
				 PAGE: - System
					Enable com200 Long File Packet   cmdID= 17009 "
		::= { iqh3aCmdEntry 17009 }


	iqh3aSystemSetupRestartUnit OBJECT-TYPE
		SYNTAX		INTEGER { noAction(0),val-Restart-Unit(1) }
		MAX-ACCESS		read-write
		STATUS			current
		DESCRIPTION
				"TYPE: - Button
				 PAGE: - System
					Restart Unit  cmdID= 16706  value= 1  "
		::= { iqh3aCmdEntry 16706 }


	iqh3aSystemSetupFormatMenuCache OBJECT-TYPE
		SYNTAX		INTEGER { noAction(0),val-Format-Now(1) }
		MAX-ACCESS		read-write
		STATUS			current
		DESCRIPTION
				"TYPE: - Checkbox
				 PAGE: - System
					Format Menu Cache  cmdID= 16702 "
		::= { iqh3aCmdEntry 16702 }


	iqh3aSystemSetupEnableMenuCache OBJECT-TYPE
		SYNTAX		INTEGER { disable(0), enable(1) }
		MAX-ACCESS		read-write
		STATUS			current
		DESCRIPTION
				"TYPE: - Checkbox
				 PAGE: - System
					Enable Menu Cache  cmdID= 17064 "
		::= { iqh3aCmdEntry 17064 }


	iqh3aSystemSetupStartTime OBJECT-TYPE
		SYNTAX		RollCallString
		MAX-ACCESS		read-only
		STATUS			current
		DESCRIPTION
				"TYPE: - Display
				 PAGE: - System
					Start Time  cmdID= 16617  format=   "
		::= { iqh3aCmdEntry 16617 }


	iqh3aSystemSetupInformation1 OBJECT-TYPE
		SYNTAX		RollCallString
		MAX-ACCESS		read-write
		STATUS			current
		DESCRIPTION
				"TYPE: - Editstring
				 PAGE: - System
				    Generic Information field 1, to hold User defined Information
					Information1  cmdID= 17140  "
		::= { iqh3aCmdEntry 17140 }


	iqh3aSystemSetupInformation2 OBJECT-TYPE
		SYNTAX		RollCallString
		MAX-ACCESS		read-write
		STATUS			current
		DESCRIPTION
				"TYPE: - Editstring
				 PAGE: - System
				    Generic Information field 2, to hold User defined Information
					Information2  cmdID= 17141  "
		::= { iqh3aCmdEntry 17141 }


	iqh3aSystemSetupEnableWebServer OBJECT-TYPE
		SYNTAX		INTEGER { disable(0), enable(1) }
		MAX-ACCESS		read-write
		STATUS			current
		DESCRIPTION
				"TYPE: - Checkbox
				 PAGE: - System
					Enable WebServer  cmdID= 17018 "
		::= { iqh3aCmdEntry 17018 }


	iqh3aSystemSetupWebIPPort OBJECT-TYPE
		SYNTAX		RollCallString
		MAX-ACCESS		read-write
		STATUS			current
		DESCRIPTION
				"TYPE: - Editstring
				 PAGE: - System
					Web IP Port  cmdID= 17037  "
		::= { iqh3aCmdEntry 17037 }


	iqh3aSystemSetupModuleUpgradeTime OBJECT-TYPE
		SYNTAX		INTEGER { noAction(0),val-Module-Upgrade-Time(1) }
		MAX-ACCESS		read-write
		STATUS			current
		DESCRIPTION
				"TYPE: - Button
				 PAGE: - System
					Module Upgrade Time  cmdID= 17177  value= 1  "
		::= { iqh3aCmdEntry 17177 }


	iqh3aSystemSetupEnableModuleUpgra OBJECT-TYPE
		SYNTAX		INTEGER { disable(0), enable(1) }
		MAX-ACCESS		read-write
		STATUS			current
		DESCRIPTION
				"TYPE: - Checkbox
				 PAGE: - System
					Enable Module Upgra  cmdID= 17176 "
		::= { iqh3aCmdEntry 17176 }


	iqh3aSystemSetupLm80fanspeed OBJECT-TYPE
		SYNTAX		INTEGER {
							val-Auto(0),
							val-Low(1),
							val-Medium(2),
							val-High(3)
							}
		MAX-ACCESS		read-write
		STATUS			current
		DESCRIPTION
				"TYPE: - RadiobuttonList
				 PAGE: - System
					Lm80 fan speed  cmdID= 17100 
					Auto  value= 0  
					Low  value= 1  
					Medium  value= 2  
					High  value= 3  "
		::= { iqh3aCmdEntry 17100 }


	iqh3aSystemSetupEnclosureType OBJECT-TYPE
		SYNTAX		INTEGER {
							val-iqh3b(0),
							val-iqh3bq(1)
							}
		MAX-ACCESS		read-write
		STATUS			current
		DESCRIPTION
				"TYPE: - RadiobuttonList
				 PAGE: - System
					Enclosure Type  cmdID= 16463 
					iqh3b  value= 0  
					iqh3bq  value= 1  "
		::= { iqh3aCmdEntry 16463 }


	iqh3aStatisticsResetNetStats OBJECT-TYPE
		SYNTAX		INTEGER { noAction(0),val-Reset-Net-Stats(1) }
		MAX-ACCESS		read-write
		STATUS			current
		DESCRIPTION
				"TYPE: - Button
				 PAGE: - Stats
					Reset Net Stats  cmdID= 16470  value= 1  "
		::= { iqh3aCmdEntry 16470 }


	iqh3aStatisticsEnableNetStats OBJECT-TYPE
		SYNTAX		INTEGER { disable(0), enable(1) }
		MAX-ACCESS		read-write
		STATUS			current
		DESCRIPTION
				"TYPE: - Checkbox
				 PAGE: - Stats
					Enable Net Stats  cmdID= 16471 "
		::= { iqh3aCmdEntry 16471 }


	iqh3aStatisticsLengthErrs OBJECT-TYPE
		SYNTAX		RollCallString
		MAX-ACCESS		read-only
		STATUS			current
		DESCRIPTION
				"TYPE: - Display
				 PAGE: - Stats
					Length Errs  cmdID= 16472  format=   "
		::= { iqh3aCmdEntry 16472 }


	iqh3aStatisticsRecons OBJECT-TYPE
		SYNTAX		RollCallString
		MAX-ACCESS		read-only
		STATUS			current
		DESCRIPTION
				"TYPE: - Display
				 PAGE: - Stats
					Recons  cmdID= 16478  format=   "
		::= { iqh3aCmdEntry 16478 }


	iqh3aStatisticsModuleCommsErrors OBJECT-TYPE
		SYNTAX		RollCallString
		MAX-ACCESS		read-only
		STATUS			current
		DESCRIPTION
				"TYPE: - Display
				 PAGE: - Stats
					Module Comms Errors  cmdID= 16479  format=   "
		::= { iqh3aCmdEntry 16479 }


	iqh3aStatisticsBadPacketErrs OBJECT-TYPE
		SYNTAX		RollCallString
		MAX-ACCESS		read-only
		STATUS			current
		DESCRIPTION
				"TYPE: - Display
				 PAGE: - Stats
					Bad Packet Errs  cmdID= 16476  format=   "
		::= { iqh3aCmdEntry 16476 }


	iqh3aStatisticsRoutingErrs OBJECT-TYPE
		SYNTAX		RollCallString
		MAX-ACCESS		read-only
		STATUS			current
		DESCRIPTION
				"TYPE: - Display
				 PAGE: - Stats
					Routing Errs  cmdID= 16475  format=   "
		::= { iqh3aCmdEntry 16475 }


	iqh3aStatisticsPacketDrops OBJECT-TYPE
		SYNTAX		RollCallString
		MAX-ACCESS		read-only
		STATUS			current
		DESCRIPTION
				"TYPE: - Display
				 PAGE: - Stats
					Packet Drops  cmdID= 16477  format=   "
		::= { iqh3aCmdEntry 16477 }


	iqh3aStatisticsDestinationErrs OBJECT-TYPE
		SYNTAX		RollCallString
		MAX-ACCESS		read-only
		STATUS			current
		DESCRIPTION
				"TYPE: - Display
				 PAGE: - Stats
					Destination Errs  cmdID= 16474  format=   "
		::= { iqh3aCmdEntry 16474 }


	iqh3aStatisticsSourceErrs OBJECT-TYPE
		SYNTAX		RollCallString
		MAX-ACCESS		read-only
		STATUS			current
		DESCRIPTION
				"TYPE: - Display
				 PAGE: - Stats
					Source Errs  cmdID= 16473  format=   "
		::= { iqh3aCmdEntry 16473 }


	iqh3aStatisticsModCommsRxBytes OBJECT-TYPE
		SYNTAX		RollCallString
		MAX-ACCESS		read-only
		STATUS			current
		DESCRIPTION
				"TYPE: - Display
				 PAGE: - Stats
					ModCommsRxBytes  cmdID= 17237  format=   "
		::= { iqh3aCmdEntry 17237 }


	iqh3aStatisticsModCommsTxBytes OBJECT-TYPE
		SYNTAX		RollCallString
		MAX-ACCESS		read-only
		STATUS			current
		DESCRIPTION
				"TYPE: - Display
				 PAGE: - Stats
					ModCommsTxBytes  cmdID= 17238  format=   "
		::= { iqh3aCmdEntry 17238 }


	iqh3aStatisticsHyperionRxBytes OBJECT-TYPE
		SYNTAX		RollCallString
		MAX-ACCESS		read-only
		STATUS			current
		DESCRIPTION
				"TYPE: - Display
				 PAGE: - Stats
					HyperionRxBytes  cmdID= 17239  format=   "
		::= { iqh3aCmdEntry 17239 }


	iqh3aStatisticsProcessorUse OBJECT-TYPE
		SYNTAX		RollCallString
		MAX-ACCESS		read-only
		STATUS			current
		DESCRIPTION
				"TYPE: - Display
				 PAGE: - Stats
					ProcessorUse  cmdID= 17240  format=   "
		::= { iqh3aCmdEntry 17240 }


	iqh3aControlSlot1AllowBlindControl OBJECT-TYPE
		SYNTAX		INTEGER { disable(0), enable(1) }
		MAX-ACCESS		read-write
		STATUS			current
		DESCRIPTION
				"TYPE: - Checkbox
				 PAGE: - Control
					Allow Blind Control  cmdID= 565 "
		::= { iqh3aCmdEntry 565 }


	iqh3aControlSlot1SingleSessionOnly OBJECT-TYPE
		SYNTAX		INTEGER { disable(0), enable(1) }
		MAX-ACCESS		read-write
		STATUS			current
		DESCRIPTION
				"TYPE: - Checkbox
				 PAGE: - Control
					Single Session Only  cmdID= 581 "
		::= { iqh3aCmdEntry 581 }


	iqh3aControlSlot1Controller OBJECT-TYPE
		SYNTAX		RollCallString
		MAX-ACCESS		read-only
		STATUS			current
		DESCRIPTION
				"TYPE: - Display
				 PAGE: - Control
					Controller  cmdID= 16490  format=   "
		::= { iqh3aCmdEntry 16490 }


	iqh3aControlSlot1ControllerName OBJECT-TYPE
		SYNTAX		RollCallString
		MAX-ACCESS		read-only
		STATUS			current
		DESCRIPTION
				"TYPE: - Display
				 PAGE: - Control
					ControllerName  cmdID= 17160  format=   "
		::= { iqh3aCmdEntry 17160 }


	iqh3aControlSlot1LastBlindUser OBJECT-TYPE
		SYNTAX		RollCallString
		MAX-ACCESS		read-only
		STATUS			current
		DESCRIPTION
				"TYPE: - Display
				 PAGE: - Control
					Last Blind User  cmdID= 16590  format=   "
		::= { iqh3aCmdEntry 16590 }


	iqh3aControlSlot1ConPktCount OBJECT-TYPE
		SYNTAX		RollCallString
		MAX-ACCESS		read-only
		STATUS			current
		DESCRIPTION
				"TYPE: - Display
				 PAGE: - Control
					Con Pkt Count  cmdID= 16550  format=   "
		::= { iqh3aCmdEntry 16550 }


	iqh3aControlSlot1ConPktTotal OBJECT-TYPE
		SYNTAX		RollCallString
		MAX-ACCESS		read-only
		STATUS			current
		DESCRIPTION
				"TYPE: - Display
				 PAGE: - Control
					Con Pkt Total  cmdID= 750  format=   "
		::= { iqh3aCmdEntry 750 }


	iqh3aControlSlot1BlindPktCount OBJECT-TYPE
		SYNTAX		RollCallString
		MAX-ACCESS		read-only
		STATUS			current
		DESCRIPTION
				"TYPE: - Display
				 PAGE: - Control
					Blind Pkt Count  cmdID= 16570  format=   "
		::= { iqh3aCmdEntry 16570 }


	iqh3aControlSlotDisconnectSession OBJECT-TYPE
		SYNTAX		INTEGER {
							val-Disconnect-Session1(1),
							val-Disconnect-Session2(2),
							val-Disconnect-Session3(3),
							val-Disconnect-Session4(4),
							val-Disconnect-Session5(5),
							val-Disconnect-Session6(6),
							val-Disconnect-Session7(7),
							val-Disconnect-Session8(8),
							val-Disconnect-Session9(9),
							val-Disconnect-Session10(10),
							val-Disconnect-Session11(11),
							val-Disconnect-Session12(12),
							val-Disconnect-Session13(13),
							val-Disconnect-Session14(14),
							val-Disconnect-Session15(15),
							val-Disconnect-Session16(16)
							}
		MAX-ACCESS		read-write
		STATUS			current
		DESCRIPTION
				"TYPE: - Button
				 PAGE: - Control
					Disconnect Session  cmdID= 16407  value= 1
					Disconnect Session  cmdID= 16407  value= 2
					Disconnect Session  cmdID= 16407  value= 3
					Disconnect Session  cmdID= 16407  value= 4
					Disconnect Session  cmdID= 16407  value= 5
					Disconnect Session  cmdID= 16407  value= 6
					Disconnect Session  cmdID= 16407  value= 7
					Disconnect Session  cmdID= 16407  value= 8
					Disconnect Session  cmdID= 16407  value= 9
					Disconnect Session  cmdID= 16407  value= 10
					Disconnect Session  cmdID= 16407  value= 11
					Disconnect Session  cmdID= 16407  value= 12
					Disconnect Session  cmdID= 16407  value= 13
					Disconnect Session  cmdID= 16407  value= 14
					Disconnect Session  cmdID= 16407  value= 15
					Disconnect Session  cmdID= 16407  value= 16  "
		::= { iqh3aCmdEntry 16407 }


	iqh3aControlSlot2AllowBlindControl OBJECT-TYPE
		SYNTAX		INTEGER { disable(0), enable(1) }
		MAX-ACCESS		read-write
		STATUS			current
		DESCRIPTION
				"TYPE: - Checkbox
				 PAGE: - Control
					Allow Blind Control  cmdID= 566 "
		::= { iqh3aCmdEntry 566 }


	iqh3aControlSlot2SingleSessionOnly OBJECT-TYPE
		SYNTAX		INTEGER { disable(0), enable(1) }
		MAX-ACCESS		read-write
		STATUS			current
		DESCRIPTION
				"TYPE: - Checkbox
				 PAGE: - Control
					Single Session Only  cmdID= 582 "
		::= { iqh3aCmdEntry 582 }


	iqh3aControlSlot2Controller OBJECT-TYPE
		SYNTAX		RollCallString
		MAX-ACCESS		read-only
		STATUS			current
		DESCRIPTION
				"TYPE: - Display
				 PAGE: - Control
					Controller  cmdID= 16491  format=   "
		::= { iqh3aCmdEntry 16491 }


	iqh3aControlSlot2ControllerName OBJECT-TYPE
		SYNTAX		RollCallString
		MAX-ACCESS		read-only
		STATUS			current
		DESCRIPTION
				"TYPE: - Display
				 PAGE: - Control
					ControllerName  cmdID= 17161  format=   "
		::= { iqh3aCmdEntry 17161 }


	iqh3aControlSlot2LastBlindUser OBJECT-TYPE
		SYNTAX		RollCallString
		MAX-ACCESS		read-only
		STATUS			current
		DESCRIPTION
				"TYPE: - Display
				 PAGE: - Control
					Last Blind User  cmdID= 16591  format=   "
		::= { iqh3aCmdEntry 16591 }


	iqh3aControlSlot2ConPktCount OBJECT-TYPE
		SYNTAX		RollCallString
		MAX-ACCESS		read-only
		STATUS			current
		DESCRIPTION
				"TYPE: - Display
				 PAGE: - Control
					Con Pkt Count  cmdID= 16551  format=   "
		::= { iqh3aCmdEntry 16551 }


	iqh3aControlSlot2ConPktTotal OBJECT-TYPE
		SYNTAX		RollCallString
		MAX-ACCESS		read-only
		STATUS			current
		DESCRIPTION
				"TYPE: - Display
				 PAGE: - Control
					Con Pkt Total  cmdID= 751  format=   "
		::= { iqh3aCmdEntry 751 }


	iqh3aControlSlot2BlindPktCount OBJECT-TYPE
		SYNTAX		RollCallString
		MAX-ACCESS		read-only
		STATUS			current
		DESCRIPTION
				"TYPE: - Display
				 PAGE: - Control
					Blind Pkt Count  cmdID= 16571  format=   "
		::= { iqh3aCmdEntry 16571 }


	iqh3aControlSlot3AllowBlindControl OBJECT-TYPE
		SYNTAX		INTEGER { disable(0), enable(1) }
		MAX-ACCESS		read-write
		STATUS			current
		DESCRIPTION
				"TYPE: - Checkbox
				 PAGE: - Control
					Allow Blind Control  cmdID= 567 "
		::= { iqh3aCmdEntry 567 }


	iqh3aControlSlot3SingleSessionOnly OBJECT-TYPE
		SYNTAX		INTEGER { disable(0), enable(1) }
		MAX-ACCESS		read-write
		STATUS			current
		DESCRIPTION
				"TYPE: - Checkbox
				 PAGE: - Control
					Single Session Only  cmdID= 583 "
		::= { iqh3aCmdEntry 583 }


	iqh3aControlSlot3Controller OBJECT-TYPE
		SYNTAX		RollCallString
		MAX-ACCESS		read-only
		STATUS			current
		DESCRIPTION
				"TYPE: - Display
				 PAGE: - Control
					Controller  cmdID= 16492  format=   "
		::= { iqh3aCmdEntry 16492 }


	iqh3aControlSlot3ControllerName OBJECT-TYPE
		SYNTAX		RollCallString
		MAX-ACCESS		read-only
		STATUS			current
		DESCRIPTION
				"TYPE: - Display
				 PAGE: - Control
					ControllerName  cmdID= 17162  format=   "
		::= { iqh3aCmdEntry 17162 }


	iqh3aControlSlot3LastBlindUser OBJECT-TYPE
		SYNTAX		RollCallString
		MAX-ACCESS		read-only
		STATUS			current
		DESCRIPTION
				"TYPE: - Display
				 PAGE: - Control
					Last Blind User  cmdID= 16592  format=   "
		::= { iqh3aCmdEntry 16592 }


	iqh3aControlSlot3ConPktCount OBJECT-TYPE
		SYNTAX		RollCallString
		MAX-ACCESS		read-only
		STATUS			current
		DESCRIPTION
				"TYPE: - Display
				 PAGE: - Control
					Con Pkt Count  cmdID= 16552  format=   "
		::= { iqh3aCmdEntry 16552 }


	iqh3aControlSlot3ConPktTotal OBJECT-TYPE
		SYNTAX		RollCallString
		MAX-ACCESS		read-only
		STATUS			current
		DESCRIPTION
				"TYPE: - Display
				 PAGE: - Control
					Con Pkt Total  cmdID= 752  format=   "
		::= { iqh3aCmdEntry 752 }


	iqh3aControlSlot3BlindPktCount OBJECT-TYPE
		SYNTAX		RollCallString
		MAX-ACCESS		read-only
		STATUS			current
		DESCRIPTION
				"TYPE: - Display
				 PAGE: - Control
					Blind Pkt Count  cmdID= 16572  format=   "
		::= { iqh3aCmdEntry 16572 }


	iqh3aControlSlot4AllowBlindControl OBJECT-TYPE
		SYNTAX		INTEGER { disable(0), enable(1) }
		MAX-ACCESS		read-write
		STATUS			current
		DESCRIPTION
				"TYPE: - Checkbox
				 PAGE: - Control
					Allow Blind Control  cmdID= 568 "
		::= { iqh3aCmdEntry 568 }


	iqh3aControlSlot4SingleSessionOnly OBJECT-TYPE
		SYNTAX		INTEGER { disable(0), enable(1) }
		MAX-ACCESS		read-write
		STATUS			current
		DESCRIPTION
				"TYPE: - Checkbox
				 PAGE: - Control
					Single Session Only  cmdID= 584 "
		::= { iqh3aCmdEntry 584 }


	iqh3aControlSlot4Controller OBJECT-TYPE
		SYNTAX		RollCallString
		MAX-ACCESS		read-only
		STATUS			current
		DESCRIPTION
				"TYPE: - Display
				 PAGE: - Control
					Controller  cmdID= 16493  format=   "
		::= { iqh3aCmdEntry 16493 }


	iqh3aControlSlot4ControllerName OBJECT-TYPE
		SYNTAX		RollCallString
		MAX-ACCESS		read-only
		STATUS			current
		DESCRIPTION
				"TYPE: - Display
				 PAGE: - Control
					ControllerName  cmdID= 17163  format=   "
		::= { iqh3aCmdEntry 17163 }


	iqh3aControlSlot4LastBlindUser OBJECT-TYPE
		SYNTAX		RollCallString
		MAX-ACCESS		read-only
		STATUS			current
		DESCRIPTION
				"TYPE: - Display
				 PAGE: - Control
					Last Blind User  cmdID= 16593  format=   "
		::= { iqh3aCmdEntry 16593 }


	iqh3aControlSlot4ConPktCount OBJECT-TYPE
		SYNTAX		RollCallString
		MAX-ACCESS		read-only
		STATUS			current
		DESCRIPTION
				"TYPE: - Display
				 PAGE: - Control
					Con Pkt Count  cmdID= 16553  format=   "
		::= { iqh3aCmdEntry 16553 }


	iqh3aControlSlot4ConPktTotal OBJECT-TYPE
		SYNTAX		RollCallString
		MAX-ACCESS		read-only
		STATUS			current
		DESCRIPTION
				"TYPE: - Display
				 PAGE: - Control
					Con Pkt Total  cmdID= 753  format=   "
		::= { iqh3aCmdEntry 753 }


	iqh3aControlSlot4BlindPktCount OBJECT-TYPE
		SYNTAX		RollCallString
		MAX-ACCESS		read-only
		STATUS			current
		DESCRIPTION
				"TYPE: - Display
				 PAGE: - Control
					Blind Pkt Count  cmdID= 16573  format=   "
		::= { iqh3aCmdEntry 16573 }


	iqh3aControlSlot5AllowBlindControl OBJECT-TYPE
		SYNTAX		INTEGER { disable(0), enable(1) }
		MAX-ACCESS		read-write
		STATUS			current
		DESCRIPTION
				"TYPE: - Checkbox
				 PAGE: - Control
					Allow Blind Control  cmdID= 569 "
		::= { iqh3aCmdEntry 569 }


	iqh3aControlSlot5SingleSessionOnly OBJECT-TYPE
		SYNTAX		INTEGER { disable(0), enable(1) }
		MAX-ACCESS		read-write
		STATUS			current
		DESCRIPTION
				"TYPE: - Checkbox
				 PAGE: - Control
					Single Session Only  cmdID= 585 "
		::= { iqh3aCmdEntry 585 }


	iqh3aControlSlot5Controller OBJECT-TYPE
		SYNTAX		RollCallString
		MAX-ACCESS		read-only
		STATUS			current
		DESCRIPTION
				"TYPE: - Display
				 PAGE: - Control
					Controller  cmdID= 16494  format=   "
		::= { iqh3aCmdEntry 16494 }


	iqh3aControlSlot5ControllerName OBJECT-TYPE
		SYNTAX		RollCallString
		MAX-ACCESS		read-only
		STATUS			current
		DESCRIPTION
				"TYPE: - Display
				 PAGE: - Control
					ControllerName  cmdID= 17164  format=   "
		::= { iqh3aCmdEntry 17164 }


	iqh3aControlSlot5LastBlindUser OBJECT-TYPE
		SYNTAX		RollCallString
		MAX-ACCESS		read-only
		STATUS			current
		DESCRIPTION
				"TYPE: - Display
				 PAGE: - Control
					Last Blind User  cmdID= 16594  format=   "
		::= { iqh3aCmdEntry 16594 }


	iqh3aControlSlot5ConPktCount OBJECT-TYPE
		SYNTAX		RollCallString
		MAX-ACCESS		read-only
		STATUS			current
		DESCRIPTION
				"TYPE: - Display
				 PAGE: - Control
					Con Pkt Count  cmdID= 16554  format=   "
		::= { iqh3aCmdEntry 16554 }


	iqh3aControlSlot5ConPktTotal OBJECT-TYPE
		SYNTAX		RollCallString
		MAX-ACCESS		read-only
		STATUS			current
		DESCRIPTION
				"TYPE: - Display
				 PAGE: - Control
					Con Pkt Total  cmdID= 754  format=   "
		::= { iqh3aCmdEntry 754 }


	iqh3aControlSlot5BlindPktCount OBJECT-TYPE
		SYNTAX		RollCallString
		MAX-ACCESS		read-only
		STATUS			current
		DESCRIPTION
				"TYPE: - Display
				 PAGE: - Control
					Blind Pkt Count  cmdID= 16574  format=   "
		::= { iqh3aCmdEntry 16574 }


	iqh3aControlSlot6AllowBlindControl OBJECT-TYPE
		SYNTAX		INTEGER { disable(0), enable(1) }
		MAX-ACCESS		read-write
		STATUS			current
		DESCRIPTION
				"TYPE: - Checkbox
				 PAGE: - Control
					Allow Blind Control  cmdID= 570 "
		::= { iqh3aCmdEntry 570 }


	iqh3aControlSlot6SingleSessionOnly OBJECT-TYPE
		SYNTAX		INTEGER { disable(0), enable(1) }
		MAX-ACCESS		read-write
		STATUS			current
		DESCRIPTION
				"TYPE: - Checkbox
				 PAGE: - Control
					Single Session Only  cmdID= 596 "
		::= { iqh3aCmdEntry 596 }


	iqh3aControlSlot6Controller OBJECT-TYPE
		SYNTAX		RollCallString
		MAX-ACCESS		read-only
		STATUS			current
		DESCRIPTION
				"TYPE: - Display
				 PAGE: - Control
					Controller  cmdID= 16495  format=   "
		::= { iqh3aCmdEntry 16495 }


	iqh3aControlSlot6ControllerName OBJECT-TYPE
		SYNTAX		RollCallString
		MAX-ACCESS		read-only
		STATUS			current
		DESCRIPTION
				"TYPE: - Display
				 PAGE: - Control
					ControllerName  cmdID= 17165  format=   "
		::= { iqh3aCmdEntry 17165 }


	iqh3aControlSlot6LastBlindUser OBJECT-TYPE
		SYNTAX		RollCallString
		MAX-ACCESS		read-only
		STATUS			current
		DESCRIPTION
				"TYPE: - Display
				 PAGE: - Control
					Last Blind User  cmdID= 16595  format=   "
		::= { iqh3aCmdEntry 16595 }


	iqh3aControlSlot6ConPktCount OBJECT-TYPE
		SYNTAX		RollCallString
		MAX-ACCESS		read-only
		STATUS			current
		DESCRIPTION
				"TYPE: - Display
				 PAGE: - Control
					Con Pkt Count  cmdID= 16555  format=   "
		::= { iqh3aCmdEntry 16555 }


	iqh3aControlSlot6ConPktTotal OBJECT-TYPE
		SYNTAX		RollCallString
		MAX-ACCESS		read-only
		STATUS			current
		DESCRIPTION
				"TYPE: - Display
				 PAGE: - Control
					Con Pkt Total  cmdID= 755  format=   "
		::= { iqh3aCmdEntry 755 }


	iqh3aControlSlot6BlindPktCount OBJECT-TYPE
		SYNTAX		RollCallString
		MAX-ACCESS		read-only
		STATUS			current
		DESCRIPTION
				"TYPE: - Display
				 PAGE: - Control
					Blind Pkt Count  cmdID= 16575  format=   "
		::= { iqh3aCmdEntry 16575 }


	iqh3aControlSlot7AllowBlindControl OBJECT-TYPE
		SYNTAX		INTEGER { disable(0), enable(1) }
		MAX-ACCESS		read-write
		STATUS			current
		DESCRIPTION
				"TYPE: - Checkbox
				 PAGE: - Control
					Allow Blind Control  cmdID= 571 "
		::= { iqh3aCmdEntry 571 }


	iqh3aControlSlot7SingleSessionOnly OBJECT-TYPE
		SYNTAX		INTEGER { disable(0), enable(1) }
		MAX-ACCESS		read-write
		STATUS			current
		DESCRIPTION
				"TYPE: - Checkbox
				 PAGE: - Control
					Single Session Only  cmdID= 597 "
		::= { iqh3aCmdEntry 597 }


	iqh3aControlSlot7Controller OBJECT-TYPE
		SYNTAX		RollCallString
		MAX-ACCESS		read-only
		STATUS			current
		DESCRIPTION
				"TYPE: - Display
				 PAGE: - Control
					Controller  cmdID= 16496  format=   "
		::= { iqh3aCmdEntry 16496 }


	iqh3aControlSlot7ControllerName OBJECT-TYPE
		SYNTAX		RollCallString
		MAX-ACCESS		read-only
		STATUS			current
		DESCRIPTION
				"TYPE: - Display
				 PAGE: - Control
					ControllerName  cmdID= 17166  format=   "
		::= { iqh3aCmdEntry 17166 }


	iqh3aControlSlot7LastBlindUser OBJECT-TYPE
		SYNTAX		RollCallString
		MAX-ACCESS		read-only
		STATUS			current
		DESCRIPTION
				"TYPE: - Display
				 PAGE: - Control
					Last Blind User  cmdID= 16596  format=   "
		::= { iqh3aCmdEntry 16596 }


	iqh3aControlSlot7ConPktCount OBJECT-TYPE
		SYNTAX		RollCallString
		MAX-ACCESS		read-only
		STATUS			current
		DESCRIPTION
				"TYPE: - Display
				 PAGE: - Control
					Con Pkt Count  cmdID= 16556  format=   "
		::= { iqh3aCmdEntry 16556 }


	iqh3aControlSlot7ConPktTotal OBJECT-TYPE
		SYNTAX		RollCallString
		MAX-ACCESS		read-only
		STATUS			current
		DESCRIPTION
				"TYPE: - Display
				 PAGE: - Control
					Con Pkt Total  cmdID= 756  format=   "
		::= { iqh3aCmdEntry 756 }


	iqh3aControlSlot7BlindPktCount OBJECT-TYPE
		SYNTAX		RollCallString
		MAX-ACCESS		read-only
		STATUS			current
		DESCRIPTION
				"TYPE: - Display
				 PAGE: - Control
					Blind Pkt Count  cmdID= 16576  format=   "
		::= { iqh3aCmdEntry 16576 }


	iqh3aControlSlot8AllowBlindControl OBJECT-TYPE
		SYNTAX		INTEGER { disable(0), enable(1) }
		MAX-ACCESS		read-write
		STATUS			current
		DESCRIPTION
				"TYPE: - Checkbox
				 PAGE: - Control
					Allow Blind Control  cmdID= 572 "
		::= { iqh3aCmdEntry 572 }


	iqh3aControlSlot8SingleSessionOnly OBJECT-TYPE
		SYNTAX		INTEGER { disable(0), enable(1) }
		MAX-ACCESS		read-write
		STATUS			current
		DESCRIPTION
				"TYPE: - Checkbox
				 PAGE: - Control
					Single Session Only  cmdID= 598 "
		::= { iqh3aCmdEntry 598 }


	iqh3aControlSlot8Controller OBJECT-TYPE
		SYNTAX		RollCallString
		MAX-ACCESS		read-only
		STATUS			current
		DESCRIPTION
				"TYPE: - Display
				 PAGE: - Control
					Controller  cmdID= 16497  format=   "
		::= { iqh3aCmdEntry 16497 }


	iqh3aControlSlot8ControllerName OBJECT-TYPE
		SYNTAX		RollCallString
		MAX-ACCESS		read-only
		STATUS			current
		DESCRIPTION
				"TYPE: - Display
				 PAGE: - Control
					ControllerName  cmdID= 17167  format=   "
		::= { iqh3aCmdEntry 17167 }


	iqh3aControlSlot8LastBlindUser OBJECT-TYPE
		SYNTAX		RollCallString
		MAX-ACCESS		read-only
		STATUS			current
		DESCRIPTION
				"TYPE: - Display
				 PAGE: - Control
					Last Blind User  cmdID= 16597  format=   "
		::= { iqh3aCmdEntry 16597 }


	iqh3aControlSlot8ConPktCount OBJECT-TYPE
		SYNTAX		RollCallString
		MAX-ACCESS		read-only
		STATUS			current
		DESCRIPTION
				"TYPE: - Display
				 PAGE: - Control
					Con Pkt Count  cmdID= 16557  format=   "
		::= { iqh3aCmdEntry 16557 }


	iqh3aControlSlot8ConPktTotal OBJECT-TYPE
		SYNTAX		RollCallString
		MAX-ACCESS		read-only
		STATUS			current
		DESCRIPTION
				"TYPE: - Display
				 PAGE: - Control
					Con Pkt Total  cmdID= 757  format=   "
		::= { iqh3aCmdEntry 757 }


	iqh3aControlSlot8BlindPktCount OBJECT-TYPE
		SYNTAX		RollCallString
		MAX-ACCESS		read-only
		STATUS			current
		DESCRIPTION
				"TYPE: - Display
				 PAGE: - Control
					Blind Pkt Count  cmdID= 16577  format=   "
		::= { iqh3aCmdEntry 16577 }


	iqh3aControlSlot9AllowBlindControl OBJECT-TYPE
		SYNTAX		INTEGER { disable(0), enable(1) }
		MAX-ACCESS		read-write
		STATUS			current
		DESCRIPTION
				"TYPE: - Checkbox
				 PAGE: - Control
					Allow Blind Control  cmdID= 573 "
		::= { iqh3aCmdEntry 573 }


	iqh3aControlSlot9SingleSessionOnly OBJECT-TYPE
		SYNTAX		INTEGER { disable(0), enable(1) }
		MAX-ACCESS		read-write
		STATUS			current
		DESCRIPTION
				"TYPE: - Checkbox
				 PAGE: - Control
					Single Session Only  cmdID= 599 "
		::= { iqh3aCmdEntry 599 }


	iqh3aControlSlot9Controller OBJECT-TYPE
		SYNTAX		RollCallString
		MAX-ACCESS		read-only
		STATUS			current
		DESCRIPTION
				"TYPE: - Display
				 PAGE: - Control
					Controller  cmdID= 16498  format=   "
		::= { iqh3aCmdEntry 16498 }


	iqh3aControlSlot9ControllerName OBJECT-TYPE
		SYNTAX		RollCallString
		MAX-ACCESS		read-only
		STATUS			current
		DESCRIPTION
				"TYPE: - Display
				 PAGE: - Control
					ControllerName  cmdID= 17168  format=   "
		::= { iqh3aCmdEntry 17168 }


	iqh3aControlSlot9LastBlindUser OBJECT-TYPE
		SYNTAX		RollCallString
		MAX-ACCESS		read-only
		STATUS			current
		DESCRIPTION
				"TYPE: - Display
				 PAGE: - Control
					Last Blind User  cmdID= 16598  format=   "
		::= { iqh3aCmdEntry 16598 }


	iqh3aControlSlot9ConPktCount OBJECT-TYPE
		SYNTAX		RollCallString
		MAX-ACCESS		read-only
		STATUS			current
		DESCRIPTION
				"TYPE: - Display
				 PAGE: - Control
					Con Pkt Count  cmdID= 16558  format=   "
		::= { iqh3aCmdEntry 16558 }


	iqh3aControlSlot9ConPktTotal OBJECT-TYPE
		SYNTAX		RollCallString
		MAX-ACCESS		read-only
		STATUS			current
		DESCRIPTION
				"TYPE: - Display
				 PAGE: - Control
					Con Pkt Total  cmdID= 758  format=   "
		::= { iqh3aCmdEntry 758 }


	iqh3aControlSlot9BlindPktCount OBJECT-TYPE
		SYNTAX		RollCallString
		MAX-ACCESS		read-only
		STATUS			current
		DESCRIPTION
				"TYPE: - Display
				 PAGE: - Control
					Blind Pkt Count  cmdID= 16578  format=   "
		::= { iqh3aCmdEntry 16578 }


	iqh3aControlSlot10AllowBlindControl OBJECT-TYPE
		SYNTAX		INTEGER { disable(0), enable(1) }
		MAX-ACCESS		read-write
		STATUS			current
		DESCRIPTION
				"TYPE: - Checkbox
				 PAGE: - Control
					Allow Blind Control  cmdID= 574 "
		::= { iqh3aCmdEntry 574 }


	iqh3aControlSlot10SingleSessionOnly OBJECT-TYPE
		SYNTAX		INTEGER { disable(0), enable(1) }
		MAX-ACCESS		read-write
		STATUS			current
		DESCRIPTION
				"TYPE: - Checkbox
				 PAGE: - Control
					Single Session Only  cmdID= 600 "
		::= { iqh3aCmdEntry 600 }


	iqh3aControlSlot10Controller OBJECT-TYPE
		SYNTAX		RollCallString
		MAX-ACCESS		read-only
		STATUS			current
		DESCRIPTION
				"TYPE: - Display
				 PAGE: - Control
					Controller  cmdID= 16499  format=   "
		::= { iqh3aCmdEntry 16499 }


	iqh3aControlSlot10ControllerName OBJECT-TYPE
		SYNTAX		RollCallString
		MAX-ACCESS		read-only
		STATUS			current
		DESCRIPTION
				"TYPE: - Display
				 PAGE: - Control
					ControllerName  cmdID= 17169  format=   "
		::= { iqh3aCmdEntry 17169 }


	iqh3aControlSlot10LastBlindUser OBJECT-TYPE
		SYNTAX		RollCallString
		MAX-ACCESS		read-only
		STATUS			current
		DESCRIPTION
				"TYPE: - Display
				 PAGE: - Control
					Last Blind User  cmdID= 16599  format=   "
		::= { iqh3aCmdEntry 16599 }


	iqh3aControlSlot10ConPktCount OBJECT-TYPE
		SYNTAX		RollCallString
		MAX-ACCESS		read-only
		STATUS			current
		DESCRIPTION
				"TYPE: - Display
				 PAGE: - Control
					Con Pkt Count  cmdID= 16559  format=   "
		::= { iqh3aCmdEntry 16559 }


	iqh3aControlSlot10ConPktTotal OBJECT-TYPE
		SYNTAX		RollCallString
		MAX-ACCESS		read-only
		STATUS			current
		DESCRIPTION
				"TYPE: - Display
				 PAGE: - Control
					Con Pkt Total  cmdID= 759  format=   "
		::= { iqh3aCmdEntry 759 }


	iqh3aControlSlot10BlindPktCount OBJECT-TYPE
		SYNTAX		RollCallString
		MAX-ACCESS		read-only
		STATUS			current
		DESCRIPTION
				"TYPE: - Display
				 PAGE: - Control
					Blind Pkt Count  cmdID= 16579  format=   "
		::= { iqh3aCmdEntry 16579 }


	iqh3aControlSlot11AllowBlindControl OBJECT-TYPE
		SYNTAX		INTEGER { disable(0), enable(1) }
		MAX-ACCESS		read-write
		STATUS			current
		DESCRIPTION
				"TYPE: - Checkbox
				 PAGE: - Control
					Allow Blind Control  cmdID= 575 "
		::= { iqh3aCmdEntry 575 }


	iqh3aControlSlot11SingleSessionOnly OBJECT-TYPE
		SYNTAX		INTEGER { disable(0), enable(1) }
		MAX-ACCESS		read-write
		STATUS			current
		DESCRIPTION
				"TYPE: - Checkbox
				 PAGE: - Control
					Single Session Only  cmdID= 601 "
		::= { iqh3aCmdEntry 601 }


	iqh3aControlSlot11Controller OBJECT-TYPE
		SYNTAX		RollCallString
		MAX-ACCESS		read-only
		STATUS			current
		DESCRIPTION
				"TYPE: - Display
				 PAGE: - Control
					Controller  cmdID= 16500  format=   "
		::= { iqh3aCmdEntry 16500 }


	iqh3aControlSlot11ControllerName OBJECT-TYPE
		SYNTAX		RollCallString
		MAX-ACCESS		read-only
		STATUS			current
		DESCRIPTION
				"TYPE: - Display
				 PAGE: - Control
					ControllerName  cmdID= 17170  format=   "
		::= { iqh3aCmdEntry 17170 }


	iqh3aControlSlot11LastBlindUser OBJECT-TYPE
		SYNTAX		RollCallString
		MAX-ACCESS		read-only
		STATUS			current
		DESCRIPTION
				"TYPE: - Display
				 PAGE: - Control
					Last Blind User  cmdID= 16600  format=   "
		::= { iqh3aCmdEntry 16600 }


	iqh3aControlSlot11ConPktCount OBJECT-TYPE
		SYNTAX		RollCallString
		MAX-ACCESS		read-only
		STATUS			current
		DESCRIPTION
				"TYPE: - Display
				 PAGE: - Control
					Con Pkt Count  cmdID= 16560  format=   "
		::= { iqh3aCmdEntry 16560 }


	iqh3aControlSlot11ConPktTotal OBJECT-TYPE
		SYNTAX		RollCallString
		MAX-ACCESS		read-only
		STATUS			current
		DESCRIPTION
				"TYPE: - Display
				 PAGE: - Control
					Con Pkt Total  cmdID= 760  format=   "
		::= { iqh3aCmdEntry 760 }


	iqh3aControlSlot11BlindPktCount OBJECT-TYPE
		SYNTAX		RollCallString
		MAX-ACCESS		read-only
		STATUS			current
		DESCRIPTION
				"TYPE: - Display
				 PAGE: - Control
					Blind Pkt Count  cmdID= 16580  format=   "
		::= { iqh3aCmdEntry 16580 }


	iqh3aControlSlot12AllowBlindControl OBJECT-TYPE
		SYNTAX		INTEGER { disable(0), enable(1) }
		MAX-ACCESS		read-write
		STATUS			current
		DESCRIPTION
				"TYPE: - Checkbox
				 PAGE: - Control
					Allow Blind Control  cmdID= 576 "
		::= { iqh3aCmdEntry 576 }


	iqh3aControlSlot12SingleSessionOnly OBJECT-TYPE
		SYNTAX		INTEGER { disable(0), enable(1) }
		MAX-ACCESS		read-write
		STATUS			current
		DESCRIPTION
				"TYPE: - Checkbox
				 PAGE: - Control
					Single Session Only  cmdID= 602 "
		::= { iqh3aCmdEntry 602 }


	iqh3aControlSlot12Controller OBJECT-TYPE
		SYNTAX		RollCallString
		MAX-ACCESS		read-only
		STATUS			current
		DESCRIPTION
				"TYPE: - Display
				 PAGE: - Control
					Controller  cmdID= 16501  format=   "
		::= { iqh3aCmdEntry 16501 }


	iqh3aControlSlot12ControllerName OBJECT-TYPE
		SYNTAX		RollCallString
		MAX-ACCESS		read-only
		STATUS			current
		DESCRIPTION
				"TYPE: - Display
				 PAGE: - Control
					ControllerName  cmdID= 17171  format=   "
		::= { iqh3aCmdEntry 17171 }


	iqh3aControlSlot12LastBlindUser OBJECT-TYPE
		SYNTAX		RollCallString
		MAX-ACCESS		read-only
		STATUS			current
		DESCRIPTION
				"TYPE: - Display
				 PAGE: - Control
					Last Blind User  cmdID= 16601  format=   "
		::= { iqh3aCmdEntry 16601 }


	iqh3aControlSlot12ConPktCount OBJECT-TYPE
		SYNTAX		RollCallString
		MAX-ACCESS		read-only
		STATUS			current
		DESCRIPTION
				"TYPE: - Display
				 PAGE: - Control
					Con Pkt Count  cmdID= 16561  format=   "
		::= { iqh3aCmdEntry 16561 }


	iqh3aControlSlot12ConPktTotal OBJECT-TYPE
		SYNTAX		RollCallString
		MAX-ACCESS		read-only
		STATUS			current
		DESCRIPTION
				"TYPE: - Display
				 PAGE: - Control
					Con Pkt Total  cmdID= 761  format=   "
		::= { iqh3aCmdEntry 761 }


	iqh3aControlSlot12BlindPktCount OBJECT-TYPE
		SYNTAX		RollCallString
		MAX-ACCESS		read-only
		STATUS			current
		DESCRIPTION
				"TYPE: - Display
				 PAGE: - Control
					Blind Pkt Count  cmdID= 16581  format=   "
		::= { iqh3aCmdEntry 16581 }


	iqh3aControlSlot13AllowBlindControl OBJECT-TYPE
		SYNTAX		INTEGER { disable(0), enable(1) }
		MAX-ACCESS		read-write
		STATUS			current
		DESCRIPTION
				"TYPE: - Checkbox
				 PAGE: - Control
					Allow Blind Control  cmdID= 577 "
		::= { iqh3aCmdEntry 577 }


	iqh3aControlSlot13SingleSessionOnly OBJECT-TYPE
		SYNTAX		INTEGER { disable(0), enable(1) }
		MAX-ACCESS		read-write
		STATUS			current
		DESCRIPTION
				"TYPE: - Checkbox
				 PAGE: - Control
					Single Session Only  cmdID= 603 "
		::= { iqh3aCmdEntry 603 }


	iqh3aControlSlot13Controller OBJECT-TYPE
		SYNTAX		RollCallString
		MAX-ACCESS		read-only
		STATUS			current
		DESCRIPTION
				"TYPE: - Display
				 PAGE: - Control
					Controller  cmdID= 16502  format=   "
		::= { iqh3aCmdEntry 16502 }


	iqh3aControlSlot13ControllerName OBJECT-TYPE
		SYNTAX		RollCallString
		MAX-ACCESS		read-only
		STATUS			current
		DESCRIPTION
				"TYPE: - Display
				 PAGE: - Control
					ControllerName  cmdID= 17172  format=   "
		::= { iqh3aCmdEntry 17172 }


	iqh3aControlSlot13LastBlindUser OBJECT-TYPE
		SYNTAX		RollCallString
		MAX-ACCESS		read-only
		STATUS			current
		DESCRIPTION
				"TYPE: - Display
				 PAGE: - Control
					Last Blind User  cmdID= 16602  format=   "
		::= { iqh3aCmdEntry 16602 }


	iqh3aControlSlot13ConPktCount OBJECT-TYPE
		SYNTAX		RollCallString
		MAX-ACCESS		read-only
		STATUS			current
		DESCRIPTION
				"TYPE: - Display
				 PAGE: - Control
					Con Pkt Count  cmdID= 16562  format=   "
		::= { iqh3aCmdEntry 16562 }


	iqh3aControlSlot13ConPktTotal OBJECT-TYPE
		SYNTAX		RollCallString
		MAX-ACCESS		read-only
		STATUS			current
		DESCRIPTION
				"TYPE: - Display
				 PAGE: - Control
					Con Pkt Total  cmdID= 762  format=   "
		::= { iqh3aCmdEntry 762 }


	iqh3aControlSlot13BlindPktCount OBJECT-TYPE
		SYNTAX		RollCallString
		MAX-ACCESS		read-only
		STATUS			current
		DESCRIPTION
				"TYPE: - Display
				 PAGE: - Control
					Blind Pkt Count  cmdID= 16582  format=   "
		::= { iqh3aCmdEntry 16582 }


	iqh3aControlSlot14AllowBlindControl OBJECT-TYPE
		SYNTAX		INTEGER { disable(0), enable(1) }
		MAX-ACCESS		read-write
		STATUS			current
		DESCRIPTION
				"TYPE: - Checkbox
				 PAGE: - Control
					Allow Blind Control  cmdID= 578 "
		::= { iqh3aCmdEntry 578 }


	iqh3aControlSlot14SingleSessionOnly OBJECT-TYPE
		SYNTAX		INTEGER { disable(0), enable(1) }
		MAX-ACCESS		read-write
		STATUS			current
		DESCRIPTION
				"TYPE: - Checkbox
				 PAGE: - Control
					Single Session Only  cmdID= 604 "
		::= { iqh3aCmdEntry 604 }


	iqh3aControlSlot14Controller OBJECT-TYPE
		SYNTAX		RollCallString
		MAX-ACCESS		read-only
		STATUS			current
		DESCRIPTION
				"TYPE: - Display
				 PAGE: - Control
					Controller  cmdID= 16503  format=   "
		::= { iqh3aCmdEntry 16503 }


	iqh3aControlSlot14ControllerName OBJECT-TYPE
		SYNTAX		RollCallString
		MAX-ACCESS		read-only
		STATUS			current
		DESCRIPTION
				"TYPE: - Display
				 PAGE: - Control
					ControllerName  cmdID= 17173  format=   "
		::= { iqh3aCmdEntry 17173 }


	iqh3aControlSlot14LastBlindUser OBJECT-TYPE
		SYNTAX		RollCallString
		MAX-ACCESS		read-only
		STATUS			current
		DESCRIPTION
				"TYPE: - Display
				 PAGE: - Control
					Last Blind User  cmdID= 16603  format=   "
		::= { iqh3aCmdEntry 16603 }


	iqh3aControlSlot14ConPktCount OBJECT-TYPE
		SYNTAX		RollCallString
		MAX-ACCESS		read-only
		STATUS			current
		DESCRIPTION
				"TYPE: - Display
				 PAGE: - Control
					Con Pkt Count  cmdID= 16563  format=   "
		::= { iqh3aCmdEntry 16563 }


	iqh3aControlSlot14ConPktTotal OBJECT-TYPE
		SYNTAX		RollCallString
		MAX-ACCESS		read-only
		STATUS			current
		DESCRIPTION
				"TYPE: - Display
				 PAGE: - Control
					Con Pkt Total  cmdID= 763  format=   "
		::= { iqh3aCmdEntry 763 }


	iqh3aControlSlot14BlindPktCount OBJECT-TYPE
		SYNTAX		RollCallString
		MAX-ACCESS		read-only
		STATUS			current
		DESCRIPTION
				"TYPE: - Display
				 PAGE: - Control
					Blind Pkt Count  cmdID= 16583  format=   "
		::= { iqh3aCmdEntry 16583 }


	iqh3aControlSlot15AllowBlindControl OBJECT-TYPE
		SYNTAX		INTEGER { disable(0), enable(1) }
		MAX-ACCESS		read-write
		STATUS			current
		DESCRIPTION
				"TYPE: - Checkbox
				 PAGE: - Control
					Allow Blind Control  cmdID= 579 "
		::= { iqh3aCmdEntry 579 }


	iqh3aControlSlot15SingleSessionOnly OBJECT-TYPE
		SYNTAX		INTEGER { disable(0), enable(1) }
		MAX-ACCESS		read-write
		STATUS			current
		DESCRIPTION
				"TYPE: - Checkbox
				 PAGE: - Control
					Single Session Only  cmdID= 605 "
		::= { iqh3aCmdEntry 605 }


	iqh3aControlSlot15Controller OBJECT-TYPE
		SYNTAX		RollCallString
		MAX-ACCESS		read-only
		STATUS			current
		DESCRIPTION
				"TYPE: - Display
				 PAGE: - Control
					Controller  cmdID= 16504  format=   "
		::= { iqh3aCmdEntry 16504 }


	iqh3aControlSlot15ControllerName OBJECT-TYPE
		SYNTAX		RollCallString
		MAX-ACCESS		read-only
		STATUS			current
		DESCRIPTION
				"TYPE: - Display
				 PAGE: - Control
					ControllerName  cmdID= 17174  format=   "
		::= { iqh3aCmdEntry 17174 }


	iqh3aControlSlot15LastBlindUser OBJECT-TYPE
		SYNTAX		RollCallString
		MAX-ACCESS		read-only
		STATUS			current
		DESCRIPTION
				"TYPE: - Display
				 PAGE: - Control
					Last Blind User  cmdID= 16604  format=   "
		::= { iqh3aCmdEntry 16604 }


	iqh3aControlSlot15ConPktCount OBJECT-TYPE
		SYNTAX		RollCallString
		MAX-ACCESS		read-only
		STATUS			current
		DESCRIPTION
				"TYPE: - Display
				 PAGE: - Control
					Con Pkt Count  cmdID= 16564  format=   "
		::= { iqh3aCmdEntry 16564 }


	iqh3aControlSlot15ConPktTotal OBJECT-TYPE
		SYNTAX		RollCallString
		MAX-ACCESS		read-only
		STATUS			current
		DESCRIPTION
				"TYPE: - Display
				 PAGE: - Control
					Con Pkt Total  cmdID= 764  format=   "
		::= { iqh3aCmdEntry 764 }


	iqh3aControlSlot15BlindPktCount OBJECT-TYPE
		SYNTAX		RollCallString
		MAX-ACCESS		read-only
		STATUS			current
		DESCRIPTION
				"TYPE: - Display
				 PAGE: - Control
					Blind Pkt Count  cmdID= 16584  format=   "
		::= { iqh3aCmdEntry 16584 }


	iqh3aControlSlot16AllowBlindControl OBJECT-TYPE
		SYNTAX		INTEGER { disable(0), enable(1) }
		MAX-ACCESS		read-write
		STATUS			current
		DESCRIPTION
				"TYPE: - Checkbox
				 PAGE: - Control
					Allow Blind Control  cmdID= 580 "
		::= { iqh3aCmdEntry 580 }


	iqh3aControlSlot16SingleSessionOnly OBJECT-TYPE
		SYNTAX		INTEGER { disable(0), enable(1) }
		MAX-ACCESS		read-write
		STATUS			current
		DESCRIPTION
				"TYPE: - Checkbox
				 PAGE: - Control
					Single Session Only  cmdID= 606 "
		::= { iqh3aCmdEntry 606 }


	iqh3aControlSlot16Controller OBJECT-TYPE
		SYNTAX		RollCallString
		MAX-ACCESS		read-only
		STATUS			current
		DESCRIPTION
				"TYPE: - Display
				 PAGE: - Control
					Controller  cmdID= 16505  format=   "
		::= { iqh3aCmdEntry 16505 }


	iqh3aControlSlot16ControllerName OBJECT-TYPE
		SYNTAX		RollCallString
		MAX-ACCESS		read-only
		STATUS			current
		DESCRIPTION
				"TYPE: - Display
				 PAGE: - Control
					ControllerName  cmdID= 17175  format=   "
		::= { iqh3aCmdEntry 17175 }


	iqh3aControlSlot16LastBlindUser OBJECT-TYPE
		SYNTAX		RollCallString
		MAX-ACCESS		read-only
		STATUS			current
		DESCRIPTION
				"TYPE: - Display
				 PAGE: - Control
					Last Blind User  cmdID= 16605  format=   "
		::= { iqh3aCmdEntry 16605 }


	iqh3aControlSlot16ConPktCount OBJECT-TYPE
		SYNTAX		RollCallString
		MAX-ACCESS		read-only
		STATUS			current
		DESCRIPTION
				"TYPE: - Display
				 PAGE: - Control
					Con Pkt Count  cmdID= 16565  format=   "
		::= { iqh3aCmdEntry 16565 }


	iqh3aControlSlot16ConPktTotal OBJECT-TYPE
		SYNTAX		RollCallString
		MAX-ACCESS		read-only
		STATUS			current
		DESCRIPTION
				"TYPE: - Display
				 PAGE: - Control
					Con Pkt Total  cmdID= 765  format=   "
		::= { iqh3aCmdEntry 765 }


	iqh3aControlSlot16BlindPktCount OBJECT-TYPE
		SYNTAX		RollCallString
		MAX-ACCESS		read-only
		STATUS			current
		DESCRIPTION
				"TYPE: - Display
				 PAGE: - Control
					Blind Pkt Count  cmdID= 16585  format=   "
		::= { iqh3aCmdEntry 16585 }


	iqh3aControlShowSession OBJECT-TYPE
		SYNTAX		INTEGER
		MAX-ACCESS		read-write
		STATUS			current
		DESCRIPTION
				"TYPE: - Number
				 PAGE: - Control
					Show Session  cmdID= 16705  min= 1  max= 58  step= 1  format= %.0f  div_scale= 1
					Min = 1  Max = 58  Step = 1 "
		::= { iqh3aCmdEntry 16705 }


	iqh3aControlPktStatsUpdatePacketStats OBJECT-TYPE
		SYNTAX		INTEGER { disable(0), enable(1) }
		MAX-ACCESS		read-write
		STATUS			current
		DESCRIPTION
				"TYPE: - Checkbox
				 PAGE: - Control
					Update Packet Stats  cmdID= 16483 "
		::= { iqh3aCmdEntry 16483 }


	iqh3aControlPktStatsClearPacketCounts OBJECT-TYPE
		SYNTAX		INTEGER { disable(0), enable(1) }
		MAX-ACCESS		read-write
		STATUS			current
		DESCRIPTION
				"TYPE: - Checkbox
				 PAGE: - Control
					Clear Packet Counts  cmdID= 16484 "
		::= { iqh3aCmdEntry 16484 }


	iqh3aControlGatewayControllerName OBJECT-TYPE
		SYNTAX		RollCallString
		MAX-ACCESS		read-only
		STATUS			current
		DESCRIPTION
				"TYPE: - Display
				 PAGE: - GatewayControl
					ControllerName  cmdID= 17152  format=   "
		::= { iqh3aCmdEntry 17152 }


	iqh3aControlGatewayControllerAddr OBJECT-TYPE
		SYNTAX		RollCallString
		MAX-ACCESS		read-only
		STATUS			current
		DESCRIPTION
				"TYPE: - Display
				 PAGE: - GatewayControl
					ControllerAddr  cmdID= 17153  format=   "
		::= { iqh3aCmdEntry 17153 }


	iqh3aControlGatewayConPktCount OBJECT-TYPE
		SYNTAX		RollCallString
		MAX-ACCESS		read-only
		STATUS			current
		DESCRIPTION
				"TYPE: - Display
				 PAGE: - GatewayControl
				    Connected packet count per control session
					Con Pkt Count  cmdID= 17154  format=   "
		::= { iqh3aCmdEntry 17154 }


	iqh3aControlGatewayConPktTotal OBJECT-TYPE
		SYNTAX		RollCallString
		MAX-ACCESS		read-only
		STATUS			current
		DESCRIPTION
				"TYPE: - Display
				 PAGE: - GatewayControl
				    Total Connected packet count for all sessions, active and inactive since last reset.
					Con Pkt Total  cmdID= 17155  format=   "
		::= { iqh3aCmdEntry 17155 }


	iqh3aControlGatewayLastBlindAddr OBJECT-TYPE
		SYNTAX		RollCallString
		MAX-ACCESS		read-only
		STATUS			current
		DESCRIPTION
				"TYPE: - Display
				 PAGE: - GatewayControl
				    RollNet address of last blind controller
					LastBlindAddr  cmdID= 17157  format=   "
		::= { iqh3aCmdEntry 17157 }


	iqh3aControlGatewayBlindPktCount OBJECT-TYPE
		SYNTAX		RollCallString
		MAX-ACCESS		read-only
		STATUS			current
		DESCRIPTION
				"TYPE: - Display
				 PAGE: - GatewayControl
				    Total received blind packet counts since last reset (may be from multiple sources).
					Blind Pkt Count  cmdID= 17158  format=   "
		::= { iqh3aCmdEntry 17158 }


	iqh3aControlGatewayDisconnectSession OBJECT-TYPE
		SYNTAX		INTEGER { noAction(0),val-Disconnect-Session(1) }
		MAX-ACCESS		read-write
		STATUS			current
		DESCRIPTION
				"TYPE: - Button
				 PAGE: - GatewayControl
					Disconnect Session  cmdID= 17151  value= 1  "
		::= { iqh3aCmdEntry 17151 }


	iqh3aControlGatewayShowSession OBJECT-TYPE
		SYNTAX		INTEGER
		MAX-ACCESS		read-write
		STATUS			current
		DESCRIPTION
				"TYPE: - Number
				 PAGE: - GatewayControl
					Show Session  cmdID= 17150  min= 1  max= 100  step= 1  format= %.0f  div_scale= 1
					Min = 1  Max = 100  Step = 1 "
		::= { iqh3aCmdEntry 17150 }


	iqh3aLoggingLogServerLogto OBJECT-TYPE
		SYNTAX		INTEGER {
							val-Logging-Disabled(1),
							val-Named-LogServer(2),
							val-Any-LogServer(3)
							}
		MAX-ACCESS		read-write
		STATUS			current
		DESCRIPTION
				"TYPE: - RadiobuttonList
				 PAGE: - Logging
					Log to  cmdID= 16481
					Logging Disabled  value= 1
					Named LogServer  value= 2
					Any LogServer  value= 3  "
		::= { iqh3aCmdEntry 16481 }


	iqh3aLoggingLogServerLogServerName OBJECT-TYPE
		SYNTAX		RollCallString
		MAX-ACCESS		read-write
		STATUS			current
		DESCRIPTION
				"TYPE: - Editstring
				 PAGE: - Logging
					LogServer Name  cmdID= 16412  "
		::= { iqh3aCmdEntry 16412 }


	iqh3aLoggingLogServerCurLogger OBJECT-TYPE
		SYNTAX		RollCallString
		MAX-ACCESS		read-only
		STATUS			current
		DESCRIPTION
				"TYPE: - Display
				 PAGE: - Logging
					Cur. Logger  cmdID= 16480  format=   "
		::= { iqh3aCmdEntry 16480 }


	iqh3aLoggingLogServerCurLoggerAddr OBJECT-TYPE
		SYNTAX		RollCallString
		MAX-ACCESS		read-only
		STATUS			current
		DESCRIPTION
				"TYPE: - Display
				 PAGE: - Logging
					Cur. Logger Addr  cmdID= 16482  format=   "
		::= { iqh3aCmdEntry 16482 }


	iqh3aLoggingLogServerLastTimeaddr OBJECT-TYPE
		SYNTAX		RollCallString
		MAX-ACCESS		read-only
		STATUS			current
		DESCRIPTION
				"TYPE: - Display
				 PAGE: - Logging
					Last Time addr  cmdID= 16486  format=   "
		::= { iqh3aCmdEntry 16486 }


	iqh3aLoggingLogServerTimefromLogger OBJECT-TYPE
		SYNTAX		INTEGER { disable(0), enable(1) }
		MAX-ACCESS		read-write
		STATUS			current
		DESCRIPTION
				"TYPE: - Checkbox
				 PAGE: - Logging
					Time from Logger  cmdID= 16487 "
		::= { iqh3aCmdEntry 16487 }


	iqh3aLoggingLogServerAcceptviaIP OBJECT-TYPE
		SYNTAX		INTEGER { disable(0), enable(1) }
		MAX-ACCESS		read-write
		STATUS			current
		DESCRIPTION
				"TYPE: - Checkbox
				 PAGE: - Logging
					Accept via IP  cmdID= 17060 "
		::= { iqh3aCmdEntry 17060 }


	iqh3aLoggingLogServerAcceptviaSerial OBJECT-TYPE
		SYNTAX		INTEGER { disable(0), enable(1) }
		MAX-ACCESS		read-write
		STATUS			current
		DESCRIPTION
				"TYPE: - Checkbox
				 PAGE: - Logging
					Accept via Serial  cmdID= 17061 "
		::= { iqh3aCmdEntry 17061 }


	iqh3aLoggingLogServerAcceptviaRollNet OBJECT-TYPE
		SYNTAX		INTEGER { disable(0), enable(1) }
		MAX-ACCESS		read-write
		STATUS			current
		DESCRIPTION
				"TYPE: - Checkbox
				 PAGE: - Logging
					Accept via RollNet  cmdID= 17062 "
		::= { iqh3aCmdEntry 17062 }


	iqh3aLoggingLogServerAcceptviaBridge OBJECT-TYPE
		SYNTAX		INTEGER { disable(0), enable(1) }
		MAX-ACCESS		read-write
		STATUS			current
		DESCRIPTION
				"TYPE: - Checkbox
				 PAGE: - Logging
					Accept via Bridge  cmdID= 17063 "
		::= { iqh3aCmdEntry 17063 }


	iqh3aLoggingSN OBJECT-TYPE
		SYNTAX		RollCallString
		MAX-ACCESS		read-only
		STATUS			current
		DESCRIPTION
				"TYPE: - Display
				 PAGE: - Logging
					SN=  cmdID= 2011  format=   "
		::= { iqh3aCmdEntry 2011 }


	iqh3aLoggingVERSION OBJECT-TYPE
		SYNTAX		RollCallString
		MAX-ACCESS		read-only
		STATUS			current
		DESCRIPTION
				"TYPE: - Display
				 PAGE: - Logging
					VERSION=  cmdID= 2012  format=   "
		::= { iqh3aCmdEntry 2012 }


	iqh3aLoggingLogOSVersion OBJECT-TYPE
		SYNTAX		INTEGER { disable(0), enable(1) }
		MAX-ACCESS		read-write
		STATUS			current
		DESCRIPTION
				"TYPE: - Checkbox
				 PAGE: - Logging
					Log OS Version  cmdID= 1014 "
		::= { iqh3aCmdEntry 1014 }


	iqh3aLoggingOSVERSION OBJECT-TYPE
		SYNTAX		RollCallString
		MAX-ACCESS		read-only
		STATUS			current
		DESCRIPTION
				"TYPE: - Display
				 PAGE: - Logging
					OS_VERSION=  cmdID= 2014  format=   "
		::= { iqh3aCmdEntry 2014 }


	iqh3aLoggingLogBuildNumber OBJECT-TYPE
		SYNTAX		INTEGER { disable(0), enable(1) }
		MAX-ACCESS		read-write
		STATUS			current
		DESCRIPTION
				"TYPE: - Checkbox
				 PAGE: - Logging
					Log Build Number  cmdID= 1015 "
		::= { iqh3aCmdEntry 1015 }


	iqh3aLoggingBUILDNUMBER OBJECT-TYPE
		SYNTAX		RollCallString
		MAX-ACCESS		read-only
		STATUS			current
		DESCRIPTION
				"TYPE: - Display
				 PAGE: - Logging
					BUILD_NUMBER=  cmdID= 2015  format=   "
		::= { iqh3aCmdEntry 2015 }


	iqh3aLoggingLogHardwareVer OBJECT-TYPE
		SYNTAX		INTEGER { disable(0), enable(1) }
		MAX-ACCESS		read-write
		STATUS			current
		DESCRIPTION
				"TYPE: - Checkbox
				 PAGE: - Logging
					Log Hardware Ver.  cmdID= 1013 "
		::= { iqh3aCmdEntry 1013 }


	iqh3aLoggingHARDWAREVERSION OBJECT-TYPE
		SYNTAX		RollCallString
		MAX-ACCESS		read-only
		STATUS			current
		DESCRIPTION
				"TYPE: - Display
				 PAGE: - Logging
					HARDWARE_VERSION=  cmdID= 2013  format=   "
		::= { iqh3aCmdEntry 2013 }


	iqh3aLoggingLogLoaderVersion OBJECT-TYPE
		SYNTAX		INTEGER { disable(0), enable(1) }
		MAX-ACCESS		read-write
		STATUS			current
		DESCRIPTION
				"TYPE: - Checkbox
				 PAGE: - Logging
					Log Loader Vers Tex  cmdID= 1049 "
		::= { iqh3aCmdEntry 1049 }


	iqh3aLoggingLOADERVERSION OBJECT-TYPE
		SYNTAX		RollCallString
		MAX-ACCESS		read-only
		STATUS			current
		DESCRIPTION
				"TYPE: - Display
				 PAGE: - Logging
					LOADER_VERSION=  cmdID= 2049  format=   "
		::= { iqh3aCmdEntry 2049 }


	iqh3aLoggingLogModuleStatus OBJECT-TYPE
		SYNTAX		INTEGER { disable(0), enable(1) }
		MAX-ACCESS		read-write
		STATUS			current
		DESCRIPTION
				"TYPE: - Checkbox
				 PAGE: - Logging
					Log Module Status  cmdID= 1017 "
		::= { iqh3aCmdEntry 1017 }


	iqh3aLoggingMODULESTATUS OBJECT-TYPE
		SYNTAX		RollCallString
		MAX-ACCESS		read-only
		STATUS			current
		DESCRIPTION
				"TYPE: - Display
				 PAGE: - Logging
					MODULE_STATUS=  cmdID= 2017  format=   "
		::= { iqh3aCmdEntry 2017 }


	iqh3aLoggingLogGwayCtrlSess OBJECT-TYPE
		SYNTAX		INTEGER { disable(0), enable(1) }
		MAX-ACCESS		read-write
		STATUS			current
		DESCRIPTION
				"TYPE: - Checkbox
				 PAGE: - Logging
					Log Gway Ctrl Sess  cmdID= 1007 "
		::= { iqh3aCmdEntry 1007 }


	iqh3aLoggingSESSIONS OBJECT-TYPE
		SYNTAX		RollCallString
		MAX-ACCESS		read-only
		STATUS			current
		DESCRIPTION
				"TYPE: - Display
				 PAGE: - Logging
					SESSIONS=  cmdID= 2007  format=   "
		::= { iqh3aCmdEntry 2007 }


	iqh3aLoggingLogLastModified OBJECT-TYPE
		SYNTAX		INTEGER { disable(0), enable(1) }
		MAX-ACCESS		read-write
		STATUS			current
		DESCRIPTION
				"TYPE: - Checkbox
				 PAGE: - Logging
					Log Last Modified  cmdID= 1016 "
		::= { iqh3aCmdEntry 1016 }


	iqh3aLoggingLASTMODIFIED OBJECT-TYPE
		SYNTAX		RollCallString
		MAX-ACCESS		read-only
		STATUS			current
		DESCRIPTION
				"TYPE: - Display
				 PAGE: - Logging
					LAST_MODIFIED=  cmdID= 2016  format=   "
		::= { iqh3aCmdEntry 2016 }


	iqh3aLoggingLogIPAddress OBJECT-TYPE
		SYNTAX		INTEGER { disable(0), enable(1) }
		MAX-ACCESS		read-write
		STATUS			current
		DESCRIPTION
				"TYPE: - Checkbox
				 PAGE: - Logging
					Log IP Address  cmdID= 1018 "
		::= { iqh3aCmdEntry 1018 }


	iqh3aLoggingIPADDRESS OBJECT-TYPE
		SYNTAX		RollCallString
		MAX-ACCESS		read-only
		STATUS			current
		DESCRIPTION
				"TYPE: - Display
				 PAGE: - Logging
					IPADDRESS=  cmdID= 2018  format=   "
		::= { iqh3aCmdEntry 2018 }


	iqh3aLoggingLogPSU1Name OBJECT-TYPE
		SYNTAX		INTEGER { disable(0), enable(1) }
		MAX-ACCESS		read-write
		STATUS			current
		DESCRIPTION
				"TYPE: - Checkbox
				 PAGE: - Logging
					Log PSU 1 Name  cmdID= 1020 "
		::= { iqh3aCmdEntry 1020 }


	iqh3aLoggingPSU1NAME OBJECT-TYPE
		SYNTAX		RollCallString
		MAX-ACCESS		read-only
		STATUS			current
		DESCRIPTION
				"TYPE: - Display
				 PAGE: - Logging
					PSU_1_NAME=  cmdID= 2020  format=   "
		::= { iqh3aCmdEntry 2020 }


	iqh3aLoggingLogPSU1State OBJECT-TYPE
		SYNTAX		INTEGER { disable(0), enable(1) }
		MAX-ACCESS		read-write
		STATUS			current
		DESCRIPTION
				"TYPE: - Checkbox
				 PAGE: - Logging
					Log PSU 1 State  cmdID= 1001 "
		::= { iqh3aCmdEntry 1001 }


	iqh3aLoggingPSU1STATE OBJECT-TYPE
		SYNTAX		RollCallString
		MAX-ACCESS		read-only
		STATUS			current
		DESCRIPTION
				"TYPE: - Display
				 PAGE: - Logging
					PSU_1_STATE=  cmdID= 2001  format=   "
		::= { iqh3aCmdEntry 2001 }


	iqh3aLoggingLogPSU2Name OBJECT-TYPE
		SYNTAX		INTEGER { disable(0), enable(1) }
		MAX-ACCESS		read-write
		STATUS			current
		DESCRIPTION
				"TYPE: - Checkbox
				 PAGE: - Logging
					Log PSU 2 Name  cmdID= 1021 "
		::= { iqh3aCmdEntry 1021 }


	iqh3aLoggingPSU2NAME OBJECT-TYPE
		SYNTAX		RollCallString
		MAX-ACCESS		read-only
		STATUS			current
		DESCRIPTION
				"TYPE: - Display
				 PAGE: - Logging
					PSU_2_NAME=  cmdID= 2021  format=   "
		::= { iqh3aCmdEntry 2021 }


	iqh3aLoggingLogPSU2State OBJECT-TYPE
		SYNTAX		INTEGER { disable(0), enable(1) }
		MAX-ACCESS		read-write
		STATUS			current
		DESCRIPTION
				"TYPE: - Checkbox
				 PAGE: - Logging
					Log PSU 2 State  cmdID= 1002 "
		::= { iqh3aCmdEntry 1002 }


	iqh3aLoggingPSU2STATE OBJECT-TYPE
		SYNTAX		RollCallString
		MAX-ACCESS		read-only
		STATUS			current
		DESCRIPTION
				"TYPE: - Display
				 PAGE: - Logging
					PSU_2_STATE=  cmdID= 2002  format=   "
		::= { iqh3aCmdEntry 2002 }


	iqh3aLoggingLogReconState OBJECT-TYPE
		SYNTAX		INTEGER { disable(0), enable(1) }
		MAX-ACCESS		read-write
		STATUS			current
		DESCRIPTION
				"TYPE: - Checkbox
				 PAGE: - Logging
					Log Recon State  cmdID= 1029 "
		::= { iqh3aCmdEntry 1029 }


	iqh3aLoggingRECONSTATE OBJECT-TYPE
		SYNTAX		RollCallString
		MAX-ACCESS		read-only
		STATUS			current
		DESCRIPTION
				"TYPE: - Display
				 PAGE: - Logging
					RECON_STATE=  cmdID= 2029  format=   "
		::= { iqh3aCmdEntry 2029 }


	iqh3aLoggingLogLanPort1Name OBJECT-TYPE
		SYNTAX		INTEGER { disable(0), enable(1) }
		MAX-ACCESS		read-write
		STATUS			current
		DESCRIPTION
				"TYPE: - Checkbox
				 PAGE: - Logging
					Log Lan Port 1 Name  cmdID= 1030 "
		::= { iqh3aCmdEntry 1030 }


	iqh3aLoggingLANPORT1NAME OBJECT-TYPE
		SYNTAX		RollCallString
		MAX-ACCESS		read-only
		STATUS			current
		DESCRIPTION
				"TYPE: - Display
				 PAGE: - Logging
					LAN_PORT_1_NAME=  cmdID= 2030  format=   "
		::= { iqh3aCmdEntry 2030 }


	iqh3aLoggingLogLanPort1State OBJECT-TYPE
		SYNTAX		INTEGER { disable(0), enable(1) }
		MAX-ACCESS		read-write
		STATUS			current
		DESCRIPTION
				"TYPE: - Checkbox
				 PAGE: - Logging
					Log Lan Port 1 Stat  cmdID= 1031 "
		::= { iqh3aCmdEntry 1031 }


	iqh3aLoggingLANPORT1STATE OBJECT-TYPE
		SYNTAX		RollCallString
		MAX-ACCESS		read-only
		STATUS			current
		DESCRIPTION
				"TYPE: - Display
				 PAGE: - Logging
					LAN_PORT_1_STATE=  cmdID= 2031  format=   "
		::= { iqh3aCmdEntry 2031 }


	iqh3aLoggingLogLanPort1Speed OBJECT-TYPE
		SYNTAX		INTEGER { disable(0), enable(1) }
		MAX-ACCESS		read-write
		STATUS			current
		DESCRIPTION
				"TYPE: - Checkbox
				 PAGE: - Logging
					Log Lan Port 1 Spee  cmdID= 1032 "
		::= { iqh3aCmdEntry 1032 }


	iqh3aLoggingLANPORT1SPEED OBJECT-TYPE
		SYNTAX		RollCallString
		MAX-ACCESS		read-only
		STATUS			current
		DESCRIPTION
				"TYPE: - Display
				 PAGE: - Logging
					LAN_PORT_1_SPEED=  cmdID= 2032  format=   "
		::= { iqh3aCmdEntry 2032 }


	iqh3aLoggingLogLanPort1LastChange OBJECT-TYPE
		SYNTAX		INTEGER { disable(0), enable(1) }
		MAX-ACCESS		read-write
		STATUS			current
		DESCRIPTION
				"TYPE: - Checkbox
				 PAGE: - Logging
					Log Lan Port 1 Last  cmdID= 1033 "
		::= { iqh3aCmdEntry 1033 }


	iqh3aLoggingLANPORT1LASTCHANGE OBJECT-TYPE
		SYNTAX		RollCallString
		MAX-ACCESS		read-only
		STATUS			current
		DESCRIPTION
				"TYPE: - Display
				 PAGE: - Logging
					LAN_PORT_1_LAST_CHA  cmdID= 2033  format=   "
		::= { iqh3aCmdEntry 2033 }


	iqh3aLoggingLogLanPort1Errors OBJECT-TYPE
		SYNTAX		INTEGER { disable(0), enable(1) }
		MAX-ACCESS		read-write
		STATUS			current
		DESCRIPTION
				"TYPE: - Checkbox
				 PAGE: - Logging
					Log Lan Port 1 Erro  cmdID= 1034 "
		::= { iqh3aCmdEntry 1034 }


	iqh3aLoggingLANPORT1ERRORS OBJECT-TYPE
		SYNTAX		RollCallString
		MAX-ACCESS		read-only
		STATUS			current
		DESCRIPTION
				"TYPE: - Display
				 PAGE: - Logging
					LAN_PORT_1_ERRORS=  cmdID= 2034  format=   "
		::= { iqh3aCmdEntry 2034 }


	iqh3aLoggingLogLanPort1InTraffic OBJECT-TYPE
		SYNTAX		INTEGER { disable(0), enable(1) }
		MAX-ACCESS		read-write
		STATUS			current
		DESCRIPTION
				"TYPE: - Checkbox
				 PAGE: - Logging
					Log Lan Port 1 InTraffic  cmdID= 1035 "
		::= { iqh3aCmdEntry 1035 }


	iqh3aLoggingLANPORT1TRAFFICIN OBJECT-TYPE
		SYNTAX		RollCallString
		MAX-ACCESS		read-only
		STATUS			current
		DESCRIPTION
				"TYPE: - Display
				 PAGE: - Logging
					LAN_PORT_1_TRAFFIC_IN  cmdID= 2035  format=   "
		::= { iqh3aCmdEntry 2035 }


	iqh3aLoggingLogLanPort1OutTraffic OBJECT-TYPE
		SYNTAX		INTEGER { disable(0), enable(1) }
		MAX-ACCESS		read-write
		STATUS			current
		DESCRIPTION
				"TYPE: - Checkbox
				 PAGE: - Logging
					Log Lan Port 1 OutTraffic  cmdID= 1036 "
		::= { iqh3aCmdEntry 1036 }


	iqh3aLoggingLANPORT1TRAFFICOUT OBJECT-TYPE
		SYNTAX		RollCallString
		MAX-ACCESS		read-only
		STATUS			current
		DESCRIPTION
				"TYPE: - Display
				 PAGE: - Logging
					LAN_PORT_1_TRAFFIC_OUT  cmdID= 2036  format=   "
		::= { iqh3aCmdEntry 2036 }


	iqh3aLoggingLogIpEvent OBJECT-TYPE
		SYNTAX		INTEGER { disable(0), enable(1) }
		MAX-ACCESS		read-write
		STATUS			current
		DESCRIPTION
				"TYPE: - Checkbox
				 PAGE: - Logging
					Log Ip Event  cmdID= 1037 "
		::= { iqh3aCmdEntry 1037 }


	iqh3aLoggingIPEVENT OBJECT-TYPE
		SYNTAX		RollCallString
		MAX-ACCESS		read-only
		STATUS			current
		DESCRIPTION
				"TYPE: - Display
				 PAGE: - Logging
					IP_EVENT=  cmdID= 2037  format=   "
		::= { iqh3aCmdEntry 2037 }


	iqh3aLoggingLogUptime OBJECT-TYPE
		SYNTAX		INTEGER { disable(0), enable(1) }
		MAX-ACCESS		read-write
		STATUS			current
		DESCRIPTION
				"TYPE: - Checkbox
				 PAGE: - Logging
					Log Uptime  cmdID= 1038 "
		::= { iqh3aCmdEntry 1038 }


	iqh3aLoggingUPTIME OBJECT-TYPE
		SYNTAX		RollCallString
		MAX-ACCESS		read-only
		STATUS			current
		DESCRIPTION
				"TYPE: - Display
				 PAGE: - Logging
					UPTIME=  cmdID= 2038  format=   "
		::= { iqh3aCmdEntry 2038 }


	iqh3aLoggingLogRestartedAt OBJECT-TYPE
		SYNTAX		INTEGER { disable(0), enable(1) }
		MAX-ACCESS		read-write
		STATUS			current
		DESCRIPTION
				"TYPE: - Checkbox
				 PAGE: - Logging
					Log Restarted At  cmdID= 1039 "
		::= { iqh3aCmdEntry 1039 }


	iqh3aLoggingRESTARTEDAT OBJECT-TYPE
		SYNTAX		RollCallString
		MAX-ACCESS		read-only
		STATUS			current
		DESCRIPTION
				"TYPE: - Display
				 PAGE: - Logging
					RESTARTED_AT=  cmdID= 2039  format=   "
		::= { iqh3aCmdEntry 2039 }


	iqh3aLoggingLogThumbIpPort OBJECT-TYPE
		SYNTAX		INTEGER { disable(0), enable(1) }
		MAX-ACCESS		read-write
		STATUS			current
		DESCRIPTION
				"TYPE: - Checkbox
				 PAGE: - Logging
					Log Thumb Ip Port  cmdID= 1040 "
		::= { iqh3aCmdEntry 1040 }


	iqh3aLoggingTHUMBIPPORT OBJECT-TYPE
		SYNTAX		RollCallString
		MAX-ACCESS		read-only
		STATUS			current
		DESCRIPTION
				"TYPE: - Display
				 PAGE: - Logging
					THUMB_IP_PORT=  cmdID= 2040  format=   "
		::= { iqh3aCmdEntry 2040 }


	iqh3aLoggingLogTemp1Name OBJECT-TYPE
		SYNTAX		INTEGER { disable(0), enable(1) }
		MAX-ACCESS		read-write
		STATUS			current
		DESCRIPTION
				"TYPE: - Checkbox
				 PAGE: - Logging
					Log Temp 1 Name  cmdID= 1022 "
		::= { iqh3aCmdEntry 1022 }


	iqh3aLoggingTEMP1NAME OBJECT-TYPE
		SYNTAX		RollCallString
		MAX-ACCESS		read-only
		STATUS			current
		DESCRIPTION
				"TYPE: - Display
				 PAGE: - Logging
					TEMP_1_NAME=  cmdID= 2022  format=   "
		::= { iqh3aCmdEntry 2022 }


	iqh3aLoggingLogTemp1State OBJECT-TYPE
		SYNTAX		INTEGER { disable(0), enable(1) }
		MAX-ACCESS		read-write
		STATUS			current
		DESCRIPTION
				"TYPE: - Checkbox
				 PAGE: - Logging
					Log Temp 1 State  cmdID= 1003 "
		::= { iqh3aCmdEntry 1003 }


	iqh3aLoggingTEMP1STATE OBJECT-TYPE
		SYNTAX		RollCallString
		MAX-ACCESS		read-only
		STATUS			current
		DESCRIPTION
				"TYPE: - Display
				 PAGE: - Logging
					TEMP_1_STATE=  cmdID= 2003  format=   "
		::= { iqh3aCmdEntry 2003 }


	iqh3aLoggingLogTemp1Celsius OBJECT-TYPE
		SYNTAX		INTEGER { disable(0), enable(1) }
		MAX-ACCESS		read-write
		STATUS			current
		DESCRIPTION
				"TYPE: - Checkbox
				 PAGE: - Logging
					Log Temp 1 Celsius  cmdID= 1008 "
		::= { iqh3aCmdEntry 1008 }


	iqh3aLoggingTEMP1CELSIUS OBJECT-TYPE
		SYNTAX		RollCallString
		MAX-ACCESS		read-only
		STATUS			current
		DESCRIPTION
				"TYPE: - Display
				 PAGE: - Logging
					TEMP_1_CELSIUS=  cmdID= 2008  format=   "
		::= { iqh3aCmdEntry 2008 }


	iqh3aLoggingLogTemp2Name OBJECT-TYPE
		SYNTAX		INTEGER { disable(0), enable(1) }
		MAX-ACCESS		read-write
		STATUS			current
		DESCRIPTION
				"TYPE: - Checkbox
				 PAGE: - Logging
					Log Temp 2 Name  cmdID= 1023 "
		::= { iqh3aCmdEntry 1023 }


	iqh3aLoggingTEMP2NAME OBJECT-TYPE
		SYNTAX		RollCallString
		MAX-ACCESS		read-only
		STATUS			current
		DESCRIPTION
				"TYPE: - Display
				 PAGE: - Logging
					TEMP_2_NAME=  cmdID= 2023  format=   "
		::= { iqh3aCmdEntry 2023 }


	iqh3aLoggingLogTemp2State OBJECT-TYPE
		SYNTAX		INTEGER { disable(0), enable(1) }
		MAX-ACCESS		read-write
		STATUS			current
		DESCRIPTION
				"TYPE: - Checkbox
				 PAGE: - Logging
					Log Temp 2 State  cmdID= 1004 "
		::= { iqh3aCmdEntry 1004 }


	iqh3aLoggingTEMP2STATE OBJECT-TYPE
		SYNTAX		RollCallString
		MAX-ACCESS		read-only
		STATUS			current
		DESCRIPTION
				"TYPE: - Display
				 PAGE: - Logging
					TEMP_2_STATE=  cmdID= 2004  format=   "
		::= { iqh3aCmdEntry 2004 }


	iqh3aLoggingLogTemp2Celsius OBJECT-TYPE
		SYNTAX		INTEGER { disable(0), enable(1) }
		MAX-ACCESS		read-write
		STATUS			current
		DESCRIPTION
				"TYPE: - Checkbox
				 PAGE: - Logging
					Log Temp 2 Celsius  cmdID= 1009 "
		::= { iqh3aCmdEntry 1009 }


	iqh3aLoggingTEMP2CELSIUS OBJECT-TYPE
		SYNTAX		RollCallString
		MAX-ACCESS		read-only
		STATUS			current
		DESCRIPTION
				"TYPE: - Display
				 PAGE: - Logging
					TEMP_2_CELSIUS=  cmdID= 2009  format=   "
		::= { iqh3aCmdEntry 2009 }


	iqh3aLoggingLogFan1Name OBJECT-TYPE
		SYNTAX		INTEGER { disable(0), enable(1) }
		MAX-ACCESS		read-write
		STATUS			current
		DESCRIPTION
				"TYPE: - Checkbox
				 PAGE: - Logging
					Log Fan 1 Name  cmdID= 1019 "
		::= { iqh3aCmdEntry 1019 }


	iqh3aLoggingFAN1NAME OBJECT-TYPE
		SYNTAX		RollCallString
		MAX-ACCESS		read-only
		STATUS			current
		DESCRIPTION
				"TYPE: - Display
				 PAGE: - Logging
					FAN_1_NAME=  cmdID= 2019  format=   "
		::= { iqh3aCmdEntry 2019 }


	iqh3aLoggingLogFan1State OBJECT-TYPE
		SYNTAX		INTEGER { disable(0), enable(1) }
		MAX-ACCESS		read-write
		STATUS			current
		DESCRIPTION
				"TYPE: - Checkbox
				 PAGE: - Logging
					Log Fan 1 State  cmdID= 1000 "
		::= { iqh3aCmdEntry 1000 }


	iqh3aLoggingFAN1STATE OBJECT-TYPE
		SYNTAX		RollCallString
		MAX-ACCESS		read-only
		STATUS			current
		DESCRIPTION
				"TYPE: - Display
				 PAGE: - Logging
					FAN_1_STATE=  cmdID= 2000  format=   "
		::= { iqh3aCmdEntry 2000 }


	iqh3aLoggingLogFan2Name OBJECT-TYPE
		SYNTAX		INTEGER { disable(0), enable(1) }
		MAX-ACCESS		read-write
		STATUS			current
		DESCRIPTION
				"TYPE: - Checkbox
				 PAGE: - Logging
					Log Fan 2 Name  cmdID= 1044 "
		::= { iqh3aCmdEntry 1044 }


	iqh3aLoggingFAN2NAME OBJECT-TYPE
		SYNTAX		RollCallString
		MAX-ACCESS		read-only
		STATUS			current
		DESCRIPTION
				"TYPE: - Display
				 PAGE: - Logging
					FAN_2_NAME=  cmdID= 2044  format=   "
		::= { iqh3aCmdEntry 2044 }


	iqh3aLoggingLogFan2State OBJECT-TYPE
		SYNTAX		INTEGER { disable(0), enable(1) }
		MAX-ACCESS		read-write
		STATUS			current
		DESCRIPTION
				"TYPE: - Checkbox
				 PAGE: - Logging
					Log Fan 2 State  cmdID= 1043 "
		::= { iqh3aCmdEntry 1043 }


	iqh3aLoggingFAN2STATE OBJECT-TYPE
		SYNTAX		RollCallString
		MAX-ACCESS		read-only
		STATUS			current
		DESCRIPTION
				"TYPE: - Display
				 PAGE: - Logging
					FAN_2_STATE=  cmdID= 2043  format=   "
		::= { iqh3aCmdEntry 2043 }


	iqh3aLoggingLogFan3Name OBJECT-TYPE
		SYNTAX		INTEGER { disable(0), enable(1) }
		MAX-ACCESS		read-write
		STATUS			current
		DESCRIPTION
				"TYPE: - Checkbox
				 PAGE: - Logging
					Log Fan 3 Name  cmdID= 1046 "
		::= { iqh3aCmdEntry 1046 }


	iqh3aLoggingFAN3NAME OBJECT-TYPE
		SYNTAX		RollCallString
		MAX-ACCESS		read-only
		STATUS			current
		DESCRIPTION
				"TYPE: - Display
				 PAGE: - Logging
					FAN_3_NAME=  cmdID= 2046  format=   "
		::= { iqh3aCmdEntry 2046 }


	iqh3aLoggingLogFan3State OBJECT-TYPE
		SYNTAX		INTEGER { disable(0), enable(1) }
		MAX-ACCESS		read-write
		STATUS			current
		DESCRIPTION
				"TYPE: - Checkbox
				 PAGE: - Logging
					Log Fan 3 State  cmdID= 1045 "
		::= { iqh3aCmdEntry 1045 }


	iqh3aLoggingFAN3STATE OBJECT-TYPE
		SYNTAX		RollCallString
		MAX-ACCESS		read-only
		STATUS			current
		DESCRIPTION
				"TYPE: - Display
				 PAGE: - Logging
					FAN_3_STATE=  cmdID= 2045  format=   "
		::= { iqh3aCmdEntry 2045 }


	iqh3aLoggingLogFan4Name OBJECT-TYPE
		SYNTAX		INTEGER { disable(0), enable(1) }
		MAX-ACCESS		read-write
		STATUS			current
		DESCRIPTION
				"TYPE: - Checkbox
				 PAGE: - Logging
					Log Fan 4 Name  cmdID= 1048 "
		::= { iqh3aCmdEntry 1048 }


	iqh3aLoggingFAN4NAME OBJECT-TYPE
		SYNTAX		RollCallString
		MAX-ACCESS		read-only
		STATUS			current
		DESCRIPTION
				"TYPE: - Display
				 PAGE: - Logging
					FAN_4_NAME=  cmdID= 2048  format=   "
		::= { iqh3aCmdEntry 2048 }


	iqh3aLoggingLogFan4State OBJECT-TYPE
		SYNTAX		INTEGER { disable(0), enable(1) }
		MAX-ACCESS		read-write
		STATUS			current
		DESCRIPTION
				"TYPE: - Checkbox
				 PAGE: - Logging
					Log Fan 4 State  cmdID= 1047 "
		::= { iqh3aCmdEntry 1047 }


	iqh3aLoggingFAN4STATE OBJECT-TYPE
		SYNTAX		RollCallString
		MAX-ACCESS		read-only
		STATUS			current
		DESCRIPTION
				"TYPE: - Display
				 PAGE: - Logging
					FAN_4_STATE=  cmdID= 2047  format=   "
		::= { iqh3aCmdEntry 2047 }


	iqh3aLoggingLogEnclosure OBJECT-TYPE
		SYNTAX		INTEGER { disable(0), enable(1) }
		MAX-ACCESS		read-write
		STATUS			current
		DESCRIPTION
				"TYPE: - Checkbox
				 PAGE: - Logging
					Log Enclosure  cmdID= 1055 "
		::= { iqh3aCmdEntry 1055 }


	iqh3aLoggingENCLOSURE OBJECT-TYPE
		SYNTAX		RollCallString
		MAX-ACCESS		read-only
		STATUS			current
		DESCRIPTION
				"TYPE: - Display
				 PAGE: - Logging
					ENCLOSURE=  cmdID= 2055  format=   "
		::= { iqh3aCmdEntry 2055 }


	iqh3aLoggingLogVoltage1Name OBJECT-TYPE
		SYNTAX		INTEGER { disable(0), enable(1) }
		MAX-ACCESS		read-write
		STATUS			current
		DESCRIPTION
				"TYPE: - Checkbox
				 PAGE: - Logging
					Log Voltage 1 Name  cmdID= 1024 "
		::= { iqh3aCmdEntry 1024 }


	iqh3aLoggingVOLTAGE1NAME OBJECT-TYPE
		SYNTAX		RollCallString
		MAX-ACCESS		read-only
		STATUS			current
		DESCRIPTION
				"TYPE: - Display
				 PAGE: - Logging
					VOLTAGE_1_NAME=  cmdID= 2024  format=   "
		::= { iqh3aCmdEntry 2024 }


	iqh3aLoggingLogVoltage1State OBJECT-TYPE
		SYNTAX		INTEGER { disable(0), enable(1) }
		MAX-ACCESS		read-write
		STATUS			current
		DESCRIPTION
				"TYPE: - Checkbox
				 PAGE: - Logging
					Log Voltage 1 State  cmdID= 1005 "
		::= { iqh3aCmdEntry 1005 }


	iqh3aLoggingVOLTAGE1STATE OBJECT-TYPE
		SYNTAX		RollCallString
		MAX-ACCESS		read-only
		STATUS			current
		DESCRIPTION
				"TYPE: - Display
				 PAGE: - Logging
					VOLTAGE_1_STATE=  cmdID= 2005  format=   "
		::= { iqh3aCmdEntry 2005 }


	iqh3aLoggingLogVoltage1Value OBJECT-TYPE
		SYNTAX		INTEGER { disable(0), enable(1) }
		MAX-ACCESS		read-write
		STATUS			current
		DESCRIPTION
				"TYPE: - Checkbox
				 PAGE: - Logging
					Log Voltage 1 Value  cmdID= 1025 "
		::= { iqh3aCmdEntry 1025 }


	iqh3aLoggingVOLTAGE1VALUE OBJECT-TYPE
		SYNTAX		RollCallString
		MAX-ACCESS		read-only
		STATUS			current
		DESCRIPTION
				"TYPE: - Display
				 PAGE: - Logging
					VOLTAGE_1_VALUE=  cmdID= 2025  format=   "
		::= { iqh3aCmdEntry 2025 }


	iqh3aLoggingLogVoltage2Name OBJECT-TYPE
		SYNTAX		INTEGER { disable(0), enable(1) }
		MAX-ACCESS		read-write
		STATUS			current
		DESCRIPTION
				"TYPE: - Checkbox
				 PAGE: - Logging
					Log Voltage 2 Name  cmdID= 1026 "
		::= { iqh3aCmdEntry 1026 }


	iqh3aLoggingVOLTAGE2NAME OBJECT-TYPE
		SYNTAX		RollCallString
		MAX-ACCESS		read-only
		STATUS			current
		DESCRIPTION
				"TYPE: - Display
				 PAGE: - Logging
					VOLTAGE_2_NAME=  cmdID= 2026  format=   "
		::= { iqh3aCmdEntry 2026 }


	iqh3aLoggingLogVoltage2State OBJECT-TYPE
		SYNTAX		INTEGER { disable(0), enable(1) }
		MAX-ACCESS		read-write
		STATUS			current
		DESCRIPTION
				"TYPE: - Checkbox
				 PAGE: - Logging
					Log Voltage 2 State  cmdID= 1006 "
		::= { iqh3aCmdEntry 1006 }


	iqh3aLoggingVOLTAGE2STATE OBJECT-TYPE
		SYNTAX		RollCallString
		MAX-ACCESS		read-only
		STATUS			current
		DESCRIPTION
				"TYPE: - Display
				 PAGE: - Logging
					VOLTAGE_2_STATE=  cmdID= 2006  format=   "
		::= { iqh3aCmdEntry 2006 }


	iqh3aLoggingLogVoltage2Value OBJECT-TYPE
		SYNTAX		INTEGER { disable(0), enable(1) }
		MAX-ACCESS		read-write
		STATUS			current
		DESCRIPTION
				"TYPE: - Checkbox
				 PAGE: - Logging
					Log Voltage 2 Value  cmdID= 1027 "
		::= { iqh3aCmdEntry 1027 }


	iqh3aLoggingVOLTAGE2VALUE OBJECT-TYPE
		SYNTAX		RollCallString
		MAX-ACCESS		read-only
		STATUS			current
		DESCRIPTION
				"TYPE: - Display
				 PAGE: - Logging
					VOLTAGE_2_VALUE=  cmdID= 2027  format=   "
		::= { iqh3aCmdEntry 2027 }


	iqh3aLoggingLogInformation1 OBJECT-TYPE
		SYNTAX		INTEGER { disable(0), enable(1) }
		MAX-ACCESS		read-write
		STATUS			current
		DESCRIPTION
				"TYPE: - Checkbox
				 PAGE: - Logging
					Log Information 1 T  cmdID= 1041 "
		::= { iqh3aCmdEntry 1041 }


	iqh3aLoggingINFORMATION1 OBJECT-TYPE
		SYNTAX		RollCallString
		MAX-ACCESS		read-only
		STATUS			current
		DESCRIPTION
				"TYPE: - Display
				 PAGE: - Logging
					INFORMATION1=  cmdID= 2041  format=   "
		::= { iqh3aCmdEntry 2041 }


	iqh3aLoggingLogInformation2 OBJECT-TYPE
		SYNTAX		INTEGER { disable(0), enable(1) }
		MAX-ACCESS		read-write
		STATUS			current
		DESCRIPTION
				"TYPE: - Checkbox
				 PAGE: - Logging
					Log Information 2 T  cmdID= 1042 "
		::= { iqh3aCmdEntry 1042 }


	iqh3aLoggingINFORMATION2 OBJECT-TYPE
		SYNTAX		RollCallString
		MAX-ACCESS		read-only
		STATUS			current
		DESCRIPTION
				"TYPE: - Display
				 PAGE: - Logging
					INFORMATION2=  cmdID= 2042  format=   "
		::= { iqh3aCmdEntry 2042 }


	iqh3aLoggingLogFaults OBJECT-TYPE
		SYNTAX		INTEGER { disable(0), enable(1) }
		MAX-ACCESS		read-write
		STATUS			current
		DESCRIPTION
				"TYPE: - Checkbox
				 PAGE: - Logging
					Log Faults  cmdID= 1028 "
		::= { iqh3aCmdEntry 1028 }


	iqh3aLoggingFAULT OBJECT-TYPE
		SYNTAX		RollCallString
		MAX-ACCESS		read-only
		STATUS			current
		DESCRIPTION
				"TYPE: - Display
				 PAGE: - Logging
					FAULT=  cmdID= 2028  format=   "
		::= { iqh3aCmdEntry 2028 }


	iqh3aLoggingLogModuleComms OBJECT-TYPE
		SYNTAX		INTEGER { disable(0), enable(1) }
		MAX-ACCESS		read-write
		STATUS			current
		DESCRIPTION
				"TYPE: - Checkbox
				 PAGE: - Logging
					Log Module Comms  cmdID= 1010 "
		::= { iqh3aCmdEntry 1010 }


	iqh3aLoggingMODULECOMMS OBJECT-TYPE
		SYNTAX		RollCallString
		MAX-ACCESS		read-only
		STATUS			current
		DESCRIPTION
				"TYPE: - Display
				 PAGE: - Logging
					MODULE_COMMS=  cmdID= 2010  format=   "
		::= { iqh3aCmdEntry 2010 }


	iqh3aLoggingFanStatus OBJECT-TYPE
		SYNTAX		RollCallString
		MAX-ACCESS		read-only
		STATUS			current
		DESCRIPTION
				"TYPE: - Display
				 PAGE: - Logging
					Fan Status  cmdID= 17000  format=   "
		::= { iqh3aCmdEntry 17000 }


	iqh3aLoggingLogSnmpName OBJECT-TYPE
		SYNTAX		INTEGER { disable(0), enable(1) }
		MAX-ACCESS		read-write
		STATUS			current
		DESCRIPTION
				"TYPE: - Checkbox
				 PAGE: - Logging
					Log Snmp Name Text  cmdID= 1050 "
		::= { iqh3aCmdEntry 1050 }


	iqh3aLoggingSNMPNAME OBJECT-TYPE
		SYNTAX		RollCallString
		MAX-ACCESS		read-only
		STATUS			current
		DESCRIPTION
				"TYPE: - Display
				 PAGE: - Logging
					SNMP_NAME=  cmdID= 2050  format=   "
		::= { iqh3aCmdEntry 2050 }


	iqh3aLoggingLogLocation OBJECT-TYPE
		SYNTAX		INTEGER { disable(0), enable(1) }
		MAX-ACCESS		read-write
		STATUS			current
		DESCRIPTION
				"TYPE: - Checkbox
				 PAGE: - Logging
					Log Location Text  cmdID= 1051 "
		::= { iqh3aCmdEntry 1051 }


	iqh3aLoggingLOCATION OBJECT-TYPE
		SYNTAX		RollCallString
		MAX-ACCESS		read-only
		STATUS			current
		DESCRIPTION
				"TYPE: - Display
				 PAGE: - Logging
					LOCATION=  cmdID= 2051  format=   "
		::= { iqh3aCmdEntry 2051 }


	iqh3aLoggingLogSysContact OBJECT-TYPE
		SYNTAX		INTEGER { disable(0), enable(1) }
		MAX-ACCESS		read-write
		STATUS			current
		DESCRIPTION
				"TYPE: - Checkbox
				 PAGE: - Logging
					Log Sys Contact Tex  cmdID= 1052 "
		::= { iqh3aCmdEntry 1052 }


	iqh3aLoggingSYSTEMCONTACT OBJECT-TYPE
		SYNTAX		RollCallString
		MAX-ACCESS		read-only
		STATUS			current
		DESCRIPTION
				"TYPE: - Display
				 PAGE: - Logging
					SYSTEM_CONTACT=  cmdID= 2052  format=   "
		::= { iqh3aCmdEntry 2052 }


	iqh3aLoggingLogSysDescription OBJECT-TYPE
		SYNTAX		INTEGER { disable(0), enable(1) }
		MAX-ACCESS		read-write
		STATUS			current
		DESCRIPTION
				"TYPE: - Checkbox
				 PAGE: - Logging
					Log Sys Description  cmdID= 1053 "
		::= { iqh3aCmdEntry 1053 }


	iqh3aLoggingSYSTEMDESCRIPTION OBJECT-TYPE
		SYNTAX		RollCallString
		MAX-ACCESS		read-only
		STATUS			current
		DESCRIPTION
				"TYPE: - Display
				 PAGE: - Logging
					SYSTEM_DESCRIPTION=  cmdID= 2053  format=   "
		::= { iqh3aCmdEntry 2053 }


	iqh3aLoggingLoggingState OBJECT-TYPE
		SYNTAX		INTEGER { disable(0), enable(1) }
		MAX-ACCESS		read-write
		STATUS			current
		DESCRIPTION
				"TYPE: - Checkbox
				 PAGE: - Logging
					Logging State  cmdID= 1054 "
		::= { iqh3aCmdEntry 1054 }


	iqh3aLoggingLOGGINGSTATE OBJECT-TYPE
		SYNTAX		RollCallString
		MAX-ACCESS		read-only
		STATUS			current
		DESCRIPTION
				"TYPE: - Display
				 PAGE: - Logging
					LOGGING_STATE=  cmdID= 2054  format=   "
		::= { iqh3aCmdEntry 2054 }


	iqh3aLoggingPowerMaxEnable OBJECT-TYPE
		SYNTAX		INTEGER { disable(0), enable(1) }
		MAX-ACCESS		read-write
		STATUS			current
		DESCRIPTION
				"TYPE: - Checkbox
				 PAGE: - Logging
					Power Max Enable  cmdID= 1057 "
		::= { iqh3aCmdEntry 1057 }


	iqh3aLoggingPOWERMAX OBJECT-TYPE
		SYNTAX		RollCallString
		MAX-ACCESS		read-only
		STATUS			current
		DESCRIPTION
				"TYPE: - Display
				 PAGE: - Logging
					POWER_MAX=  cmdID= 2057  format=   "
		::= { iqh3aCmdEntry 2057 }


	iqh3aLoggingPowerUsageEnable OBJECT-TYPE
		SYNTAX		INTEGER { disable(0), enable(1) }
		MAX-ACCESS		read-write
		STATUS			current
		DESCRIPTION
				"TYPE: - Checkbox
				 PAGE: - Logging
					Power Usage Enable  cmdID= 1056 "
		::= { iqh3aCmdEntry 1056 }


	iqh3aLoggingPOWERUSAGE OBJECT-TYPE
		SYNTAX		RollCallString
		MAX-ACCESS		read-only
		STATUS			current
		DESCRIPTION
				"TYPE: - Display
				 PAGE: - Logging
					POWER_USAGE=  cmdID= 2056  format=   "
		::= { iqh3aCmdEntry 2056 }


	iqh3aLoggingPowerCheckEnable OBJECT-TYPE
		SYNTAX		INTEGER { disable(0), enable(1) }
		MAX-ACCESS		read-write
		STATUS			current
		DESCRIPTION
				"TYPE: - Checkbox
				 PAGE: - Logging
					Power Check Enable  cmdID= 1058 "
		::= { iqh3aCmdEntry 1058 }


	iqh3aLoggingPOWERCHECK OBJECT-TYPE
		SYNTAX		RollCallString
		MAX-ACCESS		read-only
		STATUS			current
		DESCRIPTION
				"TYPE: - Display
				 PAGE: - Logging
					POWER_CHECK=  cmdID= 2058  format=   "
		::= { iqh3aCmdEntry 2058 }


	iqh3aLoggingIPBridgeStatEnab OBJECT-TYPE
		SYNTAX		INTEGER { disable(0), enable(1) }
		MAX-ACCESS		read-write
		STATUS			current
		DESCRIPTION
				"TYPE: - Checkbox
				 PAGE: - Logging
					IP Bridge Stat Enab  cmdID= 1059 "
		::= { iqh3aCmdEntry 1059 }


	iqh3aLoggingIPBRIDGESTATUS OBJECT-TYPE
		SYNTAX		RollCallString
		MAX-ACCESS		read-only
		STATUS			current
		DESCRIPTION
				"TYPE: - Display
				 PAGE: - Logging
					IP_BRIDGE_STATUS=  cmdID= 2059  format=   "
		::= { iqh3aCmdEntry 2059 }


	iqh3aEthernetIPaddress OBJECT-TYPE
		SYNTAX		RollCallString
		MAX-ACCESS		read-write
		STATUS			current
		DESCRIPTION
				"TYPE: - Editstring
				 PAGE: - Ethernet
					IP address  cmdID= 16802  "
		::= { iqh3aCmdEntry 16802 }


	iqh3aEthernetSubnetmask OBJECT-TYPE
		SYNTAX		RollCallString
		MAX-ACCESS		read-write
		STATUS			current
		DESCRIPTION
				"TYPE: - Editstring
				 PAGE: - Ethernet
					Subnet mask  cmdID= 16803  "
		::= { iqh3aCmdEntry 16803 }


	iqh3aEthernetDefaultIPgateway OBJECT-TYPE
		SYNTAX		RollCallString
		MAX-ACCESS		read-write
		STATUS			current
		DESCRIPTION
				"TYPE: - Editstring
				 PAGE: - Ethernet
					Default IP gateway  cmdID= 16804  "
		::= { iqh3aCmdEntry 16804 }


	iqh3aEthernetTakeIPChange OBJECT-TYPE
		SYNTAX		INTEGER { noAction(0),val-TakeIPChange(1) }
		MAX-ACCESS		read-write
		STATUS			current
		DESCRIPTION
				"TYPE: - Button
				 PAGE: - Ethernet
					TakeIPChange  cmdID= 17019  value= 1  "
		::= { iqh3aCmdEntry 17019 }


	iqh3aEthernetIPSharePort OBJECT-TYPE
		SYNTAX		RollCallString
		MAX-ACCESS		read-write
		STATUS			current
		DESCRIPTION
				"TYPE: - Editstring
				 PAGE: - Ethernet
					IP Share Port  cmdID= 16809  "
		::= { iqh3aCmdEntry 16809 }


	iqh3aEthernetIPSharePortLocal OBJECT-TYPE
		SYNTAX		RollCallString
		MAX-ACCESS		read-write
		STATUS			current
		DESCRIPTION
				"TYPE: - Editstring
				 PAGE: - Ethernet
					IP Share Port Local  cmdID= 17241  "
		::= { iqh3aCmdEntry 17241 }


	iqh3aEthernetLinkspeed OBJECT-TYPE
		SYNTAX		INTEGER {
							val-Auto(0),
							val-10-Mbps-half(1),
							val-10-Mbps-full(2),
							val-100-Mbps-half(3),
							val-100-Mbps-full(4)
							}
		MAX-ACCESS		read-write
		STATUS			current
		DESCRIPTION
				"TYPE: - RadiobuttonList
				 PAGE: - Ethernet
					Link speed  cmdID= 16800
					Auto  value= 0
					10 Mbps half  value= 1
					10 Mbps full  value= 2
					100 Mbps half  value= 3
					100 Mbps full  value= 4  "
		::= { iqh3aCmdEntry 16800 }


	iqh3aEthernetLinkState OBJECT-TYPE
		SYNTAX		RollCallString
		MAX-ACCESS		read-only
		STATUS			current
		DESCRIPTION
				"TYPE: - Display
				 PAGE: - Ethernet
					Link State  cmdID= 16808  format=   "
		::= { iqh3aCmdEntry 16808 }


	iqh3aEthernetMACaddress OBJECT-TYPE
		SYNTAX		RollCallString
		MAX-ACCESS		read-only
		STATUS			current
		DESCRIPTION
				"TYPE: - Display
				 PAGE: - Ethernet
					MAC address  cmdID= 16801  format=   "
		::= { iqh3aCmdEntry 16801 }


	iqh3aEthernetIPRouting OBJECT-TYPE
		SYNTAX		RollCallString
		MAX-ACCESS		read-only
		STATUS			current
		DESCRIPTION
				"TYPE: - Display
				 PAGE: - Ethernet
					IP Routing  cmdID= 16807  format=   "
		::= { iqh3aCmdEntry 16807 }


	iqh3aEthernetIgnorebcastpkts OBJECT-TYPE
		SYNTAX		INTEGER { disable(0), enable(1) }
		MAX-ACCESS		read-write
		STATUS			current
		DESCRIPTION
				"TYPE: - Checkbox
				 PAGE: - Ethernet
					Ignore b'cast pkts  cmdID= 16805 "
		::= { iqh3aCmdEntry 16805 }


	iqh3aEthernetCheckclientIP OBJECT-TYPE
		SYNTAX		INTEGER { disable(0), enable(1) }
		MAX-ACCESS		read-write
		STATUS			current
		DESCRIPTION
				"TYPE: - Checkbox
				 PAGE: - Ethernet
					Check client IP  cmdID= 16806 "
		::= { iqh3aCmdEntry 16806 }


	iqh3aEthernetIPThumbPort OBJECT-TYPE
		SYNTAX		RollCallString
		MAX-ACCESS		read-write
		STATUS			current
		DESCRIPTION
				"TYPE: - Editstring
				 PAGE: - Ethernet
					IP Thumb Port  cmdID= 16810  "
		::= { iqh3aCmdEntry 16810 }


	iqh3aEthernetClientIPRangesMin1 OBJECT-TYPE
		SYNTAX		RollCallString
		MAX-ACCESS		read-write
		STATUS			current
		DESCRIPTION
				"TYPE: - Editstring
				 PAGE: - Ethernet
					Min 1  cmdID= 16811  "
		::= { iqh3aCmdEntry 16811 }


	iqh3aEthernetClientIPRangesMax1 OBJECT-TYPE
		SYNTAX		RollCallString
		MAX-ACCESS		read-write
		STATUS			current
		DESCRIPTION
				"TYPE: - Editstring
				 PAGE: - Ethernet
					Max 1  cmdID= 16819  "
		::= { iqh3aCmdEntry 16819 }


	iqh3aEthernetClientIPRangesMin2 OBJECT-TYPE
		SYNTAX		RollCallString
		MAX-ACCESS		read-write
		STATUS			current
		DESCRIPTION
				"TYPE: - Editstring
				 PAGE: - Ethernet
					Min 2  cmdID= 16812  "
		::= { iqh3aCmdEntry 16812 }


	iqh3aEthernetClientIPRangesMax2 OBJECT-TYPE
		SYNTAX		RollCallString
		MAX-ACCESS		read-write
		STATUS			current
		DESCRIPTION
				"TYPE: - Editstring
				 PAGE: - Ethernet
					Max 2  cmdID= 16820  "
		::= { iqh3aCmdEntry 16820 }


	iqh3aEthernetClientIPRangesMin3 OBJECT-TYPE
		SYNTAX		RollCallString
		MAX-ACCESS		read-write
		STATUS			current
		DESCRIPTION
				"TYPE: - Editstring
				 PAGE: - Ethernet
					Min 3  cmdID= 16813  "
		::= { iqh3aCmdEntry 16813 }


	iqh3aEthernetClientIPRangesMax3 OBJECT-TYPE
		SYNTAX		RollCallString
		MAX-ACCESS		read-write
		STATUS			current
		DESCRIPTION
				"TYPE: - Editstring
				 PAGE: - Ethernet
					Max 3  cmdID= 16821  "
		::= { iqh3aCmdEntry 16821 }


	iqh3aEthernetClientIPRangesMin4 OBJECT-TYPE
		SYNTAX		RollCallString
		MAX-ACCESS		read-write
		STATUS			current
		DESCRIPTION
				"TYPE: - Editstring
				 PAGE: - Ethernet
					Min 4  cmdID= 16814  "
		::= { iqh3aCmdEntry 16814 }


	iqh3aEthernetClientIPRangesMax4 OBJECT-TYPE
		SYNTAX		RollCallString
		MAX-ACCESS		read-write
		STATUS			current
		DESCRIPTION
				"TYPE: - Editstring
				 PAGE: - Ethernet
					Max 4  cmdID= 16822  "
		::= { iqh3aCmdEntry 16822 }


	iqh3aEthernetClientIPRangesMin5 OBJECT-TYPE
		SYNTAX		RollCallString
		MAX-ACCESS		read-write
		STATUS			current
		DESCRIPTION
				"TYPE: - Editstring
				 PAGE: - Ethernet
					Min 5  cmdID= 16815  "
		::= { iqh3aCmdEntry 16815 }


	iqh3aEthernetClientIPRangesMax5 OBJECT-TYPE
		SYNTAX		RollCallString
		MAX-ACCESS		read-write
		STATUS			current
		DESCRIPTION
				"TYPE: - Editstring
				 PAGE: - Ethernet
					Max 5  cmdID= 16823  "
		::= { iqh3aCmdEntry 16823 }


	iqh3aEthernetClientIPRangesMin6 OBJECT-TYPE
		SYNTAX		RollCallString
		MAX-ACCESS		read-write
		STATUS			current
		DESCRIPTION
				"TYPE: - Editstring
				 PAGE: - Ethernet
					Min 6  cmdID= 16816  "
		::= { iqh3aCmdEntry 16816 }


	iqh3aEthernetClientIPRangesMax6 OBJECT-TYPE
		SYNTAX		RollCallString
		MAX-ACCESS		read-write
		STATUS			current
		DESCRIPTION
				"TYPE: - Editstring
				 PAGE: - Ethernet
					Max 6  cmdID= 16824  "
		::= { iqh3aCmdEntry 16824 }


	iqh3aEthernetClientIPRangesMin7 OBJECT-TYPE
		SYNTAX		RollCallString
		MAX-ACCESS		read-write
		STATUS			current
		DESCRIPTION
				"TYPE: - Editstring
				 PAGE: - Ethernet
					Min 7  cmdID= 16817  "
		::= { iqh3aCmdEntry 16817 }


	iqh3aEthernetClientIPRangesMax7 OBJECT-TYPE
		SYNTAX		RollCallString
		MAX-ACCESS		read-write
		STATUS			current
		DESCRIPTION
				"TYPE: - Editstring
				 PAGE: - Ethernet
					Max 7  cmdID= 16825  "
		::= { iqh3aCmdEntry 16825 }


	iqh3aEthernetClientIPRangesMin8 OBJECT-TYPE
		SYNTAX		RollCallString
		MAX-ACCESS		read-write
		STATUS			current
		DESCRIPTION
				"TYPE: - Editstring
				 PAGE: - Ethernet
					Min 8  cmdID= 16818  "
		::= { iqh3aCmdEntry 16818 }


	iqh3aEthernetClientIPRangesMax8 OBJECT-TYPE
		SYNTAX		RollCallString
		MAX-ACCESS		read-write
		STATUS			current
		DESCRIPTION
				"TYPE: - Editstring
				 PAGE: - Ethernet
					Max 8  cmdID= 16826  "
		::= { iqh3aCmdEntry 16826 }


	iqh3aEthernetPassIAMIP OBJECT-TYPE
		SYNTAX		INTEGER { disable(0), enable(1) }
		MAX-ACCESS		read-write
		STATUS			current
		DESCRIPTION
				"TYPE: - Checkbox
				 PAGE: - Ethernet
					Pass I_AM (IP)  cmdID= 17050 "
		::= { iqh3aCmdEntry 17050 }


	iqh3aEthernetPassTimeIP OBJECT-TYPE
		SYNTAX		INTEGER { disable(0), enable(1) }
		MAX-ACCESS		read-write
		STATUS			current
		DESCRIPTION
				"TYPE: - Checkbox
				 PAGE: - Ethernet
					Pass Time (IP)  cmdID= 17051 "
		::= { iqh3aCmdEntry 17051 }


	iqh3aEthernetRollCallIPStatsRejectCount OBJECT-TYPE
		SYNTAX		RollCallString
		MAX-ACCESS		read-only
		STATUS			current
		DESCRIPTION
				"TYPE: - Display
				 PAGE: - Ethernet
					Reject Count  cmdID= 17021  format=   "
		::= { iqh3aCmdEntry 17021 }


	iqh3aEthernetRollCallIPStatsLastRejectClient OBJECT-TYPE
		SYNTAX		RollCallString
		MAX-ACCESS		read-only
		STATUS			current
		DESCRIPTION
				"TYPE: - Display
				 PAGE: - Ethernet
					Last Reject Client  cmdID= 17022  format=   "
		::= { iqh3aCmdEntry 17022 }


	iqh3aEthernetRollCallIPStatsClosedCount OBJECT-TYPE
		SYNTAX		RollCallString
		MAX-ACCESS		read-only
		STATUS			current
		DESCRIPTION
				"TYPE: - Display
				 PAGE: - Ethernet
					Closed Count  cmdID= 17023  format=   "
		::= { iqh3aCmdEntry 17023 }


	iqh3aEthernetRollCallIPStatsLastClosedClient OBJECT-TYPE
		SYNTAX		RollCallString
		MAX-ACCESS		read-only
		STATUS			current
		DESCRIPTION
				"TYPE: - Display
				 PAGE: - Ethernet
					Last Closed Client  cmdID= 17024  format=   "
		::= { iqh3aCmdEntry 17024 }


	iqh3aEthernetRollCallIPStatsConnection OBJECT-TYPE
		SYNTAX		INTEGER
		MAX-ACCESS		read-write
		STATUS			current
		DESCRIPTION
				"TYPE: - Number
				 PAGE: - Ethernet
					Connection  cmdID= 17010  min= 1  max= 32  step= 1  format= %.0f  div_scale= 1
					Min = 1  Max = 32  Step = 1 "
		::= { iqh3aCmdEntry 17010 }


	iqh3aEthernetRollCallIPStatsRollCallPort OBJECT-TYPE
		SYNTAX		RollCallString
		MAX-ACCESS		read-only
		STATUS			current
		DESCRIPTION
				"TYPE: - Display
				 PAGE: - Ethernet
					RollCall Port  cmdID= 17011  format=   "
		::= { iqh3aCmdEntry 17011 }


	iqh3aEthernetRollCallIPStatsName OBJECT-TYPE
		SYNTAX		RollCallString
		MAX-ACCESS		read-only
		STATUS			current
		DESCRIPTION
				"TYPE: - Display
				 PAGE: - Ethernet
					Name  cmdID= 17012  format=   "
		::= { iqh3aCmdEntry 17012 }


	iqh3aEthernetRollCallTCPStatsRemotePort OBJECT-TYPE
		SYNTAX		RollCallString
		MAX-ACCESS		read-only
		STATUS			current
		DESCRIPTION
				"TYPE: - Display
				 PAGE: - Ethernet
					Remote TCP Port of incoming connection cmdID= 17156  format=   "
		::= { iqh3aCmdEntry 17156 }


	iqh3aEthernetRollCallIPStatsAddr OBJECT-TYPE
		SYNTAX		RollCallString
		MAX-ACCESS		read-only
		STATUS			current
		DESCRIPTION
				"TYPE: - Display
				 PAGE: - Ethernet
					Addr  cmdID= 17013  format=   "
		::= { iqh3aCmdEntry 17013 }


	iqh3aEthernetRollCallIPStatsPacketsReceived OBJECT-TYPE
		SYNTAX		RollCallString
		MAX-ACCESS		read-only
		STATUS			current
		DESCRIPTION
				"TYPE: - Display
				 PAGE: - Ethernet
					Packets Received  cmdID= 17014  format=   "
		::= { iqh3aCmdEntry 17014 }


	iqh3aEthernetRollCallIPStatsPacketsSent OBJECT-TYPE
		SYNTAX		RollCallString
		MAX-ACCESS		read-only
		STATUS			current
		DESCRIPTION
				"TYPE: - Display
				 PAGE: - Ethernet
					Packets Sent  cmdID= 17015  format=   "
		::= { iqh3aCmdEntry 17015 }


	iqh3aEthernetRollCallIPStatsEverSentTime OBJECT-TYPE
		SYNTAX		RollCallString
		MAX-ACCESS		read-only
		STATUS			current
		DESCRIPTION
				"TYPE: - Display
				 PAGE: - Ethernet
					Ever Sent Time?  cmdID= 17016  format=   "
		::= { iqh3aCmdEntry 17016 }


	iqh3aEthernetRollCallIPStatsFullNetworkMap OBJECT-TYPE
		SYNTAX		RollCallString
		MAX-ACCESS		read-only
		STATUS			current
		DESCRIPTION
				"TYPE: - Display
				 PAGE: - Ethernet
					Full Network Map?  cmdID= 17242  format=   "
		::= { iqh3aCmdEntry 17242 }


	iqh3aEthernetRollCallIPStatsStartTime OBJECT-TYPE
		SYNTAX		RollCallString
		MAX-ACCESS		read-only
		STATUS			current
		DESCRIPTION
				"TYPE: - Display
				 PAGE: - Ethernet
					Start Time  cmdID= 17017  format=   "
		::= { iqh3aCmdEntry 17017 }


	iqh3aEthernetSNMPEnableSNMP OBJECT-TYPE
		SYNTAX		INTEGER { disable(0), enable(1) }
		MAX-ACCESS		read-write
		STATUS			current
		DESCRIPTION
				"TYPE: - Checkbox
				 PAGE: - Ethernet
					Enable SNMP  cmdID= 17005 "
		::= { iqh3aCmdEntry 17005 }


	iqh3aEthernetSNMPEnableLegacySNMP OBJECT-TYPE
		SYNTAX		INTEGER { disable(0), enable(1) }
		MAX-ACCESS		read-write
		STATUS			current
		DESCRIPTION
				"TYPE: - Checkbox
				 PAGE: - Ethernet
					Enable Legacy SNMP  cmdID= 17025 "
		::= { iqh3aCmdEntry 17025 }


	iqh3aEthernetSNMPReadcommunity OBJECT-TYPE
		SYNTAX		RollCallString
		MAX-ACCESS		read-write
		STATUS			current
		DESCRIPTION
				"TYPE: - Editstring
				 PAGE: - Ethernet
					Read community  cmdID= 16853  "
		::= { iqh3aCmdEntry 16853 }


	iqh3aEthernetSNMPWritecommunity OBJECT-TYPE
		SYNTAX		RollCallString
		MAX-ACCESS		read-write
		STATUS			current
		DESCRIPTION
				"TYPE: - Editstring
				 PAGE: - Ethernet
					Write community  cmdID= 16854  "
		::= { iqh3aCmdEntry 16854 }


	iqh3aEthernetSNMPMIB2sysContact OBJECT-TYPE
		SYNTAX		RollCallString
		MAX-ACCESS		read-write
		STATUS			current
		DESCRIPTION
				"TYPE: - Editstring
				 PAGE: - Ethernet
					MIB2 sysContact  cmdID= 16855  "
		::= { iqh3aCmdEntry 16855 }


	iqh3aEthernetSNMPMIB2sysName OBJECT-TYPE
		SYNTAX		RollCallString
		MAX-ACCESS		read-write
		STATUS			current
		DESCRIPTION
				"TYPE: - Editstring
				 PAGE: - Ethernet
					MIB2 sysName  cmdID= 16856  "
		::= { iqh3aCmdEntry 16856 }


	iqh3aEthernetSNMPMIB2sysLocation OBJECT-TYPE
		SYNTAX		RollCallString
		MAX-ACCESS		read-write
		STATUS			current
		DESCRIPTION
				"TYPE: - Editstring
				 PAGE: - Ethernet
					MIB2 sysLocation  cmdID= 16857  "
		::= { iqh3aCmdEntry 16857 }


	iqh3aEthernetSNMPReadWritePort OBJECT-TYPE
		SYNTAX		RollCallString
		MAX-ACCESS		read-write
		STATUS			current
		DESCRIPTION
				"TYPE: - Editstring
				 PAGE: - Ethernet
					Read Write Port  cmdID= 16860  "
		::= { iqh3aCmdEntry 16860 }


	iqh3aEthernetSNMPResendTraps OBJECT-TYPE
		SYNTAX		INTEGER { noAction(0),val-Resend-Traps(1) }
		MAX-ACCESS		read-write
		STATUS			current
		DESCRIPTION
				"TYPE: - Button
				 PAGE: - Ethernet
					Resend Traps  cmdID= 16890  value= 1  "
		::= { iqh3aCmdEntry 16890 }


	iqh3aSnmpTrapDest1IPaddr OBJECT-TYPE
		SYNTAX		RollCallString
		MAX-ACCESS		read-write
		STATUS			current
		DESCRIPTION
				"TYPE: - Editstring
				 PAGE: - Ethernet
					Trap dest IP addr  cmdID= 16850  "
		::= { iqh3aCmdEntry 16850 }


	iqh3aSnmpTrapDest1Port OBJECT-TYPE
		SYNTAX		RollCallString
		MAX-ACCESS		read-write
		STATUS			current
		DESCRIPTION
				"TYPE: - Editstring
				 PAGE: - Ethernet
					Trap dest port  cmdID= 16851  "
		::= { iqh3aCmdEntry 16851 }


	iqh3aSnmpTrapDest1Community OBJECT-TYPE
		SYNTAX		RollCallString
		MAX-ACCESS		read-write
		STATUS			current
		DESCRIPTION
				"TYPE: - Editstring
				 PAGE: - Ethernet
					Trap community  cmdID= 16852  "
		::= { iqh3aCmdEntry 16852 }


	iqh3aSnmpTrapDest2IPaddr OBJECT-TYPE
		SYNTAX		RollCallString
		MAX-ACCESS		read-write
		STATUS			current
		DESCRIPTION
				"TYPE: - Editstring
				 PAGE: - Ethernet
					Trap dest IP addr  cmdID= 16861  "
		::= { iqh3aCmdEntry 16861 }


	iqh3aSnmpTrapDest2Port OBJECT-TYPE
		SYNTAX		RollCallString
		MAX-ACCESS		read-write
		STATUS			current
		DESCRIPTION
				"TYPE: - Editstring
				 PAGE: - Ethernet
					Trap dest port  cmdID= 16862  "
		::= { iqh3aCmdEntry 16862 }


	iqh3aSnmpTrapDest2Community OBJECT-TYPE
		SYNTAX		RollCallString
		MAX-ACCESS		read-write
		STATUS			current
		DESCRIPTION
				"TYPE: - Editstring
				 PAGE: - Ethernet
					Trap community  cmdID= 16863  "
		::= { iqh3aCmdEntry 16863 }


	iqh3aSnmpTrapDest2EnableTrap OBJECT-TYPE
		SYNTAX		INTEGER { disable(0), enable(1) }
		MAX-ACCESS		read-write
		STATUS			current
		DESCRIPTION
				"TYPE: - Checkbox
				 PAGE: - Ethernet
					Enable Trap  cmdID= 16864 "
		::= { iqh3aCmdEntry 16864 }


	iqh3aSnmpTrapDest3IPaddr OBJECT-TYPE
		SYNTAX		RollCallString
		MAX-ACCESS		read-write
		STATUS			current
		DESCRIPTION
				"TYPE: - Editstring
				 PAGE: - Ethernet
					Trap dest IP addr  cmdID= 16865  "
		::= { iqh3aCmdEntry 16865 }


	iqh3aSnmpTrapDest3Port OBJECT-TYPE
		SYNTAX		RollCallString
		MAX-ACCESS		read-write
		STATUS			current
		DESCRIPTION
				"TYPE: - Editstring
				 PAGE: - Ethernet
					Trap dest port  cmdID= 16866  "
		::= { iqh3aCmdEntry 16866 }


	iqh3aSnmpTrapDest3Community OBJECT-TYPE
		SYNTAX		RollCallString
		MAX-ACCESS		read-write
		STATUS			current
		DESCRIPTION
				"TYPE: - Editstring
				 PAGE: - Ethernet
					Trap community  cmdID= 16867  "
		::= { iqh3aCmdEntry 16867 }


	iqh3aSnmpTrapDest3EnableTrap OBJECT-TYPE
		SYNTAX		INTEGER { disable(0), enable(1) }
		MAX-ACCESS		read-write
		STATUS			current
		DESCRIPTION
				"TYPE: - Checkbox
				 PAGE: - Ethernet
					Enable Trap  cmdID= 16868 "
		::= { iqh3aCmdEntry 16868 }


	iqh3aSnmpTrapDest4IPaddr OBJECT-TYPE
		SYNTAX		RollCallString
		MAX-ACCESS		read-write
		STATUS			current
		DESCRIPTION
				"TYPE: - Editstring
				 PAGE: - Ethernet
					Trap dest IP addr  cmdID= 16869  "
		::= { iqh3aCmdEntry 16869 }


	iqh3aSnmpTrapDest4Port OBJECT-TYPE
		SYNTAX		RollCallString
		MAX-ACCESS		read-write
		STATUS			current
		DESCRIPTION
				"TYPE: - Editstring
				 PAGE: - Ethernet
					Trap dest port  cmdID= 16870  "
		::= { iqh3aCmdEntry 16870 }


	iqh3aSnmpTrapDest4Community OBJECT-TYPE
		SYNTAX		RollCallString
		MAX-ACCESS		read-write
		STATUS			current
		DESCRIPTION
				"TYPE: - Editstring
				 PAGE: - Ethernet
					Trap community  cmdID= 16871  "
		::= { iqh3aCmdEntry 16871 }


	iqh3aSnmpTrapDest4EnableTrap OBJECT-TYPE
		SYNTAX		INTEGER { disable(0), enable(1) }
		MAX-ACCESS		read-write
		STATUS			current
		DESCRIPTION
				"TYPE: - Checkbox
				 PAGE: - Ethernet
					Enable Trap  cmdID= 16872 "
		::= { iqh3aCmdEntry 16872 }


	iqh3aSnmpTrapDest5IPaddr OBJECT-TYPE
		SYNTAX		RollCallString
		MAX-ACCESS		read-write
		STATUS			current
		DESCRIPTION
				"TYPE: - Editstring
				 PAGE: - Ethernet
					Trap dest IP addr  cmdID= 16873  "
		::= { iqh3aCmdEntry 16873 }


	iqh3aSnmpTrapDest5Port OBJECT-TYPE
		SYNTAX		RollCallString
		MAX-ACCESS		read-write
		STATUS			current
		DESCRIPTION
				"TYPE: - Editstring
				 PAGE: - Ethernet
					Trap dest port  cmdID= 16874  "
		::= { iqh3aCmdEntry 16874 }


	iqh3aSnmpTrapDest5Community OBJECT-TYPE
		SYNTAX		RollCallString
		MAX-ACCESS		read-write
		STATUS			current
		DESCRIPTION
				"TYPE: - Editstring
				 PAGE: - Ethernet
					Trap community  cmdID= 16875  "
		::= { iqh3aCmdEntry 16875 }


	iqh3aSnmpTrapDest5EnableTrap OBJECT-TYPE
		SYNTAX		INTEGER { disable(0), enable(1) }
		MAX-ACCESS		read-write
		STATUS			current
		DESCRIPTION
				"TYPE: - Checkbox
				 PAGE: - Ethernet
					Enable Trap  cmdID= 16876 "
		::= { iqh3aCmdEntry 16876 }


	iqh3aSnmpTrapDest6IPaddr OBJECT-TYPE
		SYNTAX		RollCallString
		MAX-ACCESS		read-write
		STATUS			current
		DESCRIPTION
				"TYPE: - Editstring
				 PAGE: - Ethernet
					Trap dest IP addr  cmdID= 16877  "
		::= { iqh3aCmdEntry 16877 }


	iqh3aSnmpTrapDest6Port OBJECT-TYPE
		SYNTAX		RollCallString
		MAX-ACCESS		read-write
		STATUS			current
		DESCRIPTION
				"TYPE: - Editstring
				 PAGE: - Ethernet
					Trap dest port  cmdID= 16878  "
		::= { iqh3aCmdEntry 16878 }


	iqh3aSnmpTrapDest6Community OBJECT-TYPE
		SYNTAX		RollCallString
		MAX-ACCESS		read-write
		STATUS			current
		DESCRIPTION
				"TYPE: - Editstring
				 PAGE: - Ethernet
					Trap community  cmdID= 16879  "
		::= { iqh3aCmdEntry 16879 }


	iqh3aSnmpTrapDest6EnableTrap OBJECT-TYPE
		SYNTAX		INTEGER { disable(0), enable(1) }
		MAX-ACCESS		read-write
		STATUS			current
		DESCRIPTION
				"TYPE: - Checkbox
				 PAGE: - Ethernet
					Enable Trap  cmdID= 16880 "
		::= { iqh3aCmdEntry 16880 }


	iqh3aSnmpTrapDest7IPaddr OBJECT-TYPE
		SYNTAX		RollCallString
		MAX-ACCESS		read-write
		STATUS			current
		DESCRIPTION
				"TYPE: - Editstring
				 PAGE: - Ethernet
					Trap dest IP addr  cmdID= 16881  "
		::= { iqh3aCmdEntry 16881 }


	iqh3aSnmpTrapDest7Port OBJECT-TYPE
		SYNTAX		RollCallString
		MAX-ACCESS		read-write
		STATUS			current
		DESCRIPTION
				"TYPE: - Editstring
				 PAGE: - Ethernet
					Trap dest port  cmdID= 16882  "
		::= { iqh3aCmdEntry 16882 }


	iqh3aSnmpTrapDest7Community OBJECT-TYPE
		SYNTAX		RollCallString
		MAX-ACCESS		read-write
		STATUS			current
		DESCRIPTION
				"TYPE: - Editstring
				 PAGE: - Ethernet
					Trap community  cmdID= 16883  "
		::= { iqh3aCmdEntry 16883 }


	iqh3aSnmpTrapDest7EnableTrap OBJECT-TYPE
		SYNTAX		INTEGER { disable(0), enable(1) }
		MAX-ACCESS		read-write
		STATUS			current
		DESCRIPTION
				"TYPE: - Checkbox
				 PAGE: - Ethernet
					Enable Trap  cmdID= 16884 "
		::= { iqh3aCmdEntry 16884 }


	iqh3aSnmpTrapDest8IPaddr OBJECT-TYPE
		SYNTAX		RollCallString
		MAX-ACCESS		read-write
		STATUS			current
		DESCRIPTION
				"TYPE: - Editstring
				 PAGE: - Ethernet
					Trap dest IP addr  cmdID= 16885  "
		::= { iqh3aCmdEntry 16885 }


	iqh3aSnmpTrapDest8Port OBJECT-TYPE
		SYNTAX		RollCallString
		MAX-ACCESS		read-write
		STATUS			current
		DESCRIPTION
				"TYPE: - Editstring
				 PAGE: - Ethernet
					Trap dest port  cmdID= 16886  "
		::= { iqh3aCmdEntry 16886 }


	iqh3aSnmpTrapDest8Community OBJECT-TYPE
		SYNTAX		RollCallString
		MAX-ACCESS		read-write
		STATUS			current
		DESCRIPTION
				"TYPE: - Editstring
				 PAGE: - Ethernet
					Trap community  cmdID= 16887  "
		::= { iqh3aCmdEntry 16887 }


	iqh3aSnmpTrapDest8EnableTrap OBJECT-TYPE
		SYNTAX		INTEGER { disable(0), enable(1) }
		MAX-ACCESS		read-write
		STATUS			current
		DESCRIPTION
				"TYPE: - Checkbox
				 PAGE: - Ethernet
					Enable Trap  cmdID= 16888 "
		::= { iqh3aCmdEntry 16888 }


	iqh3aTrapsSlotFilter0 OBJECT-TYPE
		SYNTAX		INTEGER { disable(0), enable(1) }
		MAX-ACCESS		read-write
		STATUS			current
		DESCRIPTION
				"TYPE: - Checkbox
				 PAGE: - Ethernet
					FilterSlot0  cmdID= 17065 "
		::= { iqh3aCmdEntry 17065 }


	iqh3aTrapsSlotFilter1 OBJECT-TYPE
		SYNTAX		INTEGER { disable(0), enable(1) }
		MAX-ACCESS		read-write
		STATUS			current
		DESCRIPTION
				"TYPE: - Checkbox
				 PAGE: - Ethernet
					FilterSlot1  cmdID= 17066 "
		::= { iqh3aCmdEntry 17066 }


	iqh3aTrapsSlotFilter2 OBJECT-TYPE
		SYNTAX		INTEGER { disable(0), enable(1) }
		MAX-ACCESS		read-write
		STATUS			current
		DESCRIPTION
				"TYPE: - Checkbox
				 PAGE: - Ethernet
					FilterSlot2  cmdID= 17067 "
		::= { iqh3aCmdEntry 17067 }


	iqh3aTrapsSlotFilter3 OBJECT-TYPE
		SYNTAX		INTEGER { disable(0), enable(1) }
		MAX-ACCESS		read-write
		STATUS			current
		DESCRIPTION
				"TYPE: - Checkbox
				 PAGE: - Ethernet
					FilterSlot3  cmdID= 17068 "
		::= { iqh3aCmdEntry 17068 }


	iqh3aTrapsSlotFilter4 OBJECT-TYPE
		SYNTAX		INTEGER { disable(0), enable(1) }
		MAX-ACCESS		read-write
		STATUS			current
		DESCRIPTION
				"TYPE: - Checkbox
				 PAGE: - Ethernet
					FilterSlot4  cmdID= 17069 "
		::= { iqh3aCmdEntry 17069 }


	iqh3aTrapsSlotFilter5 OBJECT-TYPE
		SYNTAX		INTEGER { disable(0), enable(1) }
		MAX-ACCESS		read-write
		STATUS			current
		DESCRIPTION
				"TYPE: - Checkbox
				 PAGE: - Ethernet
					FilterSlot5  cmdID= 17070 "
		::= { iqh3aCmdEntry 17070 }


	iqh3aTrapsSlotFilter6 OBJECT-TYPE
		SYNTAX		INTEGER { disable(0), enable(1) }
		MAX-ACCESS		read-write
		STATUS			current
		DESCRIPTION
				"TYPE: - Checkbox
				 PAGE: - Ethernet
					FilterSlot6  cmdID= 17071 "
		::= { iqh3aCmdEntry 17071 }


	iqh3aTrapsSlotFilter7 OBJECT-TYPE
		SYNTAX		INTEGER { disable(0), enable(1) }
		MAX-ACCESS		read-write
		STATUS			current
		DESCRIPTION
				"TYPE: - Checkbox
				 PAGE: - Ethernet
					FilterSlot7  cmdID= 17072 "
		::= { iqh3aCmdEntry 17072 }


	iqh3aTrapsSlotFilter8 OBJECT-TYPE
		SYNTAX		INTEGER { disable(0), enable(1) }
		MAX-ACCESS		read-write
		STATUS			current
		DESCRIPTION
				"TYPE: - Checkbox
				 PAGE: - Ethernet
					FilterSlot8  cmdID= 17073 "
		::= { iqh3aCmdEntry 17073 }


	iqh3aTrapsSlotFilter9 OBJECT-TYPE
		SYNTAX		INTEGER { disable(0), enable(1) }
		MAX-ACCESS		read-write
		STATUS			current
		DESCRIPTION
				"TYPE: - Checkbox
				 PAGE: - Ethernet
					FilterSlot9  cmdID= 17074 "
		::= { iqh3aCmdEntry 17074 }


	iqh3aTrapsSlotFilter10 OBJECT-TYPE
		SYNTAX		INTEGER { disable(0), enable(1) }
		MAX-ACCESS		read-write
		STATUS			current
		DESCRIPTION
				"TYPE: - Checkbox
				 PAGE: - Ethernet
					FilterSlot10  cmdID= 17075 "
		::= { iqh3aCmdEntry 17075 }


	iqh3aTrapsSlotFilter11 OBJECT-TYPE
		SYNTAX		INTEGER { disable(0), enable(1) }
		MAX-ACCESS		read-write
		STATUS			current
		DESCRIPTION
				"TYPE: - Checkbox
				 PAGE: - Ethernet
					FilterSlot11  cmdID= 17076 "
		::= { iqh3aCmdEntry 17076 }


	iqh3aTrapsSlotFilter12 OBJECT-TYPE
		SYNTAX		INTEGER { disable(0), enable(1) }
		MAX-ACCESS		read-write
		STATUS			current
		DESCRIPTION
				"TYPE: - Checkbox
				 PAGE: - Ethernet
					FilterSlot12  cmdID= 17077 "
		::= { iqh3aCmdEntry 17077 }


	iqh3aTrapsSlotFilter13 OBJECT-TYPE
		SYNTAX		INTEGER { disable(0), enable(1) }
		MAX-ACCESS		read-write
		STATUS			current
		DESCRIPTION
				"TYPE: - Checkbox
				 PAGE: - Ethernet
					FilterSlot13  cmdID= 17078 "
		::= { iqh3aCmdEntry 17078 }


	iqh3aTrapsSlotFilter14 OBJECT-TYPE
		SYNTAX		INTEGER { disable(0), enable(1) }
		MAX-ACCESS		read-write
		STATUS			current
		DESCRIPTION
				"TYPE: - Checkbox
				 PAGE: - Ethernet
					FilterSlot14  cmdID= 17079 "
		::= { iqh3aCmdEntry 17079 }


	iqh3aTrapsSlotFilter15 OBJECT-TYPE
		SYNTAX		INTEGER { disable(0), enable(1) }
		MAX-ACCESS		read-write
		STATUS			current
		DESCRIPTION
				"TYPE: - Checkbox
				 PAGE: - Ethernet
					FilterSlot15  cmdID= 17080 "
		::= { iqh3aCmdEntry 17080 }


	iqh3aTrapsSlotFilter16 OBJECT-TYPE
		SYNTAX		INTEGER { disable(0), enable(1) }
		MAX-ACCESS		read-write
		STATUS			current
		DESCRIPTION
				"TYPE: - Checkbox
				 PAGE: - Ethernet
					FilterSlot16  cmdID= 17081 "
		::= { iqh3aCmdEntry 17081 }


	iqh3aTrapsControlSlot0 OBJECT-TYPE
		SYNTAX		INTEGER { disable(0), enable(1) }
		MAX-ACCESS		read-write
		STATUS			current
		DESCRIPTION
				"TYPE: - Checkbox
				 PAGE: - Ethernet
					ControlSlot0  cmdID= 17082 "
		::= { iqh3aCmdEntry 17082 }


	iqh3aTrapsControlSlot1 OBJECT-TYPE
		SYNTAX		INTEGER { disable(0), enable(1) }
		MAX-ACCESS		read-write
		STATUS			current
		DESCRIPTION
				"TYPE: - Checkbox
				 PAGE: - Ethernet
					ControlSlot1  cmdID= 17083 "
		::= { iqh3aCmdEntry 17083 }


	iqh3aTrapsControlSlot2 OBJECT-TYPE
		SYNTAX		INTEGER { disable(0), enable(1) }
		MAX-ACCESS		read-write
		STATUS			current
		DESCRIPTION
				"TYPE: - Checkbox
				 PAGE: - Ethernet
					ControlSlot2  cmdID= 17084 "
		::= { iqh3aCmdEntry 17084 }


	iqh3aTrapsControlSlot3 OBJECT-TYPE
		SYNTAX		INTEGER { disable(0), enable(1) }
		MAX-ACCESS		read-write
		STATUS			current
		DESCRIPTION
				"TYPE: - Checkbox
				 PAGE: - Ethernet
					ControlSlot3  cmdID= 17085 "
		::= { iqh3aCmdEntry 17085 }


	iqh3aTrapsControlSlot4 OBJECT-TYPE
		SYNTAX		INTEGER { disable(0), enable(1) }
		MAX-ACCESS		read-write
		STATUS			current
		DESCRIPTION
				"TYPE: - Checkbox
				 PAGE: - Ethernet
					ControlSlot4  cmdID= 17086 "
		::= { iqh3aCmdEntry 17086 }


	iqh3aTrapsControlSlot5 OBJECT-TYPE
		SYNTAX		INTEGER { disable(0), enable(1) }
		MAX-ACCESS		read-write
		STATUS			current
		DESCRIPTION
				"TYPE: - Checkbox
				 PAGE: - Ethernet
					ControlSlot5  cmdID= 17087 "
		::= { iqh3aCmdEntry 17087 }


	iqh3aTrapsControlSlot6 OBJECT-TYPE
		SYNTAX		INTEGER { disable(0), enable(1) }
		MAX-ACCESS		read-write
		STATUS			current
		DESCRIPTION
				"TYPE: - Checkbox
				 PAGE: - Ethernet
					ControlSlot6  cmdID= 17088 "
		::= { iqh3aCmdEntry 17088 }


	iqh3aTrapsControlSlot7 OBJECT-TYPE
		SYNTAX		INTEGER { disable(0), enable(1) }
		MAX-ACCESS		read-write
		STATUS			current
		DESCRIPTION
				"TYPE: - Checkbox
				 PAGE: - Ethernet
					ControlSlot7  cmdID= 17089 "
		::= { iqh3aCmdEntry 17089 }


	iqh3aTrapsControlSlot8 OBJECT-TYPE
		SYNTAX		INTEGER { disable(0), enable(1) }
		MAX-ACCESS		read-write
		STATUS			current
		DESCRIPTION
				"TYPE: - Checkbox
				 PAGE: - Ethernet
					ControlSlot8  cmdID= 17090 "
		::= { iqh3aCmdEntry 17090 }


	iqh3aTrapsControlSlot9 OBJECT-TYPE
		SYNTAX		INTEGER { disable(0), enable(1) }
		MAX-ACCESS		read-write
		STATUS			current
		DESCRIPTION
				"TYPE: - Checkbox
				 PAGE: - Ethernet
					ControlSlot9  cmdID= 17091 "
		::= { iqh3aCmdEntry 17091 }


	iqh3aTrapsControlSlot10 OBJECT-TYPE
		SYNTAX		INTEGER { disable(0), enable(1) }
		MAX-ACCESS		read-write
		STATUS			current
		DESCRIPTION
				"TYPE: - Checkbox
				 PAGE: - Ethernet
					ControlSlot10  cmdID= 17092 "
		::= { iqh3aCmdEntry 17092 }


	iqh3aTrapsControlSlot11 OBJECT-TYPE
		SYNTAX		INTEGER { disable(0), enable(1) }
		MAX-ACCESS		read-write
		STATUS			current
		DESCRIPTION
				"TYPE: - Checkbox
				 PAGE: - Ethernet
					ControlSlot11  cmdID= 17093 "
		::= { iqh3aCmdEntry 17093 }


	iqh3aTrapsControlSlot12 OBJECT-TYPE
		SYNTAX		INTEGER { disable(0), enable(1) }
		MAX-ACCESS		read-write
		STATUS			current
		DESCRIPTION
				"TYPE: - Checkbox
				 PAGE: - Ethernet
					ControlSlot12  cmdID= 17094 "
		::= { iqh3aCmdEntry 17094 }


	iqh3aTrapsControlSlot13 OBJECT-TYPE
		SYNTAX		INTEGER { disable(0), enable(1) }
		MAX-ACCESS		read-write
		STATUS			current
		DESCRIPTION
				"TYPE: - Checkbox
				 PAGE: - Ethernet
					ControlSlot13  cmdID= 17095 "
		::= { iqh3aCmdEntry 17095 }


	iqh3aTrapsControlSlot14 OBJECT-TYPE
		SYNTAX		INTEGER { disable(0), enable(1) }
		MAX-ACCESS		read-write
		STATUS			current
		DESCRIPTION
				"TYPE: - Checkbox
				 PAGE: - Ethernet
					ControlSlot14  cmdID= 17096 "
		::= { iqh3aCmdEntry 17096 }


	iqh3aTrapsControlSlot15 OBJECT-TYPE
		SYNTAX		INTEGER { disable(0), enable(1) }
		MAX-ACCESS		read-write
		STATUS			current
		DESCRIPTION
				"TYPE: - Checkbox
				 PAGE: - Ethernet
					ControlSlot15  cmdID= 17097 "
		::= { iqh3aCmdEntry 17097 }


	iqh3aTrapsControlSlot16 OBJECT-TYPE
		SYNTAX		INTEGER { disable(0), enable(1) }
		MAX-ACCESS		read-write
		STATUS			current
		DESCRIPTION
				"TYPE: - Checkbox
				 PAGE: - Ethernet
					ControlSlot16  cmdID= 17098 "
		::= { iqh3aCmdEntry 17098 }


	iqh3aEthernetIPBridgeIPAddr OBJECT-TYPE
		SYNTAX		RollCallString
		MAX-ACCESS		read-write
		STATUS			current
		DESCRIPTION
				"TYPE: - Editstring
				 PAGE: - Ethernet
					Bridge IP Addr  cmdID= 17030  "
		::= { iqh3aCmdEntry 17030 }


	iqh3aEthernetIPBridgeIPAddrAlt OBJECT-TYPE
		SYNTAX		RollCallString
		MAX-ACCESS		read-write
		STATUS			current
		DESCRIPTION
				"TYPE: - Editstring
				 PAGE: - Ethernet
					Bridge IP Addr Alt  cmdID= 17038  "
		::= { iqh3aCmdEntry 17038 }


	iqh3aEthernetIPBridgeAltBridge OBJECT-TYPE
		SYNTAX		INTEGER { disable(0), enable(1) }
		MAX-ACCESS		read-write
		STATUS			current
		DESCRIPTION
				"TYPE: - Checkbox
				 PAGE: - Ethernet
					Alt Bridge  cmdID= 17039 "
		::= { iqh3aCmdEntry 17039 }


	iqh3aEthernetIPBridgeIPPort OBJECT-TYPE
		SYNTAX		RollCallString
		MAX-ACCESS		read-write
		STATUS			current
		DESCRIPTION
				"TYPE: - Editstring
				 PAGE: - Ethernet
					Bridge IP Port  cmdID= 17031  "
		::= { iqh3aCmdEntry 17031 }


	iqh3aEthernetIPBridgeOnlythisAddr OBJECT-TYPE
		SYNTAX		INTEGER { disable(0), enable(1) }
		MAX-ACCESS		read-write
		STATUS			current
		DESCRIPTION
				"TYPE: - Checkbox
				 PAGE: - Ethernet
					Only this Addr  cmdID= 17035 "
		::= { iqh3aCmdEntry 17035 }


	iqh3aEthernetIPBridgePriority OBJECT-TYPE
		SYNTAX		INTEGER { disable(0), enable(1) }
		MAX-ACCESS		read-write
		STATUS			current
		DESCRIPTION
				"TYPE: - Checkbox
				 PAGE: - Ethernet
					Priority  cmdID= 17059 "
		::= { iqh3aCmdEntry 17059 }


	iqh3aEthernetIPBridgePassIAMBridge OBJECT-TYPE
		SYNTAX		INTEGER { disable(0), enable(1) }
		MAX-ACCESS		read-write
		STATUS			current
		DESCRIPTION
				"TYPE: - Checkbox
				 PAGE: - Ethernet
					Pass I_AM (Bridge)  cmdID= 17056 "
		::= { iqh3aCmdEntry 17056 }


	iqh3aEthernetIPBridgePassTimeBridge OBJECT-TYPE
		SYNTAX		INTEGER { disable(0), enable(1) }
		MAX-ACCESS		read-write
		STATUS			current
		DESCRIPTION
				"TYPE: - Checkbox
				 PAGE: - Ethernet
					Pass Time (Bridge)  cmdID= 17057 "
		::= { iqh3aCmdEntry 17057 }


	iqh3aEthernetIPBridgeCtrlOnlyBridge OBJECT-TYPE
		SYNTAX		INTEGER { disable(0), enable(1) }
		MAX-ACCESS		read-write
		STATUS			current
		DESCRIPTION
				"TYPE: - Checkbox
				 PAGE: - Ethernet
					Ctrl Only (Bridge)  cmdID= 17058 "
		::= { iqh3aCmdEntry 17058 }


	iqh3aEthernetIPBridgeConnect OBJECT-TYPE
		SYNTAX		INTEGER { noAction(0),val-Connect(1) }
		MAX-ACCESS		read-write
		STATUS			current
		DESCRIPTION
				"TYPE: - Button
				 PAGE: - Ethernet
					Connect  cmdID= 17032  value= 1  "
		::= { iqh3aCmdEntry 17032 }


	iqh3aEthernetIPBridgeDisconnect OBJECT-TYPE
		SYNTAX		INTEGER { noAction(0),val-Disconnect(1) }
		MAX-ACCESS		read-write
		STATUS			current
		DESCRIPTION
				"TYPE: - Button
				 PAGE: - Ethernet
					Disconnect  cmdID= 17033  value= 1  "
		::= { iqh3aCmdEntry 17033 }


	iqh3aEthernetIPBridgeAutoConnect OBJECT-TYPE
		SYNTAX		INTEGER { disable(0), enable(1) }
		MAX-ACCESS		read-write
		STATUS			current
		DESCRIPTION
				"TYPE: - Checkbox
				 PAGE: - Ethernet
					Auto Connect  cmdID= 17034 "
		::= { iqh3aCmdEntry 17034 }


	iqh3aEthernetIPBridgeAddr OBJECT-TYPE
		SYNTAX		RollCallString
		MAX-ACCESS		read-only
		STATUS			current
		DESCRIPTION
				"TYPE: - Display
				 PAGE: - Ethernet
					Addr  cmdID= 17040  format=   "
		::= { iqh3aCmdEntry 17040 }


	iqh3aEthernetIPBridgePacketsReceived OBJECT-TYPE
		SYNTAX		RollCallString
		MAX-ACCESS		read-only
		STATUS			current
		DESCRIPTION
				"TYPE: - Display
				 PAGE: - Ethernet
					Packets Received  cmdID= 17041  format=   "
		::= { iqh3aCmdEntry 17041 }


	iqh3aEthernetIPBridgePacketsSent OBJECT-TYPE
		SYNTAX		RollCallString
		MAX-ACCESS		read-only
		STATUS			current
		DESCRIPTION
				"TYPE: - Display
				 PAGE: - Ethernet
					Packets Sent  cmdID= 17042  format=   "
		::= { iqh3aCmdEntry 17042 }


	iqh3aEthernetIPBridgeStartTime OBJECT-TYPE
		SYNTAX		RollCallString
		MAX-ACCESS		read-only
		STATUS			current
		DESCRIPTION
				"TYPE: - Display
				 PAGE: - Ethernet
					Start Time  cmdID= 17043  format=   "
		::= { iqh3aCmdEntry 17043 }


	iqh3aEthernetIPBridgeStartedBy OBJECT-TYPE
		SYNTAX		RollCallString
		MAX-ACCESS		read-only
		STATUS			current
		DESCRIPTION
				"TYPE: - Display
				 PAGE: - Ethernet
					Started By  cmdID= 17044  format=   "
		::= { iqh3aCmdEntry 17044 }


	iqh3aEthernetIPBridgeLogging OBJECT-TYPE
		SYNTAX		INTEGER { disable(0), enable(1) }
		MAX-ACCESS		read-write
		STATUS			current
		DESCRIPTION
				"TYPE: - Checkbox
				 PAGE: - Ethernet
					Bridge Logging  cmdID= 17036 "
		::= { iqh3aCmdEntry 17036 }
END
---------------------------------------------------------------------------------------------------
--  Logging
--  (HEADER=VALUE)
--  Logging values are stored in the swGatewayEventLogTable, swGatewayEventLogField represents the
--  table entry.  The indexing of the table works using the log header string. For example if the
--  header is "FAULT", the index OID starts with the length of the header ie 5, followed by the
--  ASCII values for each letter 70 65 85 76 84.
--  Index for "FAULT" .5.70.65.85.76.84
--  To OID for FAULT on slot 12 for swGatewayEventLogTable is 1.3.6.1.4.1.7995.2.6.2.1.1. 5.  70.65.85.76.84
--                                                         |       base                |Len| F  A  U  L  T|
--  An SNMP GET on this OID will return the Log value associated with FAULT for gateway eg "NONE" (FAULT=NONE)
--
---------------------------------------------------------------------------------------------------
-- Header		: SN
--
-- MIB ref		: swGatewayEventLogField  .2.83.78
-- absolute OID	: 1.3.6.1.4.1.7995.2.6.2.1.1.2.83.78
-- Vary			: NO
--
-- Value(s)		: S35063213
--				:
-- Comments		: Serial Number, Alpha-numberic string
--
---------------------------------------------------------------------------------------------------
-- Header		: FAULT
--
-- MIB ref		: swGatewayEventLogField  .5.70.65.85.76.84
-- absolute OID	: 1.3.6.1.4.1.7995.2.6.2.1.1.5.70.65.85.76.84
-- Vary			: YES
--
-- Value(s)		: None
--              : FAIL:MODULE_COMMS
-- Comments		:
--              : FAIL:MODULE_COMMS, backplane comms severely errored, receiver now disabled.
--
---------------------------------------------------------------------------------------------------
-- Header		: UPTIME
--
-- MIB ref		: swGatewayEventLogField  .6.85.80.84.73.77.69
-- absolute OID	: 1.3.6.1.4.1.7995.2.6.2.1.1.6.85.80.84.73.77.69
-- Vary			: YES
--
-- Value(s)		: 000:00:02:00
--				:
-- Comments		: System uptime, updated at regular intervals (60sec), format ddd:hh:mm:ss
--              : ddd=days, hh=hours, mm=minutes, ss=seconds
--
---------------------------------------------------------------------------------------------------
-- Header		: VERSION
--
-- MIB ref		: swGatewayEventLogField  .7.86.69.82.83.73.79.78
-- absolute OID	: 1.3.6.1.4.1.7995.2.6.2.1.1.7.86.69.82.83.73.79.78
-- Vary			: NO
--
-- Value(s)		: 5.11 .14
--				:
-- Comments		: Version ID, software version, alpha-numeric string
--
---------------------------------------------------------------------------------------------------
-- Header		: IP_EVENT
--
-- MIB ref		: swGatewayEventLogField  .8.73.80.95.69.86.69.78.84
-- absolute OID	: 1.3.6.1.4.1.7995.2.6.2.1.1.8.73.80.95.69.86.69.78.84
-- Vary			: YES
--
-- Value(s)		: 172.19.78.45 CONNECT FROM
--				: nnn.nnn.nnn.nnn CONNECT FROM
--				: nnn.nnn.nnn.nnn DISCONNECT FROM
--				: nnn.nnn.nnn.nnn BRIDGE CONNECT FROM
--				: nnn.nnn.nnn.nnn BRIDGE CONNECT TO
-- Comments		: Eg 172.19.23.1 CONNECT FROM
--              : Status log message only, signifying connection to or from a remote IP address.
--
---------------------------------------------------------------------------------------------------
-- Header		: LOCATION
--
-- MIB ref		: swGatewayEventLogField  .8.76.79.67.65.84.73.79.78
-- absolute OID	: 1.3.6.1.4.1.7995.2.6.2.1.1.8.76.79.67.65.84.73.79.78
-- Vary			: YES
--
-- Value(s)		: Unknown
--				:
-- Comments		: String value denoting SNMP location.
--
---------------------------------------------------------------------------------------------------
-- Header		: SESSIONS
--
-- MIB ref		: swGatewayEventLogField  .8.83.69.83.83.73.79.78.83
-- absolute OID	: 1.3.6.1.4.1.7995.2.6.2.1.1.8.83.69.83.83.73.79.78.83
-- Vary			: YES
--
-- Value(s)		: 1
--
--
---------------------------------------------------------------------------------------------------
--
-- Header		: ENCLOSURE
--
-- MIB ref		: swGatewayEventLogField  .9.69.78.67.76.79.83.85.82.69
-- absolute OID	: 1.3.6.1.4.1.7995.2.6.2.1.1.9.69.78.67.76.79.83.85.82.69
-- Vary			: YES
--
-- Value(s)		: IQH3A
--				: 
-- Comments		: 
--
---------------------------------------------------------------------------------------------------
-- Header		: IPADDRESS
--
-- MIB ref		: swGatewayEventLogField  .9.73.80.65.68.68.82.69.83.83
-- absolute OID	: 1.3.6.1.4.1.7995.2.6.2.1.1.9.73.80.65.68.68.82.69.83.83
-- Vary			: YES
--
-- Value(s)		: 172.19.81.24
--				: 
-- Comments		: IP address of unit nnn.nnn.nnn.nnn  0 <= nnn <=255
--
---------------------------------------------------------------------------------------------------
-- Header		: POWER_MAX
--
-- MIB ref		: swGatewayEventLogField  .9.80.79.87.69.82.95.77.65.88
-- absolute OID	: 1.3.6.1.4.1.7995.2.6.2.1.1.9.80.79.87.69.82.95.77.65.88
-- Vary			: YES
--
-- Value(s)		: 141W  165LU  100LU (Quiet)
--				: 
-- Comments		: Maximum rated power
--
---------------------------------------------------------------------------------------------------
-- Header		: SNMP_NAME
--
-- MIB ref		: swGatewayEventLogField  .9.83.78.77.80.95.78.65.77.69
-- absolute OID	: 1.3.6.1.4.1.7995.2.6.2.1.1.9.83.78.77.80.95.78.65.77.69
-- Vary			: YES
--
-- Value(s)		: System Name
--				: 
-- Comments		: String value of SNMP name of unit
--
---------------------------------------------------------------------------------------------------
-- Header		: FAN_1_NAME
--
-- MIB ref		: swGatewayEventLogField  .10.70.65.78.95.49.95.78.65.77.69
-- absolute OID	: 1.3.6.1.4.1.7995.2.6.2.1.1.10.70.65.78.95.49.95.78.65.77.69
-- Vary			: YES
--
-- Value(s)		: Rear Fan1
--				: 
-- Comments		: 
--
---------------------------------------------------------------------------------------------------
-- Header		: FAN_2_NAME
--
-- MIB ref		: swGatewayEventLogField  .10.70.65.78.95.50.95.78.65.77.69
-- absolute OID	: 1.3.6.1.4.1.7995.2.6.2.1.1.10.70.65.78.95.50.95.78.65.77.69
-- Vary			: YES
--
-- Value(s)		: Rear Fan2
--				: 
-- Comments		: 
--
---------------------------------------------------------------------------------------------------
-- Header		: OS_VERSION
--
-- MIB ref		: swGatewayEventLogField  .10.79.83.95.86.69.82.83.73.79.78
-- absolute OID	: 1.3.6.1.4.1.7995.2.6.2.1.1.10.79.83.95.86.69.82.83.73.79.78
-- Vary			: YES
--
-- Value(s)		: V115 Release
--				:
-- Comments		: Operating System Version ID
--
---------------------------------------------------------------------------------------------------
-- Header		: PSU_1_NAME
--
-- MIB ref		: swGatewayEventLogField  .10.80.83.85.95.49.95.78.65.77.69
-- absolute OID	: 1.3.6.1.4.1.7995.2.6.2.1.1.10.80.83.85.95.49.95.78.65.77.69
-- Vary			: YES
--
-- Value(s)		: Left PSU
--				: 
-- Comments		: Assigned name of 1st Power Supply Unit
--
---------------------------------------------------------------------------------------------------
-- Header		: PSU_2_NAME
--
-- MIB ref		: swGatewayEventLogField  .10.80.83.85.95.50.95.78.65.77.69
-- absolute OID	: 1.3.6.1.4.1.7995.2.6.2.1.1.10.80.83.85.95.50.95.78.65.77.69
-- Vary			: YES
--
-- Value(s)		: Right PSU
--				: 
-- Comments		: Assigned name of 2nd Power Supply Unit
--
---------------------------------------------------------------------------------------------------
-- Header		: FAN_1_STATE
--
-- MIB ref		: swGatewayEventLogField  .11.70.65.78.95.49.95.83.84.65.84.69
-- absolute OID	: 1.3.6.1.4.1.7995.2.6.2.1.1.11.70.65.78.95.49.95.83.84.65.84.69
-- Vary			: YES
--
-- Value(s)		: OK:Low
--				: 
-- Comments		: 
--
---------------------------------------------------------------------------------------------------
-- Header		: FAN_2_STATE
--
-- MIB ref		: swGatewayEventLogField  .11.70.65.78.95.50.95.83.84.65.84.69
-- absolute OID	: 1.3.6.1.4.1.7995.2.6.2.1.1.11.70.65.78.95.50.95.83.84.65.84.69
-- Vary			: YES
--
-- Value(s)		: Not Used
--				: 
-- Comments		: 2nd fan used in IQH3B frame
--
---------------------------------------------------------------------------------------------------
-- Header		: POWER_CHECK
--
-- MIB ref		: swGatewayEventLogField  .11.80.79.87.69.82.95.67.72.69.67.75
-- absolute OID	: 1.3.6.1.4.1.7995.2.6.2.1.1.11.80.79.87.69.82.95.67.72.69.67.75
-- Vary			: YES
--
-- Value(s)		: OK
--				: 
-- Comments		: 
--
---------------------------------------------------------------------------------------------------
-- Header		: POWER_USAGE
--
-- MIB ref		: swGatewayEventLogField  .11.80.79.87.69.82.95.85.83.65.71.69
-- absolute OID	: 1.3.6.1.4.1.7995.2.6.2.1.1.11.80.79.87.69.82.95.85.83.65.71.69
-- Vary			: YES
--
-- Value(s)		: OK:23W
--				: 
-- Comments		: 
--
---------------------------------------------------------------------------------------------------
-- Header		: PSU_1_STATE
--
-- MIB ref		: swGatewayEventLogField  .11.80.83.85.95.49.95.83.84.65.84.69
-- absolute OID	: 1.3.6.1.4.1.7995.2.6.2.1.1.11.80.83.85.95.49.95.83.84.65.84.69
-- Vary			: YES
--
-- Value(s)		: OK
--				: FAIL
--              : FAIL:Not Fitted
--              : Not Used
-- Comments		: State of 1st PSU
--
---------------------------------------------------------------------------------------------------
-- Header		: PSU_2_STATE
--
-- MIB ref		: swGatewayEventLogField  .11.80.83.85.95.50.95.83.84.65.84.69
-- absolute OID	: 1.3.6.1.4.1.7995.2.6.2.1.1.11.80.83.85.95.50.95.83.84.65.84.69
-- Vary			: YES
--
-- Value(s)		: OK
--				: FAIL
--              : FAIL:Not Fitted
--              : Not Used
-- Comments		: State of 2nd PSU
--
---------------------------------------------------------------------------------------------------
-- Header		: RECON_STATE
--
-- MIB ref		: swGatewayEventLogField  .11.82.69.67.79.78.95.83.84.65.84.69
-- absolute OID	: 1.3.6.1.4.1.7995.2.6.2.1.1.11.82.69.67.79.78.95.83.84.65.84.69
-- Vary			: YES
--
-- Value(s)		: OK
--				: WARN
--              : FAIL
-- Comments		: OK:   0  rollnet recons in last 10 seconds
--              : WARN: 1  rollnet recon  in last 10 seconds
--              : FAIL: >1 rollnet recons in last 10 seconds
---------------------------------------------------------------------------------------------------
-- Header		: TEMP_1_NAME
--
-- MIB ref		: swGatewayEventLogField  .11.84.69.77.80.95.49.95.78.65.77.69
-- absolute OID	: 1.3.6.1.4.1.7995.2.6.2.1.1.11.84.69.77.80.95.49.95.78.65.77.69
-- Vary			: NO
--
-- Value(s)		: Temperature In
--				:
-- Comments		: Assigned name of 1st Temperature monitor
--
---------------------------------------------------------------------------------------------------
-- Header		: TEMP_2_NAME
--
-- MIB ref		: swGatewayEventLogField  .11.84.69.77.80.95.50.95.78.65.77.69
-- absolute OID	: 1.3.6.1.4.1.7995.2.6.2.1.1.11.84.69.77.80.95.50.95.78.65.77.69
-- Vary			: NO
--
-- Value(s)		: Temperature Out
--				:
-- Comments		: Assigned name of 2nd Temperature monitor
--
---------------------------------------------------------------------------------------------------
-- Header		: BUILD_NUMBER
--
-- MIB ref		: swGatewayEventLogField  .12.66.85.73.76.68.95.78.85.77.66.69.82
-- absolute OID	: 1.3.6.1.4.1.7995.2.6.2.1.1.12.66.85.73.76.68.95.78.85.77.66.69.82
-- Vary			: YES
--
-- Value(s)		: 0213404719
--				: 
-- Comments		: Engineering assigned build number (from CVS) of application code
--
---------------------------------------------------------------------------------------------------
-- Header		: INFORMATION1
--
-- MIB ref		: swGatewayEventLogField  .12.73.78.70.79.82.77.65.84.73.79.78.49
-- absolute OID	: 1.3.6.1.4.1.7995.2.6.2.1.1.12.73.78.70.79.82.77.65.84.73.79.78.49
-- Vary			: YES
--
-- Value(s)		: INFO1 TEXT FIELD
--				: Any 19 char string
-- Comments		: User defined field 1.  If edit field is empty this is not logged
--
---------------------------------------------------------------------------------------------------
-- Header		: INFORMATION2
--
-- MIB ref		: swGatewayEventLogField  .12.73.78.70.79.82.77.65.84.73.79.78.50
-- absolute OID	: 1.3.6.1.4.1.7995.2.6.2.1.1.12.73.78.70.79.82.77.65.84.73.79.78.50
-- Vary			: YES
--
-- Value(s)		: INFO2 TEXT FIELD
--				: Any 19 char string
-- Comments		: User defined field 2.  If edit field is empty this is not logged
--
---------------------------------------------------------------------------------------------------
-- Header		: MODULE_COMMS
--
-- MIB ref		: swGatewayEventLogField  .12.77.79.68.85.76.69.95.67.79.77.77.83
-- absolute OID	: 1.3.6.1.4.1.7995.2.6.2.1.1.12.77.79.68.85.76.69.95.67.79.77.77.83
-- Vary			: YES
--
-- Value(s)		: 0
--				: n
-- Comments		: n >= 0, Number of I2C packet errors. Number reset when all statistics are reset
--
---------------------------------------------------------------------------------------------------
-- Header		: RESTARTED_AT
--
-- MIB ref		: swGatewayEventLogField  .12.82.69.83.84.65.82.84.69.68.95.65.84
-- absolute OID	: 1.3.6.1.4.1.7995.2.6.2.1.1.12.82.69.83.84.65.82.84.69.68.95.65.84
-- Vary			: YES
--
-- Value(s)		: 2014-02-26T11:46:23Z
--				: 
-- Comments		: UTC time and date of box restart  ISO standardised
--
---------------------------------------------------------------------------------------------------
-- Header		: TEMP_1_STATE
--
-- MIB ref		: swGatewayEventLogField  .12.84.69.77.80.95.49.95.83.84.65.84.69
-- absolute OID	: 1.3.6.1.4.1.7995.2.6.2.1.1.12.84.69.77.80.95.49.95.83.84.65.84.69
-- Vary			: YES
--
-- Value(s)		: OK
--				: WARN:Low
--              : WARN:High
--              : FAIL:Low
--              : FAIL:High
--              : FAIL:Sensor Fault
-- Comments		: State of 1st Temperature monitor (In)
--              : OK Range    5C - 35C
--              : WARN:Low    0C -  5C
--              : WARN:High  35C - 40C
--              : FAIL:Low   < 0C
--              : FAIL:High  > 40C
--              : Note absolute values may vary in future releases, values are approximate
---------------------------------------------------------------------------------------------------
-- Header		: TEMP_2_STATE
--
-- MIB ref		: swGatewayEventLogField  .12.84.69.77.80.95.50.95.83.84.65.84.69
-- absolute OID	: 1.3.6.1.4.1.7995.2.6.2.1.1.12.84.69.77.80.95.50.95.83.84.65.84.69
-- Vary			: YES
--
-- Value(s)		: OK
--				: WARN:Low
--              : WARN:High
--              : FAIL:Low
--              : FAIL:High
--              : FAIL:Sensor Fault
--              : FAIL:Not Available
--              : DISABLED
-- Comments		: State of 2nd Temperature monitor (Out - (rear)Fan)
--              : OK Range    5C - 35C
--              : WARN:Low    0C -  5C
--              : WARN:High  35C - 40C
--              : FAIL:Low   < 0C
--              : FAIL:High  > 40C
--              : Note absolute values may vary in future releases, values are approximate
--              : Not Available - Sensor not found on local communication bus
--              : Sensor Fault - Sensor unable to initialise
--              : Not Available - Sensor not found
--              : DISABLE - Rear sensor disabled (warning)
---------------------------------------------------------------------------------------------------
-- Header		: LAST_MODIFIED
--
-- MIB ref		: swGatewayEventLogField  .13.76.65.83.84.95.77.79.68.73.70.73.69.68
-- absolute OID	: 1.3.6.1.4.1.7995.2.6.2.1.1.13.76.65.83.84.95.77.79.68.73.70.73.69.68
-- Vary			: YES
--
-- Value(s)		: 2014-02-26T11:47:22Z
-- Value(s)		: -
-- Comments		: Date and time of last modification of Gateway controls,  Note this appears every
--              : 5 seconds during continual control change, and/or 5 seconds after most recent update.
--              : Format local time on Gateway dd/mm/yy hh:mm:ss
--              : -  no control changes made since last start
--
---------------------------------------------------------------------------------------------------
-- Header		: LOGGING_STATE
--
-- MIB ref		: swGatewayEventLogField  .13.76.79.71.71.73.78.71.95.83.84.65.84.69
-- absolute OID	: 1.3.6.1.4.1.7995.2.6.2.1.1.13.76.79.71.71.73.78.71.95.83.84.65.84.69
-- Vary			: YES
--
-- Value(s)		: WARN:Address change
--				: 
-- Comments		: 
--
---------------------------------------------------------------------------------------------------
-- Header		: MODULE_STATUS
--
-- MIB ref		: swGatewayEventLogField  .13.77.79.68.85.76.69.95.83.84.65.84.85.83
-- absolute OID	: 1.3.6.1.4.1.7995.2.6.2.1.1.13.77.79.68.85.76.69.95.83.84.65.84.85.83
-- Vary			: YES
--
-- Value(s)		: OK
--				: 1 EXTRA MODULE
--              : n EXTRA MODULES
--              : 1 MODULE MISSING
--              : n MODULES MISSING
--              : 1 WRONG TYPE
--              : n WRONG TYPES
-- Comments		: where 2 <= n <= 16
--              : Status of module type/per slot configuration matching or Modules mismatched / missing
---------------------------------------------------------------------------------------------------
-- Header		: THUMB_IP_PORT
--
-- MIB ref		: swGatewayEventLogField  .13.84.72.85.77.66.95.73.80.95.80.79.82.84
-- absolute OID	: 1.3.6.1.4.1.7995.2.6.2.1.1.13.84.72.85.77.66.95.73.80.95.80.79.82.84
-- Vary			: YES
--
-- Value(s)		: 2601
--				: 
-- Comments		: Number of TCP port for Hyperion service (Thumbnail)
--
---------------------------------------------------------------------------------------------------
-- Header		: LOADER_VERSION
--
-- MIB ref		: swGatewayEventLogField  .14.76.79.65.68.69.82.95.86.69.82.83.73.79.78
-- absolute OID	: 1.3.6.1.4.1.7995.2.6.2.1.1.14.76.79.65.68.69.82.95.86.69.82.83.73.79.78
-- Vary			: YES
--
-- Value(s)		: 2.24 .9
--				: 
-- Comments		: Loader Version string
--
---------------------------------------------------------------------------------------------------
-- Header		: SYSTEM_CONTACT
--
-- MIB ref		: swGatewayEventLogField  .14.83.89.83.84.69.77.95.67.79.78.84.65.67.84
-- absolute OID	: 1.3.6.1.4.1.7995.2.6.2.1.1.14.83.89.83.84.69.77.95.67.79.78.84.65.67.84
-- Vary			: YES
--
-- Value(s)		: www.snellgroup.com
--				: 
-- Comments		: String denoting name of SNMP system contact
--
---------------------------------------------------------------------------------------------------
-- Header		: TEMP_1_CELSIUS
--
-- MIB ref		: swGatewayEventLogField  .14.84.69.77.80.95.49.95.67.69.76.83.73.85.83
-- absolute OID	: 1.3.6.1.4.1.7995.2.6.2.1.1.14.84.69.77.80.95.49.95.67.69.76.83.73.85.83
-- Vary			: YES
--
-- Value(s)		: 27
--				:
-- Comments		: Current temperature of 1st Temperature monitor (In) - Celcius  -50 <-> 120
--
---------------------------------------------------------------------------------------------------
-- Header		: TEMP_2_CELSIUS
--
-- MIB ref		: swGatewayEventLogField  .14.84.69.77.80.95.50.95.67.69.76.83.73.85.83
-- absolute OID	: 1.3.6.1.4.1.7995.2.6.2.1.1.14.84.69.77.80.95.50.95.67.69.76.83.73.85.83
-- Vary			: YES
--
-- Value(s)		: 29
--				:
-- Comments		: Current temperature of 2nd Temperature monitor (Out/Fan) - Celcius  -50 <-> 120
--
---------------------------------------------------------------------------------------------------
-- Header		: VOLTAGE_1_NAME
--
-- MIB ref		: swGatewayEventLogField  .14.86.79.76.84.65.71.69.95.49.95.78.65.77.69
-- absolute OID	: 1.3.6.1.4.1.7995.2.6.2.1.1.14.86.79.76.84.65.71.69.95.49.95.78.65.77.69
-- Vary			: NO
--
-- Value(s)		: +7.5V
--				:
-- Comments		: Assigned name of rail Voltage 1
--
---------------------------------------------------------------------------------------------------
-- Header		: VOLTAGE_2_NAME
--
-- MIB ref		: swGatewayEventLogField  .14.86.79.76.84.65.71.69.95.50.95.78.65.77.69
-- absolute OID	: 1.3.6.1.4.1.7995.2.6.2.1.1.14.86.79.76.84.65.71.69.95.50.95.78.65.77.69
-- Vary			: NO
--
-- Value(s)		: -7.5V
--				:
-- Comments		: Assigned name of rail Voltage 1
--
---------------------------------------------------------------------------------------------------
-- Header		: LAN_PORT_1_NAME
--
-- MIB ref		: swGatewayEventLogField  .15.76.65.78.95.80.79.82.84.95.49.95.78.65.77.69
-- absolute OID	: 1.3.6.1.4.1.7995.2.6.2.1.1.15.76.65.78.95.80.79.82.84.95.49.95.78.65.77.69
-- Vary			: YES
--
-- Value(s)		: FastEthernet0/1
--				:
-- Comments		: Assigned name of lan port
--
---------------------------------------------------------------------------------------------------
-- Header		: VOLTAGE_1_STATE
--
-- MIB ref		: swGatewayEventLogField  .15.86.79.76.84.65.71.69.95.49.95.83.84.65.84.69
-- absolute OID	: 1.3.6.1.4.1.7995.2.6.2.1.1.15.86.79.76.84.65.71.69.95.49.95.83.84.65.84.69
-- Vary			: YES
--
-- Value(s)		: OK
--				: WARN:Low
--              : WARN:High
-- Comments		: WARN:Low  when voltage < +6.8
--              : WARN:High when voltage > +8.0
--              : Note absolute values may vary in future releases, values are approximate
---------------------------------------------------------------------------------------------------
-- Header		: VOLTAGE_1_VALUE
--
-- MIB ref		: swGatewayEventLogField  .15.86.79.76.84.65.71.69.95.49.95.86.65.76.85.69
-- absolute OID	: 1.3.6.1.4.1.7995.2.6.2.1.1.15.86.79.76.84.65.71.69.95.49.95.86.65.76.85.69
-- Vary			: YES
--
-- Value(s)		: +7.6
--				:
-- Comments		: Current upper rail voltage value (volts)
--
---------------------------------------------------------------------------------------------------
-- Header		: VOLTAGE_2_STATE
--
-- MIB ref		: swGatewayEventLogField  .15.86.79.76.84.65.71.69.95.50.95.83.84.65.84.69
-- absolute OID	: 1.3.6.1.4.1.7995.2.6.2.1.1.15.86.79.76.84.65.71.69.95.50.95.83.84.65.84.69
-- Vary			: YES
--
-- Value(s)		: OK
--				: WARN:Low
--              : WARN:High
-- Comments		: WARN:Low  when voltage < -8.0
--              : WARN:High when voltage > -6.8
--              : Note absolute values may vary in future releases, values are approximate
---------------------------------------------------------------------------------------------------
-- Header		: VOLTAGE_2_VALUE
--
-- MIB ref		: swGatewayEventLogField  .15.86.79.76.84.65.71.69.95.50.95.86.65.76.85.69
-- absolute OID	: 1.3.6.1.4.1.7995.2.6.2.1.1.15.86.79.76.84.65.71.69.95.50.95.86.65.76.85.69
-- Vary			: YES
--
-- Value(s)		: -7.6
--				:
-- Comments		: Current lower rail voltage value (volts)
--
---------------------------------------------------------------------------------------------------
-- Header		: HARDWARE_VERSION
--
-- MIB ref		: swGatewayEventLogField  .16.72.65.82.68.87.65.82.69.95.86.69.82.83.73.79.78
-- absolute OID	: 1.3.6.1.4.1.7995.2.6.2.1.1.16.72.65.82.68.87.65.82.69.95.86.69.82.83.73.79.78
-- Vary			: YES
--
-- Value(s)		: RCIF3U2B / RCIF3U2C / RCIF3U2E / RCIF3U2F
--				: 
-- Comments		: 
--
---------------------------------------------------------------------------------------------------
-- Header		: IP_BRIDGE_STATUS
--
-- MIB ref		: swGatewayEventLogField  .16.73.80.95.66.82.73.68.71.69.95.83.84.65.84.85.83
-- absolute OID	: 1.3.6.1.4.1.7995.2.6.2.1.1.16.73.80.95.66.82.73.68.71.69.95.83.84.65.84.85.83
-- Vary			: YES
--
-- Value(s)		: INFO:Inactive
--				: INFO:Active
--				: OK:Active
--				: FAIL:Inactive
-- Comments		: 
--
---------------------------------------------------------------------------------------------------
-- Header		: LAN_PORT_1_SPEED
--
-- MIB ref		: swGatewayEventLogField  .16.76.65.78.95.80.79.82.84.95.49.95.83.80.69.69.68
-- absolute OID	: 1.3.6.1.4.1.7995.2.6.2.1.1.16.76.65.78.95.80.79.82.84.95.49.95.83.80.69.69.68
-- Vary			: YES
--
-- Value(s)		: 100 Mbit/s Half Duplex
--				: 100 Mbit/s Full Duplex
--              : 10 Mbit/s Half Duplex
--              : 10 Mbit/s Full Duplex
--              : No Link
-- Comments		: Speed of ethernet link
--
---------------------------------------------------------------------------------------------------
-- Header		: LAN_PORT_1_STATE
--
-- MIB ref		: swGatewayEventLogField  .16.76.65.78.95.80.79.82.84.95.49.95.83.84.65.84.69
-- absolute OID	: 1.3.6.1.4.1.7995.2.6.2.1.1.16.76.65.78.95.80.79.82.84.95.49.95.83.84.65.84.69
-- Vary			: YES
--
-- Value(s)		: Active
--				: WARN:Inactive
-- Comments		:
--
---------------------------------------------------------------------------------------------------
-- Header		: LAN_PORT_1_ERRORS
--
-- MIB ref		: swGatewayEventLogField  .17.76.65.78.95.80.79.82.84.95.49.95.69.82.82.79.82.83
-- absolute OID	: 1.3.6.1.4.1.7995.2.6.2.1.1.17.76.65.78.95.80.79.82.84.95.49.95.69.82.82.79.82.83
-- Vary			: YES
--
-- Value(s)		: 0 in total
--				:
-- Comments		:  Summation of MIB-II values ifInDiscards+ifInErrors+ifInUnknownProtos+ifOutDiscards+ifOutErrors.
--                 Updated periodically (60 sec interval)
---------------------------------------------------------------------------------------------------
-- Header		: SYSTEM_DESCRIPTION
--
-- MIB ref		: swGatewayEventLogField  .18.83.89.83.84.69.77.95.68.69.83.67.82.73.80.84.73.79.78
-- absolute OID	: 1.3.6.1.4.1.7995.2.6.2.1.1.18.83.89.83.84.69.77.95.68.69.83.67.82.73.80.84.73.79.78
-- Vary			: YES
--
-- Value(s)		: IQH3UM4-S
--				:
-- Comments		: String, SNMP system description
--
---------------------------------------------------------------------------------------------------
-- Header		: LAN_PORT_1_TRAFFIC_IN
--
-- MIB ref		: swGatewayEventLogField  .21.76.65.78.95.80.79.82.84.95.49.95.84.82.65.70.70.73.67.95.73.78
-- absolute OID	: 1.3.6.1.4.1.7995.2.6.2.1.1.21.76.65.78.95.80.79.82.84.95.49.95.84.82.65.70.70.73.67.95.73.78
-- Vary			: YES
--
-- Value(s)		: 1.6 KBytes/sec
--				: 
-- Comments		: Traffic In per second, averaged over 60 second period
--
---------------------------------------------------------------------------------------------------
-- Header		: LAN_PORT_1_LAST_CHANGE
--
-- MIB ref		: swGatewayEventLogField  .22.76.65.78.95.80.79.82.84.95.49.95.76.65.83.84.95.67.72.65.78.71.69
-- absolute OID	: 1.3.6.1.4.1.7995.2.6.2.1.1.22.76.65.78.95.80.79.82.84.95.49.95.76.65.83.84.95.67.72.65.78.71.69
-- Vary			: YES
--
-- Value(s)		: 000:00:00:00
--				: 
-- Comments		: Last configuration change of ethernet port, ddd:hh:mm:ss  ago.
--
---------------------------------------------------------------------------------------------------
-- Header		: LAN_PORT_1_TRAFFIC_OUT
--
-- MIB ref		: swGatewayEventLogField  .22.76.65.78.95.80.79.82.84.95.49.95.84.82.65.70.70.73.67.95.79.85.84
-- absolute OID	: 1.3.6.1.4.1.7995.2.6.2.1.1.22.76.65.78.95.80.79.82.84.95.49.95.84.82.65.70.70.73.67.95.79.85.84
-- Vary			: YES
--
-- Value(s)		: 0.3 KBytes/sec
--				: 
-- Comments		: Traffic Out per second, averaged over 60 second period
--
---------------------------------------------------------------------------------------------------
