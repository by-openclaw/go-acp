-- ************************************************************************************
-- Snell&Wilcox Card:IQDMSDL
--        Module Id#:261
--       Command Set:7
--          Filename:SNELL-IQDMSDL-CMD-MIB.mib
--            Author:Jonathan Riches
--              Date:13/06/2005
--              Time:09:03
--
-- Copyright (c) 2005 Snell & Wilcox Ltd
-- All rights reserved.
--
-- ************************************************************************************

SNELL-IQDMSDL-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDMSDL,
    moduleIQDMSDLMIB
        FROM SNELL-WILCOX-PRODUCT-REG;

 moduleIQDMSDLCmdMi MODULE-IDENTITY
    LAST-UPDATED "0506130903Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDMSDLMIB 1 }




--********************************************************************************
--*
--*  Snell Wilcox Card:
--*  command set:
--*  list commands/menus:
--*
--******************************************************************************
	iqdmsdlCmdTable OBJECT-TYPE
		SYNTAX			SEQUENCE OF IqdmsdlCmdEntry
		MAX-ACCESS		not-accessible
		STATUS			current
		DESCRIPTION
				"Note the instance of this table is relected in the command set Version"
		::= { moduleIQDMSDL 1 }

	iqdmsdlCmdEntry OBJECT-TYPE
		SYNTAX		IqdmsdlCmdEntry
		MAX-ACCESS		not-accessible
		STATUS			current
		DESCRIPTION
				"Entry in command table."
		INDEX	{ iqdmsdlSlotIndex }
		::= { iqdmsdlCmdTable 1 }

	IqdmsdlCmdEntry ::=
		SEQUENCE {
			iqdmsdlSlotIndex
				Unsigned32,
			iqdmsdlInputInputSelect
				INTEGER,
			iqdmsdlInputInputStandardsPAL
				INTEGER,
			iqdmsdlInputInputStandardsPALN
				INTEGER,
			iqdmsdlInputInputStandardsSECAM
				INTEGER,
			iqdmsdlInputInputStandardsMono625
				INTEGER,
			iqdmsdlInputInputStandardsNTSC
				INTEGER,
			iqdmsdlInputInputStandardsNTSCJ
				INTEGER,
			iqdmsdlInputInputStandardsPALM
				INTEGER,
			iqdmsdlInputInputStandardsN443
				INTEGER,
			iqdmsdlInputInputStandardsMono525
				INTEGER,
			iqdmsdlInputDecoderAutoGainControl
				INTEGER,
			iqdmsdlInputDecoderAutoChromaControl
				INTEGER,
			iqdmsdlInputDecoderPALChromaAverager
				INTEGER,
			iqdmsdlInputDecoderPALLine23
				INTEGER,
			iqdmsdlInputDecoderNTSCLine21_283
				INTEGER,
			iqdmsdlOutputDefaultOutput
				INTEGER,
			iqdmsdlOutputDefaultOutputStableInput
				INTEGER,
			iqdmsdlOutputSerialOutputPassVerticalData
				INTEGER,
			iqdmsdlProcAmpLuminanceGain
				INTEGER,
			iqdmsdlProcAmpBlackLevel
				INTEGER,
			iqdmsdlProcAmpChromaGain
				INTEGER,
			iqdmsdlProcAmpNTSCHue
				INTEGER,
			iqdmsdlProcAmpTimingTimingEnable
				INTEGER,
			iqdmsdlProcAmpTimingPicturePosition
				INTEGER,
			iqdmsdlProcAmpTimingYCTiming
				INTEGER,
			iqdmsdlFreeze
				INTEGER,
			iqdmsdlFeaturesNoiseReduceNoiseReduceEnable
				INTEGER,
			iqdmsdlFeaturesNoiseReduceYNREnable
				INTEGER,
			iqdmsdlFeaturesNoiseReduceCNREnable
				INTEGER,
			iqdmsdlFeaturesNoiseReduceYLevel
				INTEGER,
			iqdmsdlFeaturesNoiseReduceCLevel
				INTEGER,
			iqdmsdlFeaturesNoiseReduceSplitScreen
				INTEGER,
			iqdmsdlFeaturesEnhanceEnhancerEnable
				INTEGER,
			iqdmsdlFeaturesEnhance
				INTEGER,
			iqdmsdlStatusStatusDisplay
				INTEGER,
			iqdmsdlStatusStatusDisplayRollTrackErrors
				INTEGER,
			iqdmsdlStatusGPIDelay
				RollCallString,
			iqdmsdlStatusSoftwareVersion
				RollCallString,
			iqdmsdlStatusSerialNumber
				RollCallString,
			iqdmsdlStatusBuildNumber
				RollCallString,
			iqdmsdlStatusRestart
				INTEGER,
			iqdmsdlMemoriesRead
				INTEGER,
			iqdmsdlMemoriesSave
				INTEGER,
			iqdmsdlMemoriesNameNameMemory1
				RollCallString,
			iqdmsdlMemoriesNameNameMemory2
				RollCallString,
			iqdmsdlMemoriesNameNameMemory3
				RollCallString,
			iqdmsdlMemoriesNameNameMemory4
				RollCallString,
			iqdmsdlMemoriesNameNameMemory5
				RollCallString,
			iqdmsdlMemoriesNameNameMemory6
				RollCallString,
			iqdmsdlMemoriesNameNameMemory7
				RollCallString,
			iqdmsdlMemoriesNameNameMemory8
				RollCallString,
			iqdmsdlMemoriesClear
				INTEGER,
			iqdmsdlSetupGenlockGenlockEnable
				INTEGER,
			iqdmsdlSetupGenlock625HPhase
				INTEGER,
			iqdmsdlSetupGenlock525HPhase
				INTEGER,
			iqdmsdlSetupPatternPatternEnable
				INTEGER,
			iqdmsdlSetupPattern
				INTEGER,
			iqdmsdlSetupGPIGPIInputEnable
				INTEGER,
			iqdmsdlGPIGPIInputSetupGPIOpen
				INTEGER,
			iqdmsdlGPIGPIInputSetupGPIClose
				INTEGER,
			iqdmsdlSetupGPIGPIOutputEnable
				INTEGER,
			iqdmsdlSetupGPIGPIOutputSetup
				INTEGER,
			iqdmsdlSetupRollTrackUnit1
				RollCallString,
			iqdmsdlSetupRollTrackUnit2
				RollCallString,
			iqdmsdlSetupRollTrackUnit3
				RollCallString,
			iqdmsdlSetupRollTrackUnit4
				RollCallString,
			iqdmsdlSetupRollTrackUnit5
				RollCallString,
			iqdmsdlSetupRollTrackUnit6
				RollCallString,
			iqdmsdlSetupRollTrackUnit7
				RollCallString,
			iqdmsdlSetupRollTrackUnit8
				RollCallString,
			iqdmsdlSetupLoggingLogInputState
				INTEGER,
			iqdmsdlSetupLoggingLogInputStandard
				INTEGER,
			iqdmsdlSetupLoggingLogReferenceState
				INTEGER,
			iqdmsdlSetupPresetUnit
				INTEGER
		}

	iqdmsdlSlotIndex OBJECT-TYPE
		SYNTAX		Unsigned32
		MAX-ACCESS		not-accessible
		STATUS			current
		DESCRIPTION
				"The unique Index value for each slot.  Its value
					ranges between 1 and the value of slotNumber."
		::= { iqdmsdlCmdEntry 0 }


	iqdmsdlInputInputSelect OBJECT-TYPE
		SYNTAX		INTEGER {
							val_Composite_A(0),
							val_Composite_B(1),
							val_YC(2)
							}
		MAX-ACCESS		read-write
		STATUS			current
		DESCRIPTION
				"TYPE: - RadiobuttonList
					Input Select  cmdID= 9 
					Composite A  value= 0  
					Composite B  value= 1  
					YC  value= 2  "
		::= { iqdmsdlCmdEntry 9 }


	iqdmsdlInputInputStandardsPAL OBJECT-TYPE
		SYNTAX		INTEGER { disable(0), enable(1) }
		MAX-ACCESS		read-write
		STATUS			current
		DESCRIPTION
				"TYPE: - Checkbox
					PAL  cmdID= 10 "
		::= { iqdmsdlCmdEntry 10 }


	iqdmsdlInputInputStandardsPALN OBJECT-TYPE
		SYNTAX		INTEGER { disable(0), enable(1) }
		MAX-ACCESS		read-write
		STATUS			current
		DESCRIPTION
				"TYPE: - Checkbox
					PALN  cmdID= 12 "
		::= { iqdmsdlCmdEntry 12 }


	iqdmsdlInputInputStandardsSECAM OBJECT-TYPE
		SYNTAX		INTEGER { disable(0), enable(1) }
		MAX-ACCESS		read-write
		STATUS			current
		DESCRIPTION
				"TYPE: - Checkbox
					SECAM  cmdID= 14 "
		::= { iqdmsdlCmdEntry 14 }


	iqdmsdlInputInputStandardsMono625 OBJECT-TYPE
		SYNTAX		INTEGER { disable(0), enable(1) }
		MAX-ACCESS		read-write
		STATUS			current
		DESCRIPTION
				"TYPE: - Checkbox
					Mono 625  cmdID= 17 "
		::= { iqdmsdlCmdEntry 17 }


	iqdmsdlInputInputStandardsNTSC OBJECT-TYPE
		SYNTAX		INTEGER { disable(0), enable(1) }
		MAX-ACCESS		read-write
		STATUS			current
		DESCRIPTION
				"TYPE: - Checkbox
					NTSC  cmdID= 11 "
		::= { iqdmsdlCmdEntry 11 }


	iqdmsdlInputInputStandardsNTSCJ OBJECT-TYPE
		SYNTAX		INTEGER { disable(0), enable(1) }
		MAX-ACCESS		read-write
		STATUS			current
		DESCRIPTION
				"TYPE: - Checkbox
					NTSCJ  cmdID= 15 "
		::= { iqdmsdlCmdEntry 15 }


	iqdmsdlInputInputStandardsPALM OBJECT-TYPE
		SYNTAX		INTEGER { disable(0), enable(1) }
		MAX-ACCESS		read-write
		STATUS			current
		DESCRIPTION
				"TYPE: - Checkbox
					PALM  cmdID= 13 "
		::= { iqdmsdlCmdEntry 13 }


	iqdmsdlInputInputStandardsN443 OBJECT-TYPE
		SYNTAX		INTEGER { disable(0), enable(1) }
		MAX-ACCESS		read-write
		STATUS			current
		DESCRIPTION
				"TYPE: - Checkbox
					N4.43  cmdID= 16 "
		::= { iqdmsdlCmdEntry 16 }


	iqdmsdlInputInputStandardsMono525 OBJECT-TYPE
		SYNTAX		INTEGER { disable(0), enable(1) }
		MAX-ACCESS		read-write
		STATUS			current
		DESCRIPTION
				"TYPE: - Checkbox
					Mono 525  cmdID= 18 "
		::= { iqdmsdlCmdEntry 18 }


	iqdmsdlInputDecoderAutoGainControl OBJECT-TYPE
		SYNTAX		INTEGER { disable(0), enable(1) }
		MAX-ACCESS		read-write
		STATUS			current
		DESCRIPTION
				"TYPE: - Checkbox
					Auto Gain Control  cmdID= 21 "
		::= { iqdmsdlCmdEntry 21 }


	iqdmsdlInputDecoderAutoChromaControl OBJECT-TYPE
		SYNTAX		INTEGER { disable(0), enable(1) }
		MAX-ACCESS		read-write
		STATUS			current
		DESCRIPTION
				"TYPE: - Checkbox
					Auto Chroma Control  cmdID= 22 "
		::= { iqdmsdlCmdEntry 22 }


	iqdmsdlInputDecoderPALChromaAverager OBJECT-TYPE
		SYNTAX		INTEGER { disable(0), enable(1) }
		MAX-ACCESS		read-write
		STATUS			current
		DESCRIPTION
				"TYPE: - Checkbox
					PAL Chroma Averager  cmdID= 44 "
		::= { iqdmsdlCmdEntry 44 }


	iqdmsdlInputDecoderPALLine23 OBJECT-TYPE
		SYNTAX		INTEGER {
							val_Process_As_Video(0),
							val_Pass_Line_23(1),
							val_Blank_Line_23(2)
							}
		MAX-ACCESS		read-write
		STATUS			current
		DESCRIPTION
				"TYPE: - RadiobuttonList
					PAL Line 23  cmdID= 25 
					Process As Video  value= 0  
					Pass  Line 23  value= 1  
					Blank Line 23  value= 2  "
		::= { iqdmsdlCmdEntry 25 }


	iqdmsdlInputDecoderNTSCLine21_283 OBJECT-TYPE
		SYNTAX		INTEGER {
							val_Process_As_Video(0),
							val_Pass_Line_21_283(1),
							val_Blank_Line_21_283(2)
							}
		MAX-ACCESS		read-write
		STATUS			current
		DESCRIPTION
				"TYPE: - RadiobuttonList
					NTSC Line 21 & 283  cmdID= 26 
					Process As Video  value= 0  
					Pass  Line 21 & 283  value= 1  
					Blank Line 21 & 283  value= 2  "
		::= { iqdmsdlCmdEntry 26 }


	iqdmsdlOutputDefaultOutput OBJECT-TYPE
		SYNTAX		INTEGER {
							val_Input(5),
							val_Pattern(3),
							val_Freeze(4)
							}
		MAX-ACCESS		read-write
		STATUS			current
		DESCRIPTION
				"TYPE: - Button
					Input  cmdID= 35  value= 5  
					Pattern  cmdID= 35  value= 3  
					Freeze  cmdID= 35  value= 4  "
		::= { iqdmsdlCmdEntry 35 }


	iqdmsdlOutputDefaultOutputStableInput OBJECT-TYPE
		SYNTAX		INTEGER { disable(0), enable(1) }
		MAX-ACCESS		read-write
		STATUS			current
		DESCRIPTION
				"TYPE: - Checkbox
					Stable Input  cmdID= 133 "
		::= { iqdmsdlCmdEntry 133 }


	iqdmsdlOutputSerialOutputPassVerticalData OBJECT-TYPE
		SYNTAX		INTEGER { disable(0), enable(1) }
		MAX-ACCESS		read-write
		STATUS			current
		DESCRIPTION
				"TYPE: - Checkbox
					Pass Vertical Data  cmdID= 43 "
		::= { iqdmsdlCmdEntry 43 }


	iqdmsdlProcAmpLuminanceGain OBJECT-TYPE
		SYNTAX		INTEGER
		MAX-ACCESS		read-write
		STATUS			current
		DESCRIPTION
				"TYPE: - Number
					Luminance Gain  cmdID= 29  min= -30  max= 30  step= 1  format= %0.1f dB  div_scale= 10 
					Min = -3.0 dB  Max = 3.0 dB  Step = 0.1 dB "
		::= { iqdmsdlCmdEntry 29 }


	iqdmsdlProcAmpBlackLevel OBJECT-TYPE
		SYNTAX		INTEGER
		MAX-ACCESS		read-write
		STATUS			current
		DESCRIPTION
				"TYPE: - Number
					Black Level  cmdID= 31  min= -1024  max= 1024  step= 16  format= %0.1f mV  div_scale= 10 
					Min = -102.4 mV  Max = 102.4 mV  Step = 1.6 mV "
		::= { iqdmsdlCmdEntry 31 }


	iqdmsdlProcAmpChromaGain OBJECT-TYPE
		SYNTAX		INTEGER
		MAX-ACCESS		read-write
		STATUS			current
		DESCRIPTION
				"TYPE: - Number
					Chroma Gain  cmdID= 30  min= -30  max= 30  step= 1  format= %0.1f dB  div_scale= 10 
					Min = -3.0 dB  Max = 3.0 dB  Step = 0.1 dB "
		::= { iqdmsdlCmdEntry 30 }


	iqdmsdlProcAmpNTSCHue OBJECT-TYPE
		SYNTAX		INTEGER
		MAX-ACCESS		read-write
		STATUS			current
		DESCRIPTION
				"TYPE: - Number
					NTSC Hue  cmdID= 32  min= -180  max= 179  step= 1  format= %1.0f Deg  div_scale= 1 
					Min = -180 Deg  Max = 179 Deg  Step = 1 Deg "
		::= { iqdmsdlCmdEntry 32 }


	iqdmsdlProcAmpTimingTimingEnable OBJECT-TYPE
		SYNTAX		INTEGER { disable(0), enable(1) }
		MAX-ACCESS		read-write
		STATUS			current
		DESCRIPTION
				"TYPE: - Checkbox
					Timing Enable  cmdID= 118 "
		::= { iqdmsdlCmdEntry 118 }


	iqdmsdlProcAmpTimingPicturePosition OBJECT-TYPE
		SYNTAX		INTEGER
		MAX-ACCESS		read-write
		STATUS			current
		DESCRIPTION
				"TYPE: - Number
					Picture Position  cmdID= 38  min= -1036  max= 1036  step= 148  format= %.0f ns  div_scale= 1 
					Min = -1036 ns  Max = 1036 ns  Step = 148 ns "
		::= { iqdmsdlCmdEntry 38 }


	iqdmsdlProcAmpTimingYCTiming OBJECT-TYPE
		SYNTAX		INTEGER
		MAX-ACCESS		read-write
		STATUS			current
		DESCRIPTION
				"TYPE: - Number
					YC Timing  cmdID= 37  min= -1036  max= 1036  step= 148  format=  %.0f ns  div_scale= 1 
					Min =  -1036 ns  Max =  1036 ns  Step =  148 ns "
		::= { iqdmsdlCmdEntry 37 }


	iqdmsdlFreeze OBJECT-TYPE
		SYNTAX		INTEGER { disable(0), enable(1) }
		MAX-ACCESS		read-write
		STATUS			current
		DESCRIPTION
				"TYPE: - Checkbox
					Freeze  cmdID= 40 "
		::= { iqdmsdlCmdEntry 40 }


	iqdmsdlFeaturesNoiseReduceNoiseReduceEnable OBJECT-TYPE
		SYNTAX		INTEGER { disable(0), enable(1) }
		MAX-ACCESS		read-write
		STATUS			current
		DESCRIPTION
				"TYPE: - Checkbox
					Noise Reduce Enable  cmdID= 123 "
		::= { iqdmsdlCmdEntry 123 }


	iqdmsdlFeaturesNoiseReduceYNREnable OBJECT-TYPE
		SYNTAX		INTEGER { disable(0), enable(1) }
		MAX-ACCESS		read-write
		STATUS			current
		DESCRIPTION
				"TYPE: - Checkbox
					Y NR Enable  cmdID= 41 "
		::= { iqdmsdlCmdEntry 41 }


	iqdmsdlFeaturesNoiseReduceCNREnable OBJECT-TYPE
		SYNTAX		INTEGER { disable(0), enable(1) }
		MAX-ACCESS		read-write
		STATUS			current
		DESCRIPTION
				"TYPE: - Checkbox
					C NR Enable  cmdID= 42 "
		::= { iqdmsdlCmdEntry 42 }


	iqdmsdlFeaturesNoiseReduceYLevel OBJECT-TYPE
		SYNTAX		INTEGER {
							val_Y_Off(0),
							val_Y_Low(1),
							val_Y_Medium(2),
							val_Y_High(3)
							}
		MAX-ACCESS		read-write
		STATUS			current
		DESCRIPTION
				"TYPE: - RadiobuttonList
					Y Level  cmdID= 34 
					Y Off  value= 0  
					Y Low  value= 1  
					Y Medium  value= 2  
					Y High  value= 3  "
		::= { iqdmsdlCmdEntry 34 }


	iqdmsdlFeaturesNoiseReduceCLevel OBJECT-TYPE
		SYNTAX		INTEGER {
							val_C_OFF(0),
							val_C_Low(1),
							val_C_Medium(2),
							val_C_High(3)
							}
		MAX-ACCESS		read-write
		STATUS			current
		DESCRIPTION
				"TYPE: - RadiobuttonList
					C Level  cmdID= 36 
					C OFF  value= 0  
					C Low  value= 1  
					C Medium  value= 2  
					C High  value= 3  "
		::= { iqdmsdlCmdEntry 36 }


	iqdmsdlFeaturesNoiseReduceSplitScreen OBJECT-TYPE
		SYNTAX		INTEGER {
							val_Split_Screen_Off(0),
							val_Left_Right(2),
							val_Top_Bottom(1)
							}
		MAX-ACCESS		read-write
		STATUS			current
		DESCRIPTION
				"TYPE: - RadiobuttonList
					Split Screen  cmdID= 52 
					Split Screen Off  value= 0  
					Left Right  value= 2  
					Top Bottom  value= 1  "
		::= { iqdmsdlCmdEntry 52 }


	iqdmsdlFeaturesEnhanceEnhancerEnable OBJECT-TYPE
		SYNTAX		INTEGER { disable(0), enable(1) }
		MAX-ACCESS		read-write
		STATUS			current
		DESCRIPTION
				"TYPE: - Checkbox
					Enhancer Enable  cmdID= 45 "
		::= { iqdmsdlCmdEntry 45 }


	iqdmsdlFeaturesEnhance OBJECT-TYPE
		SYNTAX		INTEGER {
							val_De_Enhance(0),
							val_Enhancer_Low(1),
							val_Enhancer_Medium(2),
							val_Enhancer_High(3)
							}
		MAX-ACCESS		read-write
		STATUS			current
		DESCRIPTION
				"TYPE: - Button
					De-Enhance  cmdID= 23  value= 0  
					Enhancer Low  cmdID= 23  value= 1  
					Enhancer Medium  cmdID= 23  value= 2  
					Enhancer High  cmdID= 23  value= 3  "
		::= { iqdmsdlCmdEntry 23 }


	iqdmsdlStatusStatusDisplay OBJECT-TYPE
		SYNTAX		INTEGER {
							val_Default_Display(0),
							val_Status_Display(1)
							}
		MAX-ACCESS		read-write
		STATUS			current
		DESCRIPTION
				"TYPE: - Button
					Default Display  cmdID= 116  value= 0  
					Status Display  cmdID= 116  value= 1  "
		::= { iqdmsdlCmdEntry 116 }


	iqdmsdlStatusStatusDisplayRollTrackErrors OBJECT-TYPE
		SYNTAX		INTEGER { disable(0), enable(1) }
		MAX-ACCESS		read-write
		STATUS			current
		DESCRIPTION
				"TYPE: - Checkbox
					RollTrack Errors  cmdID= 71 
					Show RollTrack Err  cmdID= 71 "
		::= { iqdmsdlCmdEntry 71 }


	iqdmsdlStatusGPIDelay OBJECT-TYPE
		SYNTAX		RollCallString
		MAX-ACCESS		read-only
		STATUS			current
		DESCRIPTION
				"TYPE: - Display
					GPI Delay  cmdID= 117  format=   "
		::= { iqdmsdlCmdEntry 117 }


	iqdmsdlStatusSoftwareVersion OBJECT-TYPE
		SYNTAX		RollCallString
		MAX-ACCESS		read-only
		STATUS			current
		DESCRIPTION
				"TYPE: - Display
					Software Version  cmdID= 2  format=   "
		::= { iqdmsdlCmdEntry 2 }


	iqdmsdlStatusSerialNumber OBJECT-TYPE
		SYNTAX		RollCallString
		MAX-ACCESS		read-only
		STATUS			current
		DESCRIPTION
				"TYPE: - Display
					Serial Number  cmdID= 1  format=   "
		::= { iqdmsdlCmdEntry 1 }


	iqdmsdlStatusBuildNumber OBJECT-TYPE
		SYNTAX		RollCallString
		MAX-ACCESS		read-only
		STATUS			current
		DESCRIPTION
				"TYPE: - Display
					Build Number  cmdID= 120  format=   "
		::= { iqdmsdlCmdEntry 120 }


	iqdmsdlStatusRestart OBJECT-TYPE
		SYNTAX		INTEGER { noAction(0),val_Restart(1) }
		MAX-ACCESS		read-write
		STATUS			current
		DESCRIPTION
				"TYPE: - Button
					Restart  cmdID= 4  value= 1  "
		::= { iqdmsdlCmdEntry 4 }


	iqdmsdlMemoriesRead OBJECT-TYPE
		SYNTAX		INTEGER {
							val_Memory_1(1),
							val_Memory_2(2),
							val_Memory_3(3),
							val_Memory_4(4),
							val_Memory_5(5),
							val_Memory_6(6),
							val_Memory_7(7),
							val_Memory_8(8)
							}
		MAX-ACCESS		read-write
		STATUS			current
		DESCRIPTION
				"TYPE: - RadiobuttonList
					Read  cmdID= 55 
					Memory 1  value= 1  
					Memory 2  value= 2  
					Memory 3  value= 3  
					Memory 4  value= 4  
					Memory 5  value= 5  
					Memory 6  value= 6  
					Memory 7  value= 7  
					Memory 8  value= 8  "
		::= { iqdmsdlCmdEntry 55 }


	iqdmsdlMemoriesSave OBJECT-TYPE
		SYNTAX		INTEGER {
							val_Memory_1(1),
							val_Memory_2(2),
							val_Memory_3(3),
							val_Memory_4(4),
							val_Memory_5(5),
							val_Memory_6(6),
							val_Memory_7(7),
							val_Memory_8(8)
							}
		MAX-ACCESS		read-write
		STATUS			current
		DESCRIPTION
				"TYPE: - RadiobuttonList
					Save  cmdID= 54 
					Memory 1  value= 1  
					Memory 2  value= 2  
					Memory 3  value= 3  
					Memory 4  value= 4  
					Memory 5  value= 5  
					Memory 6  value= 6  
					Memory 7  value= 7  
					Memory 8  value= 8  "
		::= { iqdmsdlCmdEntry 54 }


	iqdmsdlMemoriesNameNameMemory1 OBJECT-TYPE
		SYNTAX		RollCallString
		MAX-ACCESS		read-write
		STATUS			current
		DESCRIPTION
				"TYPE: - Editstring
				 PAGE: - Name
					Name Memory 1  cmdID= 57  "
		::= { iqdmsdlCmdEntry 57 }


	iqdmsdlMemoriesNameNameMemory2 OBJECT-TYPE
		SYNTAX		RollCallString
		MAX-ACCESS		read-write
		STATUS			current
		DESCRIPTION
				"TYPE: - Editstring
				 PAGE: - Name
					Name Memory 2  cmdID= 58  "
		::= { iqdmsdlCmdEntry 58 }


	iqdmsdlMemoriesNameNameMemory3 OBJECT-TYPE
		SYNTAX		RollCallString
		MAX-ACCESS		read-write
		STATUS			current
		DESCRIPTION
				"TYPE: - Editstring
				 PAGE: - Name
					Name Memory 3  cmdID= 59  "
		::= { iqdmsdlCmdEntry 59 }


	iqdmsdlMemoriesNameNameMemory4 OBJECT-TYPE
		SYNTAX		RollCallString
		MAX-ACCESS		read-write
		STATUS			current
		DESCRIPTION
				"TYPE: - Editstring
				 PAGE: - Name
					Name Memory 4  cmdID= 60  "
		::= { iqdmsdlCmdEntry 60 }


	iqdmsdlMemoriesNameNameMemory5 OBJECT-TYPE
		SYNTAX		RollCallString
		MAX-ACCESS		read-write
		STATUS			current
		DESCRIPTION
				"TYPE: - Editstring
				 PAGE: - Name
					Name Memory 5  cmdID= 61  "
		::= { iqdmsdlCmdEntry 61 }


	iqdmsdlMemoriesNameNameMemory6 OBJECT-TYPE
		SYNTAX		RollCallString
		MAX-ACCESS		read-write
		STATUS			current
		DESCRIPTION
				"TYPE: - Editstring
				 PAGE: - Name
					Name Memory 6  cmdID= 62  "
		::= { iqdmsdlCmdEntry 62 }


	iqdmsdlMemoriesNameNameMemory7 OBJECT-TYPE
		SYNTAX		RollCallString
		MAX-ACCESS		read-write
		STATUS			current
		DESCRIPTION
				"TYPE: - Editstring
				 PAGE: - Name
					Name Memory 7  cmdID= 63  "
		::= { iqdmsdlCmdEntry 63 }


	iqdmsdlMemoriesNameNameMemory8 OBJECT-TYPE
		SYNTAX		RollCallString
		MAX-ACCESS		read-write
		STATUS			current
		DESCRIPTION
				"TYPE: - Editstring
				 PAGE: - Name
					Name Memory 8  cmdID= 64  "
		::= { iqdmsdlCmdEntry 64 }


	iqdmsdlMemoriesClear OBJECT-TYPE
		SYNTAX		INTEGER {
							val_Memory_1(1),
							val_Memory_2(2),
							val_Memory_3(3),
							val_Memory_4(4),
							val_Memory_5(5),
							val_Memory_6(6),
							val_Memory_7(7),
							val_Memory_8(8)
							}
		MAX-ACCESS		read-write
		STATUS			current
		DESCRIPTION
				"TYPE: - RadiobuttonList
					Clear  cmdID= 56 
					Memory 1  value= 1  
					Memory 2  value= 2  
					Memory 3  value= 3  
					Memory 4  value= 4  
					Memory 5  value= 5  
					Memory 6  value= 6  
					Memory 7  value= 7  
					Memory 8  value= 8  "
		::= { iqdmsdlCmdEntry 56 }


	iqdmsdlSetupGenlockGenlockEnable OBJECT-TYPE
		SYNTAX		INTEGER { disable(0), enable(1) }
		MAX-ACCESS		read-write
		STATUS			current
		DESCRIPTION
				"TYPE: - Checkbox
					Genlock Enable  cmdID= 39 "
		::= { iqdmsdlCmdEntry 39 }


	iqdmsdlSetupGenlock625HPhase OBJECT-TYPE
		SYNTAX		INTEGER
		MAX-ACCESS		read-write
		STATUS			current
		DESCRIPTION
				"TYPE: - Number
					625 H  Phase  cmdID= 87  min= -505  max= 505  step= 1  format= %1.0f ns  div_scale= 1 
					Min = -505 ns  Max = 505 ns  Step = 1 ns "
		::= { iqdmsdlCmdEntry 87 }


	iqdmsdlSetupGenlock525HPhase OBJECT-TYPE
		SYNTAX		INTEGER
		MAX-ACCESS		read-write
		STATUS			current
		DESCRIPTION
				"TYPE: - Number
					525 H  Phase  cmdID= 88  min= -410  max= 410  step= 1  format= %1.0f ns  div_scale= 1 
					Min = -410 ns  Max = 410 ns  Step = 1 ns "
		::= { iqdmsdlCmdEntry 88 }


	iqdmsdlSetupPatternPatternEnable OBJECT-TYPE
		SYNTAX		INTEGER { disable(0), enable(1) }
		MAX-ACCESS		read-write
		STATUS			current
		DESCRIPTION
				"TYPE: - Checkbox
					Pattern Enable  cmdID= 33 "
		::= { iqdmsdlCmdEntry 33 }


	iqdmsdlSetupPattern OBJECT-TYPE
		SYNTAX		INTEGER {
							val_Black(0),
							val_75_Colour_Bars(1),
							val_100_Colour_Bars(2),
							val_MultiBurst(3)
							}
		MAX-ACCESS		read-write
		STATUS			current
		DESCRIPTION
				"TYPE: - Button
					Black  cmdID= 24  value= 0  
					75% Colour Bars  cmdID= 24  value= 1  
					100% Colour Bars  cmdID= 24  value= 2  
					MultiBurst  cmdID= 24  value= 3  "
		::= { iqdmsdlCmdEntry 24 }


	iqdmsdlSetupGPIGPIInputEnable OBJECT-TYPE
		SYNTAX		INTEGER { disable(0), enable(1) }
		MAX-ACCESS		read-write
		STATUS			current
		DESCRIPTION
				"TYPE: - Checkbox
					GPI Input Enable  cmdID= 83 "
		::= { iqdmsdlCmdEntry 83 }


	iqdmsdlGPIGPIInputSetupGPIOpen OBJECT-TYPE
		SYNTAX		INTEGER {
							val_Off(0),
							val_Pattern_On(11),
							val_Pattern_Off(12),
							val_Freeze_On(9),
							val_Freeze_Off(10),
							val_Memory_1(1),
							val_Memory_2(2),
							val_Memory_3(3),
							val_Memory_4(4),
							val_Memory_5(5),
							val_Memory_6(6),
							val_Memory_7(7),
							val_Memory_8(8)
							}
		MAX-ACCESS		read-write
		STATUS			current
		DESCRIPTION
				"TYPE: - RadiobuttonList
					GPI Open  cmdID= 81 
					Off  value= 0  
					Pattern On  value= 11  
					Pattern Off  value= 12  
					Freeze On  value= 9  
					Freeze Off  value= 10  
					Memory 1  value= 1  
					Memory 2  value= 2  
					Memory 3  value= 3  
					Memory 4  value= 4  
					Memory 5  value= 5  
					Memory 6  value= 6  
					Memory 7  value= 7  
					Memory 8  value= 8  "
		::= { iqdmsdlCmdEntry 81 }


	iqdmsdlGPIGPIInputSetupGPIClose OBJECT-TYPE
		SYNTAX		INTEGER {
							val_Off(0),
							val_Pattern_On(11),
							val_Pattern_Off(12),
							val_Freeze_On(9),
							val_Freeze_Off(10),
							val_Memory_1(1),
							val_Memory_2(2),
							val_Memory_3(3),
							val_Memory_4(4),
							val_Memory_5(5),
							val_Memory_6(6),
							val_Memory_7(7),
							val_Memory_8(8)
							}
		MAX-ACCESS		read-write
		STATUS			current
		DESCRIPTION
				"TYPE: - RadiobuttonList
					GPI Close  cmdID= 82 
					Off  value= 0  
					Pattern On  value= 11  
					Pattern Off  value= 12  
					Freeze On  value= 9  
					Freeze Off  value= 10  
					Memory 1  value= 1  
					Memory 2  value= 2  
					Memory 3  value= 3  
					Memory 4  value= 4  
					Memory 5  value= 5  
					Memory 6  value= 6  
					Memory 7  value= 7  
					Memory 8  value= 8  "
		::= { iqdmsdlCmdEntry 82 }


	iqdmsdlSetupGPIGPIOutputEnable OBJECT-TYPE
		SYNTAX		INTEGER { disable(0), enable(1) }
		MAX-ACCESS		read-write
		STATUS			current
		DESCRIPTION
				"TYPE: - Checkbox
					GPI Output Enable  cmdID= 84 "
		::= { iqdmsdlCmdEntry 84 }


	iqdmsdlSetupGPIGPIOutputSetup OBJECT-TYPE
		SYNTAX		INTEGER {
							val_Delay_Flag(0),
							val_High_On_Input_Loss(1),
							val_Low_On_Input_Loss(2),
							val_Input_Line_Std_625(3),
							val_Input_Line_Std_525(4)
							}
		MAX-ACCESS		read-write
		STATUS			current
		DESCRIPTION
				"TYPE: - RadiobuttonList
					GPI Output Setup  cmdID= 115 
					Delay Flag  value= 0  
					High On Input Loss  value= 1  
					Low  On Input Loss  value= 2  
					Input Line Std 625  value= 3  
					Input Line Std 525  value= 4  "
		::= { iqdmsdlCmdEntry 115 }


	iqdmsdlSetupRollTrackUnit1 OBJECT-TYPE
		SYNTAX		RollCallString
		MAX-ACCESS		read-write
		STATUS			current
		DESCRIPTION
				"TYPE: - Editstring
				 PAGE: - RollTrack
					Unit 1  cmdID= 72  "
		::= { iqdmsdlCmdEntry 72 }


	iqdmsdlSetupRollTrackUnit2 OBJECT-TYPE
		SYNTAX		RollCallString
		MAX-ACCESS		read-write
		STATUS			current
		DESCRIPTION
				"TYPE: - Editstring
				 PAGE: - RollTrack
					Unit 2  cmdID= 73  "
		::= { iqdmsdlCmdEntry 73 }


	iqdmsdlSetupRollTrackUnit3 OBJECT-TYPE
		SYNTAX		RollCallString
		MAX-ACCESS		read-write
		STATUS			current
		DESCRIPTION
				"TYPE: - Editstring
				 PAGE: - RollTrack
					Unit 3  cmdID= 74  "
		::= { iqdmsdlCmdEntry 74 }


	iqdmsdlSetupRollTrackUnit4 OBJECT-TYPE
		SYNTAX		RollCallString
		MAX-ACCESS		read-write
		STATUS			current
		DESCRIPTION
				"TYPE: - Editstring
				 PAGE: - RollTrack
					Unit 4  cmdID= 75  "
		::= { iqdmsdlCmdEntry 75 }


	iqdmsdlSetupRollTrackUnit5 OBJECT-TYPE
		SYNTAX		RollCallString
		MAX-ACCESS		read-write
		STATUS			current
		DESCRIPTION
				"TYPE: - Editstring
				 PAGE: - RollTrack
					Unit 5  cmdID= 76  "
		::= { iqdmsdlCmdEntry 76 }


	iqdmsdlSetupRollTrackUnit6 OBJECT-TYPE
		SYNTAX		RollCallString
		MAX-ACCESS		read-write
		STATUS			current
		DESCRIPTION
				"TYPE: - Editstring
				 PAGE: - RollTrack
					Unit 6  cmdID= 77  "
		::= { iqdmsdlCmdEntry 77 }


	iqdmsdlSetupRollTrackUnit7 OBJECT-TYPE
		SYNTAX		RollCallString
		MAX-ACCESS		read-write
		STATUS			current
		DESCRIPTION
				"TYPE: - Editstring
				 PAGE: - RollTrack
					Unit 7  cmdID= 78  "
		::= { iqdmsdlCmdEntry 78 }


	iqdmsdlSetupRollTrackUnit8 OBJECT-TYPE
		SYNTAX		RollCallString
		MAX-ACCESS		read-write
		STATUS			current
		DESCRIPTION
				"TYPE: - Editstring
				 PAGE: - RollTrack
					Unit 8  cmdID= 79  "
		::= { iqdmsdlCmdEntry 79 }


	iqdmsdlSetupLoggingLogInputState OBJECT-TYPE
		SYNTAX		INTEGER { disable(0), enable(1) }
		MAX-ACCESS		read-write
		STATUS			current
		DESCRIPTION
				"TYPE: - Checkbox
					Log Input State  cmdID= 28 "
		::= { iqdmsdlCmdEntry 28 }


	iqdmsdlSetupLoggingLogInputStandard OBJECT-TYPE
		SYNTAX		INTEGER { disable(0), enable(1) }
		MAX-ACCESS		read-write
		STATUS			current
		DESCRIPTION
				"TYPE: - Checkbox
					Log Input Standard  cmdID= 130 "
		::= { iqdmsdlCmdEntry 130 }


	iqdmsdlSetupLoggingLogReferenceState OBJECT-TYPE
		SYNTAX		INTEGER { disable(0), enable(1) }
		MAX-ACCESS		read-write
		STATUS			current
		DESCRIPTION
				"TYPE: - Checkbox
					Log Reference State  cmdID= 27 "
		::= { iqdmsdlCmdEntry 27 }


	iqdmsdlSetupPresetUnit OBJECT-TYPE
		SYNTAX		INTEGER { noAction(0),val_Preset_Unit(1) }
		MAX-ACCESS		read-write
		STATUS			current
		DESCRIPTION
				"TYPE: - Button
					Preset Unit  cmdID= 3  value= 1  "
		::= { iqdmsdlCmdEntry 3 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: UNKNOWN
--				: AUTO
--				: NTSC
--				: PAL
--				: PAL-M
--				: PAL-N
--				: NTSC-443
--				: SECAM
--				: MONO
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
--				: ERROR
-- Comments		: 
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: N/A
--				: OK
--				: LOST
-- Comments		: 
--
---------------------------------------------------------------------------------------------------
