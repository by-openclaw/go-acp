-- ************************************************************************************
-- Snell    Card:IQMUX47
--        Module Id#:495
--       Command Set:17
--          Filename:SNELL-IQMUX47-CMD-MIB.mib
--            Author:Jonathan Riches
--              Date:27/01/2010
--              Time:10:46
--
-- Copyright (c) 2010 Snell Ltd
-- All rights reserved.
--
-- ************************************************************************************

SNELL-IQMUX47-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQMUX47,
    moduleIQMUX47MIB
        FROM SNELL-WILCOX-PRODUCT-REG;

 moduleIQMUX47CmdMi MODULE-IDENTITY
    LAST-UPDATED "1001271046Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQMUX47MIB 1 }




--********************************************************************************
--*
--*  Snell Wilcox Card:
--*  command set:
--*  list commands/menus:
--*
--******************************************************************************
	iqmux47CmdTable OBJECT-TYPE
		SYNTAX			SEQUENCE OF Iqmux47CmdEntry
		MAX-ACCESS		not-accessible
		STATUS			current
		DESCRIPTION
				"Note the instance of this table is relected in the command set Version"
		::= { moduleIQMUX47 1 }

	iqmux47CmdEntry OBJECT-TYPE
		SYNTAX		Iqmux47CmdEntry
		MAX-ACCESS		not-accessible
		STATUS			current
		DESCRIPTION
				"Entry in command table."
		INDEX	{ iqmux47SlotIndex }
		::= { iqmux47CmdTable 1 }

	Iqmux47CmdEntry ::=
		SEQUENCE {
			iqmux47SlotIndex
				Unsigned32,
			iqmux47InputIPLoss
				INTEGER,
			iqmux47InputValidStdsAllValid
				INTEGER,
			iqmux47InputValidStdsAllInvalid
				INTEGER,
			iqmux47InputValidStds108023sF
				INTEGER,
			iqmux47InputValidStds108023p
				INTEGER,
			iqmux47InputValidStds108024sF
				INTEGER,
			iqmux47InputValidStds108024p
				INTEGER,
			iqmux47InputValidStds108025i
				INTEGER,
			iqmux47InputValidStds108025p
				INTEGER,
			iqmux47InputValidStds103529i
				INTEGER,
			iqmux47InputValidStds108029i
				INTEGER,
			iqmux47InputValidStds108029p
				INTEGER,
			iqmux47InputValidStds103530i
				INTEGER,
			iqmux47InputValidStds108030i
				INTEGER,
			iqmux47InputValidStds108030p
				INTEGER,
			iqmux47InputValidStds72050p
				INTEGER,
			iqmux47InputValidStds72059p
				INTEGER,
			iqmux47InputValidStds72060p
				INTEGER,
			iqmux47InputValidStds62525i
				INTEGER,
			iqmux47InputValidStds52529i
				INTEGER,
			iqmux47InputErrorsCRCErrs
				RollCallString,
			iqmux47InputErrorsCRCErrSec
				RollCallString,
			iqmux47InputErrorsANCErrs
				RollCallString,
			iqmux47InputErrorsANCErrSec
				RollCallString,
			iqmux47InputErrorsResetSec
				RollCallString,
			iqmux47InputErrorsErrorReset
				INTEGER,
			iqmux47OutputStandard
				INTEGER,
			iqmux47OutputSelectStandard
				INTEGER,
			iqmux47OutputVideoProcAmpsMasterGain
				INTEGER,
			iqmux47OutputVideoProcAmpsYGain
				INTEGER,
			iqmux47OutputVideoProcAmpsCGain
				INTEGER,
			iqmux47OutputVideoProcAmpsBlackLevel
				INTEGER,
			iqmux47OutputDefaultOutput
				INTEGER,
			iqmux47OutputDefaultOPStd
				INTEGER,
			iqmux47AudioADelaySourcesManual
				INTEGER,
			iqmux47AudioADelaySourcesGPIPWM
				INTEGER,
			iqmux47AudioADelaySourcesRollTrack14
				INTEGER,
			iqmux47AudioADelaySourcesRollTrack15
				INTEGER,
			iqmux47AudioADelaySourcesRollTrack16
				INTEGER,
			iqmux47AudioADelaySourcesRollTrack17
				INTEGER,
			iqmux47AudioAAdjustCoarseDelay
				INTEGER,
			iqmux47AudioACurrentAudioDelay
				RollCallString,
			iqmux47AudioBDelaySourcesManual
				INTEGER,
			iqmux47AudioBDelaySourcesGPIPWM
				INTEGER,
			iqmux47AudioBDelaySourcesRollTrack14
				INTEGER,
			iqmux47AudioBDelaySourcesRollTrack15
				INTEGER,
			iqmux47AudioBDelaySourcesRollTrack16
				INTEGER,
			iqmux47AudioBDelaySourcesRollTrack17
				INTEGER,
			iqmux47AudioBAdjustCoarseDelay
				INTEGER,
			iqmux47AudioBCurrentAudioDelay
				RollCallString,
			iqmux47AudioAESDelaySelectDelay1
				INTEGER,
			iqmux47AudioAESDelaySelectInternal1
				INTEGER,
			iqmux47AudioAESDelaySelectAutoDolbyEPhase1
				INTEGER,
			iqmux47AudioAESDelaySelectDelayLimit1
				RollCallString,
			iqmux47AudioAESDelaySelectAES1FineDelay
				INTEGER,
			iqmux47AudioAESDelaySelectDelay2
				INTEGER,
			iqmux47AudioAESDelaySelectInternal2
				INTEGER,
			iqmux47AudioAESDelaySelectAutoDolbyEPhase2
				INTEGER,
			iqmux47AudioAESDelaySelectDelayLimit2
				RollCallString,
			iqmux47AudioAESDelaySelectAES2FineDelay
				INTEGER,
			iqmux47AudioAESDelaySelectDelay3
				INTEGER,
			iqmux47AudioAESDelaySelectInternal3
				INTEGER,
			iqmux47AudioAESDelaySelectAutoDolbyEPhase3
				INTEGER,
			iqmux47AudioAESDelaySelectDelayLimit3
				RollCallString,
			iqmux47AudioAESDelaySelectAES3FineDelay
				INTEGER,
			iqmux47AudioAESDelaySelectDelay4
				INTEGER,
			iqmux47AudioAESDelaySelectInternal4
				INTEGER,
			iqmux47AudioAESDelaySelectAutoDolbyEPhase4
				INTEGER,
			iqmux47AudioAESDelaySelectDelayLimit4
				RollCallString,
			iqmux47AudioAESDelaySelectAES4FineDelay
				INTEGER,
			iqmux47AudioAESDelaySelectDelay5
				INTEGER,
			iqmux47AudioAESDelaySelectInternal5
				INTEGER,
			iqmux47AudioAESDelaySelectAutoDolbyEPhase5
				INTEGER,
			iqmux47AudioAESDelaySelectDelayLimit5
				RollCallString,
			iqmux47AudioAESDelaySelectAES5FineDelay
				INTEGER,
			iqmux47AudioAESDelaySelectDelay6
				INTEGER,
			iqmux47AudioAESDelaySelectInternal6
				INTEGER,
			iqmux47AudioAESDelaySelectAutoDolbyEPhase6
				INTEGER,
			iqmux47AudioAESDelaySelectDelayLimit6
				RollCallString,
			iqmux47AudioAESDelaySelectAES6FineDelay
				INTEGER,
			iqmux47AudioAESDelaySelectDelay7
				INTEGER,
			iqmux47AudioAESDelaySelectInternal7
				INTEGER,
			iqmux47AudioAESDelaySelectAutoDolbyEPhase7
				INTEGER,
			iqmux47AudioAESDelaySelectDelayLimit7
				RollCallString,
			iqmux47AudioAESDelaySelectAES7FineDelay
				INTEGER,
			iqmux47AudioAESDelaySelectDelay8
				INTEGER,
			iqmux47AudioAESDelaySelectInternal8
				INTEGER,
			iqmux47AudioAESDelaySelectAutoDolbyEPhase8
				INTEGER,
			iqmux47AudioAESDelaySelectDelayLimit8
				RollCallString,
			iqmux47AudioAESDelaySelectAES8FineDelay
				INTEGER,
			iqmux47AudEMBDelaySelectDelay1
				INTEGER,
			iqmux47AudEMBDelaySelectInternal1
				INTEGER,
			iqmux47AudEMBDelaySelectAutoDolbyEPhase1
				INTEGER,
			iqmux47AudEMBDelaySelectDelayLimit1
				RollCallString,
			iqmux47AudEMBDelaySelectEMB1FineDelay
				INTEGER,
			iqmux47AudEMBDelaySelectDelay2
				INTEGER,
			iqmux47AudEMBDelaySelectInternal2
				INTEGER,
			iqmux47AudEMBDelaySelectAutoDolbyEPhase2
				INTEGER,
			iqmux47AudEMBDelaySelectDelayLimit2
				RollCallString,
			iqmux47AudEMBDelaySelectEMB2FineDelay
				INTEGER,
			iqmux47AudEMBDelaySelectDelay3
				INTEGER,
			iqmux47AudEMBDelaySelectInternal3
				INTEGER,
			iqmux47AudEMBDelaySelectAutoDolbyEPhase3
				INTEGER,
			iqmux47AudEMBDelaySelectDelayLimit3
				RollCallString,
			iqmux47AudEMBDelaySelectEMB3FineDelay
				INTEGER,
			iqmux47AudEMBDelaySelectDelay4
				INTEGER,
			iqmux47AudEMBDelaySelectInternal4
				INTEGER,
			iqmux47AudEMBDelaySelectAutoDolbyEPhase4
				INTEGER,
			iqmux47AudEMBDelaySelectDelayLimit4
				RollCallString,
			iqmux47AudEMBDelaySelectEMB4FineDelay
				INTEGER,
			iqmux47AudEMBDelaySelectDelay5
				INTEGER,
			iqmux47AudEMBDelaySelectInternal5
				INTEGER,
			iqmux47AudEMBDelaySelectAutoDolbyEPhase5
				INTEGER,
			iqmux47AudEMBDelaySelectDelayLimit5
				RollCallString,
			iqmux47AudEMBDelaySelectEMB5FineDelay
				INTEGER,
			iqmux47AudEMBDelaySelectDelay6
				INTEGER,
			iqmux47AudEMBDelaySelectInternal6
				INTEGER,
			iqmux47AudEMBDelaySelectAutoDolbyEPhase6
				INTEGER,
			iqmux47AudEMBDelaySelectDelayLimit6
				RollCallString,
			iqmux47AudEMBDelaySelectEMB6FineDelay
				INTEGER,
			iqmux47AudEMBDelaySelectDelay7
				INTEGER,
			iqmux47AudEMBDelaySelectInternal7
				INTEGER,
			iqmux47AudEMBDelaySelectAutoDolbyEPhase7
				INTEGER,
			iqmux47AudEMBDelaySelectDelayLimit7
				RollCallString,
			iqmux47AudEMBDelaySelectEMB7FineDelay
				INTEGER,
			iqmux47AudEMBDelaySelectDelay8
				INTEGER,
			iqmux47AudEMBDelaySelectInternal8
				INTEGER,
			iqmux47AudEMBDelaySelectDelayLimit8
				RollCallString,
			iqmux47AudEMBDelaySelectAutoDolbyEPhase8
				INTEGER,
			iqmux47AudEMBDelaySelectEMB8FineDelay
				INTEGER,
			iqmux47AudioDelaysRollTrack14
				RollCallString,
			iqmux47AudioDelaysRollTrack15
				RollCallString,
			iqmux47AudioDelaysRollTrack16
				RollCallString,
			iqmux47AudioDelaysRollTrack17
				RollCallString,
			iqmux47AudioDelaysCrashSRCLimit
				INTEGER,
			iqmux47EmbCtrlGroupGroup1Audio
				INTEGER,
			iqmux47EmbCtrlGroupGroup2Audio
				INTEGER,
			iqmux47EmbCtrlGroupGroup3Audio
				INTEGER,
			iqmux47EmbCtrlGroupGroup4Audio
				INTEGER,
			iqmux47EmbCtrlChannelPair1LActive
				INTEGER,
			iqmux47EmbCtrlChannelPair1RActive
				INTEGER,
			iqmux47EmbCtrlChannelPair2LActive
				INTEGER,
			iqmux47EmbCtrlChannelPair2RActive
				INTEGER,
			iqmux47EmbCtrlChannelPair3LActive
				INTEGER,
			iqmux47EmbCtrlChannelPair3RActive
				INTEGER,
			iqmux47EmbCtrlChannelPair4LActive
				INTEGER,
			iqmux47EmbCtrlChannelPair4RActive
				INTEGER,
			iqmux47EmbCtrlChannelPair5LActive
				INTEGER,
			iqmux47EmbCtrlChannelPair5RActive
				INTEGER,
			iqmux47EmbCtrlChannelPair6LActive
				INTEGER,
			iqmux47EmbCtrlChannelPair6RActive
				INTEGER,
			iqmux47EmbCtrlChannelPair7LActive
				INTEGER,
			iqmux47EmbCtrlChannelPair7RActive
				INTEGER,
			iqmux47EmbCtrlChannelPair8LActive
				INTEGER,
			iqmux47EmbCtrlChannelPair8RActive
				INTEGER,
			iqmux47AudioEmbCtrlEmbedderPriority
				INTEGER,
			iqmux47EmbGainEmbedPair1Embed1MuteL
				INTEGER,
			iqmux47EmbGainEmbedPair1Embed1MuteR
				INTEGER,
			iqmux47EmbGainEmbedPair1Embed1LGain
				INTEGER,
			iqmux47EmbGainEmbedPair1Embed1RGain
				INTEGER,
			iqmux47EmbGainEmbedPair1Stereo
				INTEGER,
			iqmux47EmbGainEmbedPair1Embed1InvertL
				INTEGER,
			iqmux47EmbGainEmbedPair1Embed1InvertR
				INTEGER,
			iqmux47EmbGainEmbedPair1Embed1LClip
				RollCallString,
			iqmux47EmbGainEmbedPair1Embed1RClip
				RollCallString,
			iqmux47EmbGainEmbedPair2Embed2MuteL
				INTEGER,
			iqmux47EmbGainEmbedPair2Embed2MuteR
				INTEGER,
			iqmux47EmbGainEmbedPair2Embed2LGain
				INTEGER,
			iqmux47EmbGainEmbedPair2Embed2RGain
				INTEGER,
			iqmux47EmbGainEmbedPair2Stereo
				INTEGER,
			iqmux47EmbGainEmbedPair2Embed2InvertL
				INTEGER,
			iqmux47EmbGainEmbedPair2Embed2InvertR
				INTEGER,
			iqmux47EmbGainEmbedPair2Embed2LClip
				RollCallString,
			iqmux47EmbGainEmbedPair2Embed2RClip
				RollCallString,
			iqmux47EmbGainEmbedPair3Embed3MuteL
				INTEGER,
			iqmux47EmbGainEmbedPair3Embed3MuteR
				INTEGER,
			iqmux47EmbGainEmbedPair3Embed3LGain
				INTEGER,
			iqmux47EmbGainEmbedPair3Embed3RGain
				INTEGER,
			iqmux47EmbGainEmbedPair3Stereo
				INTEGER,
			iqmux47EmbGainEmbedPair3Embed3InvertL
				INTEGER,
			iqmux47EmbGainEmbedPair3Embed3InvertR
				INTEGER,
			iqmux47EmbGainEmbedPair3Embed3LClip
				RollCallString,
			iqmux47EmbGainEmbedPair3Embed3RClip
				RollCallString,
			iqmux47EmbGainEmbedPair4Embed4MuteL
				INTEGER,
			iqmux47EmbGainEmbedPair4Embed4MuteR
				INTEGER,
			iqmux47EmbGainEmbedPair4Embed4LGain
				INTEGER,
			iqmux47EmbGainEmbedPair4Embed4RGain
				INTEGER,
			iqmux47EmbGainEmbedPair4Stereo
				INTEGER,
			iqmux47EmbGainEmbedPair4Embed4InvertL
				INTEGER,
			iqmux47EmbGainEmbedPair4Embed4InvertR
				INTEGER,
			iqmux47EmbGainEmbedPair4Embed4LClip
				RollCallString,
			iqmux47EmbGainEmbedPair4Embed4RClip
				RollCallString,
			iqmux47EmbGainEmbedPair5Embed5MuteL
				INTEGER,
			iqmux47EmbGainEmbedPair5Embed5MuteR
				INTEGER,
			iqmux47EmbGainEmbedPair5Embed5LGain
				INTEGER,
			iqmux47EmbGainEmbedPair5Embed5RGain
				INTEGER,
			iqmux47EmbGainEmbedPair5Stereo
				INTEGER,
			iqmux47EmbGainEmbedPair5Embed5InvertL
				INTEGER,
			iqmux47EmbGainEmbedPair5Embed5InvertR
				INTEGER,
			iqmux47EmbGainEmbedPair5Embed5LClip
				RollCallString,
			iqmux47EmbGainEmbedPair5Embed5RClip
				RollCallString,
			iqmux47EmbGainEmbedPair6Embed6MuteL
				INTEGER,
			iqmux47EmbGainEmbedPair6Embed6MuteR
				INTEGER,
			iqmux47EmbGainEmbedPair6Embed6LGain
				INTEGER,
			iqmux47EmbGainEmbedPair6Embed6RGain
				INTEGER,
			iqmux47EmbGainEmbedPair6Stereo
				INTEGER,
			iqmux47EmbGainEmbedPair6Embed6InvertL
				INTEGER,
			iqmux47EmbGainEmbedPair6Embed6InvertR
				INTEGER,
			iqmux47EmbGainEmbedPair6Embed6LClip
				RollCallString,
			iqmux47EmbGainEmbedPair6Embed6RClip
				RollCallString,
			iqmux47EmbGainEmbedPair7Embed7MuteL
				INTEGER,
			iqmux47EmbGainEmbedPair7Embed7MuteR
				INTEGER,
			iqmux47EmbGainEmbedPair7Embed7LGain
				INTEGER,
			iqmux47EmbGainEmbedPair7Embed7RGain
				INTEGER,
			iqmux47EmbGainEmbedPair7Stereo
				INTEGER,
			iqmux47EmbGainEmbedPair7Embed7InvertL
				INTEGER,
			iqmux47EmbGainEmbedPair7Embed7InvertR
				INTEGER,
			iqmux47EmbGainEmbedPair7Embed7LClip
				RollCallString,
			iqmux47EmbGainEmbedPair7Embed7RClip
				RollCallString,
			iqmux47EmbGainEmbedPair8Embed8MuteL
				INTEGER,
			iqmux47EmbGainEmbedPair8Embed8MuteR
				INTEGER,
			iqmux47EmbGainEmbedPair8Embed8LGain
				INTEGER,
			iqmux47EmbGainEmbedPair8Embed8RGain
				INTEGER,
			iqmux47EmbGainEmbedPair8Stereo
				INTEGER,
			iqmux47EmbGainEmbedPair8Embed8InvertL
				INTEGER,
			iqmux47EmbGainEmbedPair8Embed8InvertR
				INTEGER,
			iqmux47EmbGainEmbedPair8Embed8LClip
				RollCallString,
			iqmux47EmbGainEmbedPair8Embed8RClip
				RollCallString,
			iqmux47EmbOutEmbedPair1Left
				INTEGER,
			iqmux47EmbOutEmbedPair1Right
				INTEGER,
			iqmux47EmbOutEmbedPair1LinkLRSelection
				INTEGER,
			iqmux47EmbOutEmbedPair2Left
				INTEGER,
			iqmux47EmbOutEmbedPair2Right
				INTEGER,
			iqmux47EmbOutEmbedPair2LinkLRSelection
				INTEGER,
			iqmux47EmbOutEmbedPair3Left
				INTEGER,
			iqmux47EmbOutEmbedPair3Right
				INTEGER,
			iqmux47EmbOutEmbedPair3LinkLRSelection
				INTEGER,
			iqmux47EmbOutEmbedPair4Left
				INTEGER,
			iqmux47EmbOutEmbedPair4Right
				INTEGER,
			iqmux47EmbOutEmbedPair4LinkLRSelection
				INTEGER,
			iqmux47EmbOutEmbedPair5Left
				INTEGER,
			iqmux47EmbOutEmbedPair5Right
				INTEGER,
			iqmux47EmbOutEmbedPair5LinkLRSelection
				INTEGER,
			iqmux47EmbOutEmbedPair6Left
				INTEGER,
			iqmux47EmbOutEmbedPair6Right
				INTEGER,
			iqmux47EmbOutEmbedPair6LinkLRSelection
				INTEGER,
			iqmux47EmbOutEmbedPair7Left
				INTEGER,
			iqmux47EmbOutEmbedPair7Right
				INTEGER,
			iqmux47EmbOutEmbedPair7LinkLRSelection
				INTEGER,
			iqmux47EmbOutEmbedPair8Left
				INTEGER,
			iqmux47EmbOutEmbedPair8Right
				INTEGER,
			iqmux47EmbOutEmbedPair8LinkLRSelection
				INTEGER,
			iqmux47AudioEmbModeInput1
				INTEGER,
			iqmux47AudioEmbModeInput2
				INTEGER,
			iqmux47AudioEmbModeInput3
				INTEGER,
			iqmux47AudioEmbModeInput4
				INTEGER,
			iqmux47AudioEmbModeInput5
				INTEGER,
			iqmux47AudioEmbModeInput6
				INTEGER,
			iqmux47AudioEmbModeInput7
				INTEGER,
			iqmux47AudioEmbModeInput8
				INTEGER,
			iqmux47EmbedNamesDisembeder1
				RollCallString,
			iqmux47EmbedNamesDisembeder1R
				RollCallString,
			iqmux47EmbedNamesDisembeder2
				RollCallString,
			iqmux47EmbedNamesDisembeder2R
				RollCallString,
			iqmux47EmbedNamesDisembeder3
				RollCallString,
			iqmux47EmbedNamesDisembeder3R
				RollCallString,
			iqmux47EmbedNamesDisembeder4
				RollCallString,
			iqmux47EmbedNamesDisembeder4R
				RollCallString,
			iqmux47EmbedNamesDisembeder5
				RollCallString,
			iqmux47EmbedNamesDisembeder5R
				RollCallString,
			iqmux47EmbedNamesDisembeder6
				RollCallString,
			iqmux47EmbedNamesDisembeder6R
				RollCallString,
			iqmux47EmbedNamesDisembeder7
				RollCallString,
			iqmux47EmbedNamesDisembeder7R
				RollCallString,
			iqmux47EmbedNamesDisembeder8
				RollCallString,
			iqmux47EmbedNamesDisembeder8R
				RollCallString,
			iqmux47EmbedNamesEmbeddedOP1
				RollCallString,
			iqmux47EmbedNamesEmbeddedOP1R
				RollCallString,
			iqmux47EmbedNamesEmbeddedOP2
				RollCallString,
			iqmux47EmbedNamesEmbeddedOP2R
				RollCallString,
			iqmux47EmbedNamesEmbeddedOP3
				RollCallString,
			iqmux47EmbedNamesEmbeddedOP3R
				RollCallString,
			iqmux47EmbedNamesEmbeddedOP4
				RollCallString,
			iqmux47EmbedNamesEmbeddedOP4R
				RollCallString,
			iqmux47EmbedNamesEmbeddedOP5
				RollCallString,
			iqmux47EmbedNamesEmbeddedOP5R
				RollCallString,
			iqmux47EmbedNamesEmbeddedOP6
				RollCallString,
			iqmux47EmbedNamesEmbeddedOP6R
				RollCallString,
			iqmux47EmbedNamesEmbeddedOP7
				RollCallString,
			iqmux47EmbedNamesEmbeddedOP7R
				RollCallString,
			iqmux47EmbedNamesEmbeddedOP8
				RollCallString,
			iqmux47EmbedNamesEmbeddedOP8R
				RollCallString,
			iqmux47EmbedNamesIPStereoDisemb1
				INTEGER,
			iqmux47EmbedNamesIPStereoDisemb2
				INTEGER,
			iqmux47EmbedNamesIPStereoDisemb3
				INTEGER,
			iqmux47EmbedNamesIPStereoDisemb4
				INTEGER,
			iqmux47EmbedNamesIPStereoDisemb5
				INTEGER,
			iqmux47EmbedNamesIPStereoDisemb6
				INTEGER,
			iqmux47EmbedNamesIPStereoDisemb7
				INTEGER,
			iqmux47EmbedNamesIPStereoDisemb8
				INTEGER,
			iqmux47EmbedNamesOPStereoEmbed1
				INTEGER,
			iqmux47EmbedNamesOPStereoEmbed2
				INTEGER,
			iqmux47EmbedNamesOPStereoEmbed3
				INTEGER,
			iqmux47EmbedNamesOPStereoEmbed4
				INTEGER,
			iqmux47EmbedNamesOPStereoEmbed5
				INTEGER,
			iqmux47EmbedNamesOPStereoEmbed6
				INTEGER,
			iqmux47EmbedNamesOPStereoEmbed7
				INTEGER,
			iqmux47EmbedNamesOPStereoEmbed8
				INTEGER,
			iqmux47AudioMixNamesMix1
				RollCallString,
			iqmux47AudioMixNamesMix2
				RollCallString,
			iqmux47AudioMixNamesMix3
				RollCallString,
			iqmux47AudioMixNamesMix4
				RollCallString,
			iqmux47Mix1RoutingSource1
				INTEGER,
			iqmux47Mix1RoutingInvert1
				INTEGER,
			iqmux47Mix1RoutingSource2
				INTEGER,
			iqmux47Mix1RoutingInvert2
				INTEGER,
			iqmux47Mix1RoutingSource3
				INTEGER,
			iqmux47Mix1RoutingInvert3
				INTEGER,
			iqmux47Mix1RoutingSource4
				INTEGER,
			iqmux47Mix1RoutingInvert4
				INTEGER,
			iqmux47Mix1GainGain1
				INTEGER,
			iqmux47Mix1GainMute1
				INTEGER,
			iqmux47Mix1GainGain2
				INTEGER,
			iqmux47Mix1GainMute2
				INTEGER,
			iqmux47Mix1GainGain3
				INTEGER,
			iqmux47Mix1GainMute3
				INTEGER,
			iqmux47Mix1GainGain4
				INTEGER,
			iqmux47Mix1GainMute4
				INTEGER,
			iqmux47Mix1GainInp1Clip
				RollCallString,
			iqmux47Mix1GainInp2Clip
				RollCallString,
			iqmux47Mix1GainInp3Clip
				RollCallString,
			iqmux47Mix1GainInp4Clip
				RollCallString,
			iqmux47Mix1GainOPClip
				RollCallString,
			iqmux47Mix2RoutingSource1
				INTEGER,
			iqmux47Mix2RoutingInvert1
				INTEGER,
			iqmux47Mix2RoutingSource2
				INTEGER,
			iqmux47Mix2RoutingInvert2
				INTEGER,
			iqmux47Mix2RoutingSource3
				INTEGER,
			iqmux47Mix2RoutingInvert3
				INTEGER,
			iqmux47Mix2RoutingSource4
				INTEGER,
			iqmux47Mix2RoutingInvert4
				INTEGER,
			iqmux47Mix2GainGain1
				INTEGER,
			iqmux47Mix2GainMute1
				INTEGER,
			iqmux47Mix2GainGain2
				INTEGER,
			iqmux47Mix2GainMute2
				INTEGER,
			iqmux47Mix2GainGain3
				INTEGER,
			iqmux47Mix2GainMute3
				INTEGER,
			iqmux47Mix2GainGain4
				INTEGER,
			iqmux47Mix2GainMute4
				INTEGER,
			iqmux47Mix2GainInp1Clip
				RollCallString,
			iqmux47Mix2GainInp2Clip
				RollCallString,
			iqmux47Mix2GainInp3Clip
				RollCallString,
			iqmux47Mix2GainInp4Clip
				RollCallString,
			iqmux47Mix2GainOPClip
				RollCallString,
			iqmux47Mix3RoutingSource1
				INTEGER,
			iqmux47Mix3RoutingInvert1
				INTEGER,
			iqmux47Mix3RoutingSource2
				INTEGER,
			iqmux47Mix3RoutingInvert2
				INTEGER,
			iqmux47Mix3RoutingSource3
				INTEGER,
			iqmux47Mix3RoutingInvert3
				INTEGER,
			iqmux47Mix3RoutingSource4
				INTEGER,
			iqmux47Mix3RoutingInvert4
				INTEGER,
			iqmux47Mix3GainGain1
				INTEGER,
			iqmux47Mix3GainMute1
				INTEGER,
			iqmux47Mix3GainGain2
				INTEGER,
			iqmux47Mix3GainMute2
				INTEGER,
			iqmux47Mix3GainGain3
				INTEGER,
			iqmux47Mix3GainMute3
				INTEGER,
			iqmux47Mix3GainGain4
				INTEGER,
			iqmux47Mix3GainMute4
				INTEGER,
			iqmux47Mix3GainInp1Clip
				RollCallString,
			iqmux47Mix3GainInp2Clip
				RollCallString,
			iqmux47Mix3GainInp3Clip
				RollCallString,
			iqmux47Mix3GainInp4Clip
				RollCallString,
			iqmux47Mix3GainOPClip
				RollCallString,
			iqmux47Mix4RoutingSource1
				INTEGER,
			iqmux47Mix4RoutingInvert1
				INTEGER,
			iqmux47Mix4RoutingSource2
				INTEGER,
			iqmux47Mix4RoutingInvert2
				INTEGER,
			iqmux47Mix4RoutingSource3
				INTEGER,
			iqmux47Mix4RoutingInvert3
				INTEGER,
			iqmux47Mix4RoutingSource4
				INTEGER,
			iqmux47Mix4RoutingInvert4
				INTEGER,
			iqmux47Mix4GainGain1
				INTEGER,
			iqmux47Mix4GainMute1
				INTEGER,
			iqmux47Mix4GainGain2
				INTEGER,
			iqmux47Mix4GainMute2
				INTEGER,
			iqmux47Mix4GainGain3
				INTEGER,
			iqmux47Mix4GainMute3
				INTEGER,
			iqmux47Mix4GainGain4
				INTEGER,
			iqmux47Mix4GainMute4
				INTEGER,
			iqmux47Mix4GainInp1Clip
				RollCallString,
			iqmux47Mix4GainInp2Clip
				RollCallString,
			iqmux47Mix4GainInp3Clip
				RollCallString,
			iqmux47Mix4GainInp4Clip
				RollCallString,
			iqmux47Mix4GainOPClip
				RollCallString,
			iqmux47AESGainOut1AESOut1MuteL
				INTEGER,
			iqmux47AESGainOut1AESOut1MuteR
				INTEGER,
			iqmux47AESGainOut1AESOut1LGain
				INTEGER,
			iqmux47AESGainOut1AESOut1RGain
				INTEGER,
			iqmux47AESGainOut1Stereo
				INTEGER,
			iqmux47AESGainOut1AESOut1InvertL
				INTEGER,
			iqmux47AESGainOut1AESOut1InvertR
				INTEGER,
			iqmux47AESGainOut1AESOut1LClip
				RollCallString,
			iqmux47AESGainOut1AESOut1RClip
				RollCallString,
			iqmux47AESGainOut2AESOut2MuteL
				INTEGER,
			iqmux47AESGainOut2AESOut2MuteR
				INTEGER,
			iqmux47AESGainOut2AESOut2LGain
				INTEGER,
			iqmux47AESGainOut2AESOut2RGain
				INTEGER,
			iqmux47AESGainOut2Stereo
				INTEGER,
			iqmux47AESGainOut2AESOut2InvertL
				INTEGER,
			iqmux47AESGainOut2AESOut2InvertR
				INTEGER,
			iqmux47AESGainOut2AESOut2LClip
				RollCallString,
			iqmux47AESGainOut2AESOut2RClip
				RollCallString,
			iqmux47AESGainOut3AESOut3MuteL
				INTEGER,
			iqmux47AESGainOut3AESOut3MuteR
				INTEGER,
			iqmux47AESGainOut3AESOut3LGain
				INTEGER,
			iqmux47AESGainOut3AESOut3RGain
				INTEGER,
			iqmux47AESGainOut3Stereo
				INTEGER,
			iqmux47AESGainOut3AESOut3InvertL
				INTEGER,
			iqmux47AESGainOut3AESOut3InvertR
				INTEGER,
			iqmux47AESGainOut3AESOut3LClip
				RollCallString,
			iqmux47AESGainOut3AESOut3RClip
				RollCallString,
			iqmux47AESGainOut4AESOut4MuteL
				INTEGER,
			iqmux47AESGainOut4AESOut4MuteR
				INTEGER,
			iqmux47AESGainOut4AESOut4LGain
				INTEGER,
			iqmux47AESGainOut4AESOut4RGain
				INTEGER,
			iqmux47AESGainOut4Stereo
				INTEGER,
			iqmux47AESGainOut4AESOut4InvertL
				INTEGER,
			iqmux47AESGainOut4AESOut4InvertR
				INTEGER,
			iqmux47AESGainOut4AESOut4LClip
				RollCallString,
			iqmux47AESGainOut4AESOut4RClip
				RollCallString,
			iqmux47AESGainOut5AESOut5MuteL
				INTEGER,
			iqmux47AESGainOut5AESOut5MuteR
				INTEGER,
			iqmux47AESGainOut5AESOut5LGain
				INTEGER,
			iqmux47AESGainOut5AESOut5RGain
				INTEGER,
			iqmux47AESGainOut5Stereo
				INTEGER,
			iqmux47AESGainOut5AESOut5InvertL
				INTEGER,
			iqmux47AESGainOut5AESOut5InvertR
				INTEGER,
			iqmux47AESGainOut5AESOut5LClip
				RollCallString,
			iqmux47AESGainOut5AESOut5RClip
				RollCallString,
			iqmux47AESGainOut6AESOut6MuteL
				INTEGER,
			iqmux47AESGainOut6AESOut6MuteR
				INTEGER,
			iqmux47AESGainOut6AESOut6LGain
				INTEGER,
			iqmux47AESGainOut6AESOut6RGain
				INTEGER,
			iqmux47AESGainOut6Stereo
				INTEGER,
			iqmux47AESGainOut6AESOut6InvertL
				INTEGER,
			iqmux47AESGainOut6AESOut6InvertR
				INTEGER,
			iqmux47AESGainOut6AESOut6LClip
				RollCallString,
			iqmux47AESGainOut6AESOut6RClip
				RollCallString,
			iqmux47AESGainOut7AESOut7MuteL
				INTEGER,
			iqmux47AESGainOut7AESOut7MuteR
				INTEGER,
			iqmux47AESGainOut7AESOut7LGain
				INTEGER,
			iqmux47AESGainOut7AESOut7RGain
				INTEGER,
			iqmux47AESGainOut7Stereo
				INTEGER,
			iqmux47AESGainOut7AESOut7InvertL
				INTEGER,
			iqmux47AESGainOut7AESOut7InvertR
				INTEGER,
			iqmux47AESGainOut7AESOut7LClip
				RollCallString,
			iqmux47AESGainOut7AESOut7RClip
				RollCallString,
			iqmux47AESGainOut8AESOut8MuteL
				INTEGER,
			iqmux47AESGainOut8AESOut8MuteR
				INTEGER,
			iqmux47AESGainOut8AESOut8LGain
				INTEGER,
			iqmux47AESGainOut8AESOut8RGain
				INTEGER,
			iqmux47AESGainOut8Stereo
				INTEGER,
			iqmux47AESGainOut8AESOut8InvertL
				INTEGER,
			iqmux47AESGainOut8AESOut8InvertR
				INTEGER,
			iqmux47AESGainOut8AESOut8LClip
				RollCallString,
			iqmux47AESGainOut8AESOut8RClip
				RollCallString,
			iqmux47AESOut1Left
				INTEGER,
			iqmux47AESOut1Right
				INTEGER,
			iqmux47AESOut1LinkLRSelection
				INTEGER,
			iqmux47AESOut2Left
				INTEGER,
			iqmux47AESOut2Right
				INTEGER,
			iqmux47AESOut2LinkLRSelection
				INTEGER,
			iqmux47AESOut3Left
				INTEGER,
			iqmux47AESOut3Right
				INTEGER,
			iqmux47AESOut3LinkLRSelection
				INTEGER,
			iqmux47AESOut4Left
				INTEGER,
			iqmux47AESOut4Right
				INTEGER,
			iqmux47AESOut4LinkLRSelection
				INTEGER,
			iqmux47AESOut5Left
				INTEGER,
			iqmux47AESOut5Right
				INTEGER,
			iqmux47AESOut5LinkLRSelection
				INTEGER,
			iqmux47AESOut6Left
				INTEGER,
			iqmux47AESOut6Right
				INTEGER,
			iqmux47AESOut6LinkLRSelection
				INTEGER,
			iqmux47AESOut7Left
				INTEGER,
			iqmux47AESOut7Right
				INTEGER,
			iqmux47AESOut7LinkLRSelection
				INTEGER,
			iqmux47AESOut8Left
				INTEGER,
			iqmux47AESOut8Right
				INTEGER,
			iqmux47AESOut8LinkLRSelection
				INTEGER,
			iqmux47AESOutMonitoropLeft
				INTEGER,
			iqmux47AESOutMonitoropRight
				INTEGER,
			iqmux47AESOutMonitoropLinkLRSelection
				INTEGER,
			iqmux47AESOutPortNamesAESPort1Stereo
				INTEGER,
			iqmux47AESOutPortNamesAESPort1L
				RollCallString,
			iqmux47AESOutPortNamesAESPort1R
				RollCallString,
			iqmux47AESOutPortNamesAESPort2Stereo
				INTEGER,
			iqmux47AESOutPortNamesAESPort2L
				RollCallString,
			iqmux47AESOutPortNamesAESPort2R
				RollCallString,
			iqmux47AESOutPortNamesAESPort3Stereo
				INTEGER,
			iqmux47AESOutPortNamesAESPort3L
				RollCallString,
			iqmux47AESOutPortNamesAESPort3R
				RollCallString,
			iqmux47AESOutPortNamesAESPort4Stereo
				INTEGER,
			iqmux47AESOutPortNamesAESPort4L
				RollCallString,
			iqmux47AESOutPortNamesAESPort4R
				RollCallString,
			iqmux47AESOutPortNamesAESPort5Stereo
				INTEGER,
			iqmux47AESOutPortNamesAESPort5L
				RollCallString,
			iqmux47AESOutPortNamesAESPort5R
				RollCallString,
			iqmux47AESOutPortNamesAESPort6Stereo
				INTEGER,
			iqmux47AESOutPortNamesAESPort6L
				RollCallString,
			iqmux47AESOutPortNamesAESPort6R
				RollCallString,
			iqmux47AESOutPortNamesAESPort7Stereo
				INTEGER,
			iqmux47AESOutPortNamesAESPort7L
				RollCallString,
			iqmux47AESOutPortNamesAESPort7R
				RollCallString,
			iqmux47AESOutPortNamesAESPort8Stereo
				INTEGER,
			iqmux47AESOutPortNamesAESPort8L
				RollCallString,
			iqmux47AESOutPortNamesAESPort8R
				RollCallString,
			iqmux47AESBusDataModeInput1
				INTEGER,
			iqmux47AESBusDataModeInput2
				INTEGER,
			iqmux47AESBusDataModeInput3
				INTEGER,
			iqmux47AESBusDataModeInput4
				INTEGER,
			iqmux47AESBusDataModeInput5
				INTEGER,
			iqmux47AESBusDataModeInput6
				INTEGER,
			iqmux47AESBusDataModeInput7
				INTEGER,
			iqmux47AESBusDataModeInput8
				INTEGER,
			iqmux47AESBusNamesAESBus1Stereo
				INTEGER,
			iqmux47AESBusNamesAESBus1
				RollCallString,
			iqmux47AESBusNamesAESBus1R
				RollCallString,
			iqmux47AESBusNamesAESBus2Stereo
				INTEGER,
			iqmux47AESBusNamesAESBus2
				RollCallString,
			iqmux47AESBusNamesAESBus2R
				RollCallString,
			iqmux47AESBusNamesAESBus3Stereo
				INTEGER,
			iqmux47AESBusNamesAESBus3
				RollCallString,
			iqmux47AESBusNamesAESBus3R
				RollCallString,
			iqmux47AESBusNamesAESBus4Stereo
				INTEGER,
			iqmux47AESBusNamesAESBus4
				RollCallString,
			iqmux47AESBusNamesAESBus4R
				RollCallString,
			iqmux47AESBusNamesAESBus5Stereo
				INTEGER,
			iqmux47AESBusNamesAESBus5
				RollCallString,
			iqmux47AESBusNamesAESBus5R
				RollCallString,
			iqmux47AESBusNamesAESBus6Stereo
				INTEGER,
			iqmux47AESBusNamesAESBus6
				RollCallString,
			iqmux47AESBusNamesAESBus6R
				RollCallString,
			iqmux47AESBusNamesAESBus7Stereo
				INTEGER,
			iqmux47AESBusNamesAESBus7
				RollCallString,
			iqmux47AESBusNamesAESBus7R
				RollCallString,
			iqmux47AESBusNamesAESBus8Stereo
				INTEGER,
			iqmux47AESBusNamesAESBus8
				RollCallString,
			iqmux47AESBusNamesAESBus8R
				RollCallString,
			iqmux47AESBusRoutingSource1
				INTEGER,
			iqmux47AESBusRoutingSource2
				INTEGER,
			iqmux47AESBusRoutingSource3
				INTEGER,
			iqmux47AESBusRoutingSource4
				INTEGER,
			iqmux47AESBusRoutingSource5
				INTEGER,
			iqmux47AESBusRoutingSource6
				INTEGER,
			iqmux47AESBusRoutingSource7
				INTEGER,
			iqmux47AESBusRoutingSource8
				INTEGER,
			iqmux47AESPortsDirectionAES1Out
				INTEGER,
			iqmux47AESPortsDirectionAES2Out
				INTEGER,
			iqmux47AESPortsDirectionAES3Out
				INTEGER,
			iqmux47AESPortsDirectionAES4Out
				INTEGER,
			iqmux47AESPortsDirectionAES5Out
				INTEGER,
			iqmux47AESPortsDirectionAES6Out
				INTEGER,
			iqmux47AESPortsDirectionAES7Out
				INTEGER,
			iqmux47AESPortsDirectionAES8Out
				INTEGER,
			iqmux47AudioDolbyETimingSelAudioPair
				INTEGER,
			iqmux47AudioDolbyETimingRelativeTiming
				RollCallString,
			iqmux47AudioDolbyETimingStatus
				RollCallString,
			iqmux47AudioDolbyETimingError
				RollCallString,
			iqmux47DolbyETimingLineStandard
				INTEGER,
			iqmux47DolbyETimingLineAutoLineNo
				INTEGER,
			iqmux47DolbyELineUserDolbyELinePair1
				INTEGER,
			iqmux47DolbyELineUserDolbyELinePair2
				INTEGER,
			iqmux47DolbyELineUserDolbyELinePair3
				INTEGER,
			iqmux47DolbyELineUserDolbyELinePair4
				INTEGER,
			iqmux47DolbyELineUserDolbyELinePair5
				INTEGER,
			iqmux47DolbyELineUserDolbyELinePair6
				INTEGER,
			iqmux47DolbyELineUserDolbyELinePair7
				INTEGER,
			iqmux47DolbyELineUserDolbyELinePair8
				INTEGER,
			iqmux47VidDelayInternalDelay
				RollCallString,
			iqmux47VidDelayDelayMode
				INTEGER,
			iqmux47VidSetDelayDelayFrames
				INTEGER,
			iqmux47VidSetDelayVerticalTiming
				INTEGER,
			iqmux47VidSetDelayHorizontalTiming
				INTEGER,
			iqmux47VidSetDelayDelayms
				INTEGER,
			iqmux47UtilsPatternsPatternEnable
				INTEGER,
			iqmux47UtilsPatternsScrollPattern
				INTEGER,
			iqmux47UtilsPatternsPatternType
				INTEGER,
			iqmux47UtilsANCblankonMismat
				INTEGER,
			iqmux47UtilsFreezeForceFreeze
				INTEGER,
			iqmux47UtilsFreezeFreezeType
				INTEGER,
			iqmux47UtilsMonochrome
				INTEGER,
			iqmux47UtilsMonochromeMonochromeType
				INTEGER,
			iqmux47UtilsVBIBlankingANCMode
				INTEGER,
			iqmux47UtilsVBIBlankingStandard
				INTEGER,
			iqmux47UtilsVBIBlankingBlankAll
				INTEGER,
			iqmux47UtilsVBIBlankingPassAll
				INTEGER,
			iqmux47UtilsVBIBlankingBlank1
				INTEGER,
			iqmux47UtilsVBIBlankingBlank2
				INTEGER,
			iqmux47UtilsVBIBlankingBlank3
				INTEGER,
			iqmux47UtilsVBIBlankingBlank4
				INTEGER,
			iqmux47UtilsVBIBlankingBlank5
				INTEGER,
			iqmux47UtilsVBIBlankingBlank6
				INTEGER,
			iqmux47UtilsVBIBlankingBlank7
				INTEGER,
			iqmux47UtilsVBIBlankingBlank8
				INTEGER,
			iqmux47UtilsVBIBlankingBlank9
				INTEGER,
			iqmux47UtilsVBIBlankingBlank10
				INTEGER,
			iqmux47UtilsVBIBlankingBlank11
				INTEGER,
			iqmux47UtilsVBIBlankingBlank12
				INTEGER,
			iqmux47UtilsVBIBlankingBlank13
				INTEGER,
			iqmux47UtilsVBIBlankingBlank14
				INTEGER,
			iqmux47UtilsVBIBlankingBlank15
				INTEGER,
			iqmux47UtilsVBIBlankingBlank16
				INTEGER,
			iqmux47UtilsVBIBlankingBlank17
				INTEGER,
			iqmux47UtilsVBIBlankingBlank18
				INTEGER,
			iqmux47UtilsVBIBlankingBlank19
				INTEGER,
			iqmux47UtilsVBIBlankingBlank20
				INTEGER,
			iqmux47UtilsVBIBlankingBlank21
				INTEGER,
			iqmux47UtilsVBIBlankingBlank22
				INTEGER,
			iqmux47UtilsVBIBlankingBlank23
				INTEGER,
			iqmux47UtilsVBIBlankingBlank24
				INTEGER,
			iqmux47UtilsVBIBlankingBlank25
				INTEGER,
			iqmux47UtilsVBIBlankingBlank26
				INTEGER,
			iqmux47UtilsVBIBlankingBlank27
				INTEGER,
			iqmux47UtilsVBIBlankingBlank28
				INTEGER,
			iqmux47UtilsVBIBlankingBlank29
				INTEGER,
			iqmux47UtilsVBIBlankingBlank30
				INTEGER,
			iqmux47UtilsVBIBlankingBlank31
				INTEGER,
			iqmux47UtilsVBIBlankingBlank32
				INTEGER,
			iqmux47UtilsVBIBlankingBlank33
				INTEGER,
			iqmux47UtilsVBIBlankingBlank34
				INTEGER,
			iqmux47MemoriesRecallMemory
				INTEGER,
			iqmux47MemoriesSelMemory
				INTEGER,
			iqmux47SaveMemories
				INTEGER,
			iqmux47ClearMemories
				INTEGER,
			iqmux47MemoriesMemoryNameChangeName
				RollCallString,
			iqmux47MemoriesLastUserMemory
				RollCallString,
			iqmux47MemoriesMemoryName1
				RollCallString,
			iqmux47MemoriesMemoryName2
				RollCallString,
			iqmux47MemoriesMemoryName3
				RollCallString,
			iqmux47MemoriesMemoryName4
				RollCallString,
			iqmux47MemoriesMemoryName5
				RollCallString,
			iqmux47MemoriesMemoryName6
				RollCallString,
			iqmux47MemoriesMemoryName7
				RollCallString,
			iqmux47MemoriesMemoryName8
				RollCallString,
			iqmux47MemoriesMemoryName9
				RollCallString,
			iqmux47MemoriesMemoryName10
				RollCallString,
			iqmux47MemoriesMemoryName11
				RollCallString,
			iqmux47MemoriesMemoryName12
				RollCallString,
			iqmux47MemoriesMemoryName13
				RollCallString,
			iqmux47MemoriesMemoryName14
				RollCallString,
			iqmux47MemoriesMemoryName15
				RollCallString,
			iqmux47MemoriesMemoryName16
				RollCallString,
			iqmux47LoggingVideoLogInput1Type
				INTEGER,
			iqmux47LoggingVideoInput1Type
				RollCallString,
			iqmux47LoggingVideoLogInput1Status
				INTEGER,
			iqmux47LoggingVideoInput1Status
				RollCallString,
			iqmux47LoggingVideoLogInput1Std
				INTEGER,
			iqmux47LoggingVideoInput1Std
				RollCallString,
			iqmux47LoggingVideoLogInput1Errors
				INTEGER,
			iqmux47LoggingVideoInput1Errors
				RollCallString,
			iqmux47LoggingVideoLogInput1ErrSecs
				INTEGER,
			iqmux47LoggingVideoInput1ErrSecs
				RollCallString,
			iqmux47LoggingVideoLogInput1ANCErr35000
				INTEGER,
			iqmux47LoggingVideoInput1ANCErrors
				RollCallString,
			iqmux47LoggingVideoLogInput1ANCErr35001
				INTEGER,
			iqmux47LoggingVideoInput1ANCErrSecs
				RollCallString,
			iqmux47LoggingVideoLogOutputState
				INTEGER,
			iqmux47LoggingVideoOutputState
				RollCallString,
			iqmux47LoggingVideoLogOutputType
				INTEGER,
			iqmux47LoggingVideoOutputType
				RollCallString,
			iqmux47LoggingVideoLogOutputStandard
				INTEGER,
			iqmux47LoggingVideoOutputStandard
				RollCallString,
			iqmux47LoggingVideoLogoutputANCstat
				INTEGER,
			iqmux47LoggingVideoOutputANCstate
				RollCallString,
			iqmux47LoggingEmbedAudioLogInp1Emb1stat
				INTEGER,
			iqmux47LoggingEmbedAudioInp1Emb1state
				RollCallString,
			iqmux47LoggingEmbedAudioLogInp1Emb2stat
				INTEGER,
			iqmux47LoggingEmbedAudioInp1Emb2state
				RollCallString,
			iqmux47LoggingEmbedAudioLogInp1Emb3stat
				INTEGER,
			iqmux47LoggingEmbedAudioInp1Emb3state
				RollCallString,
			iqmux47LoggingEmbedAudioLogInp1Emb4stat
				INTEGER,
			iqmux47LoggingEmbedAudioInp1Emb4state
				RollCallString,
			iqmux47LoggingEmbedAudioLogInp1Emb5stat
				INTEGER,
			iqmux47LoggingEmbedAudioInp1Emb5state
				RollCallString,
			iqmux47LoggingEmbedAudioLogInp1Emb6stat
				INTEGER,
			iqmux47LoggingEmbedAudioInp1Emb6state
				RollCallString,
			iqmux47LoggingEmbedAudioLogInp1Emb7stat
				INTEGER,
			iqmux47LoggingEmbedAudioInp1Emb7state
				RollCallString,
			iqmux47LoggingEmbedAudioLogInp1Emb8stat
				INTEGER,
			iqmux47LoggingEmbedAudioInp1Emb8state
				RollCallString,
			iqmux47LoggingEmbedAudioLogInp1Emb1type
				INTEGER,
			iqmux47LoggingEmbedAudioInp1Emb1type
				RollCallString,
			iqmux47LoggingEmbedAudioLogInp1Emb2type
				INTEGER,
			iqmux47LoggingEmbedAudioInp1Emb2type
				RollCallString,
			iqmux47LoggingEmbedAudioLogInp1Emb3type
				INTEGER,
			iqmux47LoggingEmbedAudioInp1Emb3type
				RollCallString,
			iqmux47LoggingEmbedAudioLogInp1Emb4type
				INTEGER,
			iqmux47LoggingEmbedAudioInp1Emb4type
				RollCallString,
			iqmux47LoggingEmbedAudioLogInp1Emb5type
				INTEGER,
			iqmux47LoggingEmbedAudioInp1Emb5type
				RollCallString,
			iqmux47LoggingEmbedAudioLogInp1Emb6type
				INTEGER,
			iqmux47LoggingEmbedAudioInp1Emb6type
				RollCallString,
			iqmux47LoggingEmbedAudioLogInp1Emb7type
				INTEGER,
			iqmux47LoggingEmbedAudioInp1Emb7type
				RollCallString,
			iqmux47LoggingEmbedAudioLogInp1Emb8type
				INTEGER,
			iqmux47LoggingEmbedAudioInp1Emb8type
				RollCallString,
			iqmux47LoggingOPAudioLogOutEmb1state
				INTEGER,
			iqmux47LoggingOPAudioOutEmb1state
				RollCallString,
			iqmux47LoggingOPAudioLogOutEmb2state
				INTEGER,
			iqmux47LoggingOPAudioOutEmb2state
				RollCallString,
			iqmux47LoggingOPAudioLogOutEmb3state
				INTEGER,
			iqmux47LoggingOPAudioOutEmb3state
				RollCallString,
			iqmux47LoggingOPAudioLogOutEmb4state
				INTEGER,
			iqmux47LoggingOPAudioOutEmb4state
				RollCallString,
			iqmux47LoggingOPAudioLogOutEmb5state
				INTEGER,
			iqmux47LoggingOPAudioOutEmb5state
				RollCallString,
			iqmux47LoggingOPAudioLogOutEmb6state
				INTEGER,
			iqmux47LoggingOPAudioOutEmb6state
				RollCallString,
			iqmux47LoggingOPAudioLogOutEmb7state
				INTEGER,
			iqmux47LoggingOPAudioOutEmb7state
				RollCallString,
			iqmux47LoggingOPAudioLogOutEmb8state
				INTEGER,
			iqmux47LoggingOPAudioOutEmb8state
				RollCallString,
			iqmux47LoggingOPAudioLogOutEmb1type
				INTEGER,
			iqmux47LoggingOPAudioOutEmb1type
				RollCallString,
			iqmux47LoggingOPAudioLogOutEmb2type
				INTEGER,
			iqmux47LoggingOPAudioOutEmb2type
				RollCallString,
			iqmux47LoggingOPAudioLogOutEmb3type
				INTEGER,
			iqmux47LoggingOPAudioOutEmb3type
				RollCallString,
			iqmux47LoggingOPAudioLogOutEmb4type
				INTEGER,
			iqmux47LoggingOPAudioOutEmb4type
				RollCallString,
			iqmux47LoggingOPAudioLogOutEmb5type
				INTEGER,
			iqmux47LoggingOPAudioOutEmb5type
				RollCallString,
			iqmux47LoggingOPAudioLogOutEmb6type
				INTEGER,
			iqmux47LoggingOPAudioOutEmb6type
				RollCallString,
			iqmux47LoggingOPAudioLogOutEmb7type
				INTEGER,
			iqmux47LoggingOPAudioOutEmb7type
				RollCallString,
			iqmux47LoggingOPAudioLogOutEmb8type
				INTEGER,
			iqmux47LoggingOPAudioOutEmb8type
				RollCallString,
			iqmux47LoggingOPAudioLevelLogOutEmb1LLev
				INTEGER,
			iqmux47LoggingOPAudioLevelOutEmb1LLevel
				RollCallString,
			iqmux47LoggingOPAudioLevelLogOutEmb1RLev
				INTEGER,
			iqmux47LoggingOPAudioLevelOutEmb1RLevel
				RollCallString,
			iqmux47LoggingOPAudioLevelLogOutEmb2LLev
				INTEGER,
			iqmux47LoggingOPAudioLevelOutEmb2LLevel
				RollCallString,
			iqmux47LoggingOPAudioLevelLogOutEmb2RLev
				INTEGER,
			iqmux47LoggingOPAudioLevelOutEmb2RLevel
				RollCallString,
			iqmux47LoggingOPAudioLevelLogOutEmb3LLev
				INTEGER,
			iqmux47LoggingOPAudioLevelOutEmb3LLevel
				RollCallString,
			iqmux47LoggingOPAudioLevelLogOutEmb3RLev
				INTEGER,
			iqmux47LoggingOPAudioLevelOutEmb3RLevel
				RollCallString,
			iqmux47LoggingOPAudioLevelLogOutEmb4LLev
				INTEGER,
			iqmux47LoggingOPAudioLevelOutEmb4LLevel
				RollCallString,
			iqmux47LoggingOPAudioLevelLogOutEmb4RLev
				INTEGER,
			iqmux47LoggingOPAudioLevelOutEmb4RLevel
				RollCallString,
			iqmux47LoggingOPAudioLevelLogOutEmb5LLev
				INTEGER,
			iqmux47LoggingOPAudioLevelOutEmb5LLevel
				RollCallString,
			iqmux47LoggingOPAudioLevelLogOutEmb5RLev
				INTEGER,
			iqmux47LoggingOPAudioLevelOutEmb5RLevel
				RollCallString,
			iqmux47LoggingOPAudioLevelLogOutEmb6LLev
				INTEGER,
			iqmux47LoggingOPAudioLevelOutEmb6LLevel
				RollCallString,
			iqmux47LoggingOPAudioLevelLogOutEmb6RLev
				INTEGER,
			iqmux47LoggingOPAudioLevelOutEmb6RLevel
				RollCallString,
			iqmux47LoggingOPAudioLevelLogOutEmb7LLev
				INTEGER,
			iqmux47LoggingOPAudioLevelOutEmb7LLevel
				RollCallString,
			iqmux47LoggingOPAudioLevelLogOutEmb7RLev
				INTEGER,
			iqmux47LoggingOPAudioLevelOutEmb7RLevel
				RollCallString,
			iqmux47LoggingOPAudioLevelLogOutEmb8LLev
				INTEGER,
			iqmux47LoggingOPAudioLevelOutEmb8LLevel
				RollCallString,
			iqmux47LoggingOPAudioLevelLogOutEmb8RLev
				INTEGER,
			iqmux47LoggingOPAudioLevelOutEmb8RLevel
				RollCallString,
			iqmux47LoggingOPDolbyELogEmbDolbyE1
				INTEGER,
			iqmux47LoggingOPDolbyEEmbDolbyE1
				RollCallString,
			iqmux47LoggingOPDolbyELogEmbDolbyE2
				INTEGER,
			iqmux47LoggingOPDolbyEEmbDolbyE2
				RollCallString,
			iqmux47LoggingOPDolbyELogEmbDolbyE3
				INTEGER,
			iqmux47LoggingOPDolbyEEmbDolbyE3
				RollCallString,
			iqmux47LoggingOPDolbyELogEmbDolbyE4
				INTEGER,
			iqmux47LoggingOPDolbyEEmbDolbyE4
				RollCallString,
			iqmux47LoggingOPDolbyELogEmbDolbyE5
				INTEGER,
			iqmux47LoggingOPDolbyEEmbDolbyE5
				RollCallString,
			iqmux47LoggingOPDolbyELogEmbDolbyE6
				INTEGER,
			iqmux47LoggingOPDolbyEEmbDolbyE6
				RollCallString,
			iqmux47LoggingOPDolbyELogEmbDolbyE7
				INTEGER,
			iqmux47LoggingOPDolbyEEmbDolbyE7
				RollCallString,
			iqmux47LoggingOPDolbyELogEmbDolbyE8
				INTEGER,
			iqmux47LoggingOPDolbyEEmbDolbyE8
				RollCallString,
			iqmux47LoggingAESInputLogAESInput1sta
				INTEGER,
			iqmux47LoggingAESInputAESInput1state
				RollCallString,
			iqmux47LoggingAESInputLogAESInput2sta
				INTEGER,
			iqmux47LoggingAESInputAESInput2state
				RollCallString,
			iqmux47LoggingAESInputLogAESInput3sta
				INTEGER,
			iqmux47LoggingAESInputAESInput3state
				RollCallString,
			iqmux47LoggingAESInputLogAESInput4sta
				INTEGER,
			iqmux47LoggingAESInputAESInput4state
				RollCallString,
			iqmux47LoggingAESInputLogAESInput5sta
				INTEGER,
			iqmux47LoggingAESInputAESInput5state
				RollCallString,
			iqmux47LoggingAESInputLogAESInput6sta
				INTEGER,
			iqmux47LoggingAESInputAESInput6state
				RollCallString,
			iqmux47LoggingAESInputLogAESInput7sta
				INTEGER,
			iqmux47LoggingAESInputAESInput7state
				RollCallString,
			iqmux47LoggingAESInputLogAESInput8sta
				INTEGER,
			iqmux47LoggingAESInputAESInput8state
				RollCallString,
			iqmux47LoggingAESInputLogAESInput1typ
				INTEGER,
			iqmux47LoggingAESInputAESInput1type
				RollCallString,
			iqmux47LoggingAESInputLogAESInput2typ
				INTEGER,
			iqmux47LoggingAESInputAESInput2type
				RollCallString,
			iqmux47LoggingAESInputLogAESInput3typ
				INTEGER,
			iqmux47LoggingAESInputAESInput3type
				RollCallString,
			iqmux47LoggingAESInputLogAESInput4typ
				INTEGER,
			iqmux47LoggingAESInputAESInput4type
				RollCallString,
			iqmux47LoggingAESInputLogAESInput5typ
				INTEGER,
			iqmux47LoggingAESInputAESInput5type
				RollCallString,
			iqmux47LoggingAESInputLogAESInput6typ
				INTEGER,
			iqmux47LoggingAESInputAESInput6type
				RollCallString,
			iqmux47LoggingAESInputLogAESInput7typ
				INTEGER,
			iqmux47LoggingAESInputAESInput7type
				RollCallString,
			iqmux47LoggingAESInputLogAESInput8typ
				INTEGER,
			iqmux47LoggingAESInputAESInput8type
				RollCallString,
			iqmux47LoggingAESOutputLogAESOutput1st
				INTEGER,
			iqmux47LoggingAESOutputAESOutput1state
				RollCallString,
			iqmux47LoggingAESOutputLogAESOutput2st
				INTEGER,
			iqmux47LoggingAESOutputAESOutput2state
				RollCallString,
			iqmux47LoggingAESOutputLogAESOutput3st
				INTEGER,
			iqmux47LoggingAESOutputAESOutput3state
				RollCallString,
			iqmux47LoggingAESOutputLogAESOutput4st
				INTEGER,
			iqmux47LoggingAESOutputAESOutput4state
				RollCallString,
			iqmux47LoggingAESOutputLogAESOutput5st
				INTEGER,
			iqmux47LoggingAESOutputAESOutput5state
				RollCallString,
			iqmux47LoggingAESOutputLogAESOutput6st
				INTEGER,
			iqmux47LoggingAESOutputAESOutput6state
				RollCallString,
			iqmux47LoggingAESOutputLogAESOutput7st
				INTEGER,
			iqmux47LoggingAESOutputAESOutput7state
				RollCallString,
			iqmux47LoggingAESOutputLogAESOutput8st
				INTEGER,
			iqmux47LoggingAESOutputAESOutput8state
				RollCallString,
			iqmux47LoggingAESOutputLogAESOutput1ty
				INTEGER,
			iqmux47LoggingAESOutputAESOutput1type
				RollCallString,
			iqmux47LoggingAESOutputLogAESOutput2ty
				INTEGER,
			iqmux47LoggingAESOutputAESOutput2type
				RollCallString,
			iqmux47LoggingAESOutputLogAESOutput3ty
				INTEGER,
			iqmux47LoggingAESOutputAESOutput3type
				RollCallString,
			iqmux47LoggingAESOutputLogAESOutput4ty
				INTEGER,
			iqmux47LoggingAESOutputAESOutput4type
				RollCallString,
			iqmux47LoggingAESOutputLogAESOutput5ty
				INTEGER,
			iqmux47LoggingAESOutputAESOutput5type
				RollCallString,
			iqmux47LoggingAESOutputLogAESOutput6ty
				INTEGER,
			iqmux47LoggingAESOutputAESOutput6type
				RollCallString,
			iqmux47LoggingAESOutputLogAESOutput7ty
				INTEGER,
			iqmux47LoggingAESOutputAESOutput7type
				RollCallString,
			iqmux47LoggingAESOutputLogAESOutput8ty
				INTEGER,
			iqmux47LoggingAESOutputAESOutput8type
				RollCallString,
			iqmux47LoggingMiscLogSerialNo
				INTEGER,
			iqmux47LoggingMiscSerialNo
				RollCallString,
			iqmux47LoggingMiscLogOSVersion
				INTEGER,
			iqmux47LoggingMiscOSVersion
				RollCallString,
			iqmux47LoggingMiscLogBuildNo
				INTEGER,
			iqmux47LoggingMiscBuildNo
				RollCallString,
			iqmux47LoggingMiscLogHardwareVer
				INTEGER,
			iqmux47LoggingMiscHardwareVer
				RollCallString,
			iqmux47LoggingMiscLogFirmwareVer
				INTEGER,
			iqmux47LoggingMiscFirmwareVer
				RollCallString,
			iqmux47LoggingMiscLogUpTime
				INTEGER,
			iqmux47LoggingMiscUpTime
				RollCallString,
			iqmux47RollCallRollTrackDisableAll
				INTEGER,
			iqmux47RollCallRollTrackIndex
				INTEGER,
			iqmux47RollCallRollTrackSource
				INTEGER,
			iqmux47RollCallRollTrackAddress
				RollCallString,
			iqmux47RollCallRollTrackCommand
				RollCallString,
			iqmux47RollCallRollTrackStatus
				RollCallString,
			iqmux47RollCallRollTrackSending
				RollCallString,
			iqmux47SetupProduct
				RollCallString,
			iqmux47SetupRelease
				RollCallString,
			iqmux47SetupBuild
				RollCallString,
			iqmux47SetupKOS
				RollCallString,
			iqmux47SetupSerial
				RollCallString,
			iqmux47SetupFirmware
				RollCallString,
			iqmux47SetupPCB
				RollCallString,
			iqmux47SetupFactoryDefault
				INTEGER,
			iqmux47SetupRestart
				INTEGER,
			iqmux47SetupDefaultSettings
				INTEGER,
			iqmux47SetupDisplay
				INTEGER,
			iqmux47SetupSerialNumber
				RollCallString,
			iqmux47SetupBoardID
				INTEGER,
			iqmux47SetupSaveID
				INTEGER,
			iqmux47EngineerPassword
				RollCallString,
			iqmux47EngineerShowEngineer
				INTEGER,
			iqmux47EngineerPageOptionsS134014
				INTEGER,
			iqmux47EngineerPageOptionsS134015
				INTEGER,
			iqmux47EngineerPageOptionsS1
				INTEGER,
			iqmux47EngineerPageUndoChanges
				INTEGER,
			iqmux47EngineerPageLineNumber
				RollCallString,
			iqmux47EngineerPageSampleNumber
				RollCallString,
			iqmux47EngineerPaAutoalignEmbeddedInputs
				INTEGER,
			iqmux47EngineerPaAutoalignAESInputs
				INTEGER,
			iqmux47ShowEngineer2
				INTEGER,
			iqmux47EngineerUseEmbDelayFbac
				INTEGER
		}

	iqmux47SlotIndex OBJECT-TYPE
		SYNTAX		Unsigned32
		MAX-ACCESS		not-accessible
		STATUS			current
		DESCRIPTION
				"The unique Index value for each slot.  Its value
					ranges between 1 and the value of slotNumber."
		::= { iqmux47CmdEntry 0 }


	iqmux47InputIPLoss OBJECT-TYPE
		SYNTAX		INTEGER {
							val_No_Input(0),
							val_In_Out_Std_Mismatch(1)
							}
		MAX-ACCESS		read-write
		STATUS			current
		DESCRIPTION
				"TYPE: - RadiobuttonList
				 PAGE: - Input
					I/P Loss  cmdID= 33030
					No Input  value= 0
					In/Out Std.Mismatch  value= 1  "
		::= { iqmux47CmdEntry 33030 }


	iqmux47InputValidStdsAllValid OBJECT-TYPE
		SYNTAX		INTEGER { noAction(0),val_All_Valid(1) }
		MAX-ACCESS		read-write
		STATUS			current
		DESCRIPTION
				"TYPE: - Button
				 PAGE: - Input
					All Valid  cmdID= 32900  value= 1  "
		::= { iqmux47CmdEntry 32900 }


	iqmux47InputValidStdsAllInvalid OBJECT-TYPE
		SYNTAX		INTEGER { noAction(0),val_All_Invalid(1) }
		MAX-ACCESS		read-write
		STATUS			current
		DESCRIPTION
				"TYPE: - Button
				 PAGE: - Input
					All Invalid  cmdID= 32901  value= 1  "
		::= { iqmux47CmdEntry 32901 }


	iqmux47InputValidStds108023sF OBJECT-TYPE
		SYNTAX		INTEGER { disable(0), enable(1) }
		MAX-ACCESS		read-write
		STATUS			current
		DESCRIPTION
				"TYPE: - Checkbox
				 PAGE: - Input
					1080/23sF  cmdID= 32916 "
		::= { iqmux47CmdEntry 32916 }


	iqmux47InputValidStds108023p OBJECT-TYPE
		SYNTAX		INTEGER { disable(0), enable(1) }
		MAX-ACCESS		read-write
		STATUS			current
		DESCRIPTION
				"TYPE: - Checkbox
				 PAGE: - Input
					1080/23p  cmdID= 32915 "
		::= { iqmux47CmdEntry 32915 }


	iqmux47InputValidStds108024sF OBJECT-TYPE
		SYNTAX		INTEGER { disable(0), enable(1) }
		MAX-ACCESS		read-write
		STATUS			current
		DESCRIPTION
				"TYPE: - Checkbox
				 PAGE: - Input
					1080/24sF  cmdID= 32917 "
		::= { iqmux47CmdEntry 32917 }


	iqmux47InputValidStds108024p OBJECT-TYPE
		SYNTAX		INTEGER { disable(0), enable(1) }
		MAX-ACCESS		read-write
		STATUS			current
		DESCRIPTION
				"TYPE: - Checkbox
				 PAGE: - Input
					1080/24p  cmdID= 32914 "
		::= { iqmux47CmdEntry 32914 }


	iqmux47InputValidStds108025i OBJECT-TYPE
		SYNTAX		INTEGER { disable(0), enable(1) }
		MAX-ACCESS		read-write
		STATUS			current
		DESCRIPTION
				"TYPE: - Checkbox
				 PAGE: - Input
					1080/25i  cmdID= 32910 "
		::= { iqmux47CmdEntry 32910 }


	iqmux47InputValidStds108025p OBJECT-TYPE
		SYNTAX		INTEGER { disable(0), enable(1) }
		MAX-ACCESS		read-write
		STATUS			current
		DESCRIPTION
				"TYPE: - Checkbox
				 PAGE: - Input
					1080/25p  cmdID= 32911 "
		::= { iqmux47CmdEntry 32911 }


	iqmux47InputValidStds103529i OBJECT-TYPE
		SYNTAX		INTEGER { disable(0), enable(1) }
		MAX-ACCESS		read-write
		STATUS			current
		DESCRIPTION
				"TYPE: - Checkbox
				 PAGE: - Input
					1035/29i  cmdID= 32921 "
		::= { iqmux47CmdEntry 32921 }


	iqmux47InputValidStds108029i OBJECT-TYPE
		SYNTAX		INTEGER { disable(0), enable(1) }
		MAX-ACCESS		read-write
		STATUS			current
		DESCRIPTION
				"TYPE: - Checkbox
				 PAGE: - Input
					1080/29i  cmdID= 32919 "
		::= { iqmux47CmdEntry 32919 }


	iqmux47InputValidStds108029p OBJECT-TYPE
		SYNTAX		INTEGER { disable(0), enable(1) }
		MAX-ACCESS		read-write
		STATUS			current
		DESCRIPTION
				"TYPE: - Checkbox
				 PAGE: - Input
					1080/29p  cmdID= 32918 "
		::= { iqmux47CmdEntry 32918 }


	iqmux47InputValidStds103530i OBJECT-TYPE
		SYNTAX		INTEGER { disable(0), enable(1) }
		MAX-ACCESS		read-write
		STATUS			current
		DESCRIPTION
				"TYPE: - Checkbox
				 PAGE: - Input
					1035/30i  cmdID= 32920 "
		::= { iqmux47CmdEntry 32920 }


	iqmux47InputValidStds108030i OBJECT-TYPE
		SYNTAX		INTEGER { disable(0), enable(1) }
		MAX-ACCESS		read-write
		STATUS			current
		DESCRIPTION
				"TYPE: - Checkbox
				 PAGE: - Input
					1080/30i  cmdID= 32912 "
		::= { iqmux47CmdEntry 32912 }


	iqmux47InputValidStds108030p OBJECT-TYPE
		SYNTAX		INTEGER { disable(0), enable(1) }
		MAX-ACCESS		read-write
		STATUS			current
		DESCRIPTION
				"TYPE: - Checkbox
				 PAGE: - Input
					1080/30p  cmdID= 32913 "
		::= { iqmux47CmdEntry 32913 }


	iqmux47InputValidStds72050p OBJECT-TYPE
		SYNTAX		INTEGER { disable(0), enable(1) }
		MAX-ACCESS		read-write
		STATUS			current
		DESCRIPTION
				"TYPE: - Checkbox
				 PAGE: - Input
					720/50p  cmdID= 32922 "
		::= { iqmux47CmdEntry 32922 }


	iqmux47InputValidStds72059p OBJECT-TYPE
		SYNTAX		INTEGER { disable(0), enable(1) }
		MAX-ACCESS		read-write
		STATUS			current
		DESCRIPTION
				"TYPE: - Checkbox
				 PAGE: - Input
					720/59p  cmdID= 32924 "
		::= { iqmux47CmdEntry 32924 }


	iqmux47InputValidStds72060p OBJECT-TYPE
		SYNTAX		INTEGER { disable(0), enable(1) }
		MAX-ACCESS		read-write
		STATUS			current
		DESCRIPTION
				"TYPE: - Checkbox
				 PAGE: - Input
					720/60p  cmdID= 32923 "
		::= { iqmux47CmdEntry 32923 }


	iqmux47InputValidStds62525i OBJECT-TYPE
		SYNTAX		INTEGER { disable(0), enable(1) }
		MAX-ACCESS		read-write
		STATUS			current
		DESCRIPTION
				"TYPE: - Checkbox
				 PAGE: - Input
					625/25i  cmdID= 32925 "
		::= { iqmux47CmdEntry 32925 }


	iqmux47InputValidStds52529i OBJECT-TYPE
		SYNTAX		INTEGER { disable(0), enable(1) }
		MAX-ACCESS		read-write
		STATUS			current
		DESCRIPTION
				"TYPE: - Checkbox
				 PAGE: - Input
					525/29i  cmdID= 32926 "
		::= { iqmux47CmdEntry 32926 }


	iqmux47InputErrorsCRCErrs OBJECT-TYPE
		SYNTAX		RollCallString
		MAX-ACCESS		read-only
		STATUS			current
		DESCRIPTION
				"TYPE: - Display
				 PAGE: - Input
					CRC Errs  cmdID= 33050  format=   "
		::= { iqmux47CmdEntry 33050 }


	iqmux47InputErrorsCRCErrSec OBJECT-TYPE
		SYNTAX		RollCallString
		MAX-ACCESS		read-only
		STATUS			current
		DESCRIPTION
				"TYPE: - Display
				 PAGE: - Input
					CRC ErrSec  cmdID= 33051  format=   "
		::= { iqmux47CmdEntry 33051 }


	iqmux47InputErrorsANCErrs OBJECT-TYPE
		SYNTAX		RollCallString
		MAX-ACCESS		read-only
		STATUS			current
		DESCRIPTION
				"TYPE: - Display
				 PAGE: - Input
					ANC Errs  cmdID= 33053  format=   "
		::= { iqmux47CmdEntry 33053 }


	iqmux47InputErrorsANCErrSec OBJECT-TYPE
		SYNTAX		RollCallString
		MAX-ACCESS		read-only
		STATUS			current
		DESCRIPTION
				"TYPE: - Display
				 PAGE: - Input
					ANC ErrSec  cmdID= 33054  format=   "
		::= { iqmux47CmdEntry 33054 }


	iqmux47InputErrorsResetSec OBJECT-TYPE
		SYNTAX		RollCallString
		MAX-ACCESS		read-only
		STATUS			current
		DESCRIPTION
				"TYPE: - Display
				 PAGE: - Input
					ResetSec  cmdID= 33055  format=   "
		::= { iqmux47CmdEntry 33055 }


	iqmux47InputErrorsErrorReset OBJECT-TYPE
		SYNTAX		INTEGER { noAction(0),val_Error_Reset(1) }
		MAX-ACCESS		read-write
		STATUS			current
		DESCRIPTION
				"TYPE: - Button
				 PAGE: - Input
					Error Reset  cmdID= 33052  value= 1  "
		::= { iqmux47CmdEntry 33052 }


	iqmux47OutputStandard OBJECT-TYPE
		SYNTAX		INTEGER {
							val_Manual(0),
							val_Follows_Input(1)
							}
		MAX-ACCESS		read-write
		STATUS			current
		DESCRIPTION
				"TYPE: - RadiobuttonList
					Output Standard  cmdID= 33011
					Manual  value= 0
					Follows Input  value= 1  "
		::= { iqmux47CmdEntry 33011 }


	iqmux47OutputSelectStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Select Standard  cmdID= 33010
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqmux47CmdEntry 33010 }


	iqmux47OutputVideoProcAmpsMasterGain OBJECT-TYPE
		SYNTAX		INTEGER
		MAX-ACCESS		read-write
		STATUS			current
		DESCRIPTION
				"TYPE: - Number
					Master Gain  cmdID= 33000  min= -600  max= 600  step= 10  format= %0.1f dB  div_scale= 100
					Min = -6.0 dB  Max = 6.0 dB  Step = 0.1 dB "
		::= { iqmux47CmdEntry 33000 }


	iqmux47OutputVideoProcAmpsYGain OBJECT-TYPE
		SYNTAX		INTEGER
		MAX-ACCESS		read-write
		STATUS			current
		DESCRIPTION
				"TYPE: - Number
					Y Gain  cmdID= 33001  min= -600  max= 600  step= 10  format= %0.1f dB  div_scale= 100
					Min = -6.0 dB  Max = 6.0 dB  Step = 0.1 dB "
		::= { iqmux47CmdEntry 33001 }


	iqmux47OutputVideoProcAmpsCGain OBJECT-TYPE
		SYNTAX		INTEGER
		MAX-ACCESS		read-write
		STATUS			current
		DESCRIPTION
				"TYPE: - Number
					C Gain  cmdID= 33003  min= -600  max= 600  step= 10  format= %0.1f dB  div_scale= 100
					Min = -6.0 dB  Max = 6.0 dB  Step = 0.1 dB "
		::= { iqmux47CmdEntry 33003 }


	iqmux47OutputVideoProcAmpsBlackLevel OBJECT-TYPE
		SYNTAX		INTEGER
		MAX-ACCESS		read-write
		STATUS			current
		DESCRIPTION
				"TYPE: - Number
					Black Level  cmdID= 33002  min= -200  max= 200  step= 1  format= %0.0f mV  div_scale= 1
					Min = -200 mV  Max = 200 mV  Step = 1 mV "
		::= { iqmux47CmdEntry 33002 }


	iqmux47OutputDefaultOutput OBJECT-TYPE
		SYNTAX		INTEGER {
							val_Freeze_Frame(1),
							val_Freeze_Field(5),
							val_Black(2),
							val_Input(3),
							val_Out_Pattern(4)
							}
		MAX-ACCESS		read-write
		STATUS			current
		DESCRIPTION
				"TYPE: - RadiobuttonList
					Default Output  cmdID= 33031
					Freeze Frame  value= 1
					Freeze Field  value= 5
					Black  value= 2
					Input  value= 3
					Out Pattern  value= 4  "
		::= { iqmux47CmdEntry 33031 }


	iqmux47OutputDefaultOPStd OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Default O/P Std.  cmdID= 33012
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqmux47CmdEntry 33012 }


	iqmux47AudioADelaySourcesManual OBJECT-TYPE
		SYNTAX		INTEGER { disable(0), enable(1) }
		MAX-ACCESS		read-write
		STATUS			current
		DESCRIPTION
				"TYPE: - Checkbox
				 PAGE: - Audio- Aud.Delays
					Manual  cmdID= 38041 "
		::= { iqmux47CmdEntry 38041 }


	iqmux47AudioADelaySourcesGPIPWM OBJECT-TYPE
		SYNTAX		INTEGER { disable(0), enable(1) }
		MAX-ACCESS		read-write
		STATUS			current
		DESCRIPTION
				"TYPE: - Checkbox
				 PAGE: - Audio- Aud.Delays
					GPI PWM  cmdID= 38042 "
		::= { iqmux47CmdEntry 38042 }


	iqmux47AudioADelaySourcesRollTrack14 OBJECT-TYPE
		SYNTAX		INTEGER { disable(0), enable(1) }
		MAX-ACCESS		read-write
		STATUS			current
		DESCRIPTION
				"TYPE: - Checkbox
				 PAGE: - Audio- Aud.Delays
					RollTrack14  cmdID= 38044 "
		::= { iqmux47CmdEntry 38044 }


	iqmux47AudioADelaySourcesRollTrack15 OBJECT-TYPE
		SYNTAX		INTEGER { disable(0), enable(1) }
		MAX-ACCESS		read-write
		STATUS			current
		DESCRIPTION
				"TYPE: - Checkbox
				 PAGE: - Audio- Aud.Delays
					RollTrack15  cmdID= 38045 "
		::= { iqmux47CmdEntry 38045 }


	iqmux47AudioADelaySourcesRollTrack16 OBJECT-TYPE
		SYNTAX		INTEGER { disable(0), enable(1) }
		MAX-ACCESS		read-write
		STATUS			current
		DESCRIPTION
				"TYPE: - Checkbox
				 PAGE: - Audio- Aud.Delays
					RollTrack16  cmdID= 38046 "
		::= { iqmux47CmdEntry 38046 }


	iqmux47AudioADelaySourcesRollTrack17 OBJECT-TYPE
		SYNTAX		INTEGER { disable(0), enable(1) }
		MAX-ACCESS		read-write
		STATUS			current
		DESCRIPTION
				"TYPE: - Checkbox
				 PAGE: - Audio- Aud.Delays
					RollTrack17  cmdID= 38047 "
		::= { iqmux47CmdEntry 38047 }


	iqmux47AudioAAdjustCoarseDelay OBJECT-TYPE
		SYNTAX		INTEGER
		MAX-ACCESS		read-write
		STATUS			current
		DESCRIPTION
				"TYPE: - Number
				 PAGE: - Audio- Aud.Delays
					Adjust Coarse Delay  cmdID= 38043  min= -4000  max= 200000  step= 25  format= %0.2f ms  div_scale= 100
					Min = -40.00 ms  Max = 2000.00 ms  Step = 0.25 ms "
		::= { iqmux47CmdEntry 38043 }


	iqmux47AudioACurrentAudioDelay OBJECT-TYPE
		SYNTAX		RollCallString
		MAX-ACCESS		read-only
		STATUS			current
		DESCRIPTION
				"TYPE: - Display
				 PAGE: - Audio- Aud.Delays
					Current Audio Delay  cmdID= 38048  format=   "
		::= { iqmux47CmdEntry 38048 }


	iqmux47AudioBDelaySourcesManual OBJECT-TYPE
		SYNTAX		INTEGER { disable(0), enable(1) }
		MAX-ACCESS		read-write
		STATUS			current
		DESCRIPTION
				"TYPE: - Checkbox
				 PAGE: - Audio- Aud.Delays
					Manual  cmdID= 38061 "
		::= { iqmux47CmdEntry 38061 }


	iqmux47AudioBDelaySourcesGPIPWM OBJECT-TYPE
		SYNTAX		INTEGER { disable(0), enable(1) }
		MAX-ACCESS		read-write
		STATUS			current
		DESCRIPTION
				"TYPE: - Checkbox
				 PAGE: - Audio- Aud.Delays
					GPI PWM  cmdID= 38062 "
		::= { iqmux47CmdEntry 38062 }


	iqmux47AudioBDelaySourcesRollTrack14 OBJECT-TYPE
		SYNTAX		INTEGER { disable(0), enable(1) }
		MAX-ACCESS		read-write
		STATUS			current
		DESCRIPTION
				"TYPE: - Checkbox
				 PAGE: - Audio- Aud.Delays
					RollTrack14  cmdID= 38064 "
		::= { iqmux47CmdEntry 38064 }


	iqmux47AudioBDelaySourcesRollTrack15 OBJECT-TYPE
		SYNTAX		INTEGER { disable(0), enable(1) }
		MAX-ACCESS		read-write
		STATUS			current
		DESCRIPTION
				"TYPE: - Checkbox
				 PAGE: - Audio- Aud.Delays
					RollTrack15  cmdID= 38065 "
		::= { iqmux47CmdEntry 38065 }


	iqmux47AudioBDelaySourcesRollTrack16 OBJECT-TYPE
		SYNTAX		INTEGER { disable(0), enable(1) }
		MAX-ACCESS		read-write
		STATUS			current
		DESCRIPTION
				"TYPE: - Checkbox
				 PAGE: - Audio- Aud.Delays
					RollTrack16  cmdID= 38066 "
		::= { iqmux47CmdEntry 38066 }


	iqmux47AudioBDelaySourcesRollTrack17 OBJECT-TYPE
		SYNTAX		INTEGER { disable(0), enable(1) }
		MAX-ACCESS		read-write
		STATUS			current
		DESCRIPTION
				"TYPE: - Checkbox
				 PAGE: - Audio- Aud.Delays
					RollTrack17  cmdID= 38067 "
		::= { iqmux47CmdEntry 38067 }


	iqmux47AudioBAdjustCoarseDelay OBJECT-TYPE
		SYNTAX		INTEGER
		MAX-ACCESS		read-write
		STATUS			current
		DESCRIPTION
				"TYPE: - Number
				 PAGE: - Audio- Aud.Delays
					Adjust Coarse Delay  cmdID= 38063  min= -4000  max= 200000  step= 25  format= %0.2f ms  div_scale= 100
					Min = -40.00 ms  Max = 2000.00 ms  Step = 0.25 ms "
		::= { iqmux47CmdEntry 38063 }


	iqmux47AudioBCurrentAudioDelay OBJECT-TYPE
		SYNTAX		RollCallString
		MAX-ACCESS		read-only
		STATUS			current
		DESCRIPTION
				"TYPE: - Display
				 PAGE: - Audio- Aud.Delays
					Current Audio Delay  cmdID= 38068  format=   "
		::= { iqmux47CmdEntry 38068 }


	iqmux47AudioAESDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-1  cmdID= 38600
					Min  value= 0
					Delay A  value= 1
					Delay B  value= 2  "
		::= { iqmux47CmdEntry 38600 }


	iqmux47AudioAESDelaySelectInternal1 OBJECT-TYPE
		SYNTAX		INTEGER { disable(0), enable(1) }
		MAX-ACCESS		read-write
		STATUS			current
		DESCRIPTION
				"TYPE: - Checkbox
				 PAGE: - Audio- Aud.Delays
					Internal-1  cmdID= 38620 "
		::= { iqmux47CmdEntry 38620 }


	iqmux47AudioAESDelaySelectAutoDolbyEPhase1 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38118 "
		::= { iqmux47CmdEntry 38118 }


	iqmux47AudioAESDelaySelectDelayLimit1 OBJECT-TYPE
		SYNTAX		RollCallString
		MAX-ACCESS		read-only
		STATUS			current
		DESCRIPTION
				"TYPE: - Display
				 PAGE: - Audio- Aud.Delays
					Delay Limit  cmdID= 38300  format=   "
		::= { iqmux47CmdEntry 38300 }


	iqmux47AudioAESDelaySelectAES1FineDelay OBJECT-TYPE
		SYNTAX		INTEGER
		MAX-ACCESS		read-write
		STATUS			current
		DESCRIPTION
				"TYPE: - Number
				 PAGE: - Audio- Aud.Delays
					AES 1 Fine Delay  cmdID= 38130  min= -2450  max= 2450  step= 52  format= %0.3f ms  div_scale= 10000
					Min = -0.245 ms  Max = 0.245 ms  Step = 0.005 ms "
		::= { iqmux47CmdEntry 38130 }


	iqmux47AudioAESDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-2  cmdID= 38601
					Min  value= 0
					Delay A  value= 1
					Delay B  value= 2  "
		::= { iqmux47CmdEntry 38601 }


	iqmux47AudioAESDelaySelectInternal2 OBJECT-TYPE
		SYNTAX		INTEGER { disable(0), enable(1) }
		MAX-ACCESS		read-write
		STATUS			current
		DESCRIPTION
				"TYPE: - Checkbox
				 PAGE: - Audio- Aud.Delays
					Internal-2  cmdID= 38621 "
		::= { iqmux47CmdEntry 38621 }


	iqmux47AudioAESDelaySelectAutoDolbyEPhase2 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38119 "
		::= { iqmux47CmdEntry 38119 }


	iqmux47AudioAESDelaySelectDelayLimit2 OBJECT-TYPE
		SYNTAX		RollCallString
		MAX-ACCESS		read-only
		STATUS			current
		DESCRIPTION
				"TYPE: - Display
				 PAGE: - Audio- Aud.Delays
					Delay Limit  cmdID= 38301  format=   "
		::= { iqmux47CmdEntry 38301 }


	iqmux47AudioAESDelaySelectAES2FineDelay OBJECT-TYPE
		SYNTAX		INTEGER
		MAX-ACCESS		read-write
		STATUS			current
		DESCRIPTION
				"TYPE: - Number
				 PAGE: - Audio- Aud.Delays
					AES 2 Fine Delay  cmdID= 38131  min= -2450  max= 2450  step= 52  format= %0.3f ms  div_scale= 10000
					Min = -0.245 ms  Max = 0.245 ms  Step = 0.005 ms "
		::= { iqmux47CmdEntry 38131 }


	iqmux47AudioAESDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-3  cmdID= 38602
					Min  value= 0
					Delay A  value= 1
					Delay B  value= 2  "
		::= { iqmux47CmdEntry 38602 }


	iqmux47AudioAESDelaySelectInternal3 OBJECT-TYPE
		SYNTAX		INTEGER { disable(0), enable(1) }
		MAX-ACCESS		read-write
		STATUS			current
		DESCRIPTION
				"TYPE: - Checkbox
				 PAGE: - Audio- Aud.Delays
					Internal-3  cmdID= 38622 "
		::= { iqmux47CmdEntry 38622 }


	iqmux47AudioAESDelaySelectAutoDolbyEPhase3 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38120 "
		::= { iqmux47CmdEntry 38120 }


	iqmux47AudioAESDelaySelectDelayLimit3 OBJECT-TYPE
		SYNTAX		RollCallString
		MAX-ACCESS		read-only
		STATUS			current
		DESCRIPTION
				"TYPE: - Display
				 PAGE: - Audio- Aud.Delays
					Delay Limit  cmdID= 38302  format=   "
		::= { iqmux47CmdEntry 38302 }


	iqmux47AudioAESDelaySelectAES3FineDelay OBJECT-TYPE
		SYNTAX		INTEGER
		MAX-ACCESS		read-write
		STATUS			current
		DESCRIPTION
				"TYPE: - Number
				 PAGE: - Audio- Aud.Delays
					AES 3 Fine Delay  cmdID= 38132  min= -2450  max= 2450  step= 52  format= %0.3f ms  div_scale= 10000
					Min = -0.245 ms  Max = 0.245 ms  Step = 0.005 ms "
		::= { iqmux47CmdEntry 38132 }


	iqmux47AudioAESDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-4  cmdID= 38603
					Min  value= 0
					Delay A  value= 1
					Delay B  value= 2  "
		::= { iqmux47CmdEntry 38603 }


	iqmux47AudioAESDelaySelectInternal4 OBJECT-TYPE
		SYNTAX		INTEGER { disable(0), enable(1) }
		MAX-ACCESS		read-write
		STATUS			current
		DESCRIPTION
				"TYPE: - Checkbox
				 PAGE: - Audio- Aud.Delays
					Internal-4  cmdID= 38623 "
		::= { iqmux47CmdEntry 38623 }


	iqmux47AudioAESDelaySelectAutoDolbyEPhase4 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38121 "
		::= { iqmux47CmdEntry 38121 }


	iqmux47AudioAESDelaySelectDelayLimit4 OBJECT-TYPE
		SYNTAX		RollCallString
		MAX-ACCESS		read-only
		STATUS			current
		DESCRIPTION
				"TYPE: - Display
				 PAGE: - Audio- Aud.Delays
					Delay Limit  cmdID= 38303  format=   "
		::= { iqmux47CmdEntry 38303 }


	iqmux47AudioAESDelaySelectAES4FineDelay OBJECT-TYPE
		SYNTAX		INTEGER
		MAX-ACCESS		read-write
		STATUS			current
		DESCRIPTION
				"TYPE: - Number
				 PAGE: - Audio- Aud.Delays
					AES 4 Fine Delay  cmdID= 38133  min= -2450  max= 2450  step= 52  format= %0.3f ms  div_scale= 10000
					Min = -0.245 ms  Max = 0.245 ms  Step = 0.005 ms "
		::= { iqmux47CmdEntry 38133 }


	iqmux47AudioAESDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-5  cmdID= 38604
					Min  value= 0
					Delay A  value= 1
					Delay B  value= 2  "
		::= { iqmux47CmdEntry 38604 }


	iqmux47AudioAESDelaySelectInternal5 OBJECT-TYPE
		SYNTAX		INTEGER { disable(0), enable(1) }
		MAX-ACCESS		read-write
		STATUS			current
		DESCRIPTION
				"TYPE: - Checkbox
				 PAGE: - Audio- Aud.Delays
					Internal-5  cmdID= 38624 "
		::= { iqmux47CmdEntry 38624 }


	iqmux47AudioAESDelaySelectAutoDolbyEPhase5 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38122 "
		::= { iqmux47CmdEntry 38122 }


	iqmux47AudioAESDelaySelectDelayLimit5 OBJECT-TYPE
		SYNTAX		RollCallString
		MAX-ACCESS		read-only
		STATUS			current
		DESCRIPTION
				"TYPE: - Display
				 PAGE: - Audio- Aud.Delays
					Delay Limit  cmdID= 38304  format=   "
		::= { iqmux47CmdEntry 38304 }


	iqmux47AudioAESDelaySelectAES5FineDelay OBJECT-TYPE
		SYNTAX		INTEGER
		MAX-ACCESS		read-write
		STATUS			current
		DESCRIPTION
				"TYPE: - Number
				 PAGE: - Audio- Aud.Delays
					AES 5 Fine Delay  cmdID= 38134  min= -2450  max= 2450  step= 52  format= %0.3f ms  div_scale= 10000
					Min = -0.245 ms  Max = 0.245 ms  Step = 0.005 ms "
		::= { iqmux47CmdEntry 38134 }


	iqmux47AudioAESDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-6  cmdID= 38605
					Min  value= 0
					Delay A  value= 1
					Delay B  value= 2  "
		::= { iqmux47CmdEntry 38605 }


	iqmux47AudioAESDelaySelectInternal6 OBJECT-TYPE
		SYNTAX		INTEGER { disable(0), enable(1) }
		MAX-ACCESS		read-write
		STATUS			current
		DESCRIPTION
				"TYPE: - Checkbox
				 PAGE: - Audio- Aud.Delays
					Internal-6  cmdID= 38625 "
		::= { iqmux47CmdEntry 38625 }


	iqmux47AudioAESDelaySelectAutoDolbyEPhase6 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38123 "
		::= { iqmux47CmdEntry 38123 }


	iqmux47AudioAESDelaySelectDelayLimit6 OBJECT-TYPE
		SYNTAX		RollCallString
		MAX-ACCESS		read-only
		STATUS			current
		DESCRIPTION
				"TYPE: - Display
				 PAGE: - Audio- Aud.Delays
					Delay Limit  cmdID= 38305  format=   "
		::= { iqmux47CmdEntry 38305 }


	iqmux47AudioAESDelaySelectAES6FineDelay OBJECT-TYPE
		SYNTAX		INTEGER
		MAX-ACCESS		read-write
		STATUS			current
		DESCRIPTION
				"TYPE: - Number
				 PAGE: - Audio- Aud.Delays
					AES 6 Fine Delay  cmdID= 38135  min= -2450  max= 2450  step= 52  format= %0.3f ms  div_scale= 10000
					Min = -0.245 ms  Max = 0.245 ms  Step = 0.005 ms "
		::= { iqmux47CmdEntry 38135 }


	iqmux47AudioAESDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-7  cmdID= 38606
					Min  value= 0
					Delay A  value= 1
					Delay B  value= 2  "
		::= { iqmux47CmdEntry 38606 }


	iqmux47AudioAESDelaySelectInternal7 OBJECT-TYPE
		SYNTAX		INTEGER { disable(0), enable(1) }
		MAX-ACCESS		read-write
		STATUS			current
		DESCRIPTION
				"TYPE: - Checkbox
				 PAGE: - Audio- Aud.Delays
					Internal-7  cmdID= 38626 "
		::= { iqmux47CmdEntry 38626 }


	iqmux47AudioAESDelaySelectAutoDolbyEPhase7 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38124 "
		::= { iqmux47CmdEntry 38124 }


	iqmux47AudioAESDelaySelectDelayLimit7 OBJECT-TYPE
		SYNTAX		RollCallString
		MAX-ACCESS		read-only
		STATUS			current
		DESCRIPTION
				"TYPE: - Display
				 PAGE: - Audio- Aud.Delays
					Delay Limit  cmdID= 38306  format=   "
		::= { iqmux47CmdEntry 38306 }


	iqmux47AudioAESDelaySelectAES7FineDelay OBJECT-TYPE
		SYNTAX		INTEGER
		MAX-ACCESS		read-write
		STATUS			current
		DESCRIPTION
				"TYPE: - Number
				 PAGE: - Audio- Aud.Delays
					AES 7 Fine Delay  cmdID= 38136  min= -2450  max= 2450  step= 52  format= %0.3f ms  div_scale= 10000
					Min = -0.245 ms  Max = 0.245 ms  Step = 0.005 ms "
		::= { iqmux47CmdEntry 38136 }


	iqmux47AudioAESDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-8  cmdID= 38607
					Min  value= 0
					Delay A  value= 1
					Delay B  value= 2  "
		::= { iqmux47CmdEntry 38607 }


	iqmux47AudioAESDelaySelectInternal8 OBJECT-TYPE
		SYNTAX		INTEGER { disable(0), enable(1) }
		MAX-ACCESS		read-write
		STATUS			current
		DESCRIPTION
				"TYPE: - Checkbox
				 PAGE: - Audio- Aud.Delays
					Internal-8  cmdID= 38627 "
		::= { iqmux47CmdEntry 38627 }


	iqmux47AudioAESDelaySelectAutoDolbyEPhase8 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38125 "
		::= { iqmux47CmdEntry 38125 }


	iqmux47AudioAESDelaySelectDelayLimit8 OBJECT-TYPE
		SYNTAX		RollCallString
		MAX-ACCESS		read-only
		STATUS			current
		DESCRIPTION
				"TYPE: - Display
				 PAGE: - Audio- Aud.Delays
					Delay Limit  cmdID= 38307  format=   "
		::= { iqmux47CmdEntry 38307 }


	iqmux47AudioAESDelaySelectAES8FineDelay OBJECT-TYPE
		SYNTAX		INTEGER
		MAX-ACCESS		read-write
		STATUS			current
		DESCRIPTION
				"TYPE: - Number
				 PAGE: - Audio- Aud.Delays
					AES 8 Fine Delay  cmdID= 38137  min= -2450  max= 2450  step= 52  format= %0.3f ms  div_scale= 10000
					Min = -0.245 ms  Max = 0.245 ms  Step = 0.005 ms "
		::= { iqmux47CmdEntry 38137 }


	iqmux47AudEMBDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-1  cmdID= 38080
					Min  value= 0
					Delay A  value= 1
					Delay B  value= 2  "
		::= { iqmux47CmdEntry 38080 }


	iqmux47AudEMBDelaySelectInternal1 OBJECT-TYPE
		SYNTAX		INTEGER { disable(0), enable(1) }
		MAX-ACCESS		read-write
		STATUS			current
		DESCRIPTION
				"TYPE: - Checkbox
				 PAGE: - Audio- Aud.Delays
					Internal-1  cmdID= 38100 "
		::= { iqmux47CmdEntry 38100 }


	iqmux47AudEMBDelaySelectAutoDolbyEPhase1 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38110 "
		::= { iqmux47CmdEntry 38110 }


	iqmux47AudEMBDelaySelectDelayLimit1 OBJECT-TYPE
		SYNTAX		RollCallString
		MAX-ACCESS		read-only
		STATUS			current
		DESCRIPTION
				"TYPE: - Display
				 PAGE: - Audio- Aud.Delays
					Delay Limit  cmdID= 38308  format=   "
		::= { iqmux47CmdEntry 38308 }


	iqmux47AudEMBDelaySelectEMB1FineDelay OBJECT-TYPE
		SYNTAX		INTEGER
		MAX-ACCESS		read-write
		STATUS			current
		DESCRIPTION
				"TYPE: - Number
				 PAGE: - Audio- Aud.Delays
					EMB 1 Fine Delay  cmdID= 38138  min= -2450  max= 2450  step= 52  format= %0.3f ms  div_scale= 10000
					Min = -0.245 ms  Max = 0.245 ms  Step = 0.005 ms "
		::= { iqmux47CmdEntry 38138 }


	iqmux47AudEMBDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-2  cmdID= 38081
					Min  value= 0
					Delay A  value= 1
					Delay B  value= 2  "
		::= { iqmux47CmdEntry 38081 }


	iqmux47AudEMBDelaySelectInternal2 OBJECT-TYPE
		SYNTAX		INTEGER { disable(0), enable(1) }
		MAX-ACCESS		read-write
		STATUS			current
		DESCRIPTION
				"TYPE: - Checkbox
				 PAGE: - Audio- Aud.Delays
					Internal-2  cmdID= 38101 "
		::= { iqmux47CmdEntry 38101 }


	iqmux47AudEMBDelaySelectAutoDolbyEPhase2 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38111 "
		::= { iqmux47CmdEntry 38111 }


	iqmux47AudEMBDelaySelectDelayLimit2 OBJECT-TYPE
		SYNTAX		RollCallString
		MAX-ACCESS		read-only
		STATUS			current
		DESCRIPTION
				"TYPE: - Display
				 PAGE: - Audio- Aud.Delays
					Delay Limit  cmdID= 38309  format=   "
		::= { iqmux47CmdEntry 38309 }


	iqmux47AudEMBDelaySelectEMB2FineDelay OBJECT-TYPE
		SYNTAX		INTEGER
		MAX-ACCESS		read-write
		STATUS			current
		DESCRIPTION
				"TYPE: - Number
				 PAGE: - Audio- Aud.Delays
					EMB 2 Fine Delay  cmdID= 38139  min= -2450  max= 2450  step= 52  format= %0.3f ms  div_scale= 10000
					Min = -0.245 ms  Max = 0.245 ms  Step = 0.005 ms "
		::= { iqmux47CmdEntry 38139 }


	iqmux47AudEMBDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-3  cmdID= 38082
					Min  value= 0
					Delay A  value= 1
					Delay B  value= 2  "
		::= { iqmux47CmdEntry 38082 }


	iqmux47AudEMBDelaySelectInternal3 OBJECT-TYPE
		SYNTAX		INTEGER { disable(0), enable(1) }
		MAX-ACCESS		read-write
		STATUS			current
		DESCRIPTION
				"TYPE: - Checkbox
				 PAGE: - Audio- Aud.Delays
					Internal-3  cmdID= 38102 "
		::= { iqmux47CmdEntry 38102 }


	iqmux47AudEMBDelaySelectAutoDolbyEPhase3 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38112 "
		::= { iqmux47CmdEntry 38112 }


	iqmux47AudEMBDelaySelectDelayLimit3 OBJECT-TYPE
		SYNTAX		RollCallString
		MAX-ACCESS		read-only
		STATUS			current
		DESCRIPTION
				"TYPE: - Display
				 PAGE: - Audio- Aud.Delays
					Delay Limit  cmdID= 38310  format=   "
		::= { iqmux47CmdEntry 38310 }


	iqmux47AudEMBDelaySelectEMB3FineDelay OBJECT-TYPE
		SYNTAX		INTEGER
		MAX-ACCESS		read-write
		STATUS			current
		DESCRIPTION
				"TYPE: - Number
				 PAGE: - Audio- Aud.Delays
					EMB 3 Fine Delay  cmdID= 38140  min= -2450  max= 2450  step= 52  format= %0.3f ms  div_scale= 10000
					Min = -0.245 ms  Max = 0.245 ms  Step = 0.005 ms "
		::= { iqmux47CmdEntry 38140 }


	iqmux47AudEMBDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-4  cmdID= 38083
					Min  value= 0
					Delay A  value= 1
					Delay B  value= 2  "
		::= { iqmux47CmdEntry 38083 }


	iqmux47AudEMBDelaySelectInternal4 OBJECT-TYPE
		SYNTAX		INTEGER { disable(0), enable(1) }
		MAX-ACCESS		read-write
		STATUS			current
		DESCRIPTION
				"TYPE: - Checkbox
				 PAGE: - Audio- Aud.Delays
					Internal-4  cmdID= 38103 "
		::= { iqmux47CmdEntry 38103 }


	iqmux47AudEMBDelaySelectAutoDolbyEPhase4 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38113 "
		::= { iqmux47CmdEntry 38113 }


	iqmux47AudEMBDelaySelectDelayLimit4 OBJECT-TYPE
		SYNTAX		RollCallString
		MAX-ACCESS		read-only
		STATUS			current
		DESCRIPTION
				"TYPE: - Display
				 PAGE: - Audio- Aud.Delays
					Delay Limit  cmdID= 38311  format=   "
		::= { iqmux47CmdEntry 38311 }


	iqmux47AudEMBDelaySelectEMB4FineDelay OBJECT-TYPE
		SYNTAX		INTEGER
		MAX-ACCESS		read-write
		STATUS			current
		DESCRIPTION
				"TYPE: - Number
				 PAGE: - Audio- Aud.Delays
					EMB 4 Fine Delay  cmdID= 38141  min= -2450  max= 2450  step= 52  format= %0.3f ms  div_scale= 10000
					Min = -0.245 ms  Max = 0.245 ms  Step = 0.005 ms "
		::= { iqmux47CmdEntry 38141 }


	iqmux47AudEMBDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-5  cmdID= 38084
					Min  value= 0
					Delay A  value= 1
					Delay B  value= 2  "
		::= { iqmux47CmdEntry 38084 }


	iqmux47AudEMBDelaySelectInternal5 OBJECT-TYPE
		SYNTAX		INTEGER { disable(0), enable(1) }
		MAX-ACCESS		read-write
		STATUS			current
		DESCRIPTION
				"TYPE: - Checkbox
				 PAGE: - Audio- Aud.Delays
					Internal-5  cmdID= 38104 "
		::= { iqmux47CmdEntry 38104 }


	iqmux47AudEMBDelaySelectAutoDolbyEPhase5 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38114 "
		::= { iqmux47CmdEntry 38114 }


	iqmux47AudEMBDelaySelectDelayLimit5 OBJECT-TYPE
		SYNTAX		RollCallString
		MAX-ACCESS		read-only
		STATUS			current
		DESCRIPTION
				"TYPE: - Display
				 PAGE: - Audio- Aud.Delays
					Delay Limit  cmdID= 38312  format=   "
		::= { iqmux47CmdEntry 38312 }


	iqmux47AudEMBDelaySelectEMB5FineDelay OBJECT-TYPE
		SYNTAX		INTEGER
		MAX-ACCESS		read-write
		STATUS			current
		DESCRIPTION
				"TYPE: - Number
				 PAGE: - Audio- Aud.Delays
					EMB 5 Fine Delay  cmdID= 38142  min= -2450  max= 2450  step= 52  format= %0.3f ms  div_scale= 10000
					Min = -0.245 ms  Max = 0.245 ms  Step = 0.005 ms "
		::= { iqmux47CmdEntry 38142 }


	iqmux47AudEMBDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-6  cmdID= 38085
					Min  value= 0
					Delay A  value= 1
					Delay B  value= 2  "
		::= { iqmux47CmdEntry 38085 }


	iqmux47AudEMBDelaySelectInternal6 OBJECT-TYPE
		SYNTAX		INTEGER { disable(0), enable(1) }
		MAX-ACCESS		read-write
		STATUS			current
		DESCRIPTION
				"TYPE: - Checkbox
				 PAGE: - Audio- Aud.Delays
					Internal-6  cmdID= 38105 "
		::= { iqmux47CmdEntry 38105 }


	iqmux47AudEMBDelaySelectAutoDolbyEPhase6 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38115 "
		::= { iqmux47CmdEntry 38115 }


	iqmux47AudEMBDelaySelectDelayLimit6 OBJECT-TYPE
		SYNTAX		RollCallString
		MAX-ACCESS		read-only
		STATUS			current
		DESCRIPTION
				"TYPE: - Display
				 PAGE: - Audio- Aud.Delays
					Delay Limit  cmdID= 38313  format=   "
		::= { iqmux47CmdEntry 38313 }


	iqmux47AudEMBDelaySelectEMB6FineDelay OBJECT-TYPE
		SYNTAX		INTEGER
		MAX-ACCESS		read-write
		STATUS			current
		DESCRIPTION
				"TYPE: - Number
				 PAGE: - Audio- Aud.Delays
					EMB 6 Fine Delay  cmdID= 38143  min= -2450  max= 2450  step= 52  format= %0.3f ms  div_scale= 10000
					Min = -0.245 ms  Max = 0.245 ms  Step = 0.005 ms "
		::= { iqmux47CmdEntry 38143 }


	iqmux47AudEMBDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-7  cmdID= 38086
					Min  value= 0
					Delay A  value= 1
					Delay B  value= 2  "
		::= { iqmux47CmdEntry 38086 }


	iqmux47AudEMBDelaySelectInternal7 OBJECT-TYPE
		SYNTAX		INTEGER { disable(0), enable(1) }
		MAX-ACCESS		read-write
		STATUS			current
		DESCRIPTION
				"TYPE: - Checkbox
				 PAGE: - Audio- Aud.Delays
					Internal-7  cmdID= 38106 "
		::= { iqmux47CmdEntry 38106 }


	iqmux47AudEMBDelaySelectAutoDolbyEPhase7 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38116 "
		::= { iqmux47CmdEntry 38116 }


	iqmux47AudEMBDelaySelectDelayLimit7 OBJECT-TYPE
		SYNTAX		RollCallString
		MAX-ACCESS		read-only
		STATUS			current
		DESCRIPTION
				"TYPE: - Display
				 PAGE: - Audio- Aud.Delays
					Delay Limit  cmdID= 38314  format=   "
		::= { iqmux47CmdEntry 38314 }


	iqmux47AudEMBDelaySelectEMB7FineDelay OBJECT-TYPE
		SYNTAX		INTEGER
		MAX-ACCESS		read-write
		STATUS			current
		DESCRIPTION
				"TYPE: - Number
				 PAGE: - Audio- Aud.Delays
					EMB 7 Fine Delay  cmdID= 38144  min= -2450  max= 2450  step= 52  format= %0.3f ms  div_scale= 10000
					Min = -0.245 ms  Max = 0.245 ms  Step = 0.005 ms "
		::= { iqmux47CmdEntry 38144 }


	iqmux47AudEMBDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-8  cmdID= 38087
					Min  value= 0
					Delay A  value= 1
					Delay B  value= 2  "
		::= { iqmux47CmdEntry 38087 }


	iqmux47AudEMBDelaySelectInternal8 OBJECT-TYPE
		SYNTAX		INTEGER { disable(0), enable(1) }
		MAX-ACCESS		read-write
		STATUS			current
		DESCRIPTION
				"TYPE: - Checkbox
				 PAGE: - Audio- Aud.Delays
					Internal-8  cmdID= 38107 "
		::= { iqmux47CmdEntry 38107 }


	iqmux47AudEMBDelaySelectDelayLimit8 OBJECT-TYPE
		SYNTAX		RollCallString
		MAX-ACCESS		read-only
		STATUS			current
		DESCRIPTION
				"TYPE: - Display
				 PAGE: - Audio- Aud.Delays
					Delay Limit  cmdID= 38315  format=   "
		::= { iqmux47CmdEntry 38315 }


	iqmux47AudEMBDelaySelectAutoDolbyEPhase8 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38117 "
		::= { iqmux47CmdEntry 38117 }


	iqmux47AudEMBDelaySelectEMB8FineDelay OBJECT-TYPE
		SYNTAX		INTEGER
		MAX-ACCESS		read-write
		STATUS			current
		DESCRIPTION
				"TYPE: - Number
				 PAGE: - Audio- Aud.Delays
					EMB 8 Fine Delay  cmdID= 38145  min= -2450  max= 2450  step= 52  format= %0.3f ms  div_scale= 10000
					Min = -0.245 ms  Max = 0.245 ms  Step = 0.005 ms "
		::= { iqmux47CmdEntry 38145 }


	iqmux47AudioDelaysRollTrack14 OBJECT-TYPE
		SYNTAX		RollCallString
		MAX-ACCESS		read-only
		STATUS			current
		DESCRIPTION
				"TYPE: - Display
				 PAGE: - Audio- Aud.Delays
					RollTrack14  cmdID= 14  format=   "
		::= { iqmux47CmdEntry 14 }


	iqmux47AudioDelaysRollTrack15 OBJECT-TYPE
		SYNTAX		RollCallString
		MAX-ACCESS		read-only
		STATUS			current
		DESCRIPTION
				"TYPE: - Display
				 PAGE: - Audio- Aud.Delays
					RollTrack15  cmdID= 15  format=   "
		::= { iqmux47CmdEntry 15 }


	iqmux47AudioDelaysRollTrack16 OBJECT-TYPE
		SYNTAX		RollCallString
		MAX-ACCESS		read-only
		STATUS			current
		DESCRIPTION
				"TYPE: - Display
				 PAGE: - Audio- Aud.Delays
					RollTrack16  cmdID= 16  format=   "
		::= { iqmux47CmdEntry 16 }


	iqmux47AudioDelaysRollTrack17 OBJECT-TYPE
		SYNTAX		RollCallString
		MAX-ACCESS		read-only
		STATUS			current
		DESCRIPTION
				"TYPE: - Display
				 PAGE: - Audio- Aud.Delays
					RollTrack17  cmdID= 17  format=   "
		::= { iqmux47CmdEntry 17 }


	iqmux47AudioDelaysCrashSRCLimit OBJECT-TYPE
		SYNTAX		INTEGER
		MAX-ACCESS		read-write
		STATUS			current
		DESCRIPTION
				"TYPE: - Number
				 PAGE: - Audio- Aud.Delays
					Crash SRC Limit  cmdID= 38678  min= 0  max= 80  step= 1  format= %0.0f ms  div_scale= 1
					Min = 0 ms  Max = 80 ms  Step = 1 ms "
		::= { iqmux47CmdEntry 38678 }


	iqmux47EmbCtrlGroupGroup1Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 1 Audio  cmdID= 37450
					Pass  value= 0
					Blank  value= 2
					Embed  value= 1  "
		::= { iqmux47CmdEntry 37450 }


	iqmux47EmbCtrlGroupGroup2Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 2 Audio  cmdID= 37451
					Pass  value= 0
					Blank  value= 2
					Embed  value= 1  "
		::= { iqmux47CmdEntry 37451 }


	iqmux47EmbCtrlGroupGroup3Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 3 Audio  cmdID= 37452
					Pass  value= 0
					Blank  value= 2
					Embed  value= 1  "
		::= { iqmux47CmdEntry 37452 }


	iqmux47EmbCtrlGroupGroup4Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 4 Audio  cmdID= 37453
					Pass  value= 0
					Blank  value= 2
					Embed  value= 1  "
		::= { iqmux47CmdEntry 37453 }


	iqmux47EmbCtrlChannelPair1LActive OBJECT-TYPE
		SYNTAX		INTEGER { disable(0), enable(1) }
		MAX-ACCESS		read-write
		STATUS			current
		DESCRIPTION
				"TYPE: - Checkbox
				 PAGE: - Audio- Emb.Ctrl
					Pair 1-L Active  cmdID= 37431 "
		::= { iqmux47CmdEntry 37431 }


	iqmux47EmbCtrlChannelPair1RActive OBJECT-TYPE
		SYNTAX		INTEGER { disable(0), enable(1) }
		MAX-ACCESS		read-write
		STATUS			current
		DESCRIPTION
				"TYPE: - Checkbox
				 PAGE: - Audio- Emb.Ctrl
					Pair 1-R Active  cmdID= 37432 "
		::= { iqmux47CmdEntry 37432 }


	iqmux47EmbCtrlChannelPair2LActive OBJECT-TYPE
		SYNTAX		INTEGER { disable(0), enable(1) }
		MAX-ACCESS		read-write
		STATUS			current
		DESCRIPTION
				"TYPE: - Checkbox
				 PAGE: - Audio- Emb.Ctrl
					Pair 2-L Active  cmdID= 37433 "
		::= { iqmux47CmdEntry 37433 }


	iqmux47EmbCtrlChannelPair2RActive OBJECT-TYPE
		SYNTAX		INTEGER { disable(0), enable(1) }
		MAX-ACCESS		read-write
		STATUS			current
		DESCRIPTION
				"TYPE: - Checkbox
				 PAGE: - Audio- Emb.Ctrl
					Pair 2-R Active  cmdID= 37434 "
		::= { iqmux47CmdEntry 37434 }


	iqmux47EmbCtrlChannelPair3LActive OBJECT-TYPE
		SYNTAX		INTEGER { disable(0), enable(1) }
		MAX-ACCESS		read-write
		STATUS			current
		DESCRIPTION
				"TYPE: - Checkbox
				 PAGE: - Audio- Emb.Ctrl
					Pair 3-L Active  cmdID= 37435 "
		::= { iqmux47CmdEntry 37435 }


	iqmux47EmbCtrlChannelPair3RActive OBJECT-TYPE
		SYNTAX		INTEGER { disable(0), enable(1) }
		MAX-ACCESS		read-write
		STATUS			current
		DESCRIPTION
				"TYPE: - Checkbox
				 PAGE: - Audio- Emb.Ctrl
					Pair 3-R Active  cmdID= 37436 "
		::= { iqmux47CmdEntry 37436 }


	iqmux47EmbCtrlChannelPair4LActive OBJECT-TYPE
		SYNTAX		INTEGER { disable(0), enable(1) }
		MAX-ACCESS		read-write
		STATUS			current
		DESCRIPTION
				"TYPE: - Checkbox
				 PAGE: - Audio- Emb.Ctrl
					Pair 4-L Active  cmdID= 37437 "
		::= { iqmux47CmdEntry 37437 }


	iqmux47EmbCtrlChannelPair4RActive OBJECT-TYPE
		SYNTAX		INTEGER { disable(0), enable(1) }
		MAX-ACCESS		read-write
		STATUS			current
		DESCRIPTION
				"TYPE: - Checkbox
				 PAGE: - Audio- Emb.Ctrl
					Pair 4-R Active  cmdID= 37438 "
		::= { iqmux47CmdEntry 37438 }


	iqmux47EmbCtrlChannelPair5LActive OBJECT-TYPE
		SYNTAX		INTEGER { disable(0), enable(1) }
		MAX-ACCESS		read-write
		STATUS			current
		DESCRIPTION
				"TYPE: - Checkbox
				 PAGE: - Audio- Emb.Ctrl
					Pair 5-L Active  cmdID= 37439 "
		::= { iqmux47CmdEntry 37439 }


	iqmux47EmbCtrlChannelPair5RActive OBJECT-TYPE
		SYNTAX		INTEGER { disable(0), enable(1) }
		MAX-ACCESS		read-write
		STATUS			current
		DESCRIPTION
				"TYPE: - Checkbox
				 PAGE: - Audio- Emb.Ctrl
					Pair 5-R Active  cmdID= 37440 "
		::= { iqmux47CmdEntry 37440 }


	iqmux47EmbCtrlChannelPair6LActive OBJECT-TYPE
		SYNTAX		INTEGER { disable(0), enable(1) }
		MAX-ACCESS		read-write
		STATUS			current
		DESCRIPTION
				"TYPE: - Checkbox
				 PAGE: - Audio- Emb.Ctrl
					Pair 6-L Active  cmdID= 37441 "
		::= { iqmux47CmdEntry 37441 }


	iqmux47EmbCtrlChannelPair6RActive OBJECT-TYPE
		SYNTAX		INTEGER { disable(0), enable(1) }
		MAX-ACCESS		read-write
		STATUS			current
		DESCRIPTION
				"TYPE: - Checkbox
				 PAGE: - Audio- Emb.Ctrl
					Pair 6-R Active  cmdID= 37442 "
		::= { iqmux47CmdEntry 37442 }


	iqmux47EmbCtrlChannelPair7LActive OBJECT-TYPE
		SYNTAX		INTEGER { disable(0), enable(1) }
		MAX-ACCESS		read-write
		STATUS			current
		DESCRIPTION
				"TYPE: - Checkbox
				 PAGE: - Audio- Emb.Ctrl
					Pair 7-L Active  cmdID= 37443 "
		::= { iqmux47CmdEntry 37443 }


	iqmux47EmbCtrlChannelPair7RActive OBJECT-TYPE
		SYNTAX		INTEGER { disable(0), enable(1) }
		MAX-ACCESS		read-write
		STATUS			current
		DESCRIPTION
				"TYPE: - Checkbox
				 PAGE: - Audio- Emb.Ctrl
					Pair 7-R Active  cmdID= 37444 "
		::= { iqmux47CmdEntry 37444 }


	iqmux47EmbCtrlChannelPair8LActive OBJECT-TYPE
		SYNTAX		INTEGER { disable(0), enable(1) }
		MAX-ACCESS		read-write
		STATUS			current
		DESCRIPTION
				"TYPE: - Checkbox
				 PAGE: - Audio- Emb.Ctrl
					Pair 8-L Active  cmdID= 37445 "
		::= { iqmux47CmdEntry 37445 }


	iqmux47EmbCtrlChannelPair8RActive OBJECT-TYPE
		SYNTAX		INTEGER { disable(0), enable(1) }
		MAX-ACCESS		read-write
		STATUS			current
		DESCRIPTION
				"TYPE: - Checkbox
				 PAGE: - Audio- Emb.Ctrl
					Pair 8-R Active  cmdID= 37446 "
		::= { iqmux47CmdEntry 37446 }


	iqmux47AudioEmbCtrlEmbedderPriority OBJECT-TYPE
		SYNTAX		INTEGER {
							val_Normal(0),
							val_Audio_Dolby_E(1)
							}
		MAX-ACCESS		read-write
		STATUS			current
		DESCRIPTION
				"TYPE: - RadiobuttonList
				 PAGE: - Audio- Emb.Ctrl
					Embedder Priority  cmdID= 37460
					Normal  value= 0
					Audio (Dolby-E)  value= 1  "
		::= { iqmux47CmdEntry 37460 }


	iqmux47EmbGainEmbedPair1Embed1MuteL OBJECT-TYPE
		SYNTAX		INTEGER { disable(0), enable(1) }
		MAX-ACCESS		read-write
		STATUS			current
		DESCRIPTION
				"TYPE: - Checkbox
				 PAGE: - Audio
					Embed 1 Mute L  cmdID= 37340 "
		::= { iqmux47CmdEntry 37340 }


	iqmux47EmbGainEmbedPair1Embed1MuteR OBJECT-TYPE
		SYNTAX		INTEGER { disable(0), enable(1) }
		MAX-ACCESS		read-write
		STATUS			current
		DESCRIPTION
				"TYPE: - Checkbox
				 PAGE: - Audio
					Embed 1 Mute R  cmdID= 37341 "
		::= { iqmux47CmdEntry 37341 }


	iqmux47EmbGainEmbedPair1Embed1LGain OBJECT-TYPE
		SYNTAX		INTEGER
		MAX-ACCESS		read-write
		STATUS			current
		DESCRIPTION
				"TYPE: - Number
				 PAGE: - Audio
					Embed 1 L Gain  cmdID= 37320  min= -661  max= 120  step= 1  format= %0.1f dB  div_scale= 10
					Min = -66.1 dB  Max = 12.0 dB  Step = 0.1 dB "
		::= { iqmux47CmdEntry 37320 }


	iqmux47EmbGainEmbedPair1Embed1RGain OBJECT-TYPE
		SYNTAX		INTEGER
		MAX-ACCESS		read-write
		STATUS			current
		DESCRIPTION
				"TYPE: - Number
				 PAGE: - Audio
					Embed 1 R Gain  cmdID= 37321  min= -661  max= 120  step= 1  format= %0.1f dB  div_scale= 10
					Min = -66.1 dB  Max = 12.0 dB  Step = 0.1 dB "
		::= { iqmux47CmdEntry 37321 }


	iqmux47EmbGainEmbedPair1Stereo OBJECT-TYPE
		SYNTAX		INTEGER { disable(0), enable(1) }
		MAX-ACCESS		read-write
		STATUS			current
		DESCRIPTION
				"TYPE: - Checkbox
				 PAGE: - Audio
					Stereo  cmdID= 37380 "
		::= { iqmux47CmdEntry 37380 }


	iqmux47EmbGainEmbedPair1Embed1InvertL OBJECT-TYPE
		SYNTAX		INTEGER { disable(0), enable(1) }
		MAX-ACCESS		read-write
		STATUS			current
		DESCRIPTION
				"TYPE: - Checkbox
				 PAGE: - Audio
					Embed 1 Invert L  cmdID= 37360 "
		::= { iqmux47CmdEntry 37360 }


	iqmux47EmbGainEmbedPair1Embed1InvertR OBJECT-TYPE
		SYNTAX		INTEGER { disable(0), enable(1) }
		MAX-ACCESS		read-write
		STATUS			current
		DESCRIPTION
				"TYPE: - Checkbox
				 PAGE: - Audio
					Embed 1 Invert R  cmdID= 37361 "
		::= { iqmux47CmdEntry 37361 }


	iqmux47EmbGainEmbedPair1Embed1LClip OBJECT-TYPE
		SYNTAX		RollCallString
		MAX-ACCESS		read-only
		STATUS			current
		DESCRIPTION
				"TYPE: - Display
				 PAGE: - Audio
					Embed 1-L Clip  cmdID= 37540  format=   "
		::= { iqmux47CmdEntry 37540 }


	iqmux47EmbGainEmbedPair1Embed1RClip OBJECT-TYPE
		SYNTAX		RollCallString
		MAX-ACCESS		read-only
		STATUS			current
		DESCRIPTION
				"TYPE: - Display
				 PAGE: - Audio
					Embed 1-R Clip  cmdID= 37541  format=   "
		::= { iqmux47CmdEntry 37541 }


	iqmux47EmbGainEmbedPair2Embed2MuteL OBJECT-TYPE
		SYNTAX		INTEGER { disable(0), enable(1) }
		MAX-ACCESS		read-write
		STATUS			current
		DESCRIPTION
				"TYPE: - Checkbox
				 PAGE: - Audio
					Embed 2 Mute L  cmdID= 37342 "
		::= { iqmux47CmdEntry 37342 }


	iqmux47EmbGainEmbedPair2Embed2MuteR OBJECT-TYPE
		SYNTAX		INTEGER { disable(0), enable(1) }
		MAX-ACCESS		read-write
		STATUS			current
		DESCRIPTION
				"TYPE: - Checkbox
				 PAGE: - Audio
					Embed 2 Mute R  cmdID= 37343 "
		::= { iqmux47CmdEntry 37343 }


	iqmux47EmbGainEmbedPair2Embed2LGain OBJECT-TYPE
		SYNTAX		INTEGER
		MAX-ACCESS		read-write
		STATUS			current
		DESCRIPTION
				"TYPE: - Number
				 PAGE: - Audio
					Embed 2 L Gain  cmdID= 37322  min= -661  max= 120  step= 1  format= %0.1f dB  div_scale= 10
					Min = -66.1 dB  Max = 12.0 dB  Step = 0.1 dB "
		::= { iqmux47CmdEntry 37322 }


	iqmux47EmbGainEmbedPair2Embed2RGain OBJECT-TYPE
		SYNTAX		INTEGER
		MAX-ACCESS		read-write
		STATUS			current
		DESCRIPTION
				"TYPE: - Number
				 PAGE: - Audio
					Embed 2 R Gain  cmdID= 37323  min= -661  max= 120  step= 1  format= %0.1f dB  div_scale= 10
					Min = -66.1 dB  Max = 12.0 dB  Step = 0.1 dB "
		::= { iqmux47CmdEntry 37323 }


	iqmux47EmbGainEmbedPair2Stereo OBJECT-TYPE
		SYNTAX		INTEGER { disable(0), enable(1) }
		MAX-ACCESS		read-write
		STATUS			current
		DESCRIPTION
				"TYPE: - Checkbox
				 PAGE: - Audio
					Stereo  cmdID= 37381 "
		::= { iqmux47CmdEntry 37381 }


	iqmux47EmbGainEmbedPair2Embed2InvertL OBJECT-TYPE
		SYNTAX		INTEGER { disable(0), enable(1) }
		MAX-ACCESS		read-write
		STATUS			current
		DESCRIPTION
				"TYPE: - Checkbox
				 PAGE: - Audio
					Embed 2 Invert L  cmdID= 37362 "
		::= { iqmux47CmdEntry 37362 }


	iqmux47EmbGainEmbedPair2Embed2InvertR OBJECT-TYPE
		SYNTAX		INTEGER { disable(0), enable(1) }
		MAX-ACCESS		read-write
		STATUS			current
		DESCRIPTION
				"TYPE: - Checkbox
				 PAGE: - Audio
					Embed 2 Invert R  cmdID= 37363 "
		::= { iqmux47CmdEntry 37363 }


	iqmux47EmbGainEmbedPair2Embed2LClip OBJECT-TYPE
		SYNTAX		RollCallString
		MAX-ACCESS		read-only
		STATUS			current
		DESCRIPTION
				"TYPE: - Display
				 PAGE: - Audio
					Embed 2-L Clip  cmdID= 37542  format=   "
		::= { iqmux47CmdEntry 37542 }


	iqmux47EmbGainEmbedPair2Embed2RClip OBJECT-TYPE
		SYNTAX		RollCallString
		MAX-ACCESS		read-only
		STATUS			current
		DESCRIPTION
				"TYPE: - Display
				 PAGE: - Audio
					Embed 2-R Clip  cmdID= 37543  format=   "
		::= { iqmux47CmdEntry 37543 }


	iqmux47EmbGainEmbedPair3Embed3MuteL OBJECT-TYPE
		SYNTAX		INTEGER { disable(0), enable(1) }
		MAX-ACCESS		read-write
		STATUS			current
		DESCRIPTION
				"TYPE: - Checkbox
				 PAGE: - Audio
					Embed 3 Mute L  cmdID= 37344 "
		::= { iqmux47CmdEntry 37344 }


	iqmux47EmbGainEmbedPair3Embed3MuteR OBJECT-TYPE
		SYNTAX		INTEGER { disable(0), enable(1) }
		MAX-ACCESS		read-write
		STATUS			current
		DESCRIPTION
				"TYPE: - Checkbox
				 PAGE: - Audio
					Embed 3 Mute R  cmdID= 37345 "
		::= { iqmux47CmdEntry 37345 }


	iqmux47EmbGainEmbedPair3Embed3LGain OBJECT-TYPE
		SYNTAX		INTEGER
		MAX-ACCESS		read-write
		STATUS			current
		DESCRIPTION
				"TYPE: - Number
				 PAGE: - Audio
					Embed 3 L Gain  cmdID= 37324  min= -661  max= 120  step= 1  format= %0.1f dB  div_scale= 10
					Min = -66.1 dB  Max = 12.0 dB  Step = 0.1 dB "
		::= { iqmux47CmdEntry 37324 }


	iqmux47EmbGainEmbedPair3Embed3RGain OBJECT-TYPE
		SYNTAX		INTEGER
		MAX-ACCESS		read-write
		STATUS			current
		DESCRIPTION
				"TYPE: - Number
				 PAGE: - Audio
					Embed 3 R Gain  cmdID= 37325  min= -661  max= 120  step= 1  format= %0.1f dB  div_scale= 10
					Min = -66.1 dB  Max = 12.0 dB  Step = 0.1 dB "
		::= { iqmux47CmdEntry 37325 }


	iqmux47EmbGainEmbedPair3Stereo OBJECT-TYPE
		SYNTAX		INTEGER { disable(0), enable(1) }
		MAX-ACCESS		read-write
		STATUS			current
		DESCRIPTION
				"TYPE: - Checkbox
				 PAGE: - Audio
					Stereo  cmdID= 37382 "
		::= { iqmux47CmdEntry 37382 }


	iqmux47EmbGainEmbedPair3Embed3InvertL OBJECT-TYPE
		SYNTAX		INTEGER { disable(0), enable(1) }
		MAX-ACCESS		read-write
		STATUS			current
		DESCRIPTION
				"TYPE: - Checkbox
				 PAGE: - Audio
					Embed 3 Invert L  cmdID= 37364 "
		::= { iqmux47CmdEntry 37364 }


	iqmux47EmbGainEmbedPair3Embed3InvertR OBJECT-TYPE
		SYNTAX		INTEGER { disable(0), enable(1) }
		MAX-ACCESS		read-write
		STATUS			current
		DESCRIPTION
				"TYPE: - Checkbox
				 PAGE: - Audio
					Embed 3 Invert R  cmdID= 37365 "
		::= { iqmux47CmdEntry 37365 }


	iqmux47EmbGainEmbedPair3Embed3LClip OBJECT-TYPE
		SYNTAX		RollCallString
		MAX-ACCESS		read-only
		STATUS			current
		DESCRIPTION
				"TYPE: - Display
				 PAGE: - Audio
					Embed 3-L Clip  cmdID= 37544  format=   "
		::= { iqmux47CmdEntry 37544 }


	iqmux47EmbGainEmbedPair3Embed3RClip OBJECT-TYPE
		SYNTAX		RollCallString
		MAX-ACCESS		read-only
		STATUS			current
		DESCRIPTION
				"TYPE: - Display
				 PAGE: - Audio
					Embed 3-R Clip  cmdID= 37545  format=   "
		::= { iqmux47CmdEntry 37545 }


	iqmux47EmbGainEmbedPair4Embed4MuteL OBJECT-TYPE
		SYNTAX		INTEGER { disable(0), enable(1) }
		MAX-ACCESS		read-write
		STATUS			current
		DESCRIPTION
				"TYPE: - Checkbox
				 PAGE: - Audio
					Embed 4 Mute L  cmdID= 37346 "
		::= { iqmux47CmdEntry 37346 }


	iqmux47EmbGainEmbedPair4Embed4MuteR OBJECT-TYPE
		SYNTAX		INTEGER { disable(0), enable(1) }
		MAX-ACCESS		read-write
		STATUS			current
		DESCRIPTION
				"TYPE: - Checkbox
				 PAGE: - Audio
					Embed 4 Mute R  cmdID= 37347 "
		::= { iqmux47CmdEntry 37347 }


	iqmux47EmbGainEmbedPair4Embed4LGain OBJECT-TYPE
		SYNTAX		INTEGER
		MAX-ACCESS		read-write
		STATUS			current
		DESCRIPTION
				"TYPE: - Number
				 PAGE: - Audio
					Embed 4 L Gain  cmdID= 37326  min= -661  max= 120  step= 1  format= %0.1f dB  div_scale= 10
					Min = -66.1 dB  Max = 12.0 dB  Step = 0.1 dB "
		::= { iqmux47CmdEntry 37326 }


	iqmux47EmbGainEmbedPair4Embed4RGain OBJECT-TYPE
		SYNTAX		INTEGER
		MAX-ACCESS		read-write
		STATUS			current
		DESCRIPTION
				"TYPE: - Number
				 PAGE: - Audio
					Embed 4 R Gain  cmdID= 37327  min= -661  max= 120  step= 1  format= %0.1f dB  div_scale= 10
					Min = -66.1 dB  Max = 12.0 dB  Step = 0.1 dB "
		::= { iqmux47CmdEntry 37327 }


	iqmux47EmbGainEmbedPair4Stereo OBJECT-TYPE
		SYNTAX		INTEGER { disable(0), enable(1) }
		MAX-ACCESS		read-write
		STATUS			current
		DESCRIPTION
				"TYPE: - Checkbox
				 PAGE: - Audio
					Stereo  cmdID= 37383 "
		::= { iqmux47CmdEntry 37383 }


	iqmux47EmbGainEmbedPair4Embed4InvertL OBJECT-TYPE
		SYNTAX		INTEGER { disable(0), enable(1) }
		MAX-ACCESS		read-write
		STATUS			current
		DESCRIPTION
				"TYPE: - Checkbox
				 PAGE: - Audio
					Embed 4 Invert L  cmdID= 37366 "
		::= { iqmux47CmdEntry 37366 }


	iqmux47EmbGainEmbedPair4Embed4InvertR OBJECT-TYPE
		SYNTAX		INTEGER { disable(0), enable(1) }
		MAX-ACCESS		read-write
		STATUS			current
		DESCRIPTION
				"TYPE: - Checkbox
				 PAGE: - Audio
					Embed 4 Invert R  cmdID= 37367 "
		::= { iqmux47CmdEntry 37367 }


	iqmux47EmbGainEmbedPair4Embed4LClip OBJECT-TYPE
		SYNTAX		RollCallString
		MAX-ACCESS		read-only
		STATUS			current
		DESCRIPTION
				"TYPE: - Display
				 PAGE: - Audio
					Embed 4-L Clip  cmdID= 37546  format=   "
		::= { iqmux47CmdEntry 37546 }


	iqmux47EmbGainEmbedPair4Embed4RClip OBJECT-TYPE
		SYNTAX		RollCallString
		MAX-ACCESS		read-only
		STATUS			current
		DESCRIPTION
				"TYPE: - Display
				 PAGE: - Audio
					Embed 4-R Clip  cmdID= 37547  format=   "
		::= { iqmux47CmdEntry 37547 }


	iqmux47EmbGainEmbedPair5Embed5MuteL OBJECT-TYPE
		SYNTAX		INTEGER { disable(0), enable(1) }
		MAX-ACCESS		read-write
		STATUS			current
		DESCRIPTION
				"TYPE: - Checkbox
				 PAGE: - Audio
					Embed 5 Mute L  cmdID= 37348 "
		::= { iqmux47CmdEntry 37348 }


	iqmux47EmbGainEmbedPair5Embed5MuteR OBJECT-TYPE
		SYNTAX		INTEGER { disable(0), enable(1) }
		MAX-ACCESS		read-write
		STATUS			current
		DESCRIPTION
				"TYPE: - Checkbox
				 PAGE: - Audio
					Embed 5 Mute R  cmdID= 37349 "
		::= { iqmux47CmdEntry 37349 }


	iqmux47EmbGainEmbedPair5Embed5LGain OBJECT-TYPE
		SYNTAX		INTEGER
		MAX-ACCESS		read-write
		STATUS			current
		DESCRIPTION
				"TYPE: - Number
				 PAGE: - Audio
					Embed 5 L Gain  cmdID= 37328  min= -661  max= 120  step= 1  format= %0.1f dB  div_scale= 10
					Min = -66.1 dB  Max = 12.0 dB  Step = 0.1 dB "
		::= { iqmux47CmdEntry 37328 }


	iqmux47EmbGainEmbedPair5Embed5RGain OBJECT-TYPE
		SYNTAX		INTEGER
		MAX-ACCESS		read-write
		STATUS			current
		DESCRIPTION
				"TYPE: - Number
				 PAGE: - Audio
					Embed 5 R Gain  cmdID= 37329  min= -661  max= 120  step= 1  format= %0.1f dB  div_scale= 10
					Min = -66.1 dB  Max = 12.0 dB  Step = 0.1 dB "
		::= { iqmux47CmdEntry 37329 }


	iqmux47EmbGainEmbedPair5Stereo OBJECT-TYPE
		SYNTAX		INTEGER { disable(0), enable(1) }
		MAX-ACCESS		read-write
		STATUS			current
		DESCRIPTION
				"TYPE: - Checkbox
				 PAGE: - Audio
					Stereo  cmdID= 37384 "
		::= { iqmux47CmdEntry 37384 }


	iqmux47EmbGainEmbedPair5Embed5InvertL OBJECT-TYPE
		SYNTAX		INTEGER { disable(0), enable(1) }
		MAX-ACCESS		read-write
		STATUS			current
		DESCRIPTION
				"TYPE: - Checkbox
				 PAGE: - Audio
					Embed 5 Invert L  cmdID= 37368 "
		::= { iqmux47CmdEntry 37368 }


	iqmux47EmbGainEmbedPair5Embed5InvertR OBJECT-TYPE
		SYNTAX		INTEGER { disable(0), enable(1) }
		MAX-ACCESS		read-write
		STATUS			current
		DESCRIPTION
				"TYPE: - Checkbox
				 PAGE: - Audio
					Embed 5 Invert R  cmdID= 37369 "
		::= { iqmux47CmdEntry 37369 }


	iqmux47EmbGainEmbedPair5Embed5LClip OBJECT-TYPE
		SYNTAX		RollCallString
		MAX-ACCESS		read-only
		STATUS			current
		DESCRIPTION
				"TYPE: - Display
				 PAGE: - Audio
					Embed 5-L Clip  cmdID= 37548  format=   "
		::= { iqmux47CmdEntry 37548 }


	iqmux47EmbGainEmbedPair5Embed5RClip OBJECT-TYPE
		SYNTAX		RollCallString
		MAX-ACCESS		read-only
		STATUS			current
		DESCRIPTION
				"TYPE: - Display
				 PAGE: - Audio
					Embed 5-R Clip  cmdID= 37549  format=   "
		::= { iqmux47CmdEntry 37549 }


	iqmux47EmbGainEmbedPair6Embed6MuteL OBJECT-TYPE
		SYNTAX		INTEGER { disable(0), enable(1) }
		MAX-ACCESS		read-write
		STATUS			current
		DESCRIPTION
				"TYPE: - Checkbox
				 PAGE: - Audio
					Embed 6 Mute L  cmdID= 37350 "
		::= { iqmux47CmdEntry 37350 }


	iqmux47EmbGainEmbedPair6Embed6MuteR OBJECT-TYPE
		SYNTAX		INTEGER { disable(0), enable(1) }
		MAX-ACCESS		read-write
		STATUS			current
		DESCRIPTION
				"TYPE: - Checkbox
				 PAGE: - Audio
					Embed 6 Mute R  cmdID= 37351 "
		::= { iqmux47CmdEntry 37351 }


	iqmux47EmbGainEmbedPair6Embed6LGain OBJECT-TYPE
		SYNTAX		INTEGER
		MAX-ACCESS		read-write
		STATUS			current
		DESCRIPTION
				"TYPE: - Number
				 PAGE: - Audio
					Embed 6 L Gain  cmdID= 37330  min= -661  max= 120  step= 1  format= %0.1f dB  div_scale= 10
					Min = -66.1 dB  Max = 12.0 dB  Step = 0.1 dB "
		::= { iqmux47CmdEntry 37330 }


	iqmux47EmbGainEmbedPair6Embed6RGain OBJECT-TYPE
		SYNTAX		INTEGER
		MAX-ACCESS		read-write
		STATUS			current
		DESCRIPTION
				"TYPE: - Number
				 PAGE: - Audio
					Embed 6 R Gain  cmdID= 37331  min= -661  max= 120  step= 1  format= %0.1f dB  div_scale= 10
					Min = -66.1 dB  Max = 12.0 dB  Step = 0.1 dB "
		::= { iqmux47CmdEntry 37331 }


	iqmux47EmbGainEmbedPair6Stereo OBJECT-TYPE
		SYNTAX		INTEGER { disable(0), enable(1) }
		MAX-ACCESS		read-write
		STATUS			current
		DESCRIPTION
				"TYPE: - Checkbox
				 PAGE: - Audio
					Stereo  cmdID= 37385 "
		::= { iqmux47CmdEntry 37385 }


	iqmux47EmbGainEmbedPair6Embed6InvertL OBJECT-TYPE
		SYNTAX		INTEGER { disable(0), enable(1) }
		MAX-ACCESS		read-write
		STATUS			current
		DESCRIPTION
				"TYPE: - Checkbox
				 PAGE: - Audio
					Embed 6 Invert L  cmdID= 37370 "
		::= { iqmux47CmdEntry 37370 }


	iqmux47EmbGainEmbedPair6Embed6InvertR OBJECT-TYPE
		SYNTAX		INTEGER { disable(0), enable(1) }
		MAX-ACCESS		read-write
		STATUS			current
		DESCRIPTION
				"TYPE: - Checkbox
				 PAGE: - Audio
					Embed 6 Invert R  cmdID= 37371 "
		::= { iqmux47CmdEntry 37371 }


	iqmux47EmbGainEmbedPair6Embed6LClip OBJECT-TYPE
		SYNTAX		RollCallString
		MAX-ACCESS		read-only
		STATUS			current
		DESCRIPTION
				"TYPE: - Display
				 PAGE: - Audio
					Embed 6-L Clip  cmdID= 37550  format=   "
		::= { iqmux47CmdEntry 37550 }


	iqmux47EmbGainEmbedPair6Embed6RClip OBJECT-TYPE
		SYNTAX		RollCallString
		MAX-ACCESS		read-only
		STATUS			current
		DESCRIPTION
				"TYPE: - Display
				 PAGE: - Audio
					Embed 6-R Clip  cmdID= 37551  format=   "
		::= { iqmux47CmdEntry 37551 }


	iqmux47EmbGainEmbedPair7Embed7MuteL OBJECT-TYPE
		SYNTAX		INTEGER { disable(0), enable(1) }
		MAX-ACCESS		read-write
		STATUS			current
		DESCRIPTION
				"TYPE: - Checkbox
				 PAGE: - Audio
					Embed 7 Mute L  cmdID= 37352 "
		::= { iqmux47CmdEntry 37352 }


	iqmux47EmbGainEmbedPair7Embed7MuteR OBJECT-TYPE
		SYNTAX		INTEGER { disable(0), enable(1) }
		MAX-ACCESS		read-write
		STATUS			current
		DESCRIPTION
				"TYPE: - Checkbox
				 PAGE: - Audio
					Embed 7 Mute R  cmdID= 37353 "
		::= { iqmux47CmdEntry 37353 }


	iqmux47EmbGainEmbedPair7Embed7LGain OBJECT-TYPE
		SYNTAX		INTEGER
		MAX-ACCESS		read-write
		STATUS			current
		DESCRIPTION
				"TYPE: - Number
				 PAGE: - Audio
					Embed 7 L Gain  cmdID= 37332  min= -661  max= 120  step= 1  format= %0.1f dB  div_scale= 10
					Min = -66.1 dB  Max = 12.0 dB  Step = 0.1 dB "
		::= { iqmux47CmdEntry 37332 }


	iqmux47EmbGainEmbedPair7Embed7RGain OBJECT-TYPE
		SYNTAX		INTEGER
		MAX-ACCESS		read-write
		STATUS			current
		DESCRIPTION
				"TYPE: - Number
				 PAGE: - Audio
					Embed 7 R Gain  cmdID= 37333  min= -661  max= 120  step= 1  format= %0.1f dB  div_scale= 10
					Min = -66.1 dB  Max = 12.0 dB  Step = 0.1 dB "
		::= { iqmux47CmdEntry 37333 }


	iqmux47EmbGainEmbedPair7Stereo OBJECT-TYPE
		SYNTAX		INTEGER { disable(0), enable(1) }
		MAX-ACCESS		read-write
		STATUS			current
		DESCRIPTION
				"TYPE: - Checkbox
				 PAGE: - Audio
					Stereo  cmdID= 37386 "
		::= { iqmux47CmdEntry 37386 }


	iqmux47EmbGainEmbedPair7Embed7InvertL OBJECT-TYPE
		SYNTAX		INTEGER { disable(0), enable(1) }
		MAX-ACCESS		read-write
		STATUS			current
		DESCRIPTION
				"TYPE: - Checkbox
				 PAGE: - Audio
					Embed 7 Invert L  cmdID= 37372 "
		::= { iqmux47CmdEntry 37372 }


	iqmux47EmbGainEmbedPair7Embed7InvertR OBJECT-TYPE
		SYNTAX		INTEGER { disable(0), enable(1) }
		MAX-ACCESS		read-write
		STATUS			current
		DESCRIPTION
				"TYPE: - Checkbox
				 PAGE: - Audio
					Embed 7 Invert R  cmdID= 37373 "
		::= { iqmux47CmdEntry 37373 }


	iqmux47EmbGainEmbedPair7Embed7LClip OBJECT-TYPE
		SYNTAX		RollCallString
		MAX-ACCESS		read-only
		STATUS			current
		DESCRIPTION
				"TYPE: - Display
				 PAGE: - Audio
					Embed 7-L Clip  cmdID= 37552  format=   "
		::= { iqmux47CmdEntry 37552 }


	iqmux47EmbGainEmbedPair7Embed7RClip OBJECT-TYPE
		SYNTAX		RollCallString
		MAX-ACCESS		read-only
		STATUS			current
		DESCRIPTION
				"TYPE: - Display
				 PAGE: - Audio
					Embed 7-R Clip  cmdID= 37553  format=   "
		::= { iqmux47CmdEntry 37553 }


	iqmux47EmbGainEmbedPair8Embed8MuteL OBJECT-TYPE
		SYNTAX		INTEGER { disable(0), enable(1) }
		MAX-ACCESS		read-write
		STATUS			current
		DESCRIPTION
				"TYPE: - Checkbox
				 PAGE: - Audio
					Embed 8 Mute L  cmdID= 37354 "
		::= { iqmux47CmdEntry 37354 }


	iqmux47EmbGainEmbedPair8Embed8MuteR OBJECT-TYPE
		SYNTAX		INTEGER { disable(0), enable(1) }
		MAX-ACCESS		read-write
		STATUS			current
		DESCRIPTION
				"TYPE: - Checkbox
				 PAGE: - Audio
					Embed 8 Mute R  cmdID= 37355 "
		::= { iqmux47CmdEntry 37355 }


	iqmux47EmbGainEmbedPair8Embed8LGain OBJECT-TYPE
		SYNTAX		INTEGER
		MAX-ACCESS		read-write
		STATUS			current
		DESCRIPTION
				"TYPE: - Number
				 PAGE: - Audio
					Embed 8 L Gain  cmdID= 37334  min= -661  max= 120  step= 1  format= %0.1f dB  div_scale= 10
					Min = -66.1 dB  Max = 12.0 dB  Step = 0.1 dB "
		::= { iqmux47CmdEntry 37334 }


	iqmux47EmbGainEmbedPair8Embed8RGain OBJECT-TYPE
		SYNTAX		INTEGER
		MAX-ACCESS		read-write
		STATUS			current
		DESCRIPTION
				"TYPE: - Number
				 PAGE: - Audio
					Embed 8 R Gain  cmdID= 37335  min= -661  max= 120  step= 1  format= %0.1f dB  div_scale= 10
					Min = -66.1 dB  Max = 12.0 dB  Step = 0.1 dB "
		::= { iqmux47CmdEntry 37335 }


	iqmux47EmbGainEmbedPair8Stereo OBJECT-TYPE
		SYNTAX		INTEGER { disable(0), enable(1) }
		MAX-ACCESS		read-write
		STATUS			current
		DESCRIPTION
				"TYPE: - Checkbox
				 PAGE: - Audio
					Stereo  cmdID= 37387 "
		::= { iqmux47CmdEntry 37387 }


	iqmux47EmbGainEmbedPair8Embed8InvertL OBJECT-TYPE
		SYNTAX		INTEGER { disable(0), enable(1) }
		MAX-ACCESS		read-write
		STATUS			current
		DESCRIPTION
				"TYPE: - Checkbox
				 PAGE: - Audio
					Embed 8 Invert L  cmdID= 37374 "
		::= { iqmux47CmdEntry 37374 }


	iqmux47EmbGainEmbedPair8Embed8InvertR OBJECT-TYPE
		SYNTAX		INTEGER { disable(0), enable(1) }
		MAX-ACCESS		read-write
		STATUS			current
		DESCRIPTION
				"TYPE: - Checkbox
				 PAGE: - Audio
					Embed 8 Invert R  cmdID= 37375 "
		::= { iqmux47CmdEntry 37375 }


	iqmux47EmbGainEmbedPair8Embed8LClip OBJECT-TYPE
		SYNTAX		RollCallString
		MAX-ACCESS		read-only
		STATUS			current
		DESCRIPTION
				"TYPE: - Display
				 PAGE: - Audio
					Embed 8-L Clip  cmdID= 37554  format=   "
		::= { iqmux47CmdEntry 37554 }


	iqmux47EmbGainEmbedPair8Embed8RClip OBJECT-TYPE
		SYNTAX		RollCallString
		MAX-ACCESS		read-only
		STATUS			current
		DESCRIPTION
				"TYPE: - Display
				 PAGE: - Audio
					Embed 8-R Clip  cmdID= 37555  format=   "
		::= { iqmux47CmdEntry 37555 }


	iqmux47EmbOutEmbedPair1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 1
					Left  cmdID= 37300
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37300 }


	iqmux47EmbOutEmbedPair1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 1
					Right  cmdID= 37301
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37301 }


	iqmux47EmbOutEmbedPair1LinkLRSelection OBJECT-TYPE
		SYNTAX		INTEGER { disable(0), enable(1) }
		MAX-ACCESS		read-write
		STATUS			current
		DESCRIPTION
				"TYPE: - Checkbox
				 PAGE: - Audio- Embed Pair 1
					Link L+R Selection  cmdID= 37390 "
		::= { iqmux47CmdEntry 37390 }


	iqmux47EmbOutEmbedPair2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 2
					Left  cmdID= 37302
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37302 }


	iqmux47EmbOutEmbedPair2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 2
					Right  cmdID= 37303
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37303 }


	iqmux47EmbOutEmbedPair2LinkLRSelection OBJECT-TYPE
		SYNTAX		INTEGER { disable(0), enable(1) }
		MAX-ACCESS		read-write
		STATUS			current
		DESCRIPTION
				"TYPE: - Checkbox
				 PAGE: - Audio- Embed Pair 2
					Link L+R Selection  cmdID= 37391 "
		::= { iqmux47CmdEntry 37391 }


	iqmux47EmbOutEmbedPair3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 3
					Left  cmdID= 37304
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37304 }


	iqmux47EmbOutEmbedPair3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 3
					Right  cmdID= 37305
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37305 }


	iqmux47EmbOutEmbedPair3LinkLRSelection OBJECT-TYPE
		SYNTAX		INTEGER { disable(0), enable(1) }
		MAX-ACCESS		read-write
		STATUS			current
		DESCRIPTION
				"TYPE: - Checkbox
				 PAGE: - Audio- Embed Pair 3
					Link L+R Selection  cmdID= 37392 "
		::= { iqmux47CmdEntry 37392 }


	iqmux47EmbOutEmbedPair4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 4
					Left  cmdID= 37306
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37306 }


	iqmux47EmbOutEmbedPair4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 4
					Right  cmdID= 37307
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37307 }


	iqmux47EmbOutEmbedPair4LinkLRSelection OBJECT-TYPE
		SYNTAX		INTEGER { disable(0), enable(1) }
		MAX-ACCESS		read-write
		STATUS			current
		DESCRIPTION
				"TYPE: - Checkbox
				 PAGE: - Audio- Embed Pair 4
					Link L+R Selection  cmdID= 37393 "
		::= { iqmux47CmdEntry 37393 }


	iqmux47EmbOutEmbedPair5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 5
					Left  cmdID= 37308
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37308 }


	iqmux47EmbOutEmbedPair5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 5
					Right  cmdID= 37309
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37309 }


	iqmux47EmbOutEmbedPair5LinkLRSelection OBJECT-TYPE
		SYNTAX		INTEGER { disable(0), enable(1) }
		MAX-ACCESS		read-write
		STATUS			current
		DESCRIPTION
				"TYPE: - Checkbox
				 PAGE: - Audio- Embed Pair 5
					Link L+R Selection  cmdID= 37394 "
		::= { iqmux47CmdEntry 37394 }


	iqmux47EmbOutEmbedPair6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 6
					Left  cmdID= 37310
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37310 }


	iqmux47EmbOutEmbedPair6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 6
					Right  cmdID= 37311
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37311 }


	iqmux47EmbOutEmbedPair6LinkLRSelection OBJECT-TYPE
		SYNTAX		INTEGER { disable(0), enable(1) }
		MAX-ACCESS		read-write
		STATUS			current
		DESCRIPTION
				"TYPE: - Checkbox
				 PAGE: - Audio- Embed Pair 6
					Link L+R Selection  cmdID= 37395 "
		::= { iqmux47CmdEntry 37395 }


	iqmux47EmbOutEmbedPair7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 7
					Left  cmdID= 37312
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37312 }


	iqmux47EmbOutEmbedPair7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 7
					Right  cmdID= 37313
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37313 }


	iqmux47EmbOutEmbedPair7LinkLRSelection OBJECT-TYPE
		SYNTAX		INTEGER { disable(0), enable(1) }
		MAX-ACCESS		read-write
		STATUS			current
		DESCRIPTION
				"TYPE: - Checkbox
				 PAGE: - Audio- Embed Pair 7
					Link L+R Selection  cmdID= 37396 "
		::= { iqmux47CmdEntry 37396 }


	iqmux47EmbOutEmbedPair8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 8
					Left  cmdID= 37314
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37314 }


	iqmux47EmbOutEmbedPair8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 8
					Right  cmdID= 37315
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37315 }


	iqmux47EmbOutEmbedPair8LinkLRSelection OBJECT-TYPE
		SYNTAX		INTEGER { disable(0), enable(1) }
		MAX-ACCESS		read-write
		STATUS			current
		DESCRIPTION
				"TYPE: - Checkbox
				 PAGE: - Audio- Embed Pair 8
					Link L+R Selection  cmdID= 37397 "
		::= { iqmux47CmdEntry 37397 }


	iqmux47AudioEmbModeInput1 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 1  cmdID= 37420
					PCM  value= 0
					Data  value= 1
					Mixed  value= 2  "
		::= { iqmux47CmdEntry 37420 }


	iqmux47AudioEmbModeInput2 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 2  cmdID= 37421
					PCM  value= 0
					Data  value= 1
					Mixed  value= 2  "
		::= { iqmux47CmdEntry 37421 }


	iqmux47AudioEmbModeInput3 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 3  cmdID= 37422
					PCM  value= 0
					Data  value= 1
					Mixed  value= 2  "
		::= { iqmux47CmdEntry 37422 }


	iqmux47AudioEmbModeInput4 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 4  cmdID= 37423
					PCM  value= 0
					Data  value= 1
					Mixed  value= 2  "
		::= { iqmux47CmdEntry 37423 }


	iqmux47AudioEmbModeInput5 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 5  cmdID= 37424
					PCM  value= 0
					Data  value= 1
					Mixed  value= 2  "
		::= { iqmux47CmdEntry 37424 }


	iqmux47AudioEmbModeInput6 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 6  cmdID= 37425
					PCM  value= 0
					Data  value= 1
					Mixed  value= 2  "
		::= { iqmux47CmdEntry 37425 }


	iqmux47AudioEmbModeInput7 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 7  cmdID= 37426
					PCM  value= 0
					Data  value= 1
					Mixed  value= 2  "
		::= { iqmux47CmdEntry 37426 }


	iqmux47AudioEmbModeInput8 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 8  cmdID= 37427
					PCM  value= 0
					Data  value= 1
					Mixed  value= 2  "
		::= { iqmux47CmdEntry 37427 }


	iqmux47EmbedNamesDisembeder1 OBJECT-TYPE
		SYNTAX		RollCallString
		MAX-ACCESS		read-write
		STATUS			current
		DESCRIPTION
				"TYPE: - Editstring
				 PAGE: - Audio- Emb.Names
					Disembed 1  cmdID= 37500  "
		::= { iqmux47CmdEntry 37500 }


	iqmux47EmbedNamesDisembeder1R OBJECT-TYPE
		SYNTAX		RollCallString
		MAX-ACCESS		read-write
		STATUS			current
		DESCRIPTION
				"TYPE: - Editstring
				 PAGE: - Audio- Emb.Names
					Disembed 1-R  cmdID= 37501  "
		::= { iqmux47CmdEntry 37501 }


	iqmux47EmbedNamesDisembeder2 OBJECT-TYPE
		SYNTAX		RollCallString
		MAX-ACCESS		read-write
		STATUS			current
		DESCRIPTION
				"TYPE: - Editstring
				 PAGE: - Audio- Emb.Names
					Disembed 2  cmdID= 37502  "
		::= { iqmux47CmdEntry 37502 }


	iqmux47EmbedNamesDisembeder2R OBJECT-TYPE
		SYNTAX		RollCallString
		MAX-ACCESS		read-write
		STATUS			current
		DESCRIPTION
				"TYPE: - Editstring
				 PAGE: - Audio- Emb.Names
					Disembed 2-R  cmdID= 37503  "
		::= { iqmux47CmdEntry 37503 }


	iqmux47EmbedNamesDisembeder3 OBJECT-TYPE
		SYNTAX		RollCallString
		MAX-ACCESS		read-write
		STATUS			current
		DESCRIPTION
				"TYPE: - Editstring
				 PAGE: - Audio- Emb.Names
					Disembed 3  cmdID= 37504  "
		::= { iqmux47CmdEntry 37504 }


	iqmux47EmbedNamesDisembeder3R OBJECT-TYPE
		SYNTAX		RollCallString
		MAX-ACCESS		read-write
		STATUS			current
		DESCRIPTION
				"TYPE: - Editstring
				 PAGE: - Audio- Emb.Names
					Disembed 3-R  cmdID= 37505  "
		::= { iqmux47CmdEntry 37505 }


	iqmux47EmbedNamesDisembeder4 OBJECT-TYPE
		SYNTAX		RollCallString
		MAX-ACCESS		read-write
		STATUS			current
		DESCRIPTION
				"TYPE: - Editstring
				 PAGE: - Audio- Emb.Names
					Disembed 4  cmdID= 37506  "
		::= { iqmux47CmdEntry 37506 }


	iqmux47EmbedNamesDisembeder4R OBJECT-TYPE
		SYNTAX		RollCallString
		MAX-ACCESS		read-write
		STATUS			current
		DESCRIPTION
				"TYPE: - Editstring
				 PAGE: - Audio- Emb.Names
					Disembed 4-R  cmdID= 37507  "
		::= { iqmux47CmdEntry 37507 }


	iqmux47EmbedNamesDisembeder5 OBJECT-TYPE
		SYNTAX		RollCallString
		MAX-ACCESS		read-write
		STATUS			current
		DESCRIPTION
				"TYPE: - Editstring
				 PAGE: - Audio- Emb.Names
					Disembed 5  cmdID= 37508  "
		::= { iqmux47CmdEntry 37508 }


	iqmux47EmbedNamesDisembeder5R OBJECT-TYPE
		SYNTAX		RollCallString
		MAX-ACCESS		read-write
		STATUS			current
		DESCRIPTION
				"TYPE: - Editstring
				 PAGE: - Audio- Emb.Names
					Disembed 5-R  cmdID= 37509  "
		::= { iqmux47CmdEntry 37509 }


	iqmux47EmbedNamesDisembeder6 OBJECT-TYPE
		SYNTAX		RollCallString
		MAX-ACCESS		read-write
		STATUS			current
		DESCRIPTION
				"TYPE: - Editstring
				 PAGE: - Audio- Emb.Names
					Disembed 6  cmdID= 37510  "
		::= { iqmux47CmdEntry 37510 }


	iqmux47EmbedNamesDisembeder6R OBJECT-TYPE
		SYNTAX		RollCallString
		MAX-ACCESS		read-write
		STATUS			current
		DESCRIPTION
				"TYPE: - Editstring
				 PAGE: - Audio- Emb.Names
					Disembed 6-R  cmdID= 37511  "
		::= { iqmux47CmdEntry 37511 }


	iqmux47EmbedNamesDisembeder7 OBJECT-TYPE
		SYNTAX		RollCallString
		MAX-ACCESS		read-write
		STATUS			current
		DESCRIPTION
				"TYPE: - Editstring
				 PAGE: - Audio- Emb.Names
					Disembed 7  cmdID= 37512  "
		::= { iqmux47CmdEntry 37512 }


	iqmux47EmbedNamesDisembeder7R OBJECT-TYPE
		SYNTAX		RollCallString
		MAX-ACCESS		read-write
		STATUS			current
		DESCRIPTION
				"TYPE: - Editstring
				 PAGE: - Audio- Emb.Names
					Disembed 7-R  cmdID= 37513  "
		::= { iqmux47CmdEntry 37513 }


	iqmux47EmbedNamesDisembeder8 OBJECT-TYPE
		SYNTAX		RollCallString
		MAX-ACCESS		read-write
		STATUS			current
		DESCRIPTION
				"TYPE: - Editstring
				 PAGE: - Audio- Emb.Names
					Disembed 8  cmdID= 37514  "
		::= { iqmux47CmdEntry 37514 }


	iqmux47EmbedNamesDisembeder8R OBJECT-TYPE
		SYNTAX		RollCallString
		MAX-ACCESS		read-write
		STATUS			current
		DESCRIPTION
				"TYPE: - Editstring
				 PAGE: - Audio- Emb.Names
					Disembed 8-R  cmdID= 37515  "
		::= { iqmux47CmdEntry 37515 }


	iqmux47EmbedNamesEmbeddedOP1 OBJECT-TYPE
		SYNTAX		RollCallString
		MAX-ACCESS		read-write
		STATUS			current
		DESCRIPTION
				"TYPE: - Editstring
				 PAGE: - Audio- Emb.Names
					Embed 1  cmdID= 37520  "
		::= { iqmux47CmdEntry 37520 }


	iqmux47EmbedNamesEmbeddedOP1R OBJECT-TYPE
		SYNTAX		RollCallString
		MAX-ACCESS		read-write
		STATUS			current
		DESCRIPTION
				"TYPE: - Editstring
				 PAGE: - Audio- Emb.Names
					Embed 1-R  cmdID= 37521  "
		::= { iqmux47CmdEntry 37521 }


	iqmux47EmbedNamesEmbeddedOP2 OBJECT-TYPE
		SYNTAX		RollCallString
		MAX-ACCESS		read-write
		STATUS			current
		DESCRIPTION
				"TYPE: - Editstring
				 PAGE: - Audio- Emb.Names
					Embed 2  cmdID= 37522  "
		::= { iqmux47CmdEntry 37522 }


	iqmux47EmbedNamesEmbeddedOP2R OBJECT-TYPE
		SYNTAX		RollCallString
		MAX-ACCESS		read-write
		STATUS			current
		DESCRIPTION
				"TYPE: - Editstring
				 PAGE: - Audio- Emb.Names
					Embed 2-R  cmdID= 37523  "
		::= { iqmux47CmdEntry 37523 }


	iqmux47EmbedNamesEmbeddedOP3 OBJECT-TYPE
		SYNTAX		RollCallString
		MAX-ACCESS		read-write
		STATUS			current
		DESCRIPTION
				"TYPE: - Editstring
				 PAGE: - Audio- Emb.Names
					Embed 3  cmdID= 37524  "
		::= { iqmux47CmdEntry 37524 }


	iqmux47EmbedNamesEmbeddedOP3R OBJECT-TYPE
		SYNTAX		RollCallString
		MAX-ACCESS		read-write
		STATUS			current
		DESCRIPTION
				"TYPE: - Editstring
				 PAGE: - Audio- Emb.Names
					Embed 3-R  cmdID= 37525  "
		::= { iqmux47CmdEntry 37525 }


	iqmux47EmbedNamesEmbeddedOP4 OBJECT-TYPE
		SYNTAX		RollCallString
		MAX-ACCESS		read-write
		STATUS			current
		DESCRIPTION
				"TYPE: - Editstring
				 PAGE: - Audio- Emb.Names
					Embed 4  cmdID= 37526  "
		::= { iqmux47CmdEntry 37526 }


	iqmux47EmbedNamesEmbeddedOP4R OBJECT-TYPE
		SYNTAX		RollCallString
		MAX-ACCESS		read-write
		STATUS			current
		DESCRIPTION
				"TYPE: - Editstring
				 PAGE: - Audio- Emb.Names
					Embed 4-R  cmdID= 37527  "
		::= { iqmux47CmdEntry 37527 }


	iqmux47EmbedNamesEmbeddedOP5 OBJECT-TYPE
		SYNTAX		RollCallString
		MAX-ACCESS		read-write
		STATUS			current
		DESCRIPTION
				"TYPE: - Editstring
				 PAGE: - Audio- Emb.Names
					Embed 5  cmdID= 37528  "
		::= { iqmux47CmdEntry 37528 }


	iqmux47EmbedNamesEmbeddedOP5R OBJECT-TYPE
		SYNTAX		RollCallString
		MAX-ACCESS		read-write
		STATUS			current
		DESCRIPTION
				"TYPE: - Editstring
				 PAGE: - Audio- Emb.Names
					Embed 5-R  cmdID= 37529  "
		::= { iqmux47CmdEntry 37529 }


	iqmux47EmbedNamesEmbeddedOP6 OBJECT-TYPE
		SYNTAX		RollCallString
		MAX-ACCESS		read-write
		STATUS			current
		DESCRIPTION
				"TYPE: - Editstring
				 PAGE: - Audio- Emb.Names
					Embed 6  cmdID= 37530  "
		::= { iqmux47CmdEntry 37530 }


	iqmux47EmbedNamesEmbeddedOP6R OBJECT-TYPE
		SYNTAX		RollCallString
		MAX-ACCESS		read-write
		STATUS			current
		DESCRIPTION
				"TYPE: - Editstring
				 PAGE: - Audio- Emb.Names
					Embed 6-R  cmdID= 37531  "
		::= { iqmux47CmdEntry 37531 }


	iqmux47EmbedNamesEmbeddedOP7 OBJECT-TYPE
		SYNTAX		RollCallString
		MAX-ACCESS		read-write
		STATUS			current
		DESCRIPTION
				"TYPE: - Editstring
				 PAGE: - Audio- Emb.Names
					Embed 7  cmdID= 37532  "
		::= { iqmux47CmdEntry 37532 }


	iqmux47EmbedNamesEmbeddedOP7R OBJECT-TYPE
		SYNTAX		RollCallString
		MAX-ACCESS		read-write
		STATUS			current
		DESCRIPTION
				"TYPE: - Editstring
				 PAGE: - Audio- Emb.Names
					Embed 7-R  cmdID= 37533  "
		::= { iqmux47CmdEntry 37533 }


	iqmux47EmbedNamesEmbeddedOP8 OBJECT-TYPE
		SYNTAX		RollCallString
		MAX-ACCESS		read-write
		STATUS			current
		DESCRIPTION
				"TYPE: - Editstring
				 PAGE: - Audio- Emb.Names
					Embed 8  cmdID= 37534  "
		::= { iqmux47CmdEntry 37534 }


	iqmux47EmbedNamesEmbeddedOP8R OBJECT-TYPE
		SYNTAX		RollCallString
		MAX-ACCESS		read-write
		STATUS			current
		DESCRIPTION
				"TYPE: - Editstring
				 PAGE: - Audio- Emb.Names
					Embed 8-R  cmdID= 37535  "
		::= { iqmux47CmdEntry 37535 }


	iqmux47EmbedNamesIPStereoDisemb1 OBJECT-TYPE
		SYNTAX		INTEGER { disable(0), enable(1) }
		MAX-ACCESS		read-write
		STATUS			current
		DESCRIPTION
				"TYPE: - Checkbox
				 PAGE: - Audio- Emb.Names
					Disemb 1  cmdID= 37400 "
		::= { iqmux47CmdEntry 37400 }


	iqmux47EmbedNamesIPStereoDisemb2 OBJECT-TYPE
		SYNTAX		INTEGER { disable(0), enable(1) }
		MAX-ACCESS		read-write
		STATUS			current
		DESCRIPTION
				"TYPE: - Checkbox
				 PAGE: - Audio- Emb.Names
					Disemb 2  cmdID= 37401 "
		::= { iqmux47CmdEntry 37401 }


	iqmux47EmbedNamesIPStereoDisemb3 OBJECT-TYPE
		SYNTAX		INTEGER { disable(0), enable(1) }
		MAX-ACCESS		read-write
		STATUS			current
		DESCRIPTION
				"TYPE: - Checkbox
				 PAGE: - Audio- Emb.Names
					Disemb 3  cmdID= 37402 "
		::= { iqmux47CmdEntry 37402 }


	iqmux47EmbedNamesIPStereoDisemb4 OBJECT-TYPE
		SYNTAX		INTEGER { disable(0), enable(1) }
		MAX-ACCESS		read-write
		STATUS			current
		DESCRIPTION
				"TYPE: - Checkbox
				 PAGE: - Audio- Emb.Names
					Disemb 4  cmdID= 37403 "
		::= { iqmux47CmdEntry 37403 }


	iqmux47EmbedNamesIPStereoDisemb5 OBJECT-TYPE
		SYNTAX		INTEGER { disable(0), enable(1) }
		MAX-ACCESS		read-write
		STATUS			current
		DESCRIPTION
				"TYPE: - Checkbox
				 PAGE: - Audio- Emb.Names
					Disemb 5  cmdID= 37404 "
		::= { iqmux47CmdEntry 37404 }


	iqmux47EmbedNamesIPStereoDisemb6 OBJECT-TYPE
		SYNTAX		INTEGER { disable(0), enable(1) }
		MAX-ACCESS		read-write
		STATUS			current
		DESCRIPTION
				"TYPE: - Checkbox
				 PAGE: - Audio- Emb.Names
					Disemb 6  cmdID= 37405 "
		::= { iqmux47CmdEntry 37405 }


	iqmux47EmbedNamesIPStereoDisemb7 OBJECT-TYPE
		SYNTAX		INTEGER { disable(0), enable(1) }
		MAX-ACCESS		read-write
		STATUS			current
		DESCRIPTION
				"TYPE: - Checkbox
				 PAGE: - Audio- Emb.Names
					Disemb 7  cmdID= 37406 "
		::= { iqmux47CmdEntry 37406 }


	iqmux47EmbedNamesIPStereoDisemb8 OBJECT-TYPE
		SYNTAX		INTEGER { disable(0), enable(1) }
		MAX-ACCESS		read-write
		STATUS			current
		DESCRIPTION
				"TYPE: - Checkbox
				 PAGE: - Audio- Emb.Names
					Disemb 8  cmdID= 37407 "
		::= { iqmux47CmdEntry 37407 }


	iqmux47EmbedNamesOPStereoEmbed1 OBJECT-TYPE
		SYNTAX		INTEGER { disable(0), enable(1) }
		MAX-ACCESS		read-write
		STATUS			current
		DESCRIPTION
				"TYPE: - Checkbox
				 PAGE: - Audio- Emb.Names
					Embed 1  cmdID= 37410 "
		::= { iqmux47CmdEntry 37410 }


	iqmux47EmbedNamesOPStereoEmbed2 OBJECT-TYPE
		SYNTAX		INTEGER { disable(0), enable(1) }
		MAX-ACCESS		read-write
		STATUS			current
		DESCRIPTION
				"TYPE: - Checkbox
				 PAGE: - Audio- Emb.Names
					Embed 2  cmdID= 37411 "
		::= { iqmux47CmdEntry 37411 }


	iqmux47EmbedNamesOPStereoEmbed3 OBJECT-TYPE
		SYNTAX		INTEGER { disable(0), enable(1) }
		MAX-ACCESS		read-write
		STATUS			current
		DESCRIPTION
				"TYPE: - Checkbox
				 PAGE: - Audio- Emb.Names
					Embed 3  cmdID= 37412 "
		::= { iqmux47CmdEntry 37412 }


	iqmux47EmbedNamesOPStereoEmbed4 OBJECT-TYPE
		SYNTAX		INTEGER { disable(0), enable(1) }
		MAX-ACCESS		read-write
		STATUS			current
		DESCRIPTION
				"TYPE: - Checkbox
				 PAGE: - Audio- Emb.Names
					Embed 4  cmdID= 37413 "
		::= { iqmux47CmdEntry 37413 }


	iqmux47EmbedNamesOPStereoEmbed5 OBJECT-TYPE
		SYNTAX		INTEGER { disable(0), enable(1) }
		MAX-ACCESS		read-write
		STATUS			current
		DESCRIPTION
				"TYPE: - Checkbox
				 PAGE: - Audio- Emb.Names
					Embed 5  cmdID= 37414 "
		::= { iqmux47CmdEntry 37414 }


	iqmux47EmbedNamesOPStereoEmbed6 OBJECT-TYPE
		SYNTAX		INTEGER { disable(0), enable(1) }
		MAX-ACCESS		read-write
		STATUS			current
		DESCRIPTION
				"TYPE: - Checkbox
				 PAGE: - Audio- Emb.Names
					Embed 6  cmdID= 37415 "
		::= { iqmux47CmdEntry 37415 }


	iqmux47EmbedNamesOPStereoEmbed7 OBJECT-TYPE
		SYNTAX		INTEGER { disable(0), enable(1) }
		MAX-ACCESS		read-write
		STATUS			current
		DESCRIPTION
				"TYPE: - Checkbox
				 PAGE: - Audio- Emb.Names
					Embed 7  cmdID= 37416 "
		::= { iqmux47CmdEntry 37416 }


	iqmux47EmbedNamesOPStereoEmbed8 OBJECT-TYPE
		SYNTAX		INTEGER { disable(0), enable(1) }
		MAX-ACCESS		read-write
		STATUS			current
		DESCRIPTION
				"TYPE: - Checkbox
				 PAGE: - Audio- Emb.Names
					Embed 8  cmdID= 37417 "
		::= { iqmux47CmdEntry 37417 }


	iqmux47AudioMixNamesMix1 OBJECT-TYPE
		SYNTAX		RollCallString
		MAX-ACCESS		read-write
		STATUS			current
		DESCRIPTION
				"TYPE: - Editstring
				 PAGE: - Audio
					Mix 1  cmdID= 37810  "
		::= { iqmux47CmdEntry 37810 }


	iqmux47AudioMixNamesMix2 OBJECT-TYPE
		SYNTAX		RollCallString
		MAX-ACCESS		read-write
		STATUS			current
		DESCRIPTION
				"TYPE: - Editstring
				 PAGE: - Audio
					Mix 2  cmdID= 37811  "
		::= { iqmux47CmdEntry 37811 }


	iqmux47AudioMixNamesMix3 OBJECT-TYPE
		SYNTAX		RollCallString
		MAX-ACCESS		read-write
		STATUS			current
		DESCRIPTION
				"TYPE: - Editstring
				 PAGE: - Audio
					Mix 3  cmdID= 37812  "
		::= { iqmux47CmdEntry 37812 }


	iqmux47AudioMixNamesMix4 OBJECT-TYPE
		SYNTAX		RollCallString
		MAX-ACCESS		read-write
		STATUS			current
		DESCRIPTION
				"TYPE: - Editstring
				 PAGE: - Audio
					Mix 4  cmdID= 37813  "
		::= { iqmux47CmdEntry 37813 }


	iqmux47Mix1RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 1  cmdID= 37600
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37600 }


	iqmux47Mix1RoutingInvert1 OBJECT-TYPE
		SYNTAX		INTEGER { disable(0), enable(1) }
		MAX-ACCESS		read-write
		STATUS			current
		DESCRIPTION
				"TYPE: - Checkbox
				 PAGE: - Audio- Mix 1
					Invert 1  cmdID= 37720 "
		::= { iqmux47CmdEntry 37720 }


	iqmux47Mix1RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 2  cmdID= 37601
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37601 }


	iqmux47Mix1RoutingInvert2 OBJECT-TYPE
		SYNTAX		INTEGER { disable(0), enable(1) }
		MAX-ACCESS		read-write
		STATUS			current
		DESCRIPTION
				"TYPE: - Checkbox
				 PAGE: - Audio- Mix 1
					Invert 2  cmdID= 37721 "
		::= { iqmux47CmdEntry 37721 }


	iqmux47Mix1RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 3  cmdID= 37602
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37602 }


	iqmux47Mix1RoutingInvert3 OBJECT-TYPE
		SYNTAX		INTEGER { disable(0), enable(1) }
		MAX-ACCESS		read-write
		STATUS			current
		DESCRIPTION
				"TYPE: - Checkbox
				 PAGE: - Audio- Mix 1
					Invert 3  cmdID= 37722 "
		::= { iqmux47CmdEntry 37722 }


	iqmux47Mix1RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 4  cmdID= 37603
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37603 }


	iqmux47Mix1RoutingInvert4 OBJECT-TYPE
		SYNTAX		INTEGER { disable(0), enable(1) }
		MAX-ACCESS		read-write
		STATUS			current
		DESCRIPTION
				"TYPE: - Checkbox
				 PAGE: - Audio- Mix 1
					Invert 4  cmdID= 37723 "
		::= { iqmux47CmdEntry 37723 }


	iqmux47Mix1GainGain1 OBJECT-TYPE
		SYNTAX		INTEGER
		MAX-ACCESS		read-write
		STATUS			current
		DESCRIPTION
				"TYPE: - Number
				 PAGE: - Audio- Mix 1
					Gain 1  cmdID= 37640  min= -360  max= 120  step= 1  format= %0.1f dB  div_scale= 10
					Min = -36.0 dB  Max = 12.0 dB  Step = 0.1 dB "
		::= { iqmux47CmdEntry 37640 }


	iqmux47Mix1GainMute1 OBJECT-TYPE
		SYNTAX		INTEGER { disable(0), enable(1) }
		MAX-ACCESS		read-write
		STATUS			current
		DESCRIPTION
				"TYPE: - Checkbox
				 PAGE: - Audio- Mix 1
					Mute 1  cmdID= 37680 "
		::= { iqmux47CmdEntry 37680 }


	iqmux47Mix1GainGain2 OBJECT-TYPE
		SYNTAX		INTEGER
		MAX-ACCESS		read-write
		STATUS			current
		DESCRIPTION
				"TYPE: - Number
				 PAGE: - Audio- Mix 1
					Gain 2  cmdID= 37641  min= -360  max= 120  step= 1  format= %0.1f dB  div_scale= 10
					Min = -36.0 dB  Max = 12.0 dB  Step = 0.1 dB "
		::= { iqmux47CmdEntry 37641 }


	iqmux47Mix1GainMute2 OBJECT-TYPE
		SYNTAX		INTEGER { disable(0), enable(1) }
		MAX-ACCESS		read-write
		STATUS			current
		DESCRIPTION
				"TYPE: - Checkbox
				 PAGE: - Audio- Mix 1
					Mute 2  cmdID= 37681 "
		::= { iqmux47CmdEntry 37681 }


	iqmux47Mix1GainGain3 OBJECT-TYPE
		SYNTAX		INTEGER
		MAX-ACCESS		read-write
		STATUS			current
		DESCRIPTION
				"TYPE: - Number
				 PAGE: - Audio- Mix 1
					Gain 3  cmdID= 37642  min= -360  max= 120  step= 1  format= %0.1f dB  div_scale= 10
					Min = -36.0 dB  Max = 12.0 dB  Step = 0.1 dB "
		::= { iqmux47CmdEntry 37642 }


	iqmux47Mix1GainMute3 OBJECT-TYPE
		SYNTAX		INTEGER { disable(0), enable(1) }
		MAX-ACCESS		read-write
		STATUS			current
		DESCRIPTION
				"TYPE: - Checkbox
				 PAGE: - Audio- Mix 1
					Mute 3  cmdID= 37682 "
		::= { iqmux47CmdEntry 37682 }


	iqmux47Mix1GainGain4 OBJECT-TYPE
		SYNTAX		INTEGER
		MAX-ACCESS		read-write
		STATUS			current
		DESCRIPTION
				"TYPE: - Number
				 PAGE: - Audio- Mix 1
					Gain 4  cmdID= 37643  min= -360  max= 120  step= 1  format= %0.1f dB  div_scale= 10
					Min = -36.0 dB  Max = 12.0 dB  Step = 0.1 dB "
		::= { iqmux47CmdEntry 37643 }


	iqmux47Mix1GainMute4 OBJECT-TYPE
		SYNTAX		INTEGER { disable(0), enable(1) }
		MAX-ACCESS		read-write
		STATUS			current
		DESCRIPTION
				"TYPE: - Checkbox
				 PAGE: - Audio- Mix 1
					Mute 4  cmdID= 37683 "
		::= { iqmux47CmdEntry 37683 }


	iqmux47Mix1GainInp1Clip OBJECT-TYPE
		SYNTAX		RollCallString
		MAX-ACCESS		read-only
		STATUS			current
		DESCRIPTION
				"TYPE: - Display
				 PAGE: - Audio- Mix 1
					Inp1 Clip  cmdID= 37760  format=   "
		::= { iqmux47CmdEntry 37760 }


	iqmux47Mix1GainInp2Clip OBJECT-TYPE
		SYNTAX		RollCallString
		MAX-ACCESS		read-only
		STATUS			current
		DESCRIPTION
				"TYPE: - Display
				 PAGE: - Audio- Mix 1
					Inp2 Clip  cmdID= 37761  format=   "
		::= { iqmux47CmdEntry 37761 }


	iqmux47Mix1GainInp3Clip OBJECT-TYPE
		SYNTAX		RollCallString
		MAX-ACCESS		read-only
		STATUS			current
		DESCRIPTION
				"TYPE: - Display
				 PAGE: - Audio- Mix 1
					Inp3 Clip  cmdID= 37762  format=   "
		::= { iqmux47CmdEntry 37762 }


	iqmux47Mix1GainInp4Clip OBJECT-TYPE
		SYNTAX		RollCallString
		MAX-ACCESS		read-only
		STATUS			current
		DESCRIPTION
				"TYPE: - Display
				 PAGE: - Audio- Mix 1
					Inp4 Clip  cmdID= 37763  format=   "
		::= { iqmux47CmdEntry 37763 }


	iqmux47Mix1GainOPClip OBJECT-TYPE
		SYNTAX		RollCallString
		MAX-ACCESS		read-only
		STATUS			current
		DESCRIPTION
				"TYPE: - Display
				 PAGE: - Audio- Mix 1
					O/P Clip  cmdID= 37800  format=   "
		::= { iqmux47CmdEntry 37800 }


	iqmux47Mix2RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 1  cmdID= 37604
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37604 }


	iqmux47Mix2RoutingInvert1 OBJECT-TYPE
		SYNTAX		INTEGER { disable(0), enable(1) }
		MAX-ACCESS		read-write
		STATUS			current
		DESCRIPTION
				"TYPE: - Checkbox
				 PAGE: - Audio- Mix 2
					Invert 1  cmdID= 37724 "
		::= { iqmux47CmdEntry 37724 }


	iqmux47Mix2RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 2  cmdID= 37605
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37605 }


	iqmux47Mix2RoutingInvert2 OBJECT-TYPE
		SYNTAX		INTEGER { disable(0), enable(1) }
		MAX-ACCESS		read-write
		STATUS			current
		DESCRIPTION
				"TYPE: - Checkbox
				 PAGE: - Audio- Mix 2
					Invert 2  cmdID= 37725 "
		::= { iqmux47CmdEntry 37725 }


	iqmux47Mix2RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 3  cmdID= 37606
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37606 }


	iqmux47Mix2RoutingInvert3 OBJECT-TYPE
		SYNTAX		INTEGER { disable(0), enable(1) }
		MAX-ACCESS		read-write
		STATUS			current
		DESCRIPTION
				"TYPE: - Checkbox
				 PAGE: - Audio- Mix 2
					Invert 3  cmdID= 37726 "
		::= { iqmux47CmdEntry 37726 }


	iqmux47Mix2RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 4  cmdID= 37607
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37607 }


	iqmux47Mix2RoutingInvert4 OBJECT-TYPE
		SYNTAX		INTEGER { disable(0), enable(1) }
		MAX-ACCESS		read-write
		STATUS			current
		DESCRIPTION
				"TYPE: - Checkbox
				 PAGE: - Audio- Mix 2
					Invert 4  cmdID= 37727 "
		::= { iqmux47CmdEntry 37727 }


	iqmux47Mix2GainGain1 OBJECT-TYPE
		SYNTAX		INTEGER
		MAX-ACCESS		read-write
		STATUS			current
		DESCRIPTION
				"TYPE: - Number
				 PAGE: - Audio- Mix 2
					Gain 1  cmdID= 37644  min= -360  max= 120  step= 1  format= %0.1f dB  div_scale= 10
					Min = -36.0 dB  Max = 12.0 dB  Step = 0.1 dB "
		::= { iqmux47CmdEntry 37644 }


	iqmux47Mix2GainMute1 OBJECT-TYPE
		SYNTAX		INTEGER { disable(0), enable(1) }
		MAX-ACCESS		read-write
		STATUS			current
		DESCRIPTION
				"TYPE: - Checkbox
				 PAGE: - Audio- Mix 2
					Mute 1  cmdID= 37684 "
		::= { iqmux47CmdEntry 37684 }


	iqmux47Mix2GainGain2 OBJECT-TYPE
		SYNTAX		INTEGER
		MAX-ACCESS		read-write
		STATUS			current
		DESCRIPTION
				"TYPE: - Number
				 PAGE: - Audio- Mix 2
					Gain 2  cmdID= 37645  min= -360  max= 120  step= 1  format= %0.1f dB  div_scale= 10
					Min = -36.0 dB  Max = 12.0 dB  Step = 0.1 dB "
		::= { iqmux47CmdEntry 37645 }


	iqmux47Mix2GainMute2 OBJECT-TYPE
		SYNTAX		INTEGER { disable(0), enable(1) }
		MAX-ACCESS		read-write
		STATUS			current
		DESCRIPTION
				"TYPE: - Checkbox
				 PAGE: - Audio- Mix 2
					Mute 2  cmdID= 37685 "
		::= { iqmux47CmdEntry 37685 }


	iqmux47Mix2GainGain3 OBJECT-TYPE
		SYNTAX		INTEGER
		MAX-ACCESS		read-write
		STATUS			current
		DESCRIPTION
				"TYPE: - Number
				 PAGE: - Audio- Mix 2
					Gain 3  cmdID= 37646  min= -360  max= 120  step= 1  format= %0.1f dB  div_scale= 10
					Min = -36.0 dB  Max = 12.0 dB  Step = 0.1 dB "
		::= { iqmux47CmdEntry 37646 }


	iqmux47Mix2GainMute3 OBJECT-TYPE
		SYNTAX		INTEGER { disable(0), enable(1) }
		MAX-ACCESS		read-write
		STATUS			current
		DESCRIPTION
				"TYPE: - Checkbox
				 PAGE: - Audio- Mix 2
					Mute 3  cmdID= 37686 "
		::= { iqmux47CmdEntry 37686 }


	iqmux47Mix2GainGain4 OBJECT-TYPE
		SYNTAX		INTEGER
		MAX-ACCESS		read-write
		STATUS			current
		DESCRIPTION
				"TYPE: - Number
				 PAGE: - Audio- Mix 2
					Gain 4  cmdID= 37647  min= -360  max= 120  step= 1  format= %0.1f dB  div_scale= 10
					Min = -36.0 dB  Max = 12.0 dB  Step = 0.1 dB "
		::= { iqmux47CmdEntry 37647 }


	iqmux47Mix2GainMute4 OBJECT-TYPE
		SYNTAX		INTEGER { disable(0), enable(1) }
		MAX-ACCESS		read-write
		STATUS			current
		DESCRIPTION
				"TYPE: - Checkbox
				 PAGE: - Audio- Mix 2
					Mute 4  cmdID= 37687 "
		::= { iqmux47CmdEntry 37687 }


	iqmux47Mix2GainInp1Clip OBJECT-TYPE
		SYNTAX		RollCallString
		MAX-ACCESS		read-only
		STATUS			current
		DESCRIPTION
				"TYPE: - Display
				 PAGE: - Audio- Mix 2
					Inp1 Clip  cmdID= 37764  format=   "
		::= { iqmux47CmdEntry 37764 }


	iqmux47Mix2GainInp2Clip OBJECT-TYPE
		SYNTAX		RollCallString
		MAX-ACCESS		read-only
		STATUS			current
		DESCRIPTION
				"TYPE: - Display
				 PAGE: - Audio- Mix 2
					Inp2 Clip  cmdID= 37765  format=   "
		::= { iqmux47CmdEntry 37765 }


	iqmux47Mix2GainInp3Clip OBJECT-TYPE
		SYNTAX		RollCallString
		MAX-ACCESS		read-only
		STATUS			current
		DESCRIPTION
				"TYPE: - Display
				 PAGE: - Audio- Mix 2
					Inp3 Clip  cmdID= 37766  format=   "
		::= { iqmux47CmdEntry 37766 }


	iqmux47Mix2GainInp4Clip OBJECT-TYPE
		SYNTAX		RollCallString
		MAX-ACCESS		read-only
		STATUS			current
		DESCRIPTION
				"TYPE: - Display
				 PAGE: - Audio- Mix 2
					Inp4 Clip  cmdID= 37767  format=   "
		::= { iqmux47CmdEntry 37767 }


	iqmux47Mix2GainOPClip OBJECT-TYPE
		SYNTAX		RollCallString
		MAX-ACCESS		read-only
		STATUS			current
		DESCRIPTION
				"TYPE: - Display
				 PAGE: - Audio- Mix 2
					O/P Clip  cmdID= 37801  format=   "
		::= { iqmux47CmdEntry 37801 }


	iqmux47Mix3RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 1  cmdID= 37608
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37608 }


	iqmux47Mix3RoutingInvert1 OBJECT-TYPE
		SYNTAX		INTEGER { disable(0), enable(1) }
		MAX-ACCESS		read-write
		STATUS			current
		DESCRIPTION
				"TYPE: - Checkbox
				 PAGE: - Audio- Mix 3
					Invert 1  cmdID= 37728 "
		::= { iqmux47CmdEntry 37728 }


	iqmux47Mix3RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 2  cmdID= 37609
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37609 }


	iqmux47Mix3RoutingInvert2 OBJECT-TYPE
		SYNTAX		INTEGER { disable(0), enable(1) }
		MAX-ACCESS		read-write
		STATUS			current
		DESCRIPTION
				"TYPE: - Checkbox
				 PAGE: - Audio- Mix 3
					Invert 2  cmdID= 37729 "
		::= { iqmux47CmdEntry 37729 }


	iqmux47Mix3RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 3  cmdID= 37610
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37610 }


	iqmux47Mix3RoutingInvert3 OBJECT-TYPE
		SYNTAX		INTEGER { disable(0), enable(1) }
		MAX-ACCESS		read-write
		STATUS			current
		DESCRIPTION
				"TYPE: - Checkbox
				 PAGE: - Audio- Mix 3
					Invert 3  cmdID= 37730 "
		::= { iqmux47CmdEntry 37730 }


	iqmux47Mix3RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 4  cmdID= 37611
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37611 }


	iqmux47Mix3RoutingInvert4 OBJECT-TYPE
		SYNTAX		INTEGER { disable(0), enable(1) }
		MAX-ACCESS		read-write
		STATUS			current
		DESCRIPTION
				"TYPE: - Checkbox
				 PAGE: - Audio- Mix 3
					Invert 4  cmdID= 37731 "
		::= { iqmux47CmdEntry 37731 }


	iqmux47Mix3GainGain1 OBJECT-TYPE
		SYNTAX		INTEGER
		MAX-ACCESS		read-write
		STATUS			current
		DESCRIPTION
				"TYPE: - Number
				 PAGE: - Audio- Mix 3
					Gain 1  cmdID= 37648  min= -360  max= 120  step= 1  format= %0.1f dB  div_scale= 10
					Min = -36.0 dB  Max = 12.0 dB  Step = 0.1 dB "
		::= { iqmux47CmdEntry 37648 }


	iqmux47Mix3GainMute1 OBJECT-TYPE
		SYNTAX		INTEGER { disable(0), enable(1) }
		MAX-ACCESS		read-write
		STATUS			current
		DESCRIPTION
				"TYPE: - Checkbox
				 PAGE: - Audio- Mix 3
					Mute 1  cmdID= 37688 "
		::= { iqmux47CmdEntry 37688 }


	iqmux47Mix3GainGain2 OBJECT-TYPE
		SYNTAX		INTEGER
		MAX-ACCESS		read-write
		STATUS			current
		DESCRIPTION
				"TYPE: - Number
				 PAGE: - Audio- Mix 3
					Gain 2  cmdID= 37649  min= -360  max= 120  step= 1  format= %0.1f dB  div_scale= 10
					Min = -36.0 dB  Max = 12.0 dB  Step = 0.1 dB "
		::= { iqmux47CmdEntry 37649 }


	iqmux47Mix3GainMute2 OBJECT-TYPE
		SYNTAX		INTEGER { disable(0), enable(1) }
		MAX-ACCESS		read-write
		STATUS			current
		DESCRIPTION
				"TYPE: - Checkbox
				 PAGE: - Audio- Mix 3
					Mute 2  cmdID= 37689 "
		::= { iqmux47CmdEntry 37689 }


	iqmux47Mix3GainGain3 OBJECT-TYPE
		SYNTAX		INTEGER
		MAX-ACCESS		read-write
		STATUS			current
		DESCRIPTION
				"TYPE: - Number
				 PAGE: - Audio- Mix 3
					Gain 3  cmdID= 37650  min= -360  max= 120  step= 1  format= %0.1f dB  div_scale= 10
					Min = -36.0 dB  Max = 12.0 dB  Step = 0.1 dB "
		::= { iqmux47CmdEntry 37650 }


	iqmux47Mix3GainMute3 OBJECT-TYPE
		SYNTAX		INTEGER { disable(0), enable(1) }
		MAX-ACCESS		read-write
		STATUS			current
		DESCRIPTION
				"TYPE: - Checkbox
				 PAGE: - Audio- Mix 3
					Mute 3  cmdID= 37690 "
		::= { iqmux47CmdEntry 37690 }


	iqmux47Mix3GainGain4 OBJECT-TYPE
		SYNTAX		INTEGER
		MAX-ACCESS		read-write
		STATUS			current
		DESCRIPTION
				"TYPE: - Number
				 PAGE: - Audio- Mix 3
					Gain 4  cmdID= 37651  min= -360  max= 120  step= 1  format= %0.1f dB  div_scale= 10
					Min = -36.0 dB  Max = 12.0 dB  Step = 0.1 dB "
		::= { iqmux47CmdEntry 37651 }


	iqmux47Mix3GainMute4 OBJECT-TYPE
		SYNTAX		INTEGER { disable(0), enable(1) }
		MAX-ACCESS		read-write
		STATUS			current
		DESCRIPTION
				"TYPE: - Checkbox
				 PAGE: - Audio- Mix 3
					Mute 4  cmdID= 37691 "
		::= { iqmux47CmdEntry 37691 }


	iqmux47Mix3GainInp1Clip OBJECT-TYPE
		SYNTAX		RollCallString
		MAX-ACCESS		read-only
		STATUS			current
		DESCRIPTION
				"TYPE: - Display
				 PAGE: - Audio- Mix 3
					Inp1 Clip  cmdID= 37768  format=   "
		::= { iqmux47CmdEntry 37768 }


	iqmux47Mix3GainInp2Clip OBJECT-TYPE
		SYNTAX		RollCallString
		MAX-ACCESS		read-only
		STATUS			current
		DESCRIPTION
				"TYPE: - Display
				 PAGE: - Audio- Mix 3
					Inp2 Clip  cmdID= 37769  format=   "
		::= { iqmux47CmdEntry 37769 }


	iqmux47Mix3GainInp3Clip OBJECT-TYPE
		SYNTAX		RollCallString
		MAX-ACCESS		read-only
		STATUS			current
		DESCRIPTION
				"TYPE: - Display
				 PAGE: - Audio- Mix 3
					Inp3 Clip  cmdID= 37770  format=   "
		::= { iqmux47CmdEntry 37770 }


	iqmux47Mix3GainInp4Clip OBJECT-TYPE
		SYNTAX		RollCallString
		MAX-ACCESS		read-only
		STATUS			current
		DESCRIPTION
				"TYPE: - Display
				 PAGE: - Audio- Mix 3
					Inp4 Clip  cmdID= 37771  format=   "
		::= { iqmux47CmdEntry 37771 }


	iqmux47Mix3GainOPClip OBJECT-TYPE
		SYNTAX		RollCallString
		MAX-ACCESS		read-only
		STATUS			current
		DESCRIPTION
				"TYPE: - Display
				 PAGE: - Audio- Mix 3
					O/P Clip  cmdID= 37802  format=   "
		::= { iqmux47CmdEntry 37802 }


	iqmux47Mix4RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 1  cmdID= 37612
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37612 }


	iqmux47Mix4RoutingInvert1 OBJECT-TYPE
		SYNTAX		INTEGER { disable(0), enable(1) }
		MAX-ACCESS		read-write
		STATUS			current
		DESCRIPTION
				"TYPE: - Checkbox
				 PAGE: - Audio- Mix 4
					Invert 1  cmdID= 37732 "
		::= { iqmux47CmdEntry 37732 }


	iqmux47Mix4RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 2  cmdID= 37613
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37613 }


	iqmux47Mix4RoutingInvert2 OBJECT-TYPE
		SYNTAX		INTEGER { disable(0), enable(1) }
		MAX-ACCESS		read-write
		STATUS			current
		DESCRIPTION
				"TYPE: - Checkbox
				 PAGE: - Audio- Mix 4
					Invert 2  cmdID= 37733 "
		::= { iqmux47CmdEntry 37733 }


	iqmux47Mix4RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 3  cmdID= 37614
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37614 }


	iqmux47Mix4RoutingInvert3 OBJECT-TYPE
		SYNTAX		INTEGER { disable(0), enable(1) }
		MAX-ACCESS		read-write
		STATUS			current
		DESCRIPTION
				"TYPE: - Checkbox
				 PAGE: - Audio- Mix 4
					Invert 3  cmdID= 37734 "
		::= { iqmux47CmdEntry 37734 }


	iqmux47Mix4RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 4  cmdID= 37615
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 37615 }


	iqmux47Mix4RoutingInvert4 OBJECT-TYPE
		SYNTAX		INTEGER { disable(0), enable(1) }
		MAX-ACCESS		read-write
		STATUS			current
		DESCRIPTION
				"TYPE: - Checkbox
				 PAGE: - Audio- Mix 4
					Invert 4  cmdID= 37735 "
		::= { iqmux47CmdEntry 37735 }


	iqmux47Mix4GainGain1 OBJECT-TYPE
		SYNTAX		INTEGER
		MAX-ACCESS		read-write
		STATUS			current
		DESCRIPTION
				"TYPE: - Number
				 PAGE: - Audio- Mix 4
					Gain 1  cmdID= 37652  min= -360  max= 120  step= 1  format= %0.1f dB  div_scale= 10
					Min = -36.0 dB  Max = 12.0 dB  Step = 0.1 dB "
		::= { iqmux47CmdEntry 37652 }


	iqmux47Mix4GainMute1 OBJECT-TYPE
		SYNTAX		INTEGER { disable(0), enable(1) }
		MAX-ACCESS		read-write
		STATUS			current
		DESCRIPTION
				"TYPE: - Checkbox
				 PAGE: - Audio- Mix 4
					Mute 1  cmdID= 37692 "
		::= { iqmux47CmdEntry 37692 }


	iqmux47Mix4GainGain2 OBJECT-TYPE
		SYNTAX		INTEGER
		MAX-ACCESS		read-write
		STATUS			current
		DESCRIPTION
				"TYPE: - Number
				 PAGE: - Audio- Mix 4
					Gain 2  cmdID= 37653  min= -360  max= 120  step= 1  format= %0.1f dB  div_scale= 10
					Min = -36.0 dB  Max = 12.0 dB  Step = 0.1 dB "
		::= { iqmux47CmdEntry 37653 }


	iqmux47Mix4GainMute2 OBJECT-TYPE
		SYNTAX		INTEGER { disable(0), enable(1) }
		MAX-ACCESS		read-write
		STATUS			current
		DESCRIPTION
				"TYPE: - Checkbox
				 PAGE: - Audio- Mix 4
					Mute 2  cmdID= 37693 "
		::= { iqmux47CmdEntry 37693 }


	iqmux47Mix4GainGain3 OBJECT-TYPE
		SYNTAX		INTEGER
		MAX-ACCESS		read-write
		STATUS			current
		DESCRIPTION
				"TYPE: - Number
				 PAGE: - Audio- Mix 4
					Gain 3  cmdID= 37654  min= -360  max= 120  step= 1  format= %0.1f dB  div_scale= 10
					Min = -36.0 dB  Max = 12.0 dB  Step = 0.1 dB "
		::= { iqmux47CmdEntry 37654 }


	iqmux47Mix4GainMute3 OBJECT-TYPE
		SYNTAX		INTEGER { disable(0), enable(1) }
		MAX-ACCESS		read-write
		STATUS			current
		DESCRIPTION
				"TYPE: - Checkbox
				 PAGE: - Audio- Mix 4
					Mute 3  cmdID= 37694 "
		::= { iqmux47CmdEntry 37694 }


	iqmux47Mix4GainGain4 OBJECT-TYPE
		SYNTAX		INTEGER
		MAX-ACCESS		read-write
		STATUS			current
		DESCRIPTION
				"TYPE: - Number
				 PAGE: - Audio- Mix 4
					Gain 4  cmdID= 37655  min= -360  max= 120  step= 1  format= %0.1f dB  div_scale= 10
					Min = -36.0 dB  Max = 12.0 dB  Step = 0.1 dB "
		::= { iqmux47CmdEntry 37655 }


	iqmux47Mix4GainMute4 OBJECT-TYPE
		SYNTAX		INTEGER { disable(0), enable(1) }
		MAX-ACCESS		read-write
		STATUS			current
		DESCRIPTION
				"TYPE: - Checkbox
				 PAGE: - Audio- Mix 4
					Mute 4  cmdID= 37695 "
		::= { iqmux47CmdEntry 37695 }


	iqmux47Mix4GainInp1Clip OBJECT-TYPE
		SYNTAX		RollCallString
		MAX-ACCESS		read-only
		STATUS			current
		DESCRIPTION
				"TYPE: - Display
				 PAGE: - Audio- Mix 4
					Inp1 Clip  cmdID= 37772  format=   "
		::= { iqmux47CmdEntry 37772 }


	iqmux47Mix4GainInp2Clip OBJECT-TYPE
		SYNTAX		RollCallString
		MAX-ACCESS		read-only
		STATUS			current
		DESCRIPTION
				"TYPE: - Display
				 PAGE: - Audio- Mix 4
					Inp2 Clip  cmdID= 37773  format=   "
		::= { iqmux47CmdEntry 37773 }


	iqmux47Mix4GainInp3Clip OBJECT-TYPE
		SYNTAX		RollCallString
		MAX-ACCESS		read-only
		STATUS			current
		DESCRIPTION
				"TYPE: - Display
				 PAGE: - Audio- Mix 4
					Inp3 Clip  cmdID= 37774  format=   "
		::= { iqmux47CmdEntry 37774 }


	iqmux47Mix4GainInp4Clip OBJECT-TYPE
		SYNTAX		RollCallString
		MAX-ACCESS		read-only
		STATUS			current
		DESCRIPTION
				"TYPE: - Display
				 PAGE: - Audio- Mix 4
					Inp4 Clip  cmdID= 37775  format=   "
		::= { iqmux47CmdEntry 37775 }


	iqmux47Mix4GainOPClip OBJECT-TYPE
		SYNTAX		RollCallString
		MAX-ACCESS		read-only
		STATUS			current
		DESCRIPTION
				"TYPE: - Display
				 PAGE: - Audio- Mix 4
					O/P Clip  cmdID= 37803  format=   "
		::= { iqmux47CmdEntry 37803 }


	iqmux47AESGainOut1AESOut1MuteL OBJECT-TYPE
		SYNTAX		INTEGER { disable(0), enable(1) }
		MAX-ACCESS		read-write
		STATUS			current
		DESCRIPTION
				"TYPE: - Checkbox
				 PAGE: - Audio- AES Ports- AES Gain
					AES Out 1 Mute L  cmdID= 38280 "
		::= { iqmux47CmdEntry 38280 }


	iqmux47AESGainOut1AESOut1MuteR OBJECT-TYPE
		SYNTAX		INTEGER { disable(0), enable(1) }
		MAX-ACCESS		read-write
		STATUS			current
		DESCRIPTION
				"TYPE: - Checkbox
				 PAGE: - Audio- AES Ports- AES Gain
					AES Out 1 Mute R  cmdID= 38281 "
		::= { iqmux47CmdEntry 38281 }


	iqmux47AESGainOut1AESOut1LGain OBJECT-TYPE
		SYNTAX		INTEGER
		MAX-ACCESS		read-write
		STATUS			current
		DESCRIPTION
				"TYPE: - Number
				 PAGE: - Audio- AES Ports- AES Gain
					AES Out 1 L Gain  cmdID= 38240  min= -661  max= 120  step= 1  format= %0.1f dB  div_scale= 10
					Min = -66.1 dB  Max = 12.0 dB  Step = 0.1 dB "
		::= { iqmux47CmdEntry 38240 }


	iqmux47AESGainOut1AESOut1RGain OBJECT-TYPE
		SYNTAX		INTEGER
		MAX-ACCESS		read-write
		STATUS			current
		DESCRIPTION
				"TYPE: - Number
				 PAGE: - Audio- AES Ports- AES Gain
					AES Out 1 R Gain  cmdID= 38241  min= -661  max= 120  step= 1  format= %0.1f dB  div_scale= 10
					Min = -66.1 dB  Max = 12.0 dB  Step = 0.1 dB "
		::= { iqmux47CmdEntry 38241 }


	iqmux47AESGainOut1Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38360 "
		::= { iqmux47CmdEntry 38360 }


	iqmux47AESGainOut1AESOut1InvertL OBJECT-TYPE
		SYNTAX		INTEGER { disable(0), enable(1) }
		MAX-ACCESS		read-write
		STATUS			current
		DESCRIPTION
				"TYPE: - Checkbox
				 PAGE: - Audio- AES Ports- AES Gain
					AES Out 1 Invert L  cmdID= 38320 "
		::= { iqmux47CmdEntry 38320 }


	iqmux47AESGainOut1AESOut1InvertR OBJECT-TYPE
		SYNTAX		INTEGER { disable(0), enable(1) }
		MAX-ACCESS		read-write
		STATUS			current
		DESCRIPTION
				"TYPE: - Checkbox
				 PAGE: - Audio- AES Ports- AES Gain
					AES Out 1 Invert R  cmdID= 38321 "
		::= { iqmux47CmdEntry 38321 }


	iqmux47AESGainOut1AESOut1LClip OBJECT-TYPE
		SYNTAX		RollCallString
		MAX-ACCESS		read-only
		STATUS			current
		DESCRIPTION
				"TYPE: - Display
				 PAGE: - Audio- AES Ports- AES Gain
					AES Out 1-L Clip  cmdID= 38520  format=   "
		::= { iqmux47CmdEntry 38520 }


	iqmux47AESGainOut1AESOut1RClip OBJECT-TYPE
		SYNTAX		RollCallString
		MAX-ACCESS		read-only
		STATUS			current
		DESCRIPTION
				"TYPE: - Display
				 PAGE: - Audio- AES Ports- AES Gain
					AES Out 1-R Clip  cmdID= 38521  format=   "
		::= { iqmux47CmdEntry 38521 }


	iqmux47AESGainOut2AESOut2MuteL OBJECT-TYPE
		SYNTAX		INTEGER { disable(0), enable(1) }
		MAX-ACCESS		read-write
		STATUS			current
		DESCRIPTION
				"TYPE: - Checkbox
				 PAGE: - Audio- AES Ports- AES Gain
					AES Out 2 Mute L  cmdID= 38282 "
		::= { iqmux47CmdEntry 38282 }


	iqmux47AESGainOut2AESOut2MuteR OBJECT-TYPE
		SYNTAX		INTEGER { disable(0), enable(1) }
		MAX-ACCESS		read-write
		STATUS			current
		DESCRIPTION
				"TYPE: - Checkbox
				 PAGE: - Audio- AES Ports- AES Gain
					AES Out 2 Mute R  cmdID= 38283 "
		::= { iqmux47CmdEntry 38283 }


	iqmux47AESGainOut2AESOut2LGain OBJECT-TYPE
		SYNTAX		INTEGER
		MAX-ACCESS		read-write
		STATUS			current
		DESCRIPTION
				"TYPE: - Number
				 PAGE: - Audio- AES Ports- AES Gain
					AES Out 2 L Gain  cmdID= 38242  min= -661  max= 120  step= 1  format= %0.1f dB  div_scale= 10
					Min = -66.1 dB  Max = 12.0 dB  Step = 0.1 dB "
		::= { iqmux47CmdEntry 38242 }


	iqmux47AESGainOut2AESOut2RGain OBJECT-TYPE
		SYNTAX		INTEGER
		MAX-ACCESS		read-write
		STATUS			current
		DESCRIPTION
				"TYPE: - Number
				 PAGE: - Audio- AES Ports- AES Gain
					AES Out 2 R Gain  cmdID= 38243  min= -661  max= 120  step= 1  format= %0.1f dB  div_scale= 10
					Min = -66.1 dB  Max = 12.0 dB  Step = 0.1 dB "
		::= { iqmux47CmdEntry 38243 }


	iqmux47AESGainOut2Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38361 "
		::= { iqmux47CmdEntry 38361 }


	iqmux47AESGainOut2AESOut2InvertL OBJECT-TYPE
		SYNTAX		INTEGER { disable(0), enable(1) }
		MAX-ACCESS		read-write
		STATUS			current
		DESCRIPTION
				"TYPE: - Checkbox
				 PAGE: - Audio- AES Ports- AES Gain
					AES Out 2 Invert L  cmdID= 38322 "
		::= { iqmux47CmdEntry 38322 }


	iqmux47AESGainOut2AESOut2InvertR OBJECT-TYPE
		SYNTAX		INTEGER { disable(0), enable(1) }
		MAX-ACCESS		read-write
		STATUS			current
		DESCRIPTION
				"TYPE: - Checkbox
				 PAGE: - Audio- AES Ports- AES Gain
					AES Out 2 Invert R  cmdID= 38323 "
		::= { iqmux47CmdEntry 38323 }


	iqmux47AESGainOut2AESOut2LClip OBJECT-TYPE
		SYNTAX		RollCallString
		MAX-ACCESS		read-only
		STATUS			current
		DESCRIPTION
				"TYPE: - Display
				 PAGE: - Audio- AES Ports- AES Gain
					AES Out 2-L Clip  cmdID= 38522  format=   "
		::= { iqmux47CmdEntry 38522 }


	iqmux47AESGainOut2AESOut2RClip OBJECT-TYPE
		SYNTAX		RollCallString
		MAX-ACCESS		read-only
		STATUS			current
		DESCRIPTION
				"TYPE: - Display
				 PAGE: - Audio- AES Ports- AES Gain
					AES Out 2-R Clip  cmdID= 38523  format=   "
		::= { iqmux47CmdEntry 38523 }


	iqmux47AESGainOut3AESOut3MuteL OBJECT-TYPE
		SYNTAX		INTEGER { disable(0), enable(1) }
		MAX-ACCESS		read-write
		STATUS			current
		DESCRIPTION
				"TYPE: - Checkbox
				 PAGE: - Audio- AES Ports- AES Gain
					AES Out 3 Mute L  cmdID= 38284 "
		::= { iqmux47CmdEntry 38284 }


	iqmux47AESGainOut3AESOut3MuteR OBJECT-TYPE
		SYNTAX		INTEGER { disable(0), enable(1) }
		MAX-ACCESS		read-write
		STATUS			current
		DESCRIPTION
				"TYPE: - Checkbox
				 PAGE: - Audio- AES Ports- AES Gain
					AES Out 3 Mute R  cmdID= 38285 "
		::= { iqmux47CmdEntry 38285 }


	iqmux47AESGainOut3AESOut3LGain OBJECT-TYPE
		SYNTAX		INTEGER
		MAX-ACCESS		read-write
		STATUS			current
		DESCRIPTION
				"TYPE: - Number
				 PAGE: - Audio- AES Ports- AES Gain
					AES Out 3 L Gain  cmdID= 38244  min= -661  max= 120  step= 1  format= %0.1f dB  div_scale= 10
					Min = -66.1 dB  Max = 12.0 dB  Step = 0.1 dB "
		::= { iqmux47CmdEntry 38244 }


	iqmux47AESGainOut3AESOut3RGain OBJECT-TYPE
		SYNTAX		INTEGER
		MAX-ACCESS		read-write
		STATUS			current
		DESCRIPTION
				"TYPE: - Number
				 PAGE: - Audio- AES Ports- AES Gain
					AES Out 3 R Gain  cmdID= 38245  min= -661  max= 120  step= 1  format= %0.1f dB  div_scale= 10
					Min = -66.1 dB  Max = 12.0 dB  Step = 0.1 dB "
		::= { iqmux47CmdEntry 38245 }


	iqmux47AESGainOut3Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38362 "
		::= { iqmux47CmdEntry 38362 }


	iqmux47AESGainOut3AESOut3InvertL OBJECT-TYPE
		SYNTAX		INTEGER { disable(0), enable(1) }
		MAX-ACCESS		read-write
		STATUS			current
		DESCRIPTION
				"TYPE: - Checkbox
				 PAGE: - Audio- AES Ports- AES Gain
					AES Out 3 Invert L  cmdID= 38324 "
		::= { iqmux47CmdEntry 38324 }


	iqmux47AESGainOut3AESOut3InvertR OBJECT-TYPE
		SYNTAX		INTEGER { disable(0), enable(1) }
		MAX-ACCESS		read-write
		STATUS			current
		DESCRIPTION
				"TYPE: - Checkbox
				 PAGE: - Audio- AES Ports- AES Gain
					AES Out 3 Invert R  cmdID= 38325 "
		::= { iqmux47CmdEntry 38325 }


	iqmux47AESGainOut3AESOut3LClip OBJECT-TYPE
		SYNTAX		RollCallString
		MAX-ACCESS		read-only
		STATUS			current
		DESCRIPTION
				"TYPE: - Display
				 PAGE: - Audio- AES Ports- AES Gain
					AES Out 3-L Clip  cmdID= 38524  format=   "
		::= { iqmux47CmdEntry 38524 }


	iqmux47AESGainOut3AESOut3RClip OBJECT-TYPE
		SYNTAX		RollCallString
		MAX-ACCESS		read-only
		STATUS			current
		DESCRIPTION
				"TYPE: - Display
				 PAGE: - Audio- AES Ports- AES Gain
					AES Out 3-R Clip  cmdID= 38525  format=   "
		::= { iqmux47CmdEntry 38525 }


	iqmux47AESGainOut4AESOut4MuteL OBJECT-TYPE
		SYNTAX		INTEGER { disable(0), enable(1) }
		MAX-ACCESS		read-write
		STATUS			current
		DESCRIPTION
				"TYPE: - Checkbox
				 PAGE: - Audio- AES Ports- AES Gain
					AES Out 4 Mute L  cmdID= 38286 "
		::= { iqmux47CmdEntry 38286 }


	iqmux47AESGainOut4AESOut4MuteR OBJECT-TYPE
		SYNTAX		INTEGER { disable(0), enable(1) }
		MAX-ACCESS		read-write
		STATUS			current
		DESCRIPTION
				"TYPE: - Checkbox
				 PAGE: - Audio- AES Ports- AES Gain
					AES Out 4 Mute R  cmdID= 38287 "
		::= { iqmux47CmdEntry 38287 }


	iqmux47AESGainOut4AESOut4LGain OBJECT-TYPE
		SYNTAX		INTEGER
		MAX-ACCESS		read-write
		STATUS			current
		DESCRIPTION
				"TYPE: - Number
				 PAGE: - Audio- AES Ports- AES Gain
					AES Out 4 L Gain  cmdID= 38246  min= -661  max= 120  step= 1  format= %0.1f dB  div_scale= 10
					Min = -66.1 dB  Max = 12.0 dB  Step = 0.1 dB "
		::= { iqmux47CmdEntry 38246 }


	iqmux47AESGainOut4AESOut4RGain OBJECT-TYPE
		SYNTAX		INTEGER
		MAX-ACCESS		read-write
		STATUS			current
		DESCRIPTION
				"TYPE: - Number
				 PAGE: - Audio- AES Ports- AES Gain
					AES Out 4 R Gain  cmdID= 38247  min= -661  max= 120  step= 1  format= %0.1f dB  div_scale= 10
					Min = -66.1 dB  Max = 12.0 dB  Step = 0.1 dB "
		::= { iqmux47CmdEntry 38247 }


	iqmux47AESGainOut4Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38363 "
		::= { iqmux47CmdEntry 38363 }


	iqmux47AESGainOut4AESOut4InvertL OBJECT-TYPE
		SYNTAX		INTEGER { disable(0), enable(1) }
		MAX-ACCESS		read-write
		STATUS			current
		DESCRIPTION
				"TYPE: - Checkbox
				 PAGE: - Audio- AES Ports- AES Gain
					AES Out 4 Invert L  cmdID= 38326 "
		::= { iqmux47CmdEntry 38326 }


	iqmux47AESGainOut4AESOut4InvertR OBJECT-TYPE
		SYNTAX		INTEGER { disable(0), enable(1) }
		MAX-ACCESS		read-write
		STATUS			current
		DESCRIPTION
				"TYPE: - Checkbox
				 PAGE: - Audio- AES Ports- AES Gain
					AES Out 4 Invert R  cmdID= 38327 "
		::= { iqmux47CmdEntry 38327 }


	iqmux47AESGainOut4AESOut4LClip OBJECT-TYPE
		SYNTAX		RollCallString
		MAX-ACCESS		read-only
		STATUS			current
		DESCRIPTION
				"TYPE: - Display
				 PAGE: - Audio- AES Ports- AES Gain
					AES Out 4-L Clip  cmdID= 38526  format=   "
		::= { iqmux47CmdEntry 38526 }


	iqmux47AESGainOut4AESOut4RClip OBJECT-TYPE
		SYNTAX		RollCallString
		MAX-ACCESS		read-only
		STATUS			current
		DESCRIPTION
				"TYPE: - Display
				 PAGE: - Audio- AES Ports- AES Gain
					AES Out 4-R Clip  cmdID= 38527  format=   "
		::= { iqmux47CmdEntry 38527 }


	iqmux47AESGainOut5AESOut5MuteL OBJECT-TYPE
		SYNTAX		INTEGER { disable(0), enable(1) }
		MAX-ACCESS		read-write
		STATUS			current
		DESCRIPTION
				"TYPE: - Checkbox
				 PAGE: - Audio- AES Ports- AES Gain
					AES Out 5 Mute L  cmdID= 38288 "
		::= { iqmux47CmdEntry 38288 }


	iqmux47AESGainOut5AESOut5MuteR OBJECT-TYPE
		SYNTAX		INTEGER { disable(0), enable(1) }
		MAX-ACCESS		read-write
		STATUS			current
		DESCRIPTION
				"TYPE: - Checkbox
				 PAGE: - Audio- AES Ports- AES Gain
					AES Out 5 Mute R  cmdID= 38289 "
		::= { iqmux47CmdEntry 38289 }


	iqmux47AESGainOut5AESOut5LGain OBJECT-TYPE
		SYNTAX		INTEGER
		MAX-ACCESS		read-write
		STATUS			current
		DESCRIPTION
				"TYPE: - Number
				 PAGE: - Audio- AES Ports- AES Gain
					AES Out 5 L Gain  cmdID= 38248  min= -661  max= 120  step= 1  format= %0.1f dB  div_scale= 10
					Min = -66.1 dB  Max = 12.0 dB  Step = 0.1 dB "
		::= { iqmux47CmdEntry 38248 }


	iqmux47AESGainOut5AESOut5RGain OBJECT-TYPE
		SYNTAX		INTEGER
		MAX-ACCESS		read-write
		STATUS			current
		DESCRIPTION
				"TYPE: - Number
				 PAGE: - Audio- AES Ports- AES Gain
					AES Out 5 R Gain  cmdID= 38249  min= -661  max= 120  step= 1  format= %0.1f dB  div_scale= 10
					Min = -66.1 dB  Max = 12.0 dB  Step = 0.1 dB "
		::= { iqmux47CmdEntry 38249 }


	iqmux47AESGainOut5Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38364 "
		::= { iqmux47CmdEntry 38364 }


	iqmux47AESGainOut5AESOut5InvertL OBJECT-TYPE
		SYNTAX		INTEGER { disable(0), enable(1) }
		MAX-ACCESS		read-write
		STATUS			current
		DESCRIPTION
				"TYPE: - Checkbox
				 PAGE: - Audio- AES Ports- AES Gain
					AES Out 5 Invert L  cmdID= 38328 "
		::= { iqmux47CmdEntry 38328 }


	iqmux47AESGainOut5AESOut5InvertR OBJECT-TYPE
		SYNTAX		INTEGER { disable(0), enable(1) }
		MAX-ACCESS		read-write
		STATUS			current
		DESCRIPTION
				"TYPE: - Checkbox
				 PAGE: - Audio- AES Ports- AES Gain
					AES Out 5 Invert R  cmdID= 38329 "
		::= { iqmux47CmdEntry 38329 }


	iqmux47AESGainOut5AESOut5LClip OBJECT-TYPE
		SYNTAX		RollCallString
		MAX-ACCESS		read-only
		STATUS			current
		DESCRIPTION
				"TYPE: - Display
				 PAGE: - Audio- AES Ports- AES Gain
					AES Out 5-L Clip  cmdID= 38528  format=   "
		::= { iqmux47CmdEntry 38528 }


	iqmux47AESGainOut5AESOut5RClip OBJECT-TYPE
		SYNTAX		RollCallString
		MAX-ACCESS		read-only
		STATUS			current
		DESCRIPTION
				"TYPE: - Display
				 PAGE: - Audio- AES Ports- AES Gain
					AES Out 5-R Clip  cmdID= 38529  format=   "
		::= { iqmux47CmdEntry 38529 }


	iqmux47AESGainOut6AESOut6MuteL OBJECT-TYPE
		SYNTAX		INTEGER { disable(0), enable(1) }
		MAX-ACCESS		read-write
		STATUS			current
		DESCRIPTION
				"TYPE: - Checkbox
				 PAGE: - Audio- AES Ports- AES Gain
					AES Out 6 Mute L  cmdID= 38290 "
		::= { iqmux47CmdEntry 38290 }


	iqmux47AESGainOut6AESOut6MuteR OBJECT-TYPE
		SYNTAX		INTEGER { disable(0), enable(1) }
		MAX-ACCESS		read-write
		STATUS			current
		DESCRIPTION
				"TYPE: - Checkbox
				 PAGE: - Audio- AES Ports- AES Gain
					AES Out 6 Mute R  cmdID= 38291 "
		::= { iqmux47CmdEntry 38291 }


	iqmux47AESGainOut6AESOut6LGain OBJECT-TYPE
		SYNTAX		INTEGER
		MAX-ACCESS		read-write
		STATUS			current
		DESCRIPTION
				"TYPE: - Number
				 PAGE: - Audio- AES Ports- AES Gain
					AES Out 6 L Gain  cmdID= 38250  min= -661  max= 120  step= 1  format= %0.1f dB  div_scale= 10
					Min = -66.1 dB  Max = 12.0 dB  Step = 0.1 dB "
		::= { iqmux47CmdEntry 38250 }


	iqmux47AESGainOut6AESOut6RGain OBJECT-TYPE
		SYNTAX		INTEGER
		MAX-ACCESS		read-write
		STATUS			current
		DESCRIPTION
				"TYPE: - Number
				 PAGE: - Audio- AES Ports- AES Gain
					AES Out 6 R Gain  cmdID= 38251  min= -661  max= 120  step= 1  format= %0.1f dB  div_scale= 10
					Min = -66.1 dB  Max = 12.0 dB  Step = 0.1 dB "
		::= { iqmux47CmdEntry 38251 }


	iqmux47AESGainOut6Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38365 "
		::= { iqmux47CmdEntry 38365 }


	iqmux47AESGainOut6AESOut6InvertL OBJECT-TYPE
		SYNTAX		INTEGER { disable(0), enable(1) }
		MAX-ACCESS		read-write
		STATUS			current
		DESCRIPTION
				"TYPE: - Checkbox
				 PAGE: - Audio- AES Ports- AES Gain
					AES Out 6 Invert L  cmdID= 38330 "
		::= { iqmux47CmdEntry 38330 }


	iqmux47AESGainOut6AESOut6InvertR OBJECT-TYPE
		SYNTAX		INTEGER { disable(0), enable(1) }
		MAX-ACCESS		read-write
		STATUS			current
		DESCRIPTION
				"TYPE: - Checkbox
				 PAGE: - Audio- AES Ports- AES Gain
					AES Out 6 Invert R  cmdID= 38331 "
		::= { iqmux47CmdEntry 38331 }


	iqmux47AESGainOut6AESOut6LClip OBJECT-TYPE
		SYNTAX		RollCallString
		MAX-ACCESS		read-only
		STATUS			current
		DESCRIPTION
				"TYPE: - Display
				 PAGE: - Audio- AES Ports- AES Gain
					AES Out 6-L Clip  cmdID= 38530  format=   "
		::= { iqmux47CmdEntry 38530 }


	iqmux47AESGainOut6AESOut6RClip OBJECT-TYPE
		SYNTAX		RollCallString
		MAX-ACCESS		read-only
		STATUS			current
		DESCRIPTION
				"TYPE: - Display
				 PAGE: - Audio- AES Ports- AES Gain
					AES Out 6-R Clip  cmdID= 38531  format=   "
		::= { iqmux47CmdEntry 38531 }


	iqmux47AESGainOut7AESOut7MuteL OBJECT-TYPE
		SYNTAX		INTEGER { disable(0), enable(1) }
		MAX-ACCESS		read-write
		STATUS			current
		DESCRIPTION
				"TYPE: - Checkbox
				 PAGE: - Audio- AES Ports- AES Gain
					AES Out 7 Mute L  cmdID= 38292 "
		::= { iqmux47CmdEntry 38292 }


	iqmux47AESGainOut7AESOut7MuteR OBJECT-TYPE
		SYNTAX		INTEGER { disable(0), enable(1) }
		MAX-ACCESS		read-write
		STATUS			current
		DESCRIPTION
				"TYPE: - Checkbox
				 PAGE: - Audio- AES Ports- AES Gain
					AES Out 7 Mute R  cmdID= 38293 "
		::= { iqmux47CmdEntry 38293 }


	iqmux47AESGainOut7AESOut7LGain OBJECT-TYPE
		SYNTAX		INTEGER
		MAX-ACCESS		read-write
		STATUS			current
		DESCRIPTION
				"TYPE: - Number
				 PAGE: - Audio- AES Ports- AES Gain
					AES Out 7 L Gain  cmdID= 38252  min= -661  max= 120  step= 1  format= %0.1f dB  div_scale= 10
					Min = -66.1 dB  Max = 12.0 dB  Step = 0.1 dB "
		::= { iqmux47CmdEntry 38252 }


	iqmux47AESGainOut7AESOut7RGain OBJECT-TYPE
		SYNTAX		INTEGER
		MAX-ACCESS		read-write
		STATUS			current
		DESCRIPTION
				"TYPE: - Number
				 PAGE: - Audio- AES Ports- AES Gain
					AES Out 7 R Gain  cmdID= 38253  min= -661  max= 120  step= 1  format= %0.1f dB  div_scale= 10
					Min = -66.1 dB  Max = 12.0 dB  Step = 0.1 dB "
		::= { iqmux47CmdEntry 38253 }


	iqmux47AESGainOut7Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38366 "
		::= { iqmux47CmdEntry 38366 }


	iqmux47AESGainOut7AESOut7InvertL OBJECT-TYPE
		SYNTAX		INTEGER { disable(0), enable(1) }
		MAX-ACCESS		read-write
		STATUS			current
		DESCRIPTION
				"TYPE: - Checkbox
				 PAGE: - Audio- AES Ports- AES Gain
					AES Out 7 Invert L  cmdID= 38332 "
		::= { iqmux47CmdEntry 38332 }


	iqmux47AESGainOut7AESOut7InvertR OBJECT-TYPE
		SYNTAX		INTEGER { disable(0), enable(1) }
		MAX-ACCESS		read-write
		STATUS			current
		DESCRIPTION
				"TYPE: - Checkbox
				 PAGE: - Audio- AES Ports- AES Gain
					AES Out 7 Invert R  cmdID= 38333 "
		::= { iqmux47CmdEntry 38333 }


	iqmux47AESGainOut7AESOut7LClip OBJECT-TYPE
		SYNTAX		RollCallString
		MAX-ACCESS		read-only
		STATUS			current
		DESCRIPTION
				"TYPE: - Display
				 PAGE: - Audio- AES Ports- AES Gain
					AES Out 7-L Clip  cmdID= 38532  format=   "
		::= { iqmux47CmdEntry 38532 }


	iqmux47AESGainOut7AESOut7RClip OBJECT-TYPE
		SYNTAX		RollCallString
		MAX-ACCESS		read-only
		STATUS			current
		DESCRIPTION
				"TYPE: - Display
				 PAGE: - Audio- AES Ports- AES Gain
					AES Out 7-R Clip  cmdID= 38533  format=   "
		::= { iqmux47CmdEntry 38533 }


	iqmux47AESGainOut8AESOut8MuteL OBJECT-TYPE
		SYNTAX		INTEGER { disable(0), enable(1) }
		MAX-ACCESS		read-write
		STATUS			current
		DESCRIPTION
				"TYPE: - Checkbox
				 PAGE: - Audio- AES Ports- AES Gain
					AES Out 8 Mute L  cmdID= 38294 "
		::= { iqmux47CmdEntry 38294 }


	iqmux47AESGainOut8AESOut8MuteR OBJECT-TYPE
		SYNTAX		INTEGER { disable(0), enable(1) }
		MAX-ACCESS		read-write
		STATUS			current
		DESCRIPTION
				"TYPE: - Checkbox
				 PAGE: - Audio- AES Ports- AES Gain
					AES Out 8 Mute R  cmdID= 38295 "
		::= { iqmux47CmdEntry 38295 }


	iqmux47AESGainOut8AESOut8LGain OBJECT-TYPE
		SYNTAX		INTEGER
		MAX-ACCESS		read-write
		STATUS			current
		DESCRIPTION
				"TYPE: - Number
				 PAGE: - Audio- AES Ports- AES Gain
					AES Out 8 L Gain  cmdID= 38254  min= -661  max= 120  step= 1  format= %0.1f dB  div_scale= 10
					Min = -66.1 dB  Max = 12.0 dB  Step = 0.1 dB "
		::= { iqmux47CmdEntry 38254 }


	iqmux47AESGainOut8AESOut8RGain OBJECT-TYPE
		SYNTAX		INTEGER
		MAX-ACCESS		read-write
		STATUS			current
		DESCRIPTION
				"TYPE: - Number
				 PAGE: - Audio- AES Ports- AES Gain
					AES Out 8 R Gain  cmdID= 38255  min= -661  max= 120  step= 1  format= %0.1f dB  div_scale= 10
					Min = -66.1 dB  Max = 12.0 dB  Step = 0.1 dB "
		::= { iqmux47CmdEntry 38255 }


	iqmux47AESGainOut8Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38367 "
		::= { iqmux47CmdEntry 38367 }


	iqmux47AESGainOut8AESOut8InvertL OBJECT-TYPE
		SYNTAX		INTEGER { disable(0), enable(1) }
		MAX-ACCESS		read-write
		STATUS			current
		DESCRIPTION
				"TYPE: - Checkbox
				 PAGE: - Audio- AES Ports- AES Gain
					AES Out 8 Invert L  cmdID= 38334 "
		::= { iqmux47CmdEntry 38334 }


	iqmux47AESGainOut8AESOut8InvertR OBJECT-TYPE
		SYNTAX		INTEGER { disable(0), enable(1) }
		MAX-ACCESS		read-write
		STATUS			current
		DESCRIPTION
				"TYPE: - Checkbox
				 PAGE: - Audio- AES Ports- AES Gain
					AES Out 8 Invert R  cmdID= 38335 "
		::= { iqmux47CmdEntry 38335 }


	iqmux47AESGainOut8AESOut8LClip OBJECT-TYPE
		SYNTAX		RollCallString
		MAX-ACCESS		read-only
		STATUS			current
		DESCRIPTION
				"TYPE: - Display
				 PAGE: - Audio- AES Ports- AES Gain
					AES Out 8-L Clip  cmdID= 38534  format=   "
		::= { iqmux47CmdEntry 38534 }


	iqmux47AESGainOut8AESOut8RClip OBJECT-TYPE
		SYNTAX		RollCallString
		MAX-ACCESS		read-only
		STATUS			current
		DESCRIPTION
				"TYPE: - Display
				 PAGE: - Audio- AES Ports- AES Gain
					AES Out 8-R Clip  cmdID= 38535  format=   "
		::= { iqmux47CmdEntry 38535 }


	iqmux47AESOut1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 1
					Left  cmdID= 38200
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38200 }


	iqmux47AESOut1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 1
					Right  cmdID= 38201
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38201 }


	iqmux47AESOut1LinkLRSelection OBJECT-TYPE
		SYNTAX		INTEGER { disable(0), enable(1) }
		MAX-ACCESS		read-write
		STATUS			current
		DESCRIPTION
				"TYPE: - Checkbox
				 PAGE: - Audio- AES Ports- AES Out 1
					Link L+R Selection  cmdID= 38380 "
		::= { iqmux47CmdEntry 38380 }


	iqmux47AESOut2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 2
					Left  cmdID= 38202
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38202 }


	iqmux47AESOut2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 2
					Right  cmdID= 38203
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38203 }


	iqmux47AESOut2LinkLRSelection OBJECT-TYPE
		SYNTAX		INTEGER { disable(0), enable(1) }
		MAX-ACCESS		read-write
		STATUS			current
		DESCRIPTION
				"TYPE: - Checkbox
				 PAGE: - Audio- AES Ports- AES Out 2
					Link L+R Selection  cmdID= 38381 "
		::= { iqmux47CmdEntry 38381 }


	iqmux47AESOut3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 3
					Left  cmdID= 38204
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38204 }


	iqmux47AESOut3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 3
					Right  cmdID= 38205
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38205 }


	iqmux47AESOut3LinkLRSelection OBJECT-TYPE
		SYNTAX		INTEGER { disable(0), enable(1) }
		MAX-ACCESS		read-write
		STATUS			current
		DESCRIPTION
				"TYPE: - Checkbox
				 PAGE: - Audio- AES Ports- AES Out 3
					Link L+R Selection  cmdID= 38382 "
		::= { iqmux47CmdEntry 38382 }


	iqmux47AESOut4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 4
					Left  cmdID= 38206
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38206 }


	iqmux47AESOut4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 4
					Right  cmdID= 38207
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38207 }


	iqmux47AESOut4LinkLRSelection OBJECT-TYPE
		SYNTAX		INTEGER { disable(0), enable(1) }
		MAX-ACCESS		read-write
		STATUS			current
		DESCRIPTION
				"TYPE: - Checkbox
				 PAGE: - Audio- AES Ports- AES Out 4
					Link L+R Selection  cmdID= 38383 "
		::= { iqmux47CmdEntry 38383 }


	iqmux47AESOut5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 5
					Left  cmdID= 38208
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38208 }


	iqmux47AESOut5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 5
					Right  cmdID= 38209
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38209 }


	iqmux47AESOut5LinkLRSelection OBJECT-TYPE
		SYNTAX		INTEGER { disable(0), enable(1) }
		MAX-ACCESS		read-write
		STATUS			current
		DESCRIPTION
				"TYPE: - Checkbox
				 PAGE: - Audio- AES Ports- AES Out 5
					Link L+R Selection  cmdID= 38384 "
		::= { iqmux47CmdEntry 38384 }


	iqmux47AESOut6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 6
					Left  cmdID= 38210
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38210 }


	iqmux47AESOut6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 6
					Right  cmdID= 38211
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38211 }


	iqmux47AESOut6LinkLRSelection OBJECT-TYPE
		SYNTAX		INTEGER { disable(0), enable(1) }
		MAX-ACCESS		read-write
		STATUS			current
		DESCRIPTION
				"TYPE: - Checkbox
				 PAGE: - Audio- AES Ports- AES Out 6
					Link L+R Selection  cmdID= 38385 "
		::= { iqmux47CmdEntry 38385 }


	iqmux47AESOut7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 7
					Left  cmdID= 38212
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38212 }


	iqmux47AESOut7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 7
					Right  cmdID= 38213
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38213 }


	iqmux47AESOut7LinkLRSelection OBJECT-TYPE
		SYNTAX		INTEGER { disable(0), enable(1) }
		MAX-ACCESS		read-write
		STATUS			current
		DESCRIPTION
				"TYPE: - Checkbox
				 PAGE: - Audio- AES Ports- AES Out 7
					Link L+R Selection  cmdID= 38386 "
		::= { iqmux47CmdEntry 38386 }


	iqmux47AESOut8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 8
					Left  cmdID= 38214
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38214 }


	iqmux47AESOut8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 8
					Right  cmdID= 38215
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38215 }


	iqmux47AESOut8LinkLRSelection OBJECT-TYPE
		SYNTAX		INTEGER { disable(0), enable(1) }
		MAX-ACCESS		read-write
		STATUS			current
		DESCRIPTION
				"TYPE: - Checkbox
				 PAGE: - Audio- AES Ports- AES Out 8
					Link L+R Selection  cmdID= 38387 "
		::= { iqmux47CmdEntry 38387 }


	iqmux47AESOutMonitoropLeft OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- Monitor o/p
					Left  cmdID= 38641
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38641 }


	iqmux47AESOutMonitoropRight OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- Monitor o/p
					Right  cmdID= 38642
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux47CmdEntry 38642 }


	iqmux47AESOutMonitoropLinkLRSelection OBJECT-TYPE
		SYNTAX		INTEGER { disable(0), enable(1) }
		MAX-ACCESS		read-write
		STATUS			current
		DESCRIPTION
				"TYPE: - Checkbox
				 PAGE: - Audio- AES Ports- Monitor o/p
					Link L+R Selection  cmdID= 38640 "
		::= { iqmux47CmdEntry 38640 }


	iqmux47AESOutPortNamesAESPort1Stereo OBJECT-TYPE
		SYNTAX		INTEGER { disable(0), enable(1) }
		MAX-ACCESS		read-write
		STATUS			current
		DESCRIPTION
				"TYPE: - Checkbox
				 PAGE: - Audio- AES Ports- AES Port Names
					AES Port 1 Stereo  cmdID= 38448 "
		::= { iqmux47CmdEntry 38448 }


	iqmux47AESOutPortNamesAESPort1L OBJECT-TYPE
		SYNTAX		RollCallString
		MAX-ACCESS		read-write
		STATUS			current
		DESCRIPTION
				"TYPE: - Editstring
				 PAGE: - Audio- AES Ports- AES Port Names
					AES Port 1-L  cmdID= 38496  "
		::= { iqmux47CmdEntry 38496 }


	iqmux47AESOutPortNamesAESPort1R OBJECT-TYPE
		SYNTAX		RollCallString
		MAX-ACCESS		read-write
		STATUS			current
		DESCRIPTION
				"TYPE: - Editstring
				 PAGE: - Audio- AES Ports- AES Port Names
					AES Port 1-R  cmdID= 38497  "
		::= { iqmux47CmdEntry 38497 }


	iqmux47AESOutPortNamesAESPort2Stereo OBJECT-TYPE
		SYNTAX		INTEGER { disable(0), enable(1) }
		MAX-ACCESS		read-write
		STATUS			current
		DESCRIPTION
				"TYPE: - Checkbox
				 PAGE: - Audio- AES Ports- AES Port Names
					AES Port 2 Stereo  cmdID= 38449 "
		::= { iqmux47CmdEntry 38449 }


	iqmux47AESOutPortNamesAESPort2L OBJECT-TYPE
		SYNTAX		RollCallString
		MAX-ACCESS		read-write
		STATUS			current
		DESCRIPTION
				"TYPE: - Editstring
				 PAGE: - Audio- AES Ports- AES Port Names
					AES Port 2-L  cmdID= 38498  "
		::= { iqmux47CmdEntry 38498 }


	iqmux47AESOutPortNamesAESPort2R OBJECT-TYPE
		SYNTAX		RollCallString
		MAX-ACCESS		read-write
		STATUS			current
		DESCRIPTION
				"TYPE: - Editstring
				 PAGE: - Audio- AES Ports- AES Port Names
					AES Port 2-R  cmdID= 38499  "
		::= { iqmux47CmdEntry 38499 }


	iqmux47AESOutPortNamesAESPort3Stereo OBJECT-TYPE
		SYNTAX		INTEGER { disable(0), enable(1) }
		MAX-ACCESS		read-write
		STATUS			current
		DESCRIPTION
				"TYPE: - Checkbox
				 PAGE: - Audio- AES Ports- AES Port Names
					AES Port 3 Stereo  cmdID= 38450 "
		::= { iqmux47CmdEntry 38450 }


	iqmux47AESOutPortNamesAESPort3L OBJECT-TYPE
		SYNTAX		RollCallString
		MAX-ACCESS		read-write
		STATUS			current
		DESCRIPTION
				"TYPE: - Editstring
				 PAGE: - Audio- AES Ports- AES Port Names
					AES Port 3-L  cmdID= 38500  "
		::= { iqmux47CmdEntry 38500 }


	iqmux47AESOutPortNamesAESPort3R OBJECT-TYPE
		SYNTAX		RollCallString
		MAX-ACCESS		read-write
		STATUS			current
		DESCRIPTION
				"TYPE: - Editstring
				 PAGE: - Audio- AES Ports- AES Port Names
					AES Port 3-R  cmdID= 38501  "
		::= { iqmux47CmdEntry 38501 }


	iqmux47AESOutPortNamesAESPort4Stereo OBJECT-TYPE
		SYNTAX		INTEGER { disable(0), enable(1) }
		MAX-ACCESS		read-write
		STATUS			current
		DESCRIPTION
				"TYPE: - Checkbox
				 PAGE: - Audio- AES Ports- AES Port Names
					AES Port 4 Stereo  cmdID= 38451 "
		::= { iqmux47CmdEntry 38451 }


	iqmux47AESOutPortNamesAESPort4L OBJECT-TYPE
		SYNTAX		RollCallString
		MAX-ACCESS		read-write
		STATUS			current
		DESCRIPTION
				"TYPE: - Editstring
				 PAGE: - Audio- AES Ports- AES Port Names
					AES Port 4-L  cmdID= 38502  "
		::= { iqmux47CmdEntry 38502 }


	iqmux47AESOutPortNamesAESPort4R OBJECT-TYPE
		SYNTAX		RollCallString
		MAX-ACCESS		read-write
		STATUS			current
		DESCRIPTION
				"TYPE: - Editstring
				 PAGE: - Audio- AES Ports- AES Port Names
					AES Port 4-R  cmdID= 38503  "
		::= { iqmux47CmdEntry 38503 }


	iqmux47AESOutPortNamesAESPort5Stereo OBJECT-TYPE
		SYNTAX		INTEGER { disable(0), enable(1) }
		MAX-ACCESS		read-write
		STATUS			current
		DESCRIPTION
				"TYPE: - Checkbox
				 PAGE: - Audio- AES Ports- AES Port Names
					AES Port 5 Stereo  cmdID= 38452 "
		::= { iqmux47CmdEntry 38452 }


	iqmux47AESOutPortNamesAESPort5L OBJECT-TYPE
		SYNTAX		RollCallString
		MAX-ACCESS		read-write
		STATUS			current
		DESCRIPTION
				"TYPE: - Editstring
				 PAGE: - Audio- AES Ports- AES Port Names
					AES Port 5-L  cmdID= 38504  "
		::= { iqmux47CmdEntry 38504 }


	iqmux47AESOutPortNamesAESPort5R OBJECT-TYPE
		SYNTAX		RollCallString
		MAX-ACCESS		read-write
		STATUS			current
		DESCRIPTION
				"TYPE: - Editstring
				 PAGE: - Audio- AES Ports- AES Port Names
					AES Port 5-R  cmdID= 38505  "
		::= { iqmux47CmdEntry 38505 }


	iqmux47AESOutPortNamesAESPort6Stereo OBJECT-TYPE
		SYNTAX		INTEGER { disable(0), enable(1) }
		MAX-ACCESS		read-write
		STATUS			current
		DESCRIPTION
				"TYPE: - Checkbox
				 PAGE: - Audio- AES Ports- AES Port Names
					AES Port 6 Stereo  cmdID= 38453 "
		::= { iqmux47CmdEntry 38453 }


	iqmux47AESOutPortNamesAESPort6L OBJECT-TYPE
		SYNTAX		RollCallString
		MAX-ACCESS		read-write
		STATUS			current
		DESCRIPTION
				"TYPE: - Editstring
				 PAGE: - Audio- AES Ports- AES Port Names
					AES Port 6-L  cmdID= 38506  "
		::= { iqmux47CmdEntry 38506 }


	iqmux47AESOutPortNamesAESPort6R OBJECT-TYPE
		SYNTAX		RollCallString
		MAX-ACCESS		read-write
		STATUS			current
		DESCRIPTION
				"TYPE: - Editstring
				 PAGE: - Audio- AES Ports- AES Port Names
					AES Port 6-R  cmdID= 38507  "
		::= { iqmux47CmdEntry 38507 }


	iqmux47AESOutPortNamesAESPort7Stereo OBJECT-TYPE
		SYNTAX		INTEGER { disable(0), enable(1) }
		MAX-ACCESS		read-write
		STATUS			current
		DESCRIPTION
				"TYPE: - Checkbox
				 PAGE: - Audio- AES Ports- AES Port Names
					AES Port 7 Stereo  cmdID= 38454 "
		::= { iqmux47CmdEntry 38454 }


	iqmux47AESOutPortNamesAESPort7L OBJECT-TYPE
		SYNTAX		RollCallString
		MAX-ACCESS		read-write
		STATUS			current
		DESCRIPTION
				"TYPE: - Editstring
				 PAGE: - Audio- AES Ports- AES Port Names
					AES Port 7-L  cmdID= 38508  "
		::= { iqmux47CmdEntry 38508 }


	iqmux47AESOutPortNamesAESPort7R OBJECT-TYPE
		SYNTAX		RollCallString
		MAX-ACCESS		read-write
		STATUS			current
		DESCRIPTION
				"TYPE: - Editstring
				 PAGE: - Audio- AES Ports- AES Port Names
					AES Port 7-R  cmdID= 38509  "
		::= { iqmux47CmdEntry 38509 }


	iqmux47AESOutPortNamesAESPort8Stereo OBJECT-TYPE
		SYNTAX		INTEGER { disable(0), enable(1) }
		MAX-ACCESS		read-write
		STATUS			current
		DESCRIPTION
				"TYPE: - Checkbox
				 PAGE: - Audio- AES Ports- AES Port Names
					AES Port 8 Stereo  cmdID= 38455 "
		::= { iqmux47CmdEntry 38455 }


	iqmux47AESOutPortNamesAESPort8L OBJECT-TYPE
		SYNTAX		RollCallString
		MAX-ACCESS		read-write
		STATUS			current
		DESCRIPTION
				"TYPE: - Editstring
				 PAGE: - Audio- AES Ports- AES Port Names
					AES Port 8-L  cmdID= 38510  "
		::= { iqmux47CmdEntry 38510 }


	iqmux47AESOutPortNamesAESPort8R OBJECT-TYPE
		SYNTAX		RollCallString
		MAX-ACCESS		read-write
		STATUS			current
		DESCRIPTION
				"TYPE: - Editstring
				 PAGE: - Audio- AES Ports- AES Port Names
					AES Port 8-R  cmdID= 38511  "
		::= { iqmux47CmdEntry 38511 }


	iqmux47AESBusDataModeInput1 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 1  cmdID= 38400
					PCM  value= 0
					Data  value= 1
					Mixed  value= 2  "
		::= { iqmux47CmdEntry 38400 }


	iqmux47AESBusDataModeInput2 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 2  cmdID= 38401
					PCM  value= 0
					Data  value= 1
					Mixed  value= 2  "
		::= { iqmux47CmdEntry 38401 }


	iqmux47AESBusDataModeInput3 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 3  cmdID= 38402
					PCM  value= 0
					Data  value= 1
					Mixed  value= 2  "
		::= { iqmux47CmdEntry 38402 }


	iqmux47AESBusDataModeInput4 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 4  cmdID= 38403
					PCM  value= 0
					Data  value= 1
					Mixed  value= 2  "
		::= { iqmux47CmdEntry 38403 }


	iqmux47AESBusDataModeInput5 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 5  cmdID= 38404
					PCM  value= 0
					Data  value= 1
					Mixed  value= 2  "
		::= { iqmux47CmdEntry 38404 }


	iqmux47AESBusDataModeInput6 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 6  cmdID= 38405
					PCM  value= 0
					Data  value= 1
					Mixed  value= 2  "
		::= { iqmux47CmdEntry 38405 }


	iqmux47AESBusDataModeInput7 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 7  cmdID= 38406
					PCM  value= 0
					Data  value= 1
					Mixed  value= 2  "
		::= { iqmux47CmdEntry 38406 }


	iqmux47AESBusDataModeInput8 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 8  cmdID= 38407
					PCM  value= 0
					Data  value= 1
					Mixed  value= 2  "
		::= { iqmux47CmdEntry 38407 }


	iqmux47AESBusNamesAESBus1Stereo OBJECT-TYPE
		SYNTAX		INTEGER { disable(0), enable(1) }
		MAX-ACCESS		read-write
		STATUS			current
		DESCRIPTION
				"TYPE: - Checkbox
				 PAGE: - Audio- AES Ports- AES Bus
					AES Bus 1 Stereo  cmdID= 38440 "
		::= { iqmux47CmdEntry 38440 }


	iqmux47AESBusNamesAESBus1 OBJECT-TYPE
		SYNTAX		RollCallString
		MAX-ACCESS		read-write
		STATUS			current
		DESCRIPTION
				"TYPE: - Editstring
				 PAGE: - Audio- AES Ports- AES Bus
					AES Bus 1  cmdID= 38480  "
		::= { iqmux47CmdEntry 38480 }


	iqmux47AESBusNamesAESBus1R OBJECT-TYPE
		SYNTAX		RollCallString
		MAX-ACCESS		read-write
		STATUS			current
		DESCRIPTION
				"TYPE: - Editstring
				 PAGE: - Audio- AES Ports- AES Bus
					AES Bus 1-R  cmdID= 38481  "
		::= { iqmux47CmdEntry 38481 }


	iqmux47AESBusNamesAESBus2Stereo OBJECT-TYPE
		SYNTAX		INTEGER { disable(0), enable(1) }
		MAX-ACCESS		read-write
		STATUS			current
		DESCRIPTION
				"TYPE: - Checkbox
				 PAGE: - Audio- AES Ports- AES Bus
					AES Bus 2 Stereo  cmdID= 38441 "
		::= { iqmux47CmdEntry 38441 }


	iqmux47AESBusNamesAESBus2 OBJECT-TYPE
		SYNTAX		RollCallString
		MAX-ACCESS		read-write
		STATUS			current
		DESCRIPTION
				"TYPE: - Editstring
				 PAGE: - Audio- AES Ports- AES Bus
					AES Bus 2  cmdID= 38482  "
		::= { iqmux47CmdEntry 38482 }


	iqmux47AESBusNamesAESBus2R OBJECT-TYPE
		SYNTAX		RollCallString
		MAX-ACCESS		read-write
		STATUS			current
		DESCRIPTION
				"TYPE: - Editstring
				 PAGE: - Audio- AES Ports- AES Bus
					AES Bus 2-R  cmdID= 38483  "
		::= { iqmux47CmdEntry 38483 }


	iqmux47AESBusNamesAESBus3Stereo OBJECT-TYPE
		SYNTAX		INTEGER { disable(0), enable(1) }
		MAX-ACCESS		read-write
		STATUS			current
		DESCRIPTION
				"TYPE: - Checkbox
				 PAGE: - Audio- AES Ports- AES Bus
					AES Bus 3 Stereo  cmdID= 38442 "
		::= { iqmux47CmdEntry 38442 }


	iqmux47AESBusNamesAESBus3 OBJECT-TYPE
		SYNTAX		RollCallString
		MAX-ACCESS		read-write
		STATUS			current
		DESCRIPTION
				"TYPE: - Editstring
				 PAGE: - Audio- AES Ports- AES Bus
					AES Bus 3  cmdID= 38484  "
		::= { iqmux47CmdEntry 38484 }


	iqmux47AESBusNamesAESBus3R OBJECT-TYPE
		SYNTAX		RollCallString
		MAX-ACCESS		read-write
		STATUS			current
		DESCRIPTION
				"TYPE: - Editstring
				 PAGE: - Audio- AES Ports- AES Bus
					AES Bus 3-R  cmdID= 38485  "
		::= { iqmux47CmdEntry 38485 }


	iqmux47AESBusNamesAESBus4Stereo OBJECT-TYPE
		SYNTAX		INTEGER { disable(0), enable(1) }
		MAX-ACCESS		read-write
		STATUS			current
		DESCRIPTION
				"TYPE: - Checkbox
				 PAGE: - Audio- AES Ports- AES Bus
					AES Bus 4 Stereo  cmdID= 38443 "
		::= { iqmux47CmdEntry 38443 }


	iqmux47AESBusNamesAESBus4 OBJECT-TYPE
		SYNTAX		RollCallString
		MAX-ACCESS		read-write
		STATUS			current
		DESCRIPTION
				"TYPE: - Editstring
				 PAGE: - Audio- AES Ports- AES Bus
					AES Bus 4  cmdID= 38486  "
		::= { iqmux47CmdEntry 38486 }


	iqmux47AESBusNamesAESBus4R OBJECT-TYPE
		SYNTAX		RollCallString
		MAX-ACCESS		read-write
		STATUS			current
		DESCRIPTION
				"TYPE: - Editstring
				 PAGE: - Audio- AES Ports- AES Bus
					AES Bus 4-R  cmdID= 38487  "
		::= { iqmux47CmdEntry 38487 }


	iqmux47AESBusNamesAESBus5Stereo OBJECT-TYPE
		SYNTAX		INTEGER { disable(0), enable(1) }
		MAX-ACCESS		read-write
		STATUS			current
		DESCRIPTION
				"TYPE: - Checkbox
				 PAGE: - Audio- AES Ports- AES Bus
					AES Bus 5 Stereo  cmdID= 38444 "
		::= { iqmux47CmdEntry 38444 }


	iqmux47AESBusNamesAESBus5 OBJECT-TYPE
		SYNTAX		RollCallString
		MAX-ACCESS		read-write
		STATUS			current
		DESCRIPTION
				"TYPE: - Editstring
				 PAGE: - Audio- AES Ports- AES Bus
					AES Bus 5  cmdID= 38488  "
		::= { iqmux47CmdEntry 38488 }


	iqmux47AESBusNamesAESBus5R OBJECT-TYPE
		SYNTAX		RollCallString
		MAX-ACCESS		read-write
		STATUS			current
		DESCRIPTION
				"TYPE: - Editstring
				 PAGE: - Audio- AES Ports- AES Bus
					AES Bus 5-R  cmdID= 38489  "
		::= { iqmux47CmdEntry 38489 }


	iqmux47AESBusNamesAESBus6Stereo OBJECT-TYPE
		SYNTAX		INTEGER { disable(0), enable(1) }
		MAX-ACCESS		read-write
		STATUS			current
		DESCRIPTION
				"TYPE: - Checkbox
				 PAGE: - Audio- AES Ports- AES Bus
					AES Bus 6 Stereo  cmdID= 38445 "
		::= { iqmux47CmdEntry 38445 }


	iqmux47AESBusNamesAESBus6 OBJECT-TYPE
		SYNTAX		RollCallString
		MAX-ACCESS		read-write
		STATUS			current
		DESCRIPTION
				"TYPE: - Editstring
				 PAGE: - Audio- AES Ports- AES Bus
					AES Bus 6  cmdID= 38490  "
		::= { iqmux47CmdEntry 38490 }


	iqmux47AESBusNamesAESBus6R OBJECT-TYPE
		SYNTAX		RollCallString
		MAX-ACCESS		read-write
		STATUS			current
		DESCRIPTION
				"TYPE: - Editstring
				 PAGE: - Audio- AES Ports- AES Bus
					AES Bus 6-R  cmdID= 38491  "
		::= { iqmux47CmdEntry 38491 }


	iqmux47AESBusNamesAESBus7Stereo OBJECT-TYPE
		SYNTAX		INTEGER { disable(0), enable(1) }
		MAX-ACCESS		read-write
		STATUS			current
		DESCRIPTION
				"TYPE: - Checkbox
				 PAGE: - Audio- AES Ports- AES Bus
					AES Bus 7 Stereo  cmdID= 38446 "
		::= { iqmux47CmdEntry 38446 }


	iqmux47AESBusNamesAESBus7 OBJECT-TYPE
		SYNTAX		RollCallString
		MAX-ACCESS		read-write
		STATUS			current
		DESCRIPTION
				"TYPE: - Editstring
				 PAGE: - Audio- AES Ports- AES Bus
					AES Bus 7  cmdID= 38492  "
		::= { iqmux47CmdEntry 38492 }


	iqmux47AESBusNamesAESBus7R OBJECT-TYPE
		SYNTAX		RollCallString
		MAX-ACCESS		read-write
		STATUS			current
		DESCRIPTION
				"TYPE: - Editstring
				 PAGE: - Audio- AES Ports- AES Bus
					AES Bus 7-R  cmdID= 38493  "
		::= { iqmux47CmdEntry 38493 }


	iqmux47AESBusNamesAESBus8Stereo OBJECT-TYPE
		SYNTAX		INTEGER { disable(0), enable(1) }
		MAX-ACCESS		read-write
		STATUS			current
		DESCRIPTION
				"TYPE: - Checkbox
				 PAGE: - Audio- AES Ports- AES Bus
					AES Bus 8 Stereo  cmdID= 38447 "
		::= { iqmux47CmdEntry 38447 }


	iqmux47AESBusNamesAESBus8 OBJECT-TYPE
		SYNTAX		RollCallString
		MAX-ACCESS		read-write
		STATUS			current
		DESCRIPTION
				"TYPE: - Editstring
				 PAGE: - Audio- AES Ports- AES Bus
					AES Bus 8  cmdID= 38494  "
		::= { iqmux47CmdEntry 38494 }


	iqmux47AESBusNamesAESBus8R OBJECT-TYPE
		SYNTAX		RollCallString
		MAX-ACCESS		read-write
		STATUS			current
		DESCRIPTION
				"TYPE: - Editstring
				 PAGE: - Audio- AES Ports- AES Bus
					AES Bus 8-R  cmdID= 38495  "
		::= { iqmux47CmdEntry 38495 }


	iqmux47AESBusRoutingSource1 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 1  cmdID= 38560
					AES Port 1  value= 1
					AES Port 2  value= 2
					AES Port 3  value= 3
					AES Port 4  value= 4
					AES Port 5  value= 5
					AES Port 6  value= 6
					AES Port 7  value= 7
					AES Port 8  value= 8  "
		::= { iqmux47CmdEntry 38560 }


	iqmux47AESBusRoutingSource2 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 2  cmdID= 38561
					AES Port 1  value= 1
					AES Port 2  value= 2
					AES Port 3  value= 3
					AES Port 4  value= 4
					AES Port 5  value= 5
					AES Port 6  value= 6
					AES Port 7  value= 7
					AES Port 8  value= 8  "
		::= { iqmux47CmdEntry 38561 }


	iqmux47AESBusRoutingSource3 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 3  cmdID= 38562
					AES Port 1  value= 1
					AES Port 2  value= 2
					AES Port 3  value= 3
					AES Port 4  value= 4
					AES Port 5  value= 5
					AES Port 6  value= 6
					AES Port 7  value= 7
					AES Port 8  value= 8  "
		::= { iqmux47CmdEntry 38562 }


	iqmux47AESBusRoutingSource4 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 4  cmdID= 38563
					AES Port 1  value= 1
					AES Port 2  value= 2
					AES Port 3  value= 3
					AES Port 4  value= 4
					AES Port 5  value= 5
					AES Port 6  value= 6
					AES Port 7  value= 7
					AES Port 8  value= 8  "
		::= { iqmux47CmdEntry 38563 }


	iqmux47AESBusRoutingSource5 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 5  cmdID= 38564
					AES Port 1  value= 1
					AES Port 2  value= 2
					AES Port 3  value= 3
					AES Port 4  value= 4
					AES Port 5  value= 5
					AES Port 6  value= 6
					AES Port 7  value= 7
					AES Port 8  value= 8  "
		::= { iqmux47CmdEntry 38564 }


	iqmux47AESBusRoutingSource6 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 6  cmdID= 38565
					AES Port 1  value= 1
					AES Port 2  value= 2
					AES Port 3  value= 3
					AES Port 4  value= 4
					AES Port 5  value= 5
					AES Port 6  value= 6
					AES Port 7  value= 7
					AES Port 8  value= 8  "
		::= { iqmux47CmdEntry 38565 }


	iqmux47AESBusRoutingSource7 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 7  cmdID= 38566
					AES Port 1  value= 1
					AES Port 2  value= 2
					AES Port 3  value= 3
					AES Port 4  value= 4
					AES Port 5  value= 5
					AES Port 6  value= 6
					AES Port 7  value= 7
					AES Port 8  value= 8  "
		::= { iqmux47CmdEntry 38566 }


	iqmux47AESBusRoutingSource8 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 8  cmdID= 38567
					AES Port 1  value= 1
					AES Port 2  value= 2
					AES Port 3  value= 3
					AES Port 4  value= 4
					AES Port 5  value= 5
					AES Port 6  value= 6
					AES Port 7  value= 7
					AES Port 8  value= 8  "
		::= { iqmux47CmdEntry 38567 }


	iqmux47AESPortsDirectionAES1Out OBJECT-TYPE
		SYNTAX		INTEGER {
							val_Input(0),
							val_Output(1)
							}
		MAX-ACCESS		read-write
		STATUS			current
		DESCRIPTION
				"TYPE: - RadiobuttonList
				 PAGE: - Audio- AES Ports
					AES Port 1 Dir  cmdID= 38420
					Input  value= 0
					Output  value= 1  "
		::= { iqmux47CmdEntry 38420 }


	iqmux47AESPortsDirectionAES2Out OBJECT-TYPE
		SYNTAX		INTEGER {
							val_Input(0),
							val_Output(1)
							}
		MAX-ACCESS		read-write
		STATUS			current
		DESCRIPTION
				"TYPE: - RadiobuttonList
				 PAGE: - Audio- AES Ports
					AES Port 2 Dir  cmdID= 38421
					Input  value= 0
					Output  value= 1  "
		::= { iqmux47CmdEntry 38421 }


	iqmux47AESPortsDirectionAES3Out OBJECT-TYPE
		SYNTAX		INTEGER {
							val_Input(0),
							val_Output(1)
							}
		MAX-ACCESS		read-write
		STATUS			current
		DESCRIPTION
				"TYPE: - RadiobuttonList
				 PAGE: - Audio- AES Ports
					AES Port 3 Dir  cmdID= 38422
					Input  value= 0
					Output  value= 1  "
		::= { iqmux47CmdEntry 38422 }


	iqmux47AESPortsDirectionAES4Out OBJECT-TYPE
		SYNTAX		INTEGER {
							val_Input(0),
							val_Output(1)
							}
		MAX-ACCESS		read-write
		STATUS			current
		DESCRIPTION
				"TYPE: - RadiobuttonList
				 PAGE: - Audio- AES Ports
					AES Port 4 Dir  cmdID= 38423
					Input  value= 0
					Output  value= 1  "
		::= { iqmux47CmdEntry 38423 }


	iqmux47AESPortsDirectionAES5Out OBJECT-TYPE
		SYNTAX		INTEGER {
							val_Input(0),
							val_Output(1)
							}
		MAX-ACCESS		read-write
		STATUS			current
		DESCRIPTION
				"TYPE: - RadiobuttonList
				 PAGE: - Audio- AES Ports
					AES Port 5 Dir  cmdID= 38424
					Input  value= 0
					Output  value= 1  "
		::= { iqmux47CmdEntry 38424 }


	iqmux47AESPortsDirectionAES6Out OBJECT-TYPE
		SYNTAX		INTEGER {
							val_Input(0),
							val_Output(1)
							}
		MAX-ACCESS		read-write
		STATUS			current
		DESCRIPTION
				"TYPE: - RadiobuttonList
				 PAGE: - Audio- AES Ports
					AES Port 6 Dir  cmdID= 38425
					Input  value= 0
					Output  value= 1  "
		::= { iqmux47CmdEntry 38425 }


	iqmux47AESPortsDirectionAES7Out OBJECT-TYPE
		SYNTAX		INTEGER {
							val_Input(0),
							val_Output(1)
							}
		MAX-ACCESS		read-write
		STATUS			current
		DESCRIPTION
				"TYPE: - RadiobuttonList
				 PAGE: - Audio- AES Ports
					AES Port 7 Dir  cmdID= 38426
					Input  value= 0
					Output  value= 1  "
		::= { iqmux47CmdEntry 38426 }


	iqmux47AESPortsDirectionAES8Out OBJECT-TYPE
		SYNTAX		INTEGER {
							val_Input(0),
							val_Output(1)
							}
		MAX-ACCESS		read-write
		STATUS			current
		DESCRIPTION
				"TYPE: - RadiobuttonList
				 PAGE: - Audio- AES Ports
					AES Port 8 Dir  cmdID= 38427
					Input  value= 0
					Output  value= 1  "
		::= { iqmux47CmdEntry 38427 }


	iqmux47AudioDolbyETimingSelAudioPair OBJECT-TYPE
		SYNTAX		INTEGER
		MAX-ACCESS		read-write
		STATUS			current
		DESCRIPTION
				"TYPE: - Number
				 PAGE: - Audio
					Sel Audio Pair  cmdID= 38650  min= 1  max= 8  step= 1  format= %0.0f  div_scale= 1
					Min = 1  Max = 8  Step = 1 "
		::= { iqmux47CmdEntry 38650 }


	iqmux47AudioDolbyETimingRelativeTiming OBJECT-TYPE
		SYNTAX		RollCallString
		MAX-ACCESS		read-only
		STATUS			current
		DESCRIPTION
				"TYPE: - Display
				 PAGE: - Audio
					Relative Timing  cmdID= 38653  format=   "
		::= { iqmux47CmdEntry 38653 }


	iqmux47AudioDolbyETimingStatus OBJECT-TYPE
		SYNTAX		RollCallString
		MAX-ACCESS		read-only
		STATUS			current
		DESCRIPTION
				"TYPE: - Display
				 PAGE: - Audio
					Status  cmdID= 38652  format=   "
		::= { iqmux47CmdEntry 38652 }


	iqmux47AudioDolbyETimingError OBJECT-TYPE
		SYNTAX		RollCallString
		MAX-ACCESS		read-only
		STATUS			current
		DESCRIPTION
				"TYPE: - Display
				 PAGE: - Audio
					Error  cmdID= 38654  format=   "
		::= { iqmux47CmdEntry 38654 }


	iqmux47DolbyETimingLineStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
				 PAGE: - Audio
					Standard  cmdID= 38655
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqmux47CmdEntry 38655 }


	iqmux47DolbyETimingLineAutoLineNo OBJECT-TYPE
		SYNTAX		INTEGER
		MAX-ACCESS		read-write
		STATUS			current
		DESCRIPTION
				"TYPE: - Number
				 PAGE: - Audio
					Auto Line No.  cmdID= 38656  min= 1  max= 10000  step= 1  format= %0.0f  div_scale= 1
					Min = 1  Max = 10000  Step = 1 "
		::= { iqmux47CmdEntry 38656 }


	iqmux47DolbyELineUserDolbyELinePair1 OBJECT-TYPE
		SYNTAX		INTEGER {
							val_User_Line(1),
							val_Standard_Line(0)
							}
		MAX-ACCESS		read-write
		STATUS			current
		DESCRIPTION
				"TYPE: - RadiobuttonList
				 PAGE: - Audio
					Pair 1  cmdID= 38670
					User Line  value= 1
					Standard Line  value= 0  "
		::= { iqmux47CmdEntry 38670 }


	iqmux47DolbyELineUserDolbyELinePair2 OBJECT-TYPE
		SYNTAX		INTEGER {
							val_User_Line(1),
							val_Standard_Line(0)
							}
		MAX-ACCESS		read-write
		STATUS			current
		DESCRIPTION
				"TYPE: - RadiobuttonList
				 PAGE: - Audio
					Pair 2  cmdID= 38671
					User Line  value= 1
					Standard Line  value= 0  "
		::= { iqmux47CmdEntry 38671 }


	iqmux47DolbyELineUserDolbyELinePair3 OBJECT-TYPE
		SYNTAX		INTEGER {
							val_User_Line(1),
							val_Standard_Line(0)
							}
		MAX-ACCESS		read-write
		STATUS			current
		DESCRIPTION
				"TYPE: - RadiobuttonList
				 PAGE: - Audio
					Pair 3  cmdID= 38672
					User Line  value= 1
					Standard Line  value= 0  "
		::= { iqmux47CmdEntry 38672 }


	iqmux47DolbyELineUserDolbyELinePair4 OBJECT-TYPE
		SYNTAX		INTEGER {
							val_User_Line(1),
							val_Standard_Line(0)
							}
		MAX-ACCESS		read-write
		STATUS			current
		DESCRIPTION
				"TYPE: - RadiobuttonList
				 PAGE: - Audio
					Pair 4  cmdID= 38673
					User Line  value= 1
					Standard Line  value= 0  "
		::= { iqmux47CmdEntry 38673 }


	iqmux47DolbyELineUserDolbyELinePair5 OBJECT-TYPE
		SYNTAX		INTEGER {
							val_User_Line(1),
							val_Standard_Line(0)
							}
		MAX-ACCESS		read-write
		STATUS			current
		DESCRIPTION
				"TYPE: - RadiobuttonList
				 PAGE: - Audio
					Pair 5  cmdID= 38674
					User Line  value= 1
					Standard Line  value= 0  "
		::= { iqmux47CmdEntry 38674 }


	iqmux47DolbyELineUserDolbyELinePair6 OBJECT-TYPE
		SYNTAX		INTEGER {
							val_User_Line(1),
							val_Standard_Line(0)
							}
		MAX-ACCESS		read-write
		STATUS			current
		DESCRIPTION
				"TYPE: - RadiobuttonList
				 PAGE: - Audio
					Pair 6  cmdID= 38675
					User Line  value= 1
					Standard Line  value= 0  "
		::= { iqmux47CmdEntry 38675 }


	iqmux47DolbyELineUserDolbyELinePair7 OBJECT-TYPE
		SYNTAX		INTEGER {
							val_User_Line(1),
							val_Standard_Line(0)
							}
		MAX-ACCESS		read-write
		STATUS			current
		DESCRIPTION
				"TYPE: - RadiobuttonList
				 PAGE: - Audio
					Pair 7  cmdID= 38676
					User Line  value= 1
					Standard Line  value= 0  "
		::= { iqmux47CmdEntry 38676 }


	iqmux47DolbyELineUserDolbyELinePair8 OBJECT-TYPE
		SYNTAX		INTEGER {
							val_User_Line(1),
							val_Standard_Line(0)
							}
		MAX-ACCESS		read-write
		STATUS			current
		DESCRIPTION
				"TYPE: - RadiobuttonList
				 PAGE: - Audio
					Pair 8  cmdID= 38677
					User Line  value= 1
					Standard Line  value= 0  "
		::= { iqmux47CmdEntry 38677 }


	iqmux47VidDelayInternalDelay OBJECT-TYPE
		SYNTAX		RollCallString
		MAX-ACCESS		read-only
		STATUS			current
		DESCRIPTION
				"TYPE: - Display
				 PAGE: - Vid. Delay
					Internal Delay  cmdID= 33025  format=   "
		::= { iqmux47CmdEntry 33025 }


	iqmux47VidDelayDelayMode OBJECT-TYPE
		SYNTAX		INTEGER {
							val_Minimum_Audio(3),
							val_Frames(4),
							val_Manual_H_V(5),
							val_Manual_ms(6)
							}
		MAX-ACCESS		read-write
		STATUS			current
		DESCRIPTION
				"TYPE: - RadiobuttonList
				 PAGE: - Vid. Delay
					Delay Mode  cmdID= 33026
					Minimum Audio  value= 3
					Frames  value= 4
					Manual H/V  value= 5
					Manual ms  value= 6  "
		::= { iqmux47CmdEntry 33026 }


	iqmux47VidSetDelayDelayFrames OBJECT-TYPE
		SYNTAX		INTEGER
		MAX-ACCESS		read-write
		STATUS			current
		DESCRIPTION
				"TYPE: - Number
				 PAGE: - Vid. Delay
					Delay Frames  cmdID= 33024  min= 0  max= 11  step= 1  format= %0.0f frames  div_scale= 1
					Min = 0 frames  Max = 11 frames  Step = 1 frames "
		::= { iqmux47CmdEntry 33024 }


	iqmux47VidSetDelayVerticalTiming OBJECT-TYPE
		SYNTAX		INTEGER
		MAX-ACCESS		read-write
		STATUS			current
		DESCRIPTION
				"TYPE: - Number
				 PAGE: - Vid. Delay
					Vertical Timing  cmdID= 33022  min= -1500  max= 1500  step= 1  format= %0.0f lines  div_scale= 1
					Min = -1500 lines  Max = 1500 lines  Step = 1 lines "
		::= { iqmux47CmdEntry 33022 }


	iqmux47VidSetDelayHorizontalTiming OBJECT-TYPE
		SYNTAX		INTEGER
		MAX-ACCESS		read-write
		STATUS			current
		DESCRIPTION
				"TYPE: - Number
				 PAGE: - Vid. Delay
					Horizontal Timing  cmdID= 33021  min= -3000  max= 3000  step= 1  format= %0.0f pixels  div_scale= 1
					Min = -3000 pixels  Max = 3000 pixels  Step = 1 pixels "
		::= { iqmux47CmdEntry 33021 }


	iqmux47VidSetDelayDelayms OBJECT-TYPE
		SYNTAX		INTEGER
		MAX-ACCESS		read-write
		STATUS			current
		DESCRIPTION
				"TYPE: - Number
				 PAGE: - Vid. Delay
					Delay ms  cmdID= 33027  min= -48000  max= 48000  step= 5  format= %0.2f ms  div_scale= 100
					Min = -480.00 ms  Max = 480.00 ms  Step = 0.05 ms "
		::= { iqmux47CmdEntry 33027 }


	iqmux47UtilsPatternsPatternEnable OBJECT-TYPE
		SYNTAX		INTEGER { disable(0), enable(1) }
		MAX-ACCESS		read-write
		STATUS			current
		DESCRIPTION
				"TYPE: - Checkbox
				 PAGE: - Utils
					Pattern Enable  cmdID= 33038 "
		::= { iqmux47CmdEntry 33038 }


	iqmux47UtilsPatternsScrollPattern OBJECT-TYPE
		SYNTAX		INTEGER { disable(0), enable(1) }
		MAX-ACCESS		read-write
		STATUS			current
		DESCRIPTION
				"TYPE: - Checkbox
				 PAGE: - Utils
					Scroll Pattern  cmdID= 33040 "
		::= { iqmux47CmdEntry 33040 }


	iqmux47UtilsPatternsPatternType OBJECT-TYPE
		SYNTAX		INTEGER {
							val_100_Color_Bars(1),
							val_75_Color_Bars(2),
							val_SMPTE_Bars(3),
							val_Tartan_Bars(4),
							val_Pluge(5),
							val_Ramp(6),
							val_Sweep(7),
							val_Pulse_Bar(8),
							val_Burst(9),
							val_Black(10)
							}
		MAX-ACCESS		read-write
		STATUS			current
		DESCRIPTION
				"TYPE: - RadiobuttonList
				 PAGE: - Utils
					Pattern Type  cmdID= 33039
					100% Color Bars  value= 1
					75% Color Bars  value= 2
					SMPTE Bars  value= 3
					Tartan Bars  value= 4
					Pluge  value= 5
					Ramp  value= 6
					Sweep  value= 7
					Pulse & Bar  value= 8
					Burst  value= 9
					Black  value= 10  "
		::= { iqmux47CmdEntry 33039 }


	iqmux47UtilsANCblankonMismat OBJECT-TYPE
		SYNTAX		INTEGER { disable(0), enable(1) }
		MAX-ACCESS		read-write
		STATUS			current
		DESCRIPTION
				"TYPE: - Checkbox
				 PAGE: - Utils
					ANC blank on Mismat  cmdID= 33036 "
		::= { iqmux47CmdEntry 33036 }


	iqmux47UtilsFreezeForceFreeze OBJECT-TYPE
		SYNTAX		INTEGER { disable(0), enable(1) }
		MAX-ACCESS		read-write
		STATUS			current
		DESCRIPTION
				"TYPE: - Checkbox
				 PAGE: - Utils
					Force Freeze  cmdID= 33032 "
		::= { iqmux47CmdEntry 33032 }


	iqmux47UtilsFreezeFreezeType OBJECT-TYPE
		SYNTAX		INTEGER {
							val_Frame(0),
							val_Field(1)
							}
		MAX-ACCESS		read-write
		STATUS			current
		DESCRIPTION
				"TYPE: - RadiobuttonList
				 PAGE: - Utils
					Freeze Type  cmdID= 33033
					Frame  value= 0
					Field  value= 1  "
		::= { iqmux47CmdEntry 33033 }


	iqmux47UtilsMonochrome OBJECT-TYPE
		SYNTAX		INTEGER { disable(0), enable(1) }
		MAX-ACCESS		read-write
		STATUS			current
		DESCRIPTION
				"TYPE: - Checkbox
				 PAGE: - Utils
					Monochrome  cmdID= 33034 "
		::= { iqmux47CmdEntry 33034 }


	iqmux47UtilsMonochromeMonochromeType OBJECT-TYPE
		SYNTAX		INTEGER {
							val_Y_only(0),
							val_C_only(1)
							}
		MAX-ACCESS		read-write
		STATUS			current
		DESCRIPTION
				"TYPE: - RadiobuttonList
				 PAGE: - Utils
					Monochrome Type  cmdID= 33035
					Y only  value= 0
					C only  value= 1  "
		::= { iqmux47CmdEntry 33035 }


	iqmux47UtilsVBIBlankingANCMode OBJECT-TYPE
		SYNTAX		INTEGER {
							val_Pass_Input_ANC(0),
							val_Blank_HANC(2),
							val_Blank_All_ANC(1)
							}
		MAX-ACCESS		read-write
		STATUS			current
		DESCRIPTION
				"TYPE: - RadiobuttonList
				 PAGE: - Utils
					ANC Mode  cmdID= 33037
					Pass Input ANC  value= 0
					Blank HANC  value= 2
					Blank All ANC  value= 1  "
		::= { iqmux47CmdEntry 33037 }


	iqmux47UtilsVBIBlankingStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
				 PAGE: - Utils
					Standard  cmdID= 37200
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqmux47CmdEntry 37200 }


	iqmux47UtilsVBIBlankingBlankAll OBJECT-TYPE
		SYNTAX		INTEGER { noAction(0),val_Blank_All(1) }
		MAX-ACCESS		read-write
		STATUS			current
		DESCRIPTION
				"TYPE: - Button
				 PAGE: - Utils
					Blank All  cmdID= 37201  value= 1  "
		::= { iqmux47CmdEntry 37201 }


	iqmux47UtilsVBIBlankingPassAll OBJECT-TYPE
		SYNTAX		INTEGER { noAction(0),val_Pass_All(1) }
		MAX-ACCESS		read-write
		STATUS			current
		DESCRIPTION
				"TYPE: - Button
				 PAGE: - Utils
					Pass All  cmdID= 37202  value= 1  "
		::= { iqmux47CmdEntry 37202 }


	iqmux47UtilsVBIBlankingBlank1 OBJECT-TYPE
		SYNTAX		INTEGER { disable(0), enable(1) }
		MAX-ACCESS		read-write
		STATUS			current
		DESCRIPTION
				"TYPE: - Checkbox
				 PAGE: - Utils
					Blank 1  cmdID= 37210 "
		::= { iqmux47CmdEntry 37210 }


	iqmux47UtilsVBIBlankingBlank2 OBJECT-TYPE
		SYNTAX		INTEGER { disable(0), enable(1) }
		MAX-ACCESS		read-write
		STATUS			current
		DESCRIPTION
				"TYPE: - Checkbox
				 PAGE: - Utils
					Blank 2  cmdID= 37211 "
		::= { iqmux47CmdEntry 37211 }


	iqmux47UtilsVBIBlankingBlank3 OBJECT-TYPE
		SYNTAX		INTEGER { disable(0), enable(1) }
		MAX-ACCESS		read-write
		STATUS			current
		DESCRIPTION
				"TYPE: - Checkbox
				 PAGE: - Utils
					Blank 3  cmdID= 37212 "
		::= { iqmux47CmdEntry 37212 }


	iqmux47UtilsVBIBlankingBlank4 OBJECT-TYPE
		SYNTAX		INTEGER { disable(0), enable(1) }
		MAX-ACCESS		read-write
		STATUS			current
		DESCRIPTION
				"TYPE: - Checkbox
				 PAGE: - Utils
					Blank 4  cmdID= 37213 "
		::= { iqmux47CmdEntry 37213 }


	iqmux47UtilsVBIBlankingBlank5 OBJECT-TYPE
		SYNTAX		INTEGER { disable(0), enable(1) }
		MAX-ACCESS		read-write
		STATUS			current
		DESCRIPTION
				"TYPE: - Checkbox
				 PAGE: - Utils
					Blank 5  cmdID= 37214 "
		::= { iqmux47CmdEntry 37214 }


	iqmux47UtilsVBIBlankingBlank6 OBJECT-TYPE
		SYNTAX		INTEGER { disable(0), enable(1) }
		MAX-ACCESS		read-write
		STATUS			current
		DESCRIPTION
				"TYPE: - Checkbox
				 PAGE: - Utils
					Blank 6  cmdID= 37215 "
		::= { iqmux47CmdEntry 37215 }


	iqmux47UtilsVBIBlankingBlank7 OBJECT-TYPE
		SYNTAX		INTEGER { disable(0), enable(1) }
		MAX-ACCESS		read-write
		STATUS			current
		DESCRIPTION
				"TYPE: - Checkbox
				 PAGE: - Utils
					Blank 7  cmdID= 37216 "
		::= { iqmux47CmdEntry 37216 }


	iqmux47UtilsVBIBlankingBlank8 OBJECT-TYPE
		SYNTAX		INTEGER { disable(0), enable(1) }
		MAX-ACCESS		read-write
		STATUS			current
		DESCRIPTION
				"TYPE: - Checkbox
				 PAGE: - Utils
					Blank 8  cmdID= 37217 "
		::= { iqmux47CmdEntry 37217 }


	iqmux47UtilsVBIBlankingBlank9 OBJECT-TYPE
		SYNTAX		INTEGER { disable(0), enable(1) }
		MAX-ACCESS		read-write
		STATUS			current
		DESCRIPTION
				"TYPE: - Checkbox
				 PAGE: - Utils
					Blank 9  cmdID= 37218 "
		::= { iqmux47CmdEntry 37218 }


	iqmux47UtilsVBIBlankingBlank10 OBJECT-TYPE
		SYNTAX		INTEGER { disable(0), enable(1) }
		MAX-ACCESS		read-write
		STATUS			current
		DESCRIPTION
				"TYPE: - Checkbox
				 PAGE: - Utils
					Blank 10  cmdID= 37219 "
		::= { iqmux47CmdEntry 37219 }


	iqmux47UtilsVBIBlankingBlank11 OBJECT-TYPE
		SYNTAX		INTEGER { disable(0), enable(1) }
		MAX-ACCESS		read-write
		STATUS			current
		DESCRIPTION
				"TYPE: - Checkbox
				 PAGE: - Utils
					Blank 11  cmdID= 37220 "
		::= { iqmux47CmdEntry 37220 }


	iqmux47UtilsVBIBlankingBlank12 OBJECT-TYPE
		SYNTAX		INTEGER { disable(0), enable(1) }
		MAX-ACCESS		read-write
		STATUS			current
		DESCRIPTION
				"TYPE: - Checkbox
				 PAGE: - Utils
					Blank 12  cmdID= 37221 "
		::= { iqmux47CmdEntry 37221 }


	iqmux47UtilsVBIBlankingBlank13 OBJECT-TYPE
		SYNTAX		INTEGER { disable(0), enable(1) }
		MAX-ACCESS		read-write
		STATUS			current
		DESCRIPTION
				"TYPE: - Checkbox
				 PAGE: - Utils
					Blank 13  cmdID= 37222 "
		::= { iqmux47CmdEntry 37222 }


	iqmux47UtilsVBIBlankingBlank14 OBJECT-TYPE
		SYNTAX		INTEGER { disable(0), enable(1) }
		MAX-ACCESS		read-write
		STATUS			current
		DESCRIPTION
				"TYPE: - Checkbox
				 PAGE: - Utils
					Blank 14  cmdID= 37223 "
		::= { iqmux47CmdEntry 37223 }


	iqmux47UtilsVBIBlankingBlank15 OBJECT-TYPE
		SYNTAX		INTEGER { disable(0), enable(1) }
		MAX-ACCESS		read-write
		STATUS			current
		DESCRIPTION
				"TYPE: - Checkbox
				 PAGE: - Utils
					Blank 15  cmdID= 37224 "
		::= { iqmux47CmdEntry 37224 }


	iqmux47UtilsVBIBlankingBlank16 OBJECT-TYPE
		SYNTAX		INTEGER { disable(0), enable(1) }
		MAX-ACCESS		read-write
		STATUS			current
		DESCRIPTION
				"TYPE: - Checkbox
				 PAGE: - Utils
					Blank 16  cmdID= 37225 "
		::= { iqmux47CmdEntry 37225 }


	iqmux47UtilsVBIBlankingBlank17 OBJECT-TYPE
		SYNTAX		INTEGER { disable(0), enable(1) }
		MAX-ACCESS		read-write
		STATUS			current
		DESCRIPTION
				"TYPE: - Checkbox
				 PAGE: - Utils
					Blank 17  cmdID= 37226 "
		::= { iqmux47CmdEntry 37226 }


	iqmux47UtilsVBIBlankingBlank18 OBJECT-TYPE
		SYNTAX		INTEGER { disable(0), enable(1) }
		MAX-ACCESS		read-write
		STATUS			current
		DESCRIPTION
				"TYPE: - Checkbox
				 PAGE: - Utils
					Blank 18  cmdID= 37227 "
		::= { iqmux47CmdEntry 37227 }


	iqmux47UtilsVBIBlankingBlank19 OBJECT-TYPE
		SYNTAX		INTEGER { disable(0), enable(1) }
		MAX-ACCESS		read-write
		STATUS			current
		DESCRIPTION
				"TYPE: - Checkbox
				 PAGE: - Utils
					Blank 19  cmdID= 37228 "
		::= { iqmux47CmdEntry 37228 }


	iqmux47UtilsVBIBlankingBlank20 OBJECT-TYPE
		SYNTAX		INTEGER { disable(0), enable(1) }
		MAX-ACCESS		read-write
		STATUS			current
		DESCRIPTION
				"TYPE: - Checkbox
				 PAGE: - Utils
					Blank 20  cmdID= 37229 "
		::= { iqmux47CmdEntry 37229 }


	iqmux47UtilsVBIBlankingBlank21 OBJECT-TYPE
		SYNTAX		INTEGER { disable(0), enable(1) }
		MAX-ACCESS		read-write
		STATUS			current
		DESCRIPTION
				"TYPE: - Checkbox
				 PAGE: - Utils
					Blank 21  cmdID= 37230 "
		::= { iqmux47CmdEntry 37230 }


	iqmux47UtilsVBIBlankingBlank22 OBJECT-TYPE
		SYNTAX		INTEGER { disable(0), enable(1) }
		MAX-ACCESS		read-write
		STATUS			current
		DESCRIPTION
				"TYPE: - Checkbox
				 PAGE: - Utils
					Blank 22  cmdID= 37231 "
		::= { iqmux47CmdEntry 37231 }


	iqmux47UtilsVBIBlankingBlank23 OBJECT-TYPE
		SYNTAX		INTEGER { disable(0), enable(1) }
		MAX-ACCESS		read-write
		STATUS			current
		DESCRIPTION
				"TYPE: - Checkbox
				 PAGE: - Utils
					Blank 23  cmdID= 37232 "
		::= { iqmux47CmdEntry 37232 }


	iqmux47UtilsVBIBlankingBlank24 OBJECT-TYPE
		SYNTAX		INTEGER { disable(0), enable(1) }
		MAX-ACCESS		read-write
		STATUS			current
		DESCRIPTION
				"TYPE: - Checkbox
				 PAGE: - Utils
					Blank 24  cmdID= 37233 "
		::= { iqmux47CmdEntry 37233 }


	iqmux47UtilsVBIBlankingBlank25 OBJECT-TYPE
		SYNTAX		INTEGER { disable(0), enable(1) }
		MAX-ACCESS		read-write
		STATUS			current
		DESCRIPTION
				"TYPE: - Checkbox
				 PAGE: - Utils
					Blank 25  cmdID= 37234 "
		::= { iqmux47CmdEntry 37234 }


	iqmux47UtilsVBIBlankingBlank26 OBJECT-TYPE
		SYNTAX		INTEGER { disable(0), enable(1) }
		MAX-ACCESS		read-write
		STATUS			current
		DESCRIPTION
				"TYPE: - Checkbox
				 PAGE: - Utils
					Blank 26  cmdID= 37235 "
		::= { iqmux47CmdEntry 37235 }


	iqmux47UtilsVBIBlankingBlank27 OBJECT-TYPE
		SYNTAX		INTEGER { disable(0), enable(1) }
		MAX-ACCESS		read-write
		STATUS			current
		DESCRIPTION
				"TYPE: - Checkbox
				 PAGE: - Utils
					Blank 27  cmdID= 37236 "
		::= { iqmux47CmdEntry 37236 }


	iqmux47UtilsVBIBlankingBlank28 OBJECT-TYPE
		SYNTAX		INTEGER { disable(0), enable(1) }
		MAX-ACCESS		read-write
		STATUS			current
		DESCRIPTION
				"TYPE: - Checkbox
				 PAGE: - Utils
					Blank 28  cmdID= 37237 "
		::= { iqmux47CmdEntry 37237 }


	iqmux47UtilsVBIBlankingBlank29 OBJECT-TYPE
		SYNTAX		INTEGER { disable(0), enable(1) }
		MAX-ACCESS		read-write
		STATUS			current
		DESCRIPTION
				"TYPE: - Checkbox
				 PAGE: - Utils
					Blank 29  cmdID= 37238 "
		::= { iqmux47CmdEntry 37238 }


	iqmux47UtilsVBIBlankingBlank30 OBJECT-TYPE
		SYNTAX		INTEGER { disable(0), enable(1) }
		MAX-ACCESS		read-write
		STATUS			current
		DESCRIPTION
				"TYPE: - Checkbox
				 PAGE: - Utils
					Blank 30  cmdID= 37239 "
		::= { iqmux47CmdEntry 37239 }


	iqmux47UtilsVBIBlankingBlank31 OBJECT-TYPE
		SYNTAX		INTEGER { disable(0), enable(1) }
		MAX-ACCESS		read-write
		STATUS			current
		DESCRIPTION
				"TYPE: - Checkbox
				 PAGE: - Utils
					Blank 31  cmdID= 37240 "
		::= { iqmux47CmdEntry 37240 }


	iqmux47UtilsVBIBlankingBlank32 OBJECT-TYPE
		SYNTAX		INTEGER { disable(0), enable(1) }
		MAX-ACCESS		read-write
		STATUS			current
		DESCRIPTION
				"TYPE: - Checkbox
				 PAGE: - Utils
					Blank 32  cmdID= 37241 "
		::= { iqmux47CmdEntry 37241 }


	iqmux47UtilsVBIBlankingBlank33 OBJECT-TYPE
		SYNTAX		INTEGER { disable(0), enable(1) }
		MAX-ACCESS		read-write
		STATUS			current
		DESCRIPTION
				"TYPE: - Checkbox
				 PAGE: - Utils
					Blank 33  cmdID= 37242 "
		::= { iqmux47CmdEntry 37242 }


	iqmux47UtilsVBIBlankingBlank34 OBJECT-TYPE
		SYNTAX		INTEGER { disable(0), enable(1) }
		MAX-ACCESS		read-write
		STATUS			current
		DESCRIPTION
				"TYPE: - Checkbox
				 PAGE: - Utils
					Blank 34  cmdID= 37243 "
		::= { iqmux47CmdEntry 37243 }


	iqmux47MemoriesRecallMemory OBJECT-TYPE
		SYNTAX		INTEGER {
							val_None_Selected(0),
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Recall Memory  cmdID= 37100
					None Selected  value= 0
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqmux47CmdEntry 37100 }


	iqmux47MemoriesSelMemory OBJECT-TYPE
		SYNTAX		INTEGER {
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Sel Memory  cmdID= 37101
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqmux47CmdEntry 37101 }


	iqmux47SaveMemories OBJECT-TYPE
		SYNTAX		INTEGER { noAction(0),val_Save_Memory(1) }
		MAX-ACCESS		read-write
		STATUS			current
		DESCRIPTION
				"TYPE: - Button
				 PAGE: - Memories
					Save Memory  cmdID= 37102  value= 1 "
		::= { iqmux47CmdEntry 37102 }


	iqmux47ClearMemories OBJECT-TYPE
		SYNTAX		INTEGER { noAction(0),val_Clear_Memory(1) }
		MAX-ACCESS		read-write
		STATUS			current
		DESCRIPTION
				"TYPE: - Button
				 PAGE: - Memories
					Clear Memory  cmdID= 37105  value= 1 "
		::= { iqmux47CmdEntry 37105 }


	iqmux47MemoriesMemoryNameChangeName OBJECT-TYPE
		SYNTAX		RollCallString
		MAX-ACCESS		read-write
		STATUS			current
		DESCRIPTION
				"TYPE: - Editstring
				 PAGE: - Memories
					Change Name  cmdID= 37103  "
		::= { iqmux47CmdEntry 37103 }


	iqmux47MemoriesLastUserMemory OBJECT-TYPE
		SYNTAX		RollCallString
		MAX-ACCESS		read-only
		STATUS			current
		DESCRIPTION
				"TYPE: - Display
				 PAGE: - Memories
					Last User Memory  cmdID= 37104  format=   "
		::= { iqmux47CmdEntry 37104 }


	iqmux47MemoriesMemoryName1 OBJECT-TYPE
		SYNTAX		RollCallString
		MAX-ACCESS		read-only
		STATUS			current
		DESCRIPTION
				"TYPE: - Display
				 PAGE: - Memories
					Memory Name1  cmdID= 37106  format=   "
		::= { iqmux47CmdEntry 37106 }


	iqmux47MemoriesMemoryName2 OBJECT-TYPE
		SYNTAX		RollCallString
		MAX-ACCESS		read-only
		STATUS			current
		DESCRIPTION
				"TYPE: - Display
				 PAGE: - Memories
					Memory Name2  cmdID= 37107  format=   "
		::= { iqmux47CmdEntry 37107 }


	iqmux47MemoriesMemoryName3 OBJECT-TYPE
		SYNTAX		RollCallString
		MAX-ACCESS		read-only
		STATUS			current
		DESCRIPTION
				"TYPE: - Display
				 PAGE: - Memories
					Memory Name3  cmdID= 37108  format=   "
		::= { iqmux47CmdEntry 37108 }


	iqmux47MemoriesMemoryName4 OBJECT-TYPE
		SYNTAX		RollCallString
		MAX-ACCESS		read-only
		STATUS			current
		DESCRIPTION
				"TYPE: - Display
				 PAGE: - Memories
					Memory Name4  cmdID= 37109  format=   "
		::= { iqmux47CmdEntry 37109 }


	iqmux47MemoriesMemoryName5 OBJECT-TYPE
		SYNTAX		RollCallString
		MAX-ACCESS		read-only
		STATUS			current
		DESCRIPTION
				"TYPE: - Display
				 PAGE: - Memories
					Memory Name5  cmdID= 37110  format=   "
		::= { iqmux47CmdEntry 37110 }


	iqmux47MemoriesMemoryName6 OBJECT-TYPE
		SYNTAX		RollCallString
		MAX-ACCESS		read-only
		STATUS			current
		DESCRIPTION
				"TYPE: - Display
				 PAGE: - Memories
					Memory Name6  cmdID= 37111  format=   "
		::= { iqmux47CmdEntry 37111 }


	iqmux47MemoriesMemoryName7 OBJECT-TYPE
		SYNTAX		RollCallString
		MAX-ACCESS		read-only
		STATUS			current
		DESCRIPTION
				"TYPE: - Display
				 PAGE: - Memories
					Memory Name7  cmdID= 37112  format=   "
		::= { iqmux47CmdEntry 37112 }


	iqmux47MemoriesMemoryName8 OBJECT-TYPE
		SYNTAX		RollCallString
		MAX-ACCESS		read-only
		STATUS			current
		DESCRIPTION
				"TYPE: - Display
				 PAGE: - Memories
					Memory Name8  cmdID= 37113  format=   "
		::= { iqmux47CmdEntry 37113 }


	iqmux47MemoriesMemoryName9 OBJECT-TYPE
		SYNTAX		RollCallString
		MAX-ACCESS		read-only
		STATUS			current
		DESCRIPTION
				"TYPE: - Display
				 PAGE: - Memories
					Memory Name9  cmdID= 37114  format=   "
		::= { iqmux47CmdEntry 37114 }


	iqmux47MemoriesMemoryName10 OBJECT-TYPE
		SYNTAX		RollCallString
		MAX-ACCESS		read-only
		STATUS			current
		DESCRIPTION
				"TYPE: - Display
				 PAGE: - Memories
					Memory Name10  cmdID= 37115  format=   "
		::= { iqmux47CmdEntry 37115 }


	iqmux47MemoriesMemoryName11 OBJECT-TYPE
		SYNTAX		RollCallString
		MAX-ACCESS		read-only
		STATUS			current
		DESCRIPTION
				"TYPE: - Display
				 PAGE: - Memories
					Memory Name11  cmdID= 37116  format=   "
		::= { iqmux47CmdEntry 37116 }


	iqmux47MemoriesMemoryName12 OBJECT-TYPE
		SYNTAX		RollCallString
		MAX-ACCESS		read-only
		STATUS			current
		DESCRIPTION
				"TYPE: - Display
				 PAGE: - Memories
					Memory Name12  cmdID= 37117  format=   "
		::= { iqmux47CmdEntry 37117 }


	iqmux47MemoriesMemoryName13 OBJECT-TYPE
		SYNTAX		RollCallString
		MAX-ACCESS		read-only
		STATUS			current
		DESCRIPTION
				"TYPE: - Display
				 PAGE: - Memories
					Memory Name13  cmdID= 37118  format=   "
		::= { iqmux47CmdEntry 37118 }


	iqmux47MemoriesMemoryName14 OBJECT-TYPE
		SYNTAX		RollCallString
		MAX-ACCESS		read-only
		STATUS			current
		DESCRIPTION
				"TYPE: - Display
				 PAGE: - Memories
					Memory Name14  cmdID= 37119  format=   "
		::= { iqmux47CmdEntry 37119 }


	iqmux47MemoriesMemoryName15 OBJECT-TYPE
		SYNTAX		RollCallString
		MAX-ACCESS		read-only
		STATUS			current
		DESCRIPTION
				"TYPE: - Display
				 PAGE: - Memories
					Memory Name15  cmdID= 37120  format=   "
		::= { iqmux47CmdEntry 37120 }


	iqmux47MemoriesMemoryName16 OBJECT-TYPE
		SYNTAX		RollCallString
		MAX-ACCESS		read-only
		STATUS			current
		DESCRIPTION
				"TYPE: - Display
				 PAGE: - Memories
					Memory Name16  cmdID= 37121  format=   "
		::= { iqmux47CmdEntry 37121 }





	iqmux47LoggingVideoLogInput1Type OBJECT-TYPE
		SYNTAX		INTEGER { disable(0), enable(1) }
		MAX-ACCESS		read-write
		STATUS			current
		DESCRIPTION
				"TYPE: - Checkbox
				 PAGE: - RollCall- Logging
					Log Input 1 Type  cmdID= 35017 "
		::= { iqmux47CmdEntry 35017 }


	iqmux47LoggingVideoInput1Type OBJECT-TYPE
		SYNTAX		RollCallString
		MAX-ACCESS		read-only
		STATUS			current
		DESCRIPTION
				"TYPE: - Display
				 PAGE: - RollCall- Logging
					Input 1 Type=  cmdID= 36017  format=   "
		::= { iqmux47CmdEntry 36017 }


	iqmux47LoggingVideoLogInput1Status OBJECT-TYPE
		SYNTAX		INTEGER { disable(0), enable(1) }
		MAX-ACCESS		read-write
		STATUS			current
		DESCRIPTION
				"TYPE: - Checkbox
				 PAGE: - RollCall- Logging
					Log Input 1 Status  cmdID= 35005 "
		::= { iqmux47CmdEntry 35005 }


	iqmux47LoggingVideoInput1Status OBJECT-TYPE
		SYNTAX		RollCallString
		MAX-ACCESS		read-only
		STATUS			current
		DESCRIPTION
				"TYPE: - Display
				 PAGE: - RollCall- Logging
					Input 1 Status=  cmdID= 36005  format=   "
		::= { iqmux47CmdEntry 36005 }


	iqmux47LoggingVideoLogInput1Std OBJECT-TYPE
		SYNTAX		INTEGER { disable(0), enable(1) }
		MAX-ACCESS		read-write
		STATUS			current
		DESCRIPTION
				"TYPE: - Checkbox
				 PAGE: - RollCall- Logging
					Log Input 1 Std.  cmdID= 35016 "
		::= { iqmux47CmdEntry 35016 }


	iqmux47LoggingVideoInput1Std OBJECT-TYPE
		SYNTAX		RollCallString
		MAX-ACCESS		read-only
		STATUS			current
		DESCRIPTION
				"TYPE: - Display
				 PAGE: - RollCall- Logging
					Input 1 Std.=  cmdID= 36016  format=   "
		::= { iqmux47CmdEntry 36016 }


	iqmux47LoggingVideoLogInput1Errors OBJECT-TYPE
		SYNTAX		INTEGER { disable(0), enable(1) }
		MAX-ACCESS		read-write
		STATUS			current
		DESCRIPTION
				"TYPE: - Checkbox
				 PAGE: - RollCall- Logging
					Log Input 1 Errors  cmdID= 35002 "
		::= { iqmux47CmdEntry 35002 }


	iqmux47LoggingVideoInput1Errors OBJECT-TYPE
		SYNTAX		RollCallString
		MAX-ACCESS		read-only
		STATUS			current
		DESCRIPTION
				"TYPE: - Display
				 PAGE: - RollCall- Logging
					Input 1 Errors=  cmdID= 36002  format=   "
		::= { iqmux47CmdEntry 36002 }


	iqmux47LoggingVideoLogInput1ErrSecs OBJECT-TYPE
		SYNTAX		INTEGER { disable(0), enable(1) }
		MAX-ACCESS		read-write
		STATUS			current
		DESCRIPTION
				"TYPE: - Checkbox
				 PAGE: - RollCall- Logging
					Log Input 1 ErrSecs  cmdID= 35003 "
		::= { iqmux47CmdEntry 35003 }


	iqmux47LoggingVideoInput1ErrSecs OBJECT-TYPE
		SYNTAX		RollCallString
		MAX-ACCESS		read-only
		STATUS			current
		DESCRIPTION
				"TYPE: - Display
				 PAGE: - RollCall- Logging
					Input 1 ErrSecs=  cmdID= 36003  format=   "
		::= { iqmux47CmdEntry 36003 }


	iqmux47LoggingVideoLogInput1ANCErr35000 OBJECT-TYPE
		SYNTAX		INTEGER { disable(0), enable(1) }
		MAX-ACCESS		read-write
		STATUS			current
		DESCRIPTION
				"TYPE: - Checkbox
				 PAGE: - RollCall- Logging
					Log Input 1 ANC Err  cmdID= 35000 "
		::= { iqmux47CmdEntry 35000 }


	iqmux47LoggingVideoInput1ANCErrors OBJECT-TYPE
		SYNTAX		RollCallString
		MAX-ACCESS		read-only
		STATUS			current
		DESCRIPTION
				"TYPE: - Display
				 PAGE: - RollCall- Logging
					Input 1 ANC Errors=  cmdID= 36000  format=   "
		::= { iqmux47CmdEntry 36000 }


	iqmux47LoggingVideoLogInput1ANCErr35001 OBJECT-TYPE
		SYNTAX		INTEGER { disable(0), enable(1) }
		MAX-ACCESS		read-write
		STATUS			current
		DESCRIPTION
				"TYPE: - Checkbox
				 PAGE: - RollCall- Logging
					Log Input 1 ANC Err  cmdID= 35001 "
		::= { iqmux47CmdEntry 35001 }


	iqmux47LoggingVideoInput1ANCErrSecs OBJECT-TYPE
		SYNTAX		RollCallString
		MAX-ACCESS		read-only
		STATUS			current
		DESCRIPTION
				"TYPE: - Display
				 PAGE: - RollCall- Logging
					Input 1 ANC ErrSecs  cmdID= 36001  format=   "
		::= { iqmux47CmdEntry 36001 }


	iqmux47LoggingVideoLogOutputState OBJECT-TYPE
		SYNTAX		INTEGER { disable(0), enable(1) }
		MAX-ACCESS		read-write
		STATUS			current
		DESCRIPTION
				"TYPE: - Checkbox
				 PAGE: - RollCall- Logging
					Log Output State  cmdID= 35941 "
		::= { iqmux47CmdEntry 35941 }


	iqmux47LoggingVideoOutputState OBJECT-TYPE
		SYNTAX		RollCallString
		MAX-ACCESS		read-only
		STATUS			current
		DESCRIPTION
				"TYPE: - Display
				 PAGE: - RollCall- Logging
					Output State=  cmdID= 36941  format=   "
		::= { iqmux47CmdEntry 36941 }


	iqmux47LoggingVideoLogOutputType OBJECT-TYPE
		SYNTAX		INTEGER { disable(0), enable(1) }
		MAX-ACCESS		read-write
		STATUS			current
		DESCRIPTION
				"TYPE: - Checkbox
				 PAGE: - RollCall- Logging
					Log Output Type  cmdID= 35942 "
		::= { iqmux47CmdEntry 35942 }


	iqmux47LoggingVideoOutputType OBJECT-TYPE
		SYNTAX		RollCallString
		MAX-ACCESS		read-only
		STATUS			current
		DESCRIPTION
				"TYPE: - Display
				 PAGE: - RollCall- Logging
					Output Type=  cmdID= 36942  format=   "
		::= { iqmux47CmdEntry 36942 }


	iqmux47LoggingVideoLogOutputStandard OBJECT-TYPE
		SYNTAX		INTEGER { disable(0), enable(1) }
		MAX-ACCESS		read-write
		STATUS			current
		DESCRIPTION
				"TYPE: - Checkbox
				 PAGE: - RollCall- Logging
					Log Output Standard  cmdID= 35940 "
		::= { iqmux47CmdEntry 35940 }


	iqmux47LoggingVideoOutputStandard OBJECT-TYPE
		SYNTAX		RollCallString
		MAX-ACCESS		read-only
		STATUS			current
		DESCRIPTION
				"TYPE: - Display
				 PAGE: - RollCall- Logging
					Output Standard=  cmdID= 36940  format=   "
		::= { iqmux47CmdEntry 36940 }


	iqmux47LoggingVideoLogoutputANCstat OBJECT-TYPE
		SYNTAX		INTEGER { disable(0), enable(1) }
		MAX-ACCESS		read-write
		STATUS			current
		DESCRIPTION
				"TYPE: - Checkbox
				 PAGE: - RollCall- Logging
					Log output ANC stat  cmdID= 35946 "
		::= { iqmux47CmdEntry 35946 }


	iqmux47LoggingVideoOutputANCstate OBJECT-TYPE
		SYNTAX		RollCallString
		MAX-ACCESS		read-only
		STATUS			current
		DESCRIPTION
				"TYPE: - Display
				 PAGE: - RollCall- Logging
					Output ANC state=  cmdID= 36946  format=   "
		::= { iqmux47CmdEntry 36946 }


	iqmux47LoggingEmbedAudioLogInp1Emb1stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 stat  cmdID= 35006 "
		::= { iqmux47CmdEntry 35006 }


	iqmux47LoggingEmbedAudioInp1Emb1state OBJECT-TYPE
		SYNTAX		RollCallString
		MAX-ACCESS		read-only
		STATUS			current
		DESCRIPTION
				"TYPE: - Display
				 PAGE: - RollCall- Logging- Emb.Aud Logging
					Inp1 Emb.1 state=  cmdID= 36006  format=   "
		::= { iqmux47CmdEntry 36006 }


	iqmux47LoggingEmbedAudioLogInp1Emb2stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 stat  cmdID= 35007 "
		::= { iqmux47CmdEntry 35007 }


	iqmux47LoggingEmbedAudioInp1Emb2state OBJECT-TYPE
		SYNTAX		RollCallString
		MAX-ACCESS		read-only
		STATUS			current
		DESCRIPTION
				"TYPE: - Display
				 PAGE: - RollCall- Logging- Emb.Aud Logging
					Inp1 Emb.2 state=  cmdID= 36007  format=   "
		::= { iqmux47CmdEntry 36007 }


	iqmux47LoggingEmbedAudioLogInp1Emb3stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 stat  cmdID= 35008 "
		::= { iqmux47CmdEntry 35008 }


	iqmux47LoggingEmbedAudioInp1Emb3state OBJECT-TYPE
		SYNTAX		RollCallString
		MAX-ACCESS		read-only
		STATUS			current
		DESCRIPTION
				"TYPE: - Display
				 PAGE: - RollCall- Logging- Emb.Aud Logging
					Inp1 Emb.3 state=  cmdID= 36008  format=   "
		::= { iqmux47CmdEntry 36008 }


	iqmux47LoggingEmbedAudioLogInp1Emb4stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 stat  cmdID= 35009 "
		::= { iqmux47CmdEntry 35009 }


	iqmux47LoggingEmbedAudioInp1Emb4state OBJECT-TYPE
		SYNTAX		RollCallString
		MAX-ACCESS		read-only
		STATUS			current
		DESCRIPTION
				"TYPE: - Display
				 PAGE: - RollCall- Logging- Emb.Aud Logging
					Inp1 Emb.4 state=  cmdID= 36009  format=   "
		::= { iqmux47CmdEntry 36009 }


	iqmux47LoggingEmbedAudioLogInp1Emb5stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 stat  cmdID= 35010 "
		::= { iqmux47CmdEntry 35010 }


	iqmux47LoggingEmbedAudioInp1Emb5state OBJECT-TYPE
		SYNTAX		RollCallString
		MAX-ACCESS		read-only
		STATUS			current
		DESCRIPTION
				"TYPE: - Display
				 PAGE: - RollCall- Logging- Emb.Aud Logging
					Inp1 Emb.5 state=  cmdID= 36010  format=   "
		::= { iqmux47CmdEntry 36010 }


	iqmux47LoggingEmbedAudioLogInp1Emb6stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 stat  cmdID= 35011 "
		::= { iqmux47CmdEntry 35011 }


	iqmux47LoggingEmbedAudioInp1Emb6state OBJECT-TYPE
		SYNTAX		RollCallString
		MAX-ACCESS		read-only
		STATUS			current
		DESCRIPTION
				"TYPE: - Display
				 PAGE: - RollCall- Logging- Emb.Aud Logging
					Inp1 Emb.6 state=  cmdID= 36011  format=   "
		::= { iqmux47CmdEntry 36011 }


	iqmux47LoggingEmbedAudioLogInp1Emb7stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 stat  cmdID= 35012 "
		::= { iqmux47CmdEntry 35012 }


	iqmux47LoggingEmbedAudioInp1Emb7state OBJECT-TYPE
		SYNTAX		RollCallString
		MAX-ACCESS		read-only
		STATUS			current
		DESCRIPTION
				"TYPE: - Display
				 PAGE: - RollCall- Logging- Emb.Aud Logging
					Inp1 Emb.7 state=  cmdID= 36012  format=   "
		::= { iqmux47CmdEntry 36012 }


	iqmux47LoggingEmbedAudioLogInp1Emb8stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 stat  cmdID= 35013 "
		::= { iqmux47CmdEntry 35013 }


	iqmux47LoggingEmbedAudioInp1Emb8state OBJECT-TYPE
		SYNTAX		RollCallString
		MAX-ACCESS		read-only
		STATUS			current
		DESCRIPTION
				"TYPE: - Display
				 PAGE: - RollCall- Logging- Emb.Aud Logging
					Inp1 Emb.8 state=  cmdID= 36013  format=   "
		::= { iqmux47CmdEntry 36013 }


	iqmux47LoggingEmbedAudioLogInp1Emb1type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 type  cmdID= 35018 "
		::= { iqmux47CmdEntry 35018 }


	iqmux47LoggingEmbedAudioInp1Emb1type OBJECT-TYPE
		SYNTAX		RollCallString
		MAX-ACCESS		read-only
		STATUS			current
		DESCRIPTION
				"TYPE: - Display
				 PAGE: - RollCall- Logging- Emb.Aud Logging
					Inp1 Emb.1 type=  cmdID= 36018  format=   "
		::= { iqmux47CmdEntry 36018 }


	iqmux47LoggingEmbedAudioLogInp1Emb2type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 type  cmdID= 35019 "
		::= { iqmux47CmdEntry 35019 }


	iqmux47LoggingEmbedAudioInp1Emb2type OBJECT-TYPE
		SYNTAX		RollCallString
		MAX-ACCESS		read-only
		STATUS			current
		DESCRIPTION
				"TYPE: - Display
				 PAGE: - RollCall- Logging- Emb.Aud Logging
					Inp1 Emb.2 type=  cmdID= 36019  format=   "
		::= { iqmux47CmdEntry 36019 }


	iqmux47LoggingEmbedAudioLogInp1Emb3type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 type  cmdID= 35020 "
		::= { iqmux47CmdEntry 35020 }


	iqmux47LoggingEmbedAudioInp1Emb3type OBJECT-TYPE
		SYNTAX		RollCallString
		MAX-ACCESS		read-only
		STATUS			current
		DESCRIPTION
				"TYPE: - Display
				 PAGE: - RollCall- Logging- Emb.Aud Logging
					Inp1 Emb.3 type=  cmdID= 36020  format=   "
		::= { iqmux47CmdEntry 36020 }


	iqmux47LoggingEmbedAudioLogInp1Emb4type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 type  cmdID= 35021 "
		::= { iqmux47CmdEntry 35021 }


	iqmux47LoggingEmbedAudioInp1Emb4type OBJECT-TYPE
		SYNTAX		RollCallString
		MAX-ACCESS		read-only
		STATUS			current
		DESCRIPTION
				"TYPE: - Display
				 PAGE: - RollCall- Logging- Emb.Aud Logging
					Inp1 Emb.4 type=  cmdID= 36021  format=   "
		::= { iqmux47CmdEntry 36021 }


	iqmux47LoggingEmbedAudioLogInp1Emb5type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 type  cmdID= 35022 "
		::= { iqmux47CmdEntry 35022 }


	iqmux47LoggingEmbedAudioInp1Emb5type OBJECT-TYPE
		SYNTAX		RollCallString
		MAX-ACCESS		read-only
		STATUS			current
		DESCRIPTION
				"TYPE: - Display
				 PAGE: - RollCall- Logging- Emb.Aud Logging
					Inp1 Emb.5 type=  cmdID= 36022  format=   "
		::= { iqmux47CmdEntry 36022 }


	iqmux47LoggingEmbedAudioLogInp1Emb6type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 type  cmdID= 35023 "
		::= { iqmux47CmdEntry 35023 }


	iqmux47LoggingEmbedAudioInp1Emb6type OBJECT-TYPE
		SYNTAX		RollCallString
		MAX-ACCESS		read-only
		STATUS			current
		DESCRIPTION
				"TYPE: - Display
				 PAGE: - RollCall- Logging- Emb.Aud Logging
					Inp1 Emb.6 type=  cmdID= 36023  format=   "
		::= { iqmux47CmdEntry 36023 }


	iqmux47LoggingEmbedAudioLogInp1Emb7type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 type  cmdID= 35024 "
		::= { iqmux47CmdEntry 35024 }


	iqmux47LoggingEmbedAudioInp1Emb7type OBJECT-TYPE
		SYNTAX		RollCallString
		MAX-ACCESS		read-only
		STATUS			current
		DESCRIPTION
				"TYPE: - Display
				 PAGE: - RollCall- Logging- Emb.Aud Logging
					Inp1 Emb.7 type=  cmdID= 36024  format=   "
		::= { iqmux47CmdEntry 36024 }


	iqmux47LoggingEmbedAudioLogInp1Emb8type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 type  cmdID= 35025 "
		::= { iqmux47CmdEntry 35025 }


	iqmux47LoggingEmbedAudioInp1Emb8type OBJECT-TYPE
		SYNTAX		RollCallString
		MAX-ACCESS		read-only
		STATUS			current
		DESCRIPTION
				"TYPE: - Display
				 PAGE: - RollCall- Logging- Emb.Aud Logging
					Inp1 Emb.8 type=  cmdID= 36025  format=   "
		::= { iqmux47CmdEntry 36025 }


	iqmux47LoggingOPAudioLogOutEmb1state OBJECT-TYPE
		SYNTAX		INTEGER { disable(0), enable(1) }
		MAX-ACCESS		read-write
		STATUS			current
		DESCRIPTION
				"TYPE: - Checkbox
				 PAGE: - RollCall- Logging
					Log Out Emb.1 state  cmdID= 35920 "
		::= { iqmux47CmdEntry 35920 }


	iqmux47LoggingOPAudioOutEmb1state OBJECT-TYPE
		SYNTAX		RollCallString
		MAX-ACCESS		read-only
		STATUS			current
		DESCRIPTION
				"TYPE: - Display
				 PAGE: - RollCall- Logging
					Out Emb.1 state=  cmdID= 36920  format=   "
		::= { iqmux47CmdEntry 36920 }


	iqmux47LoggingOPAudioLogOutEmb2state OBJECT-TYPE
		SYNTAX		INTEGER { disable(0), enable(1) }
		MAX-ACCESS		read-write
		STATUS			current
		DESCRIPTION
				"TYPE: - Checkbox
				 PAGE: - RollCall- Logging
					Log Out Emb.2 state  cmdID= 35921 "
		::= { iqmux47CmdEntry 35921 }


	iqmux47LoggingOPAudioOutEmb2state OBJECT-TYPE
		SYNTAX		RollCallString
		MAX-ACCESS		read-only
		STATUS			current
		DESCRIPTION
				"TYPE: - Display
				 PAGE: - RollCall- Logging
					Out Emb.2 state=  cmdID= 36921  format=   "
		::= { iqmux47CmdEntry 36921 }


	iqmux47LoggingOPAudioLogOutEmb3state OBJECT-TYPE
		SYNTAX		INTEGER { disable(0), enable(1) }
		MAX-ACCESS		read-write
		STATUS			current
		DESCRIPTION
				"TYPE: - Checkbox
				 PAGE: - RollCall- Logging
					Log Out Emb.3 state  cmdID= 35922 "
		::= { iqmux47CmdEntry 35922 }


	iqmux47LoggingOPAudioOutEmb3state OBJECT-TYPE
		SYNTAX		RollCallString
		MAX-ACCESS		read-only
		STATUS			current
		DESCRIPTION
				"TYPE: - Display
				 PAGE: - RollCall- Logging
					Out Emb.3 state=  cmdID= 36922  format=   "
		::= { iqmux47CmdEntry 36922 }


	iqmux47LoggingOPAudioLogOutEmb4state OBJECT-TYPE
		SYNTAX		INTEGER { disable(0), enable(1) }
		MAX-ACCESS		read-write
		STATUS			current
		DESCRIPTION
				"TYPE: - Checkbox
				 PAGE: - RollCall- Logging
					Log Out Emb.4 state  cmdID= 35923 "
		::= { iqmux47CmdEntry 35923 }


	iqmux47LoggingOPAudioOutEmb4state OBJECT-TYPE
		SYNTAX		RollCallString
		MAX-ACCESS		read-only
		STATUS			current
		DESCRIPTION
				"TYPE: - Display
				 PAGE: - RollCall- Logging
					Out Emb.4 state=  cmdID= 36923  format=   "
		::= { iqmux47CmdEntry 36923 }


	iqmux47LoggingOPAudioLogOutEmb5state OBJECT-TYPE
		SYNTAX		INTEGER { disable(0), enable(1) }
		MAX-ACCESS		read-write
		STATUS			current
		DESCRIPTION
				"TYPE: - Checkbox
				 PAGE: - RollCall- Logging
					Log Out Emb.5 state  cmdID= 35924 "
		::= { iqmux47CmdEntry 35924 }


	iqmux47LoggingOPAudioOutEmb5state OBJECT-TYPE
		SYNTAX		RollCallString
		MAX-ACCESS		read-only
		STATUS			current
		DESCRIPTION
				"TYPE: - Display
				 PAGE: - RollCall- Logging
					Out Emb.5 state=  cmdID= 36924  format=   "
		::= { iqmux47CmdEntry 36924 }


	iqmux47LoggingOPAudioLogOutEmb6state OBJECT-TYPE
		SYNTAX		INTEGER { disable(0), enable(1) }
		MAX-ACCESS		read-write
		STATUS			current
		DESCRIPTION
				"TYPE: - Checkbox
				 PAGE: - RollCall- Logging
					Log Out Emb.6 state  cmdID= 35925 "
		::= { iqmux47CmdEntry 35925 }


	iqmux47LoggingOPAudioOutEmb6state OBJECT-TYPE
		SYNTAX		RollCallString
		MAX-ACCESS		read-only
		STATUS			current
		DESCRIPTION
				"TYPE: - Display
				 PAGE: - RollCall- Logging
					Out Emb.6 state=  cmdID= 36925  format=   "
		::= { iqmux47CmdEntry 36925 }


	iqmux47LoggingOPAudioLogOutEmb7state OBJECT-TYPE
		SYNTAX		INTEGER { disable(0), enable(1) }
		MAX-ACCESS		read-write
		STATUS			current
		DESCRIPTION
				"TYPE: - Checkbox
				 PAGE: - RollCall- Logging
					Log Out Emb.7 state  cmdID= 35926 "
		::= { iqmux47CmdEntry 35926 }


	iqmux47LoggingOPAudioOutEmb7state OBJECT-TYPE
		SYNTAX		RollCallString
		MAX-ACCESS		read-only
		STATUS			current
		DESCRIPTION
				"TYPE: - Display
				 PAGE: - RollCall- Logging
					Out Emb.7 state=  cmdID= 36926  format=   "
		::= { iqmux47CmdEntry 36926 }


	iqmux47LoggingOPAudioLogOutEmb8state OBJECT-TYPE
		SYNTAX		INTEGER { disable(0), enable(1) }
		MAX-ACCESS		read-write
		STATUS			current
		DESCRIPTION
				"TYPE: - Checkbox
				 PAGE: - RollCall- Logging
					Log Out Emb.8 state  cmdID= 35927 "
		::= { iqmux47CmdEntry 35927 }


	iqmux47LoggingOPAudioOutEmb8state OBJECT-TYPE
		SYNTAX		RollCallString
		MAX-ACCESS		read-only
		STATUS			current
		DESCRIPTION
				"TYPE: - Display
				 PAGE: - RollCall- Logging
					Out Emb.8 state=  cmdID= 36927  format=   "
		::= { iqmux47CmdEntry 36927 }


	iqmux47LoggingOPAudioLogOutEmb1type OBJECT-TYPE
		SYNTAX		INTEGER { disable(0), enable(1) }
		MAX-ACCESS		read-write
		STATUS			current
		DESCRIPTION
				"TYPE: - Checkbox
				 PAGE: - RollCall- Logging
					Log Out Emb.1 type  cmdID= 35930 "
		::= { iqmux47CmdEntry 35930 }


	iqmux47LoggingOPAudioOutEmb1type OBJECT-TYPE
		SYNTAX		RollCallString
		MAX-ACCESS		read-only
		STATUS			current
		DESCRIPTION
				"TYPE: - Display
				 PAGE: - RollCall- Logging
					Out Emb.1 type=  cmdID= 36930  format=   "
		::= { iqmux47CmdEntry 36930 }


	iqmux47LoggingOPAudioLogOutEmb2type OBJECT-TYPE
		SYNTAX		INTEGER { disable(0), enable(1) }
		MAX-ACCESS		read-write
		STATUS			current
		DESCRIPTION
				"TYPE: - Checkbox
				 PAGE: - RollCall- Logging
					Log Out Emb.2 type  cmdID= 35931 "
		::= { iqmux47CmdEntry 35931 }


	iqmux47LoggingOPAudioOutEmb2type OBJECT-TYPE
		SYNTAX		RollCallString
		MAX-ACCESS		read-only
		STATUS			current
		DESCRIPTION
				"TYPE: - Display
				 PAGE: - RollCall- Logging
					Out Emb.2 type=  cmdID= 36931  format=   "
		::= { iqmux47CmdEntry 36931 }


	iqmux47LoggingOPAudioLogOutEmb3type OBJECT-TYPE
		SYNTAX		INTEGER { disable(0), enable(1) }
		MAX-ACCESS		read-write
		STATUS			current
		DESCRIPTION
				"TYPE: - Checkbox
				 PAGE: - RollCall- Logging
					Log Out Emb.3 type  cmdID= 35932 "
		::= { iqmux47CmdEntry 35932 }


	iqmux47LoggingOPAudioOutEmb3type OBJECT-TYPE
		SYNTAX		RollCallString
		MAX-ACCESS		read-only
		STATUS			current
		DESCRIPTION
				"TYPE: - Display
				 PAGE: - RollCall- Logging
					Out Emb.3 type=  cmdID= 36932  format=   "
		::= { iqmux47CmdEntry 36932 }


	iqmux47LoggingOPAudioLogOutEmb4type OBJECT-TYPE
		SYNTAX		INTEGER { disable(0), enable(1) }
		MAX-ACCESS		read-write
		STATUS			current
		DESCRIPTION
				"TYPE: - Checkbox
				 PAGE: - RollCall- Logging
					Log Out Emb.4 type  cmdID= 35933 "
		::= { iqmux47CmdEntry 35933 }


	iqmux47LoggingOPAudioOutEmb4type OBJECT-TYPE
		SYNTAX		RollCallString
		MAX-ACCESS		read-only
		STATUS			current
		DESCRIPTION
				"TYPE: - Display
				 PAGE: - RollCall- Logging
					Out Emb.4 type=  cmdID= 36933  format=   "
		::= { iqmux47CmdEntry 36933 }


	iqmux47LoggingOPAudioLogOutEmb5type OBJECT-TYPE
		SYNTAX		INTEGER { disable(0), enable(1) }
		MAX-ACCESS		read-write
		STATUS			current
		DESCRIPTION
				"TYPE: - Checkbox
				 PAGE: - RollCall- Logging
					Log Out Emb.5 type  cmdID= 35934 "
		::= { iqmux47CmdEntry 35934 }


	iqmux47LoggingOPAudioOutEmb5type OBJECT-TYPE
		SYNTAX		RollCallString
		MAX-ACCESS		read-only
		STATUS			current
		DESCRIPTION
				"TYPE: - Display
				 PAGE: - RollCall- Logging
					Out Emb.5 type=  cmdID= 36934  format=   "
		::= { iqmux47CmdEntry 36934 }


	iqmux47LoggingOPAudioLogOutEmb6type OBJECT-TYPE
		SYNTAX		INTEGER { disable(0), enable(1) }
		MAX-ACCESS		read-write
		STATUS			current
		DESCRIPTION
				"TYPE: - Checkbox
				 PAGE: - RollCall- Logging
					Log Out Emb.6 type  cmdID= 35935 "
		::= { iqmux47CmdEntry 35935 }


	iqmux47LoggingOPAudioOutEmb6type OBJECT-TYPE
		SYNTAX		RollCallString
		MAX-ACCESS		read-only
		STATUS			current
		DESCRIPTION
				"TYPE: - Display
				 PAGE: - RollCall- Logging
					Out Emb.6 type=  cmdID= 36935  format=   "
		::= { iqmux47CmdEntry 36935 }


	iqmux47LoggingOPAudioLogOutEmb7type OBJECT-TYPE
		SYNTAX		INTEGER { disable(0), enable(1) }
		MAX-ACCESS		read-write
		STATUS			current
		DESCRIPTION
				"TYPE: - Checkbox
				 PAGE: - RollCall- Logging
					Log Out Emb.7 type  cmdID= 35936 "
		::= { iqmux47CmdEntry 35936 }


	iqmux47LoggingOPAudioOutEmb7type OBJECT-TYPE
		SYNTAX		RollCallString
		MAX-ACCESS		read-only
		STATUS			current
		DESCRIPTION
				"TYPE: - Display
				 PAGE: - RollCall- Logging
					Out Emb.7 type=  cmdID= 36936  format=   "
		::= { iqmux47CmdEntry 36936 }


	iqmux47LoggingOPAudioLogOutEmb8type OBJECT-TYPE
		SYNTAX		INTEGER { disable(0), enable(1) }
		MAX-ACCESS		read-write
		STATUS			current
		DESCRIPTION
				"TYPE: - Checkbox
				 PAGE: - RollCall- Logging
					Log Out Emb.8 type  cmdID= 35937 "
		::= { iqmux47CmdEntry 35937 }


	iqmux47LoggingOPAudioOutEmb8type OBJECT-TYPE
		SYNTAX		RollCallString
		MAX-ACCESS		read-only
		STATUS			current
		DESCRIPTION
				"TYPE: - Display
				 PAGE: - RollCall- Logging
					Out Emb.8 type=  cmdID= 36937  format=   "
		::= { iqmux47CmdEntry 36937 }


	iqmux47LoggingOPAudioLevelLogOutEmb1LLev OBJECT-TYPE
		SYNTAX		INTEGER { disable(0), enable(1) }
		MAX-ACCESS		read-write
		STATUS			current
		DESCRIPTION
				"TYPE: - Checkbox
				 PAGE: - RollCall- Logging
					Log Out Emb.1-L Lev  cmdID= 35900 "
		::= { iqmux47CmdEntry 35900 }


	iqmux47LoggingOPAudioLevelOutEmb1LLevel OBJECT-TYPE
		SYNTAX		RollCallString
		MAX-ACCESS		read-only
		STATUS			current
		DESCRIPTION
				"TYPE: - Display
				 PAGE: - RollCall- Logging
					Out Emb.1-L Level=  cmdID= 36900  format=   "
		::= { iqmux47CmdEntry 36900 }


	iqmux47LoggingOPAudioLevelLogOutEmb1RLev OBJECT-TYPE
		SYNTAX		INTEGER { disable(0), enable(1) }
		MAX-ACCESS		read-write
		STATUS			current
		DESCRIPTION
				"TYPE: - Checkbox
				 PAGE: - RollCall- Logging
					Log Out Emb.1-R Lev  cmdID= 35901 "
		::= { iqmux47CmdEntry 35901 }


	iqmux47LoggingOPAudioLevelOutEmb1RLevel OBJECT-TYPE
		SYNTAX		RollCallString
		MAX-ACCESS		read-only
		STATUS			current
		DESCRIPTION
				"TYPE: - Display
				 PAGE: - RollCall- Logging
					Out Emb.1-R Level=  cmdID= 36901  format=   "
		::= { iqmux47CmdEntry 36901 }


	iqmux47LoggingOPAudioLevelLogOutEmb2LLev OBJECT-TYPE
		SYNTAX		INTEGER { disable(0), enable(1) }
		MAX-ACCESS		read-write
		STATUS			current
		DESCRIPTION
				"TYPE: - Checkbox
				 PAGE: - RollCall- Logging
					Log Out Emb.2-L Lev  cmdID= 35902 "
		::= { iqmux47CmdEntry 35902 }


	iqmux47LoggingOPAudioLevelOutEmb2LLevel OBJECT-TYPE
		SYNTAX		RollCallString
		MAX-ACCESS		read-only
		STATUS			current
		DESCRIPTION
				"TYPE: - Display
				 PAGE: - RollCall- Logging
					Out Emb.2-L Level=  cmdID= 36902  format=   "
		::= { iqmux47CmdEntry 36902 }


	iqmux47LoggingOPAudioLevelLogOutEmb2RLev OBJECT-TYPE
		SYNTAX		INTEGER { disable(0), enable(1) }
		MAX-ACCESS		read-write
		STATUS			current
		DESCRIPTION
				"TYPE: - Checkbox
				 PAGE: - RollCall- Logging
					Log Out Emb.2-R Lev  cmdID= 35903 "
		::= { iqmux47CmdEntry 35903 }


	iqmux47LoggingOPAudioLevelOutEmb2RLevel OBJECT-TYPE
		SYNTAX		RollCallString
		MAX-ACCESS		read-only
		STATUS			current
		DESCRIPTION
				"TYPE: - Display
				 PAGE: - RollCall- Logging
					Out Emb.2-R Level=  cmdID= 36903  format=   "
		::= { iqmux47CmdEntry 36903 }


	iqmux47LoggingOPAudioLevelLogOutEmb3LLev OBJECT-TYPE
		SYNTAX		INTEGER { disable(0), enable(1) }
		MAX-ACCESS		read-write
		STATUS			current
		DESCRIPTION
				"TYPE: - Checkbox
				 PAGE: - RollCall- Logging
					Log Out Emb.3-L Lev  cmdID= 35904 "
		::= { iqmux47CmdEntry 35904 }


	iqmux47LoggingOPAudioLevelOutEmb3LLevel OBJECT-TYPE
		SYNTAX		RollCallString
		MAX-ACCESS		read-only
		STATUS			current
		DESCRIPTION
				"TYPE: - Display
				 PAGE: - RollCall- Logging
					Out Emb.3-L Level=  cmdID= 36904  format=   "
		::= { iqmux47CmdEntry 36904 }


	iqmux47LoggingOPAudioLevelLogOutEmb3RLev OBJECT-TYPE
		SYNTAX		INTEGER { disable(0), enable(1) }
		MAX-ACCESS		read-write
		STATUS			current
		DESCRIPTION
				"TYPE: - Checkbox
				 PAGE: - RollCall- Logging
					Log Out Emb.3-R Lev  cmdID= 35905 "
		::= { iqmux47CmdEntry 35905 }


	iqmux47LoggingOPAudioLevelOutEmb3RLevel OBJECT-TYPE
		SYNTAX		RollCallString
		MAX-ACCESS		read-only
		STATUS			current
		DESCRIPTION
				"TYPE: - Display
				 PAGE: - RollCall- Logging
					Out Emb.3-R Level=  cmdID= 36905  format=   "
		::= { iqmux47CmdEntry 36905 }


	iqmux47LoggingOPAudioLevelLogOutEmb4LLev OBJECT-TYPE
		SYNTAX		INTEGER { disable(0), enable(1) }
		MAX-ACCESS		read-write
		STATUS			current
		DESCRIPTION
				"TYPE: - Checkbox
				 PAGE: - RollCall- Logging
					Log Out Emb.4-L Lev  cmdID= 35906 "
		::= { iqmux47CmdEntry 35906 }


	iqmux47LoggingOPAudioLevelOutEmb4LLevel OBJECT-TYPE
		SYNTAX		RollCallString
		MAX-ACCESS		read-only
		STATUS			current
		DESCRIPTION
				"TYPE: - Display
				 PAGE: - RollCall- Logging
					Out Emb.4-L Level=  cmdID= 36906  format=   "
		::= { iqmux47CmdEntry 36906 }


	iqmux47LoggingOPAudioLevelLogOutEmb4RLev OBJECT-TYPE
		SYNTAX		INTEGER { disable(0), enable(1) }
		MAX-ACCESS		read-write
		STATUS			current
		DESCRIPTION
				"TYPE: - Checkbox
				 PAGE: - RollCall- Logging
					Log Out Emb.4-R Lev  cmdID= 35907 "
		::= { iqmux47CmdEntry 35907 }


	iqmux47LoggingOPAudioLevelOutEmb4RLevel OBJECT-TYPE
		SYNTAX		RollCallString
		MAX-ACCESS		read-only
		STATUS			current
		DESCRIPTION
				"TYPE: - Display
				 PAGE: - RollCall- Logging
					Out Emb.4-R Level=  cmdID= 36907  format=   "
		::= { iqmux47CmdEntry 36907 }


	iqmux47LoggingOPAudioLevelLogOutEmb5LLev OBJECT-TYPE
		SYNTAX		INTEGER { disable(0), enable(1) }
		MAX-ACCESS		read-write
		STATUS			current
		DESCRIPTION
				"TYPE: - Checkbox
				 PAGE: - RollCall- Logging
					Log Out Emb.5-L Lev  cmdID= 35908 "
		::= { iqmux47CmdEntry 35908 }


	iqmux47LoggingOPAudioLevelOutEmb5LLevel OBJECT-TYPE
		SYNTAX		RollCallString
		MAX-ACCESS		read-only
		STATUS			current
		DESCRIPTION
				"TYPE: - Display
				 PAGE: - RollCall- Logging
					Out Emb.5-L Level=  cmdID= 36908  format=   "
		::= { iqmux47CmdEntry 36908 }


	iqmux47LoggingOPAudioLevelLogOutEmb5RLev OBJECT-TYPE
		SYNTAX		INTEGER { disable(0), enable(1) }
		MAX-ACCESS		read-write
		STATUS			current
		DESCRIPTION
				"TYPE: - Checkbox
				 PAGE: - RollCall- Logging
					Log Out Emb.5-R Lev  cmdID= 35909 "
		::= { iqmux47CmdEntry 35909 }


	iqmux47LoggingOPAudioLevelOutEmb5RLevel OBJECT-TYPE
		SYNTAX		RollCallString
		MAX-ACCESS		read-only
		STATUS			current
		DESCRIPTION
				"TYPE: - Display
				 PAGE: - RollCall- Logging
					Out Emb.5-R Level=  cmdID= 36909  format=   "
		::= { iqmux47CmdEntry 36909 }


	iqmux47LoggingOPAudioLevelLogOutEmb6LLev OBJECT-TYPE
		SYNTAX		INTEGER { disable(0), enable(1) }
		MAX-ACCESS		read-write
		STATUS			current
		DESCRIPTION
				"TYPE: - Checkbox
				 PAGE: - RollCall- Logging
					Log Out Emb.6-L Lev  cmdID= 35910 "
		::= { iqmux47CmdEntry 35910 }


	iqmux47LoggingOPAudioLevelOutEmb6LLevel OBJECT-TYPE
		SYNTAX		RollCallString
		MAX-ACCESS		read-only
		STATUS			current
		DESCRIPTION
				"TYPE: - Display
				 PAGE: - RollCall- Logging
					Out Emb.6-L Level=  cmdID= 36910  format=   "
		::= { iqmux47CmdEntry 36910 }


	iqmux47LoggingOPAudioLevelLogOutEmb6RLev OBJECT-TYPE
		SYNTAX		INTEGER { disable(0), enable(1) }
		MAX-ACCESS		read-write
		STATUS			current
		DESCRIPTION
				"TYPE: - Checkbox
				 PAGE: - RollCall- Logging
					Log Out Emb.6-R Lev  cmdID= 35911 "
		::= { iqmux47CmdEntry 35911 }


	iqmux47LoggingOPAudioLevelOutEmb6RLevel OBJECT-TYPE
		SYNTAX		RollCallString
		MAX-ACCESS		read-only
		STATUS			current
		DESCRIPTION
				"TYPE: - Display
				 PAGE: - RollCall- Logging
					Out Emb.6-R Level=  cmdID= 36911  format=   "
		::= { iqmux47CmdEntry 36911 }


	iqmux47LoggingOPAudioLevelLogOutEmb7LLev OBJECT-TYPE
		SYNTAX		INTEGER { disable(0), enable(1) }
		MAX-ACCESS		read-write
		STATUS			current
		DESCRIPTION
				"TYPE: - Checkbox
				 PAGE: - RollCall- Logging
					Log Out Emb.7-L Lev  cmdID= 35912 "
		::= { iqmux47CmdEntry 35912 }


	iqmux47LoggingOPAudioLevelOutEmb7LLevel OBJECT-TYPE
		SYNTAX		RollCallString
		MAX-ACCESS		read-only
		STATUS			current
		DESCRIPTION
				"TYPE: - Display
				 PAGE: - RollCall- Logging
					Out Emb.7-L Level=  cmdID= 36912  format=   "
		::= { iqmux47CmdEntry 36912 }


	iqmux47LoggingOPAudioLevelLogOutEmb7RLev OBJECT-TYPE
		SYNTAX		INTEGER { disable(0), enable(1) }
		MAX-ACCESS		read-write
		STATUS			current
		DESCRIPTION
				"TYPE: - Checkbox
				 PAGE: - RollCall- Logging
					Log Out Emb.7-R Lev  cmdID= 35913 "
		::= { iqmux47CmdEntry 35913 }


	iqmux47LoggingOPAudioLevelOutEmb7RLevel OBJECT-TYPE
		SYNTAX		RollCallString
		MAX-ACCESS		read-only
		STATUS			current
		DESCRIPTION
				"TYPE: - Display
				 PAGE: - RollCall- Logging
					Out Emb.7-R Level=  cmdID= 36913  format=   "
		::= { iqmux47CmdEntry 36913 }


	iqmux47LoggingOPAudioLevelLogOutEmb8LLev OBJECT-TYPE
		SYNTAX		INTEGER { disable(0), enable(1) }
		MAX-ACCESS		read-write
		STATUS			current
		DESCRIPTION
				"TYPE: - Checkbox
				 PAGE: - RollCall- Logging
					Log Out Emb.8-L Lev  cmdID= 35914 "
		::= { iqmux47CmdEntry 35914 }


	iqmux47LoggingOPAudioLevelOutEmb8LLevel OBJECT-TYPE
		SYNTAX		RollCallString
		MAX-ACCESS		read-only
		STATUS			current
		DESCRIPTION
				"TYPE: - Display
				 PAGE: - RollCall- Logging
					Out Emb.8-L Level=  cmdID= 36914  format=   "
		::= { iqmux47CmdEntry 36914 }


	iqmux47LoggingOPAudioLevelLogOutEmb8RLev OBJECT-TYPE
		SYNTAX		INTEGER { disable(0), enable(1) }
		MAX-ACCESS		read-write
		STATUS			current
		DESCRIPTION
				"TYPE: - Checkbox
				 PAGE: - RollCall- Logging
					Log Out Emb.8-R Lev  cmdID= 35915 "
		::= { iqmux47CmdEntry 35915 }


	iqmux47LoggingOPAudioLevelOutEmb8RLevel OBJECT-TYPE
		SYNTAX		RollCallString
		MAX-ACCESS		read-only
		STATUS			current
		DESCRIPTION
				"TYPE: - Display
				 PAGE: - RollCall- Logging
					Out Emb.8-R Level=  cmdID= 36915  format=   "
		::= { iqmux47CmdEntry 36915 }


	iqmux47LoggingOPDolbyELogEmbDolbyE1 OBJECT-TYPE
		SYNTAX		INTEGER { disable(0), enable(1) }
		MAX-ACCESS		read-write
		STATUS			current
		DESCRIPTION
				"TYPE: - Checkbox
				 PAGE: - RollCall- Logging
					Log Emb DolbyE 1  cmdID= 35950 "
		::= { iqmux47CmdEntry 35950 }


	iqmux47LoggingOPDolbyEEmbDolbyE1 OBJECT-TYPE
		SYNTAX		RollCallString
		MAX-ACCESS		read-only
		STATUS			current
		DESCRIPTION
				"TYPE: - Display
				 PAGE: - RollCall- Logging
					Emb DolbyE 1=  cmdID= 36950  format=   "
		::= { iqmux47CmdEntry 36950 }


	iqmux47LoggingOPDolbyELogEmbDolbyE2 OBJECT-TYPE
		SYNTAX		INTEGER { disable(0), enable(1) }
		MAX-ACCESS		read-write
		STATUS			current
		DESCRIPTION
				"TYPE: - Checkbox
				 PAGE: - RollCall- Logging
					Log Emb DolbyE 2  cmdID= 35951 "
		::= { iqmux47CmdEntry 35951 }


	iqmux47LoggingOPDolbyEEmbDolbyE2 OBJECT-TYPE
		SYNTAX		RollCallString
		MAX-ACCESS		read-only
		STATUS			current
		DESCRIPTION
				"TYPE: - Display
				 PAGE: - RollCall- Logging
					Emb DolbyE 2=  cmdID= 36951  format=   "
		::= { iqmux47CmdEntry 36951 }


	iqmux47LoggingOPDolbyELogEmbDolbyE3 OBJECT-TYPE
		SYNTAX		INTEGER { disable(0), enable(1) }
		MAX-ACCESS		read-write
		STATUS			current
		DESCRIPTION
				"TYPE: - Checkbox
				 PAGE: - RollCall- Logging
					Log Emb DolbyE 3  cmdID= 35952 "
		::= { iqmux47CmdEntry 35952 }


	iqmux47LoggingOPDolbyEEmbDolbyE3 OBJECT-TYPE
		SYNTAX		RollCallString
		MAX-ACCESS		read-only
		STATUS			current
		DESCRIPTION
				"TYPE: - Display
				 PAGE: - RollCall- Logging
					Emb DolbyE 3=  cmdID= 36952  format=   "
		::= { iqmux47CmdEntry 36952 }


	iqmux47LoggingOPDolbyELogEmbDolbyE4 OBJECT-TYPE
		SYNTAX		INTEGER { disable(0), enable(1) }
		MAX-ACCESS		read-write
		STATUS			current
		DESCRIPTION
				"TYPE: - Checkbox
				 PAGE: - RollCall- Logging
					Log Emb DolbyE 4  cmdID= 35953 "
		::= { iqmux47CmdEntry 35953 }


	iqmux47LoggingOPDolbyEEmbDolbyE4 OBJECT-TYPE
		SYNTAX		RollCallString
		MAX-ACCESS		read-only
		STATUS			current
		DESCRIPTION
				"TYPE: - Display
				 PAGE: - RollCall- Logging
					Emb DolbyE 4=  cmdID= 36953  format=   "
		::= { iqmux47CmdEntry 36953 }


	iqmux47LoggingOPDolbyELogEmbDolbyE5 OBJECT-TYPE
		SYNTAX		INTEGER { disable(0), enable(1) }
		MAX-ACCESS		read-write
		STATUS			current
		DESCRIPTION
				"TYPE: - Checkbox
				 PAGE: - RollCall- Logging
					Log Emb DolbyE 5  cmdID= 35954 "
		::= { iqmux47CmdEntry 35954 }


	iqmux47LoggingOPDolbyEEmbDolbyE5 OBJECT-TYPE
		SYNTAX		RollCallString
		MAX-ACCESS		read-only
		STATUS			current
		DESCRIPTION
				"TYPE: - Display
				 PAGE: - RollCall- Logging
					Emb DolbyE 5=  cmdID= 36954  format=   "
		::= { iqmux47CmdEntry 36954 }


	iqmux47LoggingOPDolbyELogEmbDolbyE6 OBJECT-TYPE
		SYNTAX		INTEGER { disable(0), enable(1) }
		MAX-ACCESS		read-write
		STATUS			current
		DESCRIPTION
				"TYPE: - Checkbox
				 PAGE: - RollCall- Logging
					Log Emb DolbyE 6  cmdID= 35955 "
		::= { iqmux47CmdEntry 35955 }


	iqmux47LoggingOPDolbyEEmbDolbyE6 OBJECT-TYPE
		SYNTAX		RollCallString
		MAX-ACCESS		read-only
		STATUS			current
		DESCRIPTION
				"TYPE: - Display
				 PAGE: - RollCall- Logging
					Emb DolbyE 6=  cmdID= 36955  format=   "
		::= { iqmux47CmdEntry 36955 }


	iqmux47LoggingOPDolbyELogEmbDolbyE7 OBJECT-TYPE
		SYNTAX		INTEGER { disable(0), enable(1) }
		MAX-ACCESS		read-write
		STATUS			current
		DESCRIPTION
				"TYPE: - Checkbox
				 PAGE: - RollCall- Logging
					Log Emb DolbyE 7  cmdID= 35956 "
		::= { iqmux47CmdEntry 35956 }


	iqmux47LoggingOPDolbyEEmbDolbyE7 OBJECT-TYPE
		SYNTAX		RollCallString
		MAX-ACCESS		read-only
		STATUS			current
		DESCRIPTION
				"TYPE: - Display
				 PAGE: - RollCall- Logging
					Emb DolbyE 7=  cmdID= 36956  format=   "
		::= { iqmux47CmdEntry 36956 }


	iqmux47LoggingOPDolbyELogEmbDolbyE8 OBJECT-TYPE
		SYNTAX		INTEGER { disable(0), enable(1) }
		MAX-ACCESS		read-write
		STATUS			current
		DESCRIPTION
				"TYPE: - Checkbox
				 PAGE: - RollCall- Logging
					Log Emb DolbyE 8  cmdID= 35957 "
		::= { iqmux47CmdEntry 35957 }


	iqmux47LoggingOPDolbyEEmbDolbyE8 OBJECT-TYPE
		SYNTAX		RollCallString
		MAX-ACCESS		read-only
		STATUS			current
		DESCRIPTION
				"TYPE: - Display
				 PAGE: - RollCall- Logging
					Emb DolbyE 8=  cmdID= 36957  format=   "
		::= { iqmux47CmdEntry 36957 }


	iqmux47LoggingAESInputLogAESInput1sta OBJECT-TYPE
		SYNTAX		INTEGER { disable(0), enable(1) }
		MAX-ACCESS		read-write
		STATUS			current
		DESCRIPTION
				"TYPE: - Checkbox
				 PAGE: - RollCall- Logging
					Log AES Input 1 sta  cmdID= 35600 "
		::= { iqmux47CmdEntry 35600 }


	iqmux47LoggingAESInputAESInput1state OBJECT-TYPE
		SYNTAX		RollCallString
		MAX-ACCESS		read-only
		STATUS			current
		DESCRIPTION
				"TYPE: - Display
				 PAGE: - RollCall- Logging
					AES Input 1 state=  cmdID= 36600  format=   "
		::= { iqmux47CmdEntry 36600 }


	iqmux47LoggingAESInputLogAESInput2sta OBJECT-TYPE
		SYNTAX		INTEGER { disable(0), enable(1) }
		MAX-ACCESS		read-write
		STATUS			current
		DESCRIPTION
				"TYPE: - Checkbox
				 PAGE: - RollCall- Logging
					Log AES Input 2 sta  cmdID= 35601 "
		::= { iqmux47CmdEntry 35601 }


	iqmux47LoggingAESInputAESInput2state OBJECT-TYPE
		SYNTAX		RollCallString
		MAX-ACCESS		read-only
		STATUS			current
		DESCRIPTION
				"TYPE: - Display
				 PAGE: - RollCall- Logging
					AES Input 2 state=  cmdID= 36601  format=   "
		::= { iqmux47CmdEntry 36601 }


	iqmux47LoggingAESInputLogAESInput3sta OBJECT-TYPE
		SYNTAX		INTEGER { disable(0), enable(1) }
		MAX-ACCESS		read-write
		STATUS			current
		DESCRIPTION
				"TYPE: - Checkbox
				 PAGE: - RollCall- Logging
					Log AES Input 3 sta  cmdID= 35602 "
		::= { iqmux47CmdEntry 35602 }


	iqmux47LoggingAESInputAESInput3state OBJECT-TYPE
		SYNTAX		RollCallString
		MAX-ACCESS		read-only
		STATUS			current
		DESCRIPTION
				"TYPE: - Display
				 PAGE: - RollCall- Logging
					AES Input 3 state=  cmdID= 36602  format=   "
		::= { iqmux47CmdEntry 36602 }


	iqmux47LoggingAESInputLogAESInput4sta OBJECT-TYPE
		SYNTAX		INTEGER { disable(0), enable(1) }
		MAX-ACCESS		read-write
		STATUS			current
		DESCRIPTION
				"TYPE: - Checkbox
				 PAGE: - RollCall- Logging
					Log AES Input 4 sta  cmdID= 35603 "
		::= { iqmux47CmdEntry 35603 }


	iqmux47LoggingAESInputAESInput4state OBJECT-TYPE
		SYNTAX		RollCallString
		MAX-ACCESS		read-only
		STATUS			current
		DESCRIPTION
				"TYPE: - Display
				 PAGE: - RollCall- Logging
					AES Input 4 state=  cmdID= 36603  format=   "
		::= { iqmux47CmdEntry 36603 }


	iqmux47LoggingAESInputLogAESInput5sta OBJECT-TYPE
		SYNTAX		INTEGER { disable(0), enable(1) }
		MAX-ACCESS		read-write
		STATUS			current
		DESCRIPTION
				"TYPE: - Checkbox
				 PAGE: - RollCall- Logging
					Log AES Input 5 sta  cmdID= 35604 "
		::= { iqmux47CmdEntry 35604 }


	iqmux47LoggingAESInputAESInput5state OBJECT-TYPE
		SYNTAX		RollCallString
		MAX-ACCESS		read-only
		STATUS			current
		DESCRIPTION
				"TYPE: - Display
				 PAGE: - RollCall- Logging
					AES Input 5 state=  cmdID= 36604  format=   "
		::= { iqmux47CmdEntry 36604 }


	iqmux47LoggingAESInputLogAESInput6sta OBJECT-TYPE
		SYNTAX		INTEGER { disable(0), enable(1) }
		MAX-ACCESS		read-write
		STATUS			current
		DESCRIPTION
				"TYPE: - Checkbox
				 PAGE: - RollCall- Logging
					Log AES Input 6 sta  cmdID= 35605 "
		::= { iqmux47CmdEntry 35605 }


	iqmux47LoggingAESInputAESInput6state OBJECT-TYPE
		SYNTAX		RollCallString
		MAX-ACCESS		read-only
		STATUS			current
		DESCRIPTION
				"TYPE: - Display
				 PAGE: - RollCall- Logging
					AES Input 6 state=  cmdID= 36605  format=   "
		::= { iqmux47CmdEntry 36605 }


	iqmux47LoggingAESInputLogAESInput7sta OBJECT-TYPE
		SYNTAX		INTEGER { disable(0), enable(1) }
		MAX-ACCESS		read-write
		STATUS			current
		DESCRIPTION
				"TYPE: - Checkbox
				 PAGE: - RollCall- Logging
					Log AES Input 7 sta  cmdID= 35606 "
		::= { iqmux47CmdEntry 35606 }


	iqmux47LoggingAESInputAESInput7state OBJECT-TYPE
		SYNTAX		RollCallString
		MAX-ACCESS		read-only
		STATUS			current
		DESCRIPTION
				"TYPE: - Display
				 PAGE: - RollCall- Logging
					AES Input 7 state=  cmdID= 36606  format=   "
		::= { iqmux47CmdEntry 36606 }


	iqmux47LoggingAESInputLogAESInput8sta OBJECT-TYPE
		SYNTAX		INTEGER { disable(0), enable(1) }
		MAX-ACCESS		read-write
		STATUS			current
		DESCRIPTION
				"TYPE: - Checkbox
				 PAGE: - RollCall- Logging
					Log AES Input 8 sta  cmdID= 35607 "
		::= { iqmux47CmdEntry 35607 }


	iqmux47LoggingAESInputAESInput8state OBJECT-TYPE
		SYNTAX		RollCallString
		MAX-ACCESS		read-only
		STATUS			current
		DESCRIPTION
				"TYPE: - Display
				 PAGE: - RollCall- Logging
					AES Input 8 state=  cmdID= 36607  format=   "
		::= { iqmux47CmdEntry 36607 }


	iqmux47LoggingAESInputLogAESInput1typ OBJECT-TYPE
		SYNTAX		INTEGER { disable(0), enable(1) }
		MAX-ACCESS		read-write
		STATUS			current
		DESCRIPTION
				"TYPE: - Checkbox
				 PAGE: - RollCall- Logging
					Log AES Input 1 typ  cmdID= 35640 "
		::= { iqmux47CmdEntry 35640 }


	iqmux47LoggingAESInputAESInput1type OBJECT-TYPE
		SYNTAX		RollCallString
		MAX-ACCESS		read-only
		STATUS			current
		DESCRIPTION
				"TYPE: - Display
				 PAGE: - RollCall- Logging
					AES Input 1 type=  cmdID= 36640  format=   "
		::= { iqmux47CmdEntry 36640 }


	iqmux47LoggingAESInputLogAESInput2typ OBJECT-TYPE
		SYNTAX		INTEGER { disable(0), enable(1) }
		MAX-ACCESS		read-write
		STATUS			current
		DESCRIPTION
				"TYPE: - Checkbox
				 PAGE: - RollCall- Logging
					Log AES Input 2 typ  cmdID= 35641 "
		::= { iqmux47CmdEntry 35641 }


	iqmux47LoggingAESInputAESInput2type OBJECT-TYPE
		SYNTAX		RollCallString
		MAX-ACCESS		read-only
		STATUS			current
		DESCRIPTION
				"TYPE: - Display
				 PAGE: - RollCall- Logging
					AES Input 2 type=  cmdID= 36641  format=   "
		::= { iqmux47CmdEntry 36641 }


	iqmux47LoggingAESInputLogAESInput3typ OBJECT-TYPE
		SYNTAX		INTEGER { disable(0), enable(1) }
		MAX-ACCESS		read-write
		STATUS			current
		DESCRIPTION
				"TYPE: - Checkbox
				 PAGE: - RollCall- Logging
					Log AES Input 3 typ  cmdID= 35642 "
		::= { iqmux47CmdEntry 35642 }


	iqmux47LoggingAESInputAESInput3type OBJECT-TYPE
		SYNTAX		RollCallString
		MAX-ACCESS		read-only
		STATUS			current
		DESCRIPTION
				"TYPE: - Display
				 PAGE: - RollCall- Logging
					AES Input 3 type=  cmdID= 36642  format=   "
		::= { iqmux47CmdEntry 36642 }


	iqmux47LoggingAESInputLogAESInput4typ OBJECT-TYPE
		SYNTAX		INTEGER { disable(0), enable(1) }
		MAX-ACCESS		read-write
		STATUS			current
		DESCRIPTION
				"TYPE: - Checkbox
				 PAGE: - RollCall- Logging
					Log AES Input 4 typ  cmdID= 35643 "
		::= { iqmux47CmdEntry 35643 }


	iqmux47LoggingAESInputAESInput4type OBJECT-TYPE
		SYNTAX		RollCallString
		MAX-ACCESS		read-only
		STATUS			current
		DESCRIPTION
				"TYPE: - Display
				 PAGE: - RollCall- Logging
					AES Input 4 type=  cmdID= 36643  format=   "
		::= { iqmux47CmdEntry 36643 }


	iqmux47LoggingAESInputLogAESInput5typ OBJECT-TYPE
		SYNTAX		INTEGER { disable(0), enable(1) }
		MAX-ACCESS		read-write
		STATUS			current
		DESCRIPTION
				"TYPE: - Checkbox
				 PAGE: - RollCall- Logging
					Log AES Input 5 typ  cmdID= 35644 "
		::= { iqmux47CmdEntry 35644 }


	iqmux47LoggingAESInputAESInput5type OBJECT-TYPE
		SYNTAX		RollCallString
		MAX-ACCESS		read-only
		STATUS			current
		DESCRIPTION
				"TYPE: - Display
				 PAGE: - RollCall- Logging
					AES Input 5 type=  cmdID= 36644  format=   "
		::= { iqmux47CmdEntry 36644 }


	iqmux47LoggingAESInputLogAESInput6typ OBJECT-TYPE
		SYNTAX		INTEGER { disable(0), enable(1) }
		MAX-ACCESS		read-write
		STATUS			current
		DESCRIPTION
				"TYPE: - Checkbox
				 PAGE: - RollCall- Logging
					Log AES Input 6 typ  cmdID= 35645 "
		::= { iqmux47CmdEntry 35645 }


	iqmux47LoggingAESInputAESInput6type OBJECT-TYPE
		SYNTAX		RollCallString
		MAX-ACCESS		read-only
		STATUS			current
		DESCRIPTION
				"TYPE: - Display
				 PAGE: - RollCall- Logging
					AES Input 6 type=  cmdID= 36645  format=   "
		::= { iqmux47CmdEntry 36645 }


	iqmux47LoggingAESInputLogAESInput7typ OBJECT-TYPE
		SYNTAX		INTEGER { disable(0), enable(1) }
		MAX-ACCESS		read-write
		STATUS			current
		DESCRIPTION
				"TYPE: - Checkbox
				 PAGE: - RollCall- Logging
					Log AES Input 7 typ  cmdID= 35646 "
		::= { iqmux47CmdEntry 35646 }


	iqmux47LoggingAESInputAESInput7type OBJECT-TYPE
		SYNTAX		RollCallString
		MAX-ACCESS		read-only
		STATUS			current
		DESCRIPTION
				"TYPE: - Display
				 PAGE: - RollCall- Logging
					AES Input 7 type=  cmdID= 36646  format=   "
		::= { iqmux47CmdEntry 36646 }


	iqmux47LoggingAESInputLogAESInput8typ OBJECT-TYPE
		SYNTAX		INTEGER { disable(0), enable(1) }
		MAX-ACCESS		read-write
		STATUS			current
		DESCRIPTION
				"TYPE: - Checkbox
				 PAGE: - RollCall- Logging
					Log AES Input 8 typ  cmdID= 35647 "
		::= { iqmux47CmdEntry 35647 }


	iqmux47LoggingAESInputAESInput8type OBJECT-TYPE
		SYNTAX		RollCallString
		MAX-ACCESS		read-only
		STATUS			current
		DESCRIPTION
				"TYPE: - Display
				 PAGE: - RollCall- Logging
					AES Input 8 type=  cmdID= 36647  format=   "
		::= { iqmux47CmdEntry 36647 }


	iqmux47LoggingAESOutputLogAESOutput1st OBJECT-TYPE
		SYNTAX		INTEGER { disable(0), enable(1) }
		MAX-ACCESS		read-write
		STATUS			current
		DESCRIPTION
				"TYPE: - Checkbox
				 PAGE: - RollCall- Logging
					Log AES Output 1 st  cmdID= 35620 "
		::= { iqmux47CmdEntry 35620 }


	iqmux47LoggingAESOutputAESOutput1state OBJECT-TYPE
		SYNTAX		RollCallString
		MAX-ACCESS		read-only
		STATUS			current
		DESCRIPTION
				"TYPE: - Display
				 PAGE: - RollCall- Logging
					AES Output 1 state=  cmdID= 36620  format=   "
		::= { iqmux47CmdEntry 36620 }


	iqmux47LoggingAESOutputLogAESOutput2st OBJECT-TYPE
		SYNTAX		INTEGER { disable(0), enable(1) }
		MAX-ACCESS		read-write
		STATUS			current
		DESCRIPTION
				"TYPE: - Checkbox
				 PAGE: - RollCall- Logging
					Log AES Output 2 st  cmdID= 35621 "
		::= { iqmux47CmdEntry 35621 }


	iqmux47LoggingAESOutputAESOutput2state OBJECT-TYPE
		SYNTAX		RollCallString
		MAX-ACCESS		read-only
		STATUS			current
		DESCRIPTION
				"TYPE: - Display
				 PAGE: - RollCall- Logging
					AES Output 2 state=  cmdID= 36621  format=   "
		::= { iqmux47CmdEntry 36621 }


	iqmux47LoggingAESOutputLogAESOutput3st OBJECT-TYPE
		SYNTAX		INTEGER { disable(0), enable(1) }
		MAX-ACCESS		read-write
		STATUS			current
		DESCRIPTION
				"TYPE: - Checkbox
				 PAGE: - RollCall- Logging
					Log AES Output 3 st  cmdID= 35622 "
		::= { iqmux47CmdEntry 35622 }


	iqmux47LoggingAESOutputAESOutput3state OBJECT-TYPE
		SYNTAX		RollCallString
		MAX-ACCESS		read-only
		STATUS			current
		DESCRIPTION
				"TYPE: - Display
				 PAGE: - RollCall- Logging
					AES Output 3 state=  cmdID= 36622  format=   "
		::= { iqmux47CmdEntry 36622 }


	iqmux47LoggingAESOutputLogAESOutput4st OBJECT-TYPE
		SYNTAX		INTEGER { disable(0), enable(1) }
		MAX-ACCESS		read-write
		STATUS			current
		DESCRIPTION
				"TYPE: - Checkbox
				 PAGE: - RollCall- Logging
					Log AES Output 4 st  cmdID= 35623 "
		::= { iqmux47CmdEntry 35623 }


	iqmux47LoggingAESOutputAESOutput4state OBJECT-TYPE
		SYNTAX		RollCallString
		MAX-ACCESS		read-only
		STATUS			current
		DESCRIPTION
				"TYPE: - Display
				 PAGE: - RollCall- Logging
					AES Output 4 state=  cmdID= 36623  format=   "
		::= { iqmux47CmdEntry 36623 }


	iqmux47LoggingAESOutputLogAESOutput5st OBJECT-TYPE
		SYNTAX		INTEGER { disable(0), enable(1) }
		MAX-ACCESS		read-write
		STATUS			current
		DESCRIPTION
				"TYPE: - Checkbox
				 PAGE: - RollCall- Logging
					Log AES Output 5 st  cmdID= 35624 "
		::= { iqmux47CmdEntry 35624 }


	iqmux47LoggingAESOutputAESOutput5state OBJECT-TYPE
		SYNTAX		RollCallString
		MAX-ACCESS		read-only
		STATUS			current
		DESCRIPTION
				"TYPE: - Display
				 PAGE: - RollCall- Logging
					AES Output 5 state=  cmdID= 36624  format=   "
		::= { iqmux47CmdEntry 36624 }


	iqmux47LoggingAESOutputLogAESOutput6st OBJECT-TYPE
		SYNTAX		INTEGER { disable(0), enable(1) }
		MAX-ACCESS		read-write
		STATUS			current
		DESCRIPTION
				"TYPE: - Checkbox
				 PAGE: - RollCall- Logging
					Log AES Output 6 st  cmdID= 35625 "
		::= { iqmux47CmdEntry 35625 }


	iqmux47LoggingAESOutputAESOutput6state OBJECT-TYPE
		SYNTAX		RollCallString
		MAX-ACCESS		read-only
		STATUS			current
		DESCRIPTION
				"TYPE: - Display
				 PAGE: - RollCall- Logging
					AES Output 6 state=  cmdID= 36625  format=   "
		::= { iqmux47CmdEntry 36625 }


	iqmux47LoggingAESOutputLogAESOutput7st OBJECT-TYPE
		SYNTAX		INTEGER { disable(0), enable(1) }
		MAX-ACCESS		read-write
		STATUS			current
		DESCRIPTION
				"TYPE: - Checkbox
				 PAGE: - RollCall- Logging
					Log AES Output 7 st  cmdID= 35626 "
		::= { iqmux47CmdEntry 35626 }


	iqmux47LoggingAESOutputAESOutput7state OBJECT-TYPE
		SYNTAX		RollCallString
		MAX-ACCESS		read-only
		STATUS			current
		DESCRIPTION
				"TYPE: - Display
				 PAGE: - RollCall- Logging
					AES Output 7 state=  cmdID= 36626  format=   "
		::= { iqmux47CmdEntry 36626 }


	iqmux47LoggingAESOutputLogAESOutput8st OBJECT-TYPE
		SYNTAX		INTEGER { disable(0), enable(1) }
		MAX-ACCESS		read-write
		STATUS			current
		DESCRIPTION
				"TYPE: - Checkbox
				 PAGE: - RollCall- Logging
					Log AES Output 8 st  cmdID= 35627 "
		::= { iqmux47CmdEntry 35627 }


	iqmux47LoggingAESOutputAESOutput8state OBJECT-TYPE
		SYNTAX		RollCallString
		MAX-ACCESS		read-only
		STATUS			current
		DESCRIPTION
				"TYPE: - Display
				 PAGE: - RollCall- Logging
					AES Output 8 state=  cmdID= 36627  format=   "
		::= { iqmux47CmdEntry 36627 }


	iqmux47LoggingAESOutputLogAESOutput1ty OBJECT-TYPE
		SYNTAX		INTEGER { disable(0), enable(1) }
		MAX-ACCESS		read-write
		STATUS			current
		DESCRIPTION
				"TYPE: - Checkbox
				 PAGE: - RollCall- Logging
					Log AES Output 1 ty  cmdID= 35660 "
		::= { iqmux47CmdEntry 35660 }


	iqmux47LoggingAESOutputAESOutput1type OBJECT-TYPE
		SYNTAX		RollCallString
		MAX-ACCESS		read-only
		STATUS			current
		DESCRIPTION
				"TYPE: - Display
				 PAGE: - RollCall- Logging
					AES Output 1 type=  cmdID= 36660  format=   "
		::= { iqmux47CmdEntry 36660 }


	iqmux47LoggingAESOutputLogAESOutput2ty OBJECT-TYPE
		SYNTAX		INTEGER { disable(0), enable(1) }
		MAX-ACCESS		read-write
		STATUS			current
		DESCRIPTION
				"TYPE: - Checkbox
				 PAGE: - RollCall- Logging
					Log AES Output 2 ty  cmdID= 35661 "
		::= { iqmux47CmdEntry 35661 }


	iqmux47LoggingAESOutputAESOutput2type OBJECT-TYPE
		SYNTAX		RollCallString
		MAX-ACCESS		read-only
		STATUS			current
		DESCRIPTION
				"TYPE: - Display
				 PAGE: - RollCall- Logging
					AES Output 2 type=  cmdID= 36661  format=   "
		::= { iqmux47CmdEntry 36661 }


	iqmux47LoggingAESOutputLogAESOutput3ty OBJECT-TYPE
		SYNTAX		INTEGER { disable(0), enable(1) }
		MAX-ACCESS		read-write
		STATUS			current
		DESCRIPTION
				"TYPE: - Checkbox
				 PAGE: - RollCall- Logging
					Log AES Output 3 ty  cmdID= 35662 "
		::= { iqmux47CmdEntry 35662 }


	iqmux47LoggingAESOutputAESOutput3type OBJECT-TYPE
		SYNTAX		RollCallString
		MAX-ACCESS		read-only
		STATUS			current
		DESCRIPTION
				"TYPE: - Display
				 PAGE: - RollCall- Logging
					AES Output 3 type=  cmdID= 36662  format=   "
		::= { iqmux47CmdEntry 36662 }


	iqmux47LoggingAESOutputLogAESOutput4ty OBJECT-TYPE
		SYNTAX		INTEGER { disable(0), enable(1) }
		MAX-ACCESS		read-write
		STATUS			current
		DESCRIPTION
				"TYPE: - Checkbox
				 PAGE: - RollCall- Logging
					Log AES Output 4 ty  cmdID= 35663 "
		::= { iqmux47CmdEntry 35663 }


	iqmux47LoggingAESOutputAESOutput4type OBJECT-TYPE
		SYNTAX		RollCallString
		MAX-ACCESS		read-only
		STATUS			current
		DESCRIPTION
				"TYPE: - Display
				 PAGE: - RollCall- Logging
					AES Output 4 type=  cmdID= 36663  format=   "
		::= { iqmux47CmdEntry 36663 }


	iqmux47LoggingAESOutputLogAESOutput5ty OBJECT-TYPE
		SYNTAX		INTEGER { disable(0), enable(1) }
		MAX-ACCESS		read-write
		STATUS			current
		DESCRIPTION
				"TYPE: - Checkbox
				 PAGE: - RollCall- Logging
					Log AES Output 5 ty  cmdID= 35664 "
		::= { iqmux47CmdEntry 35664 }


	iqmux47LoggingAESOutputAESOutput5type OBJECT-TYPE
		SYNTAX		RollCallString
		MAX-ACCESS		read-only
		STATUS			current
		DESCRIPTION
				"TYPE: - Display
				 PAGE: - RollCall- Logging
					AES Output 5 type=  cmdID= 36664  format=   "
		::= { iqmux47CmdEntry 36664 }


	iqmux47LoggingAESOutputLogAESOutput6ty OBJECT-TYPE
		SYNTAX		INTEGER { disable(0), enable(1) }
		MAX-ACCESS		read-write
		STATUS			current
		DESCRIPTION
				"TYPE: - Checkbox
				 PAGE: - RollCall- Logging
					Log AES Output 6 ty  cmdID= 35665 "
		::= { iqmux47CmdEntry 35665 }


	iqmux47LoggingAESOutputAESOutput6type OBJECT-TYPE
		SYNTAX		RollCallString
		MAX-ACCESS		read-only
		STATUS			current
		DESCRIPTION
				"TYPE: - Display
				 PAGE: - RollCall- Logging
					AES Output 6 type=  cmdID= 36665  format=   "
		::= { iqmux47CmdEntry 36665 }


	iqmux47LoggingAESOutputLogAESOutput7ty OBJECT-TYPE
		SYNTAX		INTEGER { disable(0), enable(1) }
		MAX-ACCESS		read-write
		STATUS			current
		DESCRIPTION
				"TYPE: - Checkbox
				 PAGE: - RollCall- Logging
					Log AES Output 7 ty  cmdID= 35666 "
		::= { iqmux47CmdEntry 35666 }


	iqmux47LoggingAESOutputAESOutput7type OBJECT-TYPE
		SYNTAX		RollCallString
		MAX-ACCESS		read-only
		STATUS			current
		DESCRIPTION
				"TYPE: - Display
				 PAGE: - RollCall- Logging
					AES Output 7 type=  cmdID= 36666  format=   "
		::= { iqmux47CmdEntry 36666 }


	iqmux47LoggingAESOutputLogAESOutput8ty OBJECT-TYPE
		SYNTAX		INTEGER { disable(0), enable(1) }
		MAX-ACCESS		read-write
		STATUS			current
		DESCRIPTION
				"TYPE: - Checkbox
				 PAGE: - RollCall- Logging
					Log AES Output 8 ty  cmdID= 35667 "
		::= { iqmux47CmdEntry 35667 }


	iqmux47LoggingAESOutputAESOutput8type OBJECT-TYPE
		SYNTAX		RollCallString
		MAX-ACCESS		read-only
		STATUS			current
		DESCRIPTION
				"TYPE: - Display
				 PAGE: - RollCall- Logging
					AES Output 8 type=  cmdID= 36667  format=   "
		::= { iqmux47CmdEntry 36667 }


	iqmux47LoggingMiscLogSerialNo OBJECT-TYPE
		SYNTAX		INTEGER { disable(0), enable(1) }
		MAX-ACCESS		read-write
		STATUS			current
		DESCRIPTION
				"TYPE: - Checkbox
				 PAGE: - RollCall- Logging
					Log Serial No.  cmdID= 35015 "
		::= { iqmux47CmdEntry 35015 }


	iqmux47LoggingMiscSerialNo OBJECT-TYPE
		SYNTAX		RollCallString
		MAX-ACCESS		read-only
		STATUS			current
		DESCRIPTION
				"TYPE: - Display
				 PAGE: - RollCall- Logging
					Serial No.=  cmdID= 36015  format=   "
		::= { iqmux47CmdEntry 36015 }


	iqmux47LoggingMiscLogOSVersion OBJECT-TYPE
		SYNTAX		INTEGER { disable(0), enable(1) }
		MAX-ACCESS		read-write
		STATUS			current
		DESCRIPTION
				"TYPE: - Checkbox
				 PAGE: - RollCall- Logging
					Log OS Version  cmdID= 35993 "
		::= { iqmux47CmdEntry 35993 }


	iqmux47LoggingMiscOSVersion OBJECT-TYPE
		SYNTAX		RollCallString
		MAX-ACCESS		read-only
		STATUS			current
		DESCRIPTION
				"TYPE: - Display
				 PAGE: - RollCall- Logging
					OS Version=  cmdID= 36993  format=   "
		::= { iqmux47CmdEntry 36993 }


	iqmux47LoggingMiscLogBuildNo OBJECT-TYPE
		SYNTAX		INTEGER { disable(0), enable(1) }
		MAX-ACCESS		read-write
		STATUS			current
		DESCRIPTION
				"TYPE: - Checkbox
				 PAGE: - RollCall- Logging
					Log Build No.  cmdID= 35990 "
		::= { iqmux47CmdEntry 35990 }


	iqmux47LoggingMiscBuildNo OBJECT-TYPE
		SYNTAX		RollCallString
		MAX-ACCESS		read-only
		STATUS			current
		DESCRIPTION
				"TYPE: - Display
				 PAGE: - RollCall- Logging
					Build No.=  cmdID= 36990  format=   "
		::= { iqmux47CmdEntry 36990 }


	iqmux47LoggingMiscLogHardwareVer OBJECT-TYPE
		SYNTAX		INTEGER { disable(0), enable(1) }
		MAX-ACCESS		read-write
		STATUS			current
		DESCRIPTION
				"TYPE: - Checkbox
				 PAGE: - RollCall- Logging
					Log Hardware Ver.  cmdID= 35992 "
		::= { iqmux47CmdEntry 35992 }


	iqmux47LoggingMiscHardwareVer OBJECT-TYPE
		SYNTAX		RollCallString
		MAX-ACCESS		read-only
		STATUS			current
		DESCRIPTION
				"TYPE: - Display
				 PAGE: - RollCall- Logging
					Hardware Ver.=  cmdID= 36992  format=   "
		::= { iqmux47CmdEntry 36992 }


	iqmux47LoggingMiscLogFirmwareVer OBJECT-TYPE
		SYNTAX		INTEGER { disable(0), enable(1) }
		MAX-ACCESS		read-write
		STATUS			current
		DESCRIPTION
				"TYPE: - Checkbox
				 PAGE: - RollCall- Logging
					Log Firmware Ver.  cmdID= 35991 "
		::= { iqmux47CmdEntry 35991 }


	iqmux47LoggingMiscFirmwareVer OBJECT-TYPE
		SYNTAX		RollCallString
		MAX-ACCESS		read-only
		STATUS			current
		DESCRIPTION
				"TYPE: - Display
				 PAGE: - RollCall- Logging
					Firmware Ver.=  cmdID= 36991  format=   "
		::= { iqmux47CmdEntry 36991 }


	iqmux47LoggingMiscLogUpTime OBJECT-TYPE
		SYNTAX		INTEGER { disable(0), enable(1) }
		MAX-ACCESS		read-write
		STATUS			current
		DESCRIPTION
				"TYPE: - Checkbox
				 PAGE: - RollCall- Logging
					Log Up Time  cmdID= 35994 "
		::= { iqmux47CmdEntry 35994 }


	iqmux47LoggingMiscUpTime OBJECT-TYPE
		SYNTAX		RollCallString
		MAX-ACCESS		read-only
		STATUS			current
		DESCRIPTION
				"TYPE: - Display
				 PAGE: - RollCall- Logging
					Up Time=  cmdID= 36994  format=   "
		::= { iqmux47CmdEntry 36994 }


	iqmux47RollCallRollTrackDisableAll OBJECT-TYPE
		SYNTAX		INTEGER { disable(0), enable(1) }
		MAX-ACCESS		read-write
		STATUS			current
		DESCRIPTION
				"TYPE: - Checkbox
				 PAGE: - RollCall
					Disable All  cmdID= 36104 "
		::= { iqmux47CmdEntry 36104 }


	iqmux47RollCallRollTrackIndex OBJECT-TYPE
		SYNTAX		INTEGER
		MAX-ACCESS		read-write
		STATUS			current
		DESCRIPTION
				"TYPE: - BarGraph
				 PAGE: - RollCall
					Index  cmdID= 36100  min= 1  max= 16   step= 1  format= %0.0f  div_scale= 1
					Min = 1  Max = 16  Step = 1 "
		::= { iqmux47CmdEntry 36100 }


	iqmux47RollCallRollTrackSource OBJECT-TYPE
		SYNTAX		INTEGER {
							val_Unused(-1),
							val_Video_Delay(0),
							val_Input_Present(1),
							val_Input_Loss(2),
							val_O_p_Freeze(3),
							val_O_p_UnFreeze(4),
							val_Output_1080(53),
							val_Output_720(54),
							val_Output_576_625(55),
							val_Output_480_525(56),
							val_De_embed_1_Data(5),
							val_De_embed_1_Pcm(6),
							val_De_embed_1_Lost(7),
							val_De_embed_2_Data(8),
							val_De_embed_2_Pcm(9),
							val_De_embed_2_Lost(10),
							val_De_embed_3_Data(11),
							val_De_embed_3_Pcm(12),
							val_De_embed_3_Lost(13),
							val_De_embed_4_Data(14),
							val_De_embed_4_Pcm(15),
							val_De_embed_4_Lost(16),
							val_De_embed_5_Data(17),
							val_De_embed_5_Pcm(18),
							val_De_embed_5_Lost(19),
							val_De_embed_6_Data(20),
							val_De_embed_6_Pcm(21),
							val_De_embed_6_Lost(22),
							val_De_embed_7_Data(23),
							val_De_embed_7_Pcm(24),
							val_De_embed_7_Lost(25),
							val_De_embed_8_Data(26),
							val_De_embed_8_Pcm(27),
							val_De_embed_8_Lost(28),
							val_AES_1_Data(29),
							val_AES_1_Pcm(30),
							val_AES_1_Lost(31),
							val_AES_2_Data(32),
							val_AES_2_Pcm(33),
							val_AES_2_Lost(34),
							val_AES_3_Data(35),
							val_AES_3_Pcm(36),
							val_AES_3_Lost(37),
							val_AES_4_Data(38),
							val_AES_4_Pcm(39),
							val_AES_4_Lost(40),
							val_AES_5_Data(41),
							val_AES_5_Pcm(42),
							val_AES_5_Lost(43),
							val_AES_6_Data(44),
							val_AES_6_Pcm(45),
							val_AES_6_Lost(46),
							val_AES_7_Data(47),
							val_AES_7_Pcm(48),
							val_AES_7_Lost(49),
							val_AES_8_Data(50),
							val_AES_8_Pcm(51),
							val_AES_8_Lost(52)
							}
		MAX-ACCESS		read-write
		STATUS			current
		DESCRIPTION
				"TYPE: - RadiobuttonList
				 PAGE: - RollCall
					Source  cmdID= 36101
					Unused  value= -1
					Video Delay  value= 0
					Input Present  value= 1
					Input Loss  value= 2
					O/p Freeze  value= 3
					O/p UnFreeze  value= 4
					Output:1080  value= 53
					Output:720  value= 54
					Output:576(625)  value= 55
					Output:480(525)  value= 56
					De-embed 1 Data  value= 5
					De-embed 1 Pcm  value= 6
					De-embed 1 Lost  value= 7
					De-embed 2 Data  value= 8
					De-embed 2 Pcm  value= 9
					De-embed 2 Lost  value= 10
					De-embed 3 Data  value= 11
					De-embed 3 Pcm  value= 12
					De-embed 3 Lost  value= 13
					De-embed 4 Data  value= 14
					De-embed 4 Pcm  value= 15
					De-embed 4 Lost  value= 16
					De-embed 5 Data  value= 17
					De-embed 5 Pcm  value= 18
					De-embed 5 Lost  value= 19
					De-embed 6 Data  value= 20
					De-embed 6 Pcm  value= 21
					De-embed 6 Lost  value= 22
					De-embed 7 Data  value= 23
					De-embed 7 Pcm  value= 24
					De-embed 7 Lost  value= 25
					De-embed 8 Data  value= 26
					De-embed 8 Pcm  value= 27
					De-embed 8 Lost  value= 28
					AES 1 Data  value= 29
					AES 1 Pcm  value= 30
					AES 1 Lost  value= 31
					AES 2 Data  value= 32
					AES 2 Pcm  value= 33
					AES 2 Lost  value= 34
					AES 3 Data  value= 35
					AES 3 Pcm  value= 36
					AES 3 Lost  value= 37
					AES 4 Data  value= 38
					AES 4 Pcm  value= 39
					AES 4 Lost  value= 40
					AES 5 Data  value= 41
					AES 5 Pcm  value= 42
					AES 5 Lost  value= 43
					AES 6 Data  value= 44
					AES 6 Pcm  value= 45
					AES 6 Lost  value= 46
					AES 7 Data  value= 47
					AES 7 Pcm  value= 48
					AES 7 Lost  value= 49
					AES 8 Data  value= 50
					AES 8 Pcm  value= 51
					AES 8 Lost  value= 52  "
		::= { iqmux47CmdEntry 36101 }


	iqmux47RollCallRollTrackAddress OBJECT-TYPE
		SYNTAX		RollCallString
		MAX-ACCESS		read-write
		STATUS			current
		DESCRIPTION
				"TYPE: - Editstring
				 PAGE: - RollCall
					Address  cmdID= 36102  "
		::= { iqmux47CmdEntry 36102 }


	iqmux47RollCallRollTrackCommand OBJECT-TYPE
		SYNTAX		RollCallString
		MAX-ACCESS		read-write
		STATUS			current
		DESCRIPTION
				"TYPE: - Editstring
				 PAGE: - RollCall
					Command  cmdID= 36103  "
		::= { iqmux47CmdEntry 36103 }


	iqmux47RollCallRollTrackStatus OBJECT-TYPE
		SYNTAX		RollCallString
		MAX-ACCESS		read-only
		STATUS			current
		DESCRIPTION
				"TYPE: - Display
				 PAGE: - RollCall
					Status  cmdID= 36105  format=   "
		::= { iqmux47CmdEntry 36105 }


	iqmux47RollCallRollTrackSending OBJECT-TYPE
		SYNTAX		RollCallString
		MAX-ACCESS		read-only
		STATUS			current
		DESCRIPTION
				"TYPE: - Display
				 PAGE: - RollCall
					Sending  cmdID= 36106  format=   "
		::= { iqmux47CmdEntry 36106 }


	iqmux47SetupProduct OBJECT-TYPE
		SYNTAX		RollCallString
		MAX-ACCESS		read-only
		STATUS			current
		DESCRIPTION
				"TYPE: - Display
					Product  cmdID= 32771  format=   "
		::= { iqmux47CmdEntry 32771 }


	iqmux47SetupRelease OBJECT-TYPE
		SYNTAX		RollCallString
		MAX-ACCESS		read-only
		STATUS			current
		DESCRIPTION
				"TYPE: - Display
					Release  cmdID= 2  format=   "
		::= { iqmux47CmdEntry 2 }


	iqmux47SetupBuild OBJECT-TYPE
		SYNTAX		RollCallString
		MAX-ACCESS		read-only
		STATUS			current
		DESCRIPTION
				"TYPE: - Display
					Build  cmdID= 5  format=   "
		::= { iqmux47CmdEntry 5 }


	iqmux47SetupKOS OBJECT-TYPE
		SYNTAX		RollCallString
		MAX-ACCESS		read-only
		STATUS			current
		DESCRIPTION
				"TYPE: - Display
					KOS  cmdID= 32772  format=   "
		::= { iqmux47CmdEntry 32772 }


	iqmux47SetupSerial OBJECT-TYPE
		SYNTAX		RollCallString
		MAX-ACCESS		read-only
		STATUS			current
		DESCRIPTION
				"TYPE: - Display
					Serial No.  cmdID= 1  format=   "
		::= { iqmux47CmdEntry 1 }


	iqmux47SetupFirmware OBJECT-TYPE
		SYNTAX		RollCallString
		MAX-ACCESS		read-only
		STATUS			current
		DESCRIPTION
				"TYPE: - Display
					Firmware  cmdID= 32769  format=   "
		::= { iqmux47CmdEntry 32769 }


	iqmux47SetupPCB OBJECT-TYPE
		SYNTAX		RollCallString
		MAX-ACCESS		read-only
		STATUS			current
		DESCRIPTION
				"TYPE: - Display
					PCB  cmdID= 32770  format=   "
		::= { iqmux47CmdEntry 32770 }


	iqmux47SetupFactoryDefault OBJECT-TYPE
		SYNTAX		INTEGER { noAction(0),val_Factory_Default(1) }
		MAX-ACCESS		read-write
		STATUS			current
		DESCRIPTION
				"TYPE: - Button
					Factory Default  cmdID= 37002  value= 1  "
		::= { iqmux47CmdEntry 37002 }


	iqmux47SetupRestart OBJECT-TYPE
		SYNTAX		INTEGER { noAction(0),val_Restart(1) }
		MAX-ACCESS		read-write
		STATUS			current
		DESCRIPTION
				"TYPE: - Button
					Restart  cmdID= 4  value= 1  "
		::= { iqmux47CmdEntry 4 }


	iqmux47SetupDefaultSettings OBJECT-TYPE
		SYNTAX		INTEGER { noAction(0),val_Default_Settings(1) }
		MAX-ACCESS		read-write
		STATUS			current
		DESCRIPTION
				"TYPE: - Button
					Default Settings  cmdID= 37001  value= 1  "
		::= { iqmux47CmdEntry 37001 }


	iqmux47SetupDisplay OBJECT-TYPE
		SYNTAX		INTEGER {
							val_Video_Status(0),
							val_Audio_Status(1)
							}
		MAX-ACCESS		read-write
		STATUS			current
		DESCRIPTION
				"TYPE: - RadiobuttonList
					Display  cmdID= 32773
					Video Status  value= 0
					Audio Status  value= 1  "
		::= { iqmux47CmdEntry 32773 }


	iqmux47SetupSerialNumber OBJECT-TYPE
		SYNTAX		RollCallString
		MAX-ACCESS		read-write
		STATUS			current
		DESCRIPTION
				"TYPE: - Editstring
					Serial Number  cmdID= 32774  "
		::= { iqmux47CmdEntry 32774 }


	iqmux47SetupBoardID OBJECT-TYPE
		SYNTAX		INTEGER {
							val_IQMUX47(389),
							val_IQMUX43(390),
							val_IQMUX44(472),
							val_IQMUX47(473),
							val_IQMUX47(494),
							val_IQMUX47(495),
							val_IQMUX48(496),
							val_IQMUX49(497)
							}
		MAX-ACCESS		read-write
		STATUS			current
		DESCRIPTION
				"TYPE: - RadiobuttonList
					BoardID  cmdID= 32776
					IQMUX47  value= 389
					IQMUX43  value= 390
					IQMUX44  value= 472
					IQMUX47  value= 473
					IQMUX47  value= 494
					IQMUX47  value= 495
					IQMUX48  value= 496
					IQMUX49  value= 497  "
		::= { iqmux47CmdEntry 32776 }


	iqmux47SetupSaveID OBJECT-TYPE
		SYNTAX		INTEGER { noAction(0),val_Save_ID(1) }
		MAX-ACCESS		read-write
		STATUS			current
		DESCRIPTION
				"TYPE: - Button
					Save ID  cmdID= 32775  value= 1  "
		::= { iqmux47CmdEntry 32775 }


	iqmux47EngineerPassword OBJECT-TYPE
		SYNTAX		RollCallString
		MAX-ACCESS		read-write
		STATUS			current
		DESCRIPTION
				"TYPE: - Editstring
				 PAGE: - Engineer
					Engineer Password  cmdID= 34011  "
		::= { iqmux47CmdEntry 34011 }


	iqmux47EngineerShowEngineer OBJECT-TYPE
		SYNTAX		INTEGER { disable(0), enable(1) }
		MAX-ACCESS		read-write
		STATUS			current
		DESCRIPTION
				"TYPE: - Checkbox
				 PAGE: - Engineer
					Show Engineer  cmdID= 34012 "
		::= { iqmux47CmdEntry 34012 }


	iqmux47EngineerPageOptionsS134014 OBJECT-TYPE
		SYNTAX		INTEGER { disable(0), enable(1) }
		MAX-ACCESS		read-write
		STATUS			current
		DESCRIPTION
				"TYPE: - Checkbox
				 PAGE: - Engineer
					$S1  cmdID= 34014 "
		::= { iqmux47CmdEntry 34014 }


	iqmux47EngineerPageOptionsS134015 OBJECT-TYPE
		SYNTAX		INTEGER { disable(0), enable(1) }
		MAX-ACCESS		read-write
		STATUS			current
		DESCRIPTION
				"TYPE: - Checkbox
				 PAGE: - Engineer
					$S1  cmdID= 34015 "
		::= { iqmux47CmdEntry 34015 }


	iqmux47EngineerPageOptionsS1 OBJECT-TYPE
		SYNTAX		INTEGER { disable(0), enable(1) }
		MAX-ACCESS		read-write
		STATUS			current
		DESCRIPTION
				"TYPE: - Checkbox
				 PAGE: - Engineer
					$S1  cmdID= 34016 "
		::= { iqmux47CmdEntry 34016 }


	iqmux47EngineerPageUndoChanges OBJECT-TYPE
		SYNTAX		INTEGER { noAction(0),val_Undo_Changes(1) }
		MAX-ACCESS		read-write
		STATUS			current
		DESCRIPTION
				"TYPE: - Button
				 PAGE: - Engineer
					Undo Changes  cmdID= 34013  value= 1  "
		::= { iqmux47CmdEntry 34013 }


	iqmux47EngineerPageLineNumber OBJECT-TYPE
		SYNTAX		RollCallString
		MAX-ACCESS		read-only
		STATUS			current
		DESCRIPTION
				"TYPE: - Display
				 PAGE: - Engineer
					Line Number  cmdID= 38651  format=   "
		::= { iqmux47CmdEntry 38651 }


	iqmux47EngineerPageSampleNumber OBJECT-TYPE
		SYNTAX		RollCallString
		MAX-ACCESS		read-only
		STATUS			current
		DESCRIPTION
				"TYPE: - Display
				 PAGE: - Engineer
					Sample Number  cmdID= 38657  format=   "
		::= { iqmux47CmdEntry 38657 }


	iqmux47EngineerPaAutoalignEmbeddedInputs OBJECT-TYPE
		SYNTAX		INTEGER { disable(0), enable(1) }
		MAX-ACCESS		read-write
		STATUS			current
		DESCRIPTION
				"TYPE: - Checkbox
				 PAGE: - Engineer
					Embedded Inputs  cmdID= 34060 "
		::= { iqmux47CmdEntry 34060 }


	iqmux47EngineerPaAutoalignAESInputs OBJECT-TYPE
		SYNTAX		INTEGER { disable(0), enable(1) }
		MAX-ACCESS		read-write
		STATUS			current
		DESCRIPTION
				"TYPE: - Checkbox
				 PAGE: - Engineer
					AES Inputs  cmdID= 34061 "
		::= { iqmux47CmdEntry 34061 }


	iqmux47ShowEngineer2 OBJECT-TYPE
		SYNTAX		INTEGER { disable(0), enable(1) }
		MAX-ACCESS		read-write
		STATUS			current
		DESCRIPTION
				"TYPE: - Checkbox
					Show Engineer2  cmdID= 34050 "
		::= { iqmux47CmdEntry 34050 }


	iqmux47UseEmbDelayFbac OBJECT-TYPE
		SYNTAX		INTEGER { disable(0), enable(1) }
		MAX-ACCESS		read-write
		STATUS			current
		DESCRIPTION
				"TYPE: - Checkbox
					Use Emb Delay F/bac  cmdID= 34049 "
		::= { iqmux47CmdEntry 34049 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S35034500
--				:
-- Comments		: Serial Number or module
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:34:00
--				:
-- Comments		: Uptime in formated date-time string
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number or current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				:
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 2001420336
--				:
-- Comments		: String of current Software build number
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD / SD SDI
--				:
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2010-01-27T10:41:47Z
--				:
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: OK
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2010-01-27T10:45:05Z
--				:
-- Comments		: Time String of last control modification
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: HD / SD SDI
--				:
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: BLACK
--				: PATTERN
--				: MONO
--				: FROZEN
--				: OK
--				: FAIL
--				: LOGO
--				: PATTERN+LOGO
--				: MONO+LOGO
--				: BLACK+LOGO
--				: FROZEN+LOGO
--				: OK+LOGO
-- Comments		:
--
---------------------------------------------------------------------------------------------------
-- Header		: AES_INPUT_1_TYPE
--
-- MIB ref		: swCardEventLogSlotXX       .16.65.69.83.95.73.78.80.85.84.95.49.95.84.89.80.69
-- absolute OID	: 1.3.6.1.4.1.7995.2.6.1.1.XX.16.65.69.83.95.73.78.80.85.84.95.49.95.84.89.80.69
-- Vary			: YES
--
-- Value(s)		: Unknown
--				: NONPCM
--              : PCM
--              : WARN: No Input
-- Comments		:
--
---------------------------------------------------------------------------------------------------
-- Header		: AES_INPUT_2_TYPE
--
-- MIB ref		: swCardEventLogSlotXX       .16.65.69.83.95.73.78.80.85.84.95.50.95.84.89.80.69
-- absolute OID	: 1.3.6.1.4.1.7995.2.6.1.1.XX.16.65.69.83.95.73.78.80.85.84.95.50.95.84.89.80.69
-- Vary			: YES
--
-- Value(s)		: Unknown
--				: NONPCM
--              : PCM
--              : WARN: No Input
-- Comments		:
--
---------------------------------------------------------------------------------------------------
-- Header		: AES_INPUT_3_TYPE
--
-- MIB ref		: swCardEventLogSlotXX       .16.65.69.83.95.73.78.80.85.84.95.51.95.84.89.80.69
-- absolute OID	: 1.3.6.1.4.1.7995.2.6.1.1.XX.16.65.69.83.95.73.78.80.85.84.95.51.95.84.89.80.69
-- Vary			: YES
--
-- Value(s)		: Unknown
--				: NONPCM
--              : PCM
--              : WARN: No Input
-- Comments		:
--
---------------------------------------------------------------------------------------------------
-- Header		: AES_INPUT_4_TYPE
--
-- MIB ref		: swCardEventLogSlotXX       .16.65.69.83.95.73.78.80.85.84.95.52.95.84.89.80.69
-- absolute OID	: 1.3.6.1.4.1.7995.2.6.1.1.XX.16.65.69.83.95.73.78.80.85.84.95.52.95.84.89.80.69
-- Vary			: YES
--
-- Value(s)		: Unknown
--				: NONPCM
--              : PCM
--              : WARN: No Input
-- Comments		:
--
---------------------------------------------------------------------------------------------------
-- Header		: AES_INPUT_5_TYPE
--
-- MIB ref		: swCardEventLogSlotXX       .16.65.69.83.95.73.78.80.85.84.95.53.95.84.89.80.69
-- absolute OID	: 1.3.6.1.4.1.7995.2.6.1.1.XX.16.65.69.83.95.73.78.80.85.84.95.53.95.84.89.80.69
-- Vary			: YES
--
-- Value(s)		: Unknown
--				: NONPCM
--              : PCM
--              : WARN: No Input
-- Comments		:
--
---------------------------------------------------------------------------------------------------
-- Header		: AES_INPUT_6_TYPE
--
-- MIB ref		: swCardEventLogSlotXX       .16.65.69.83.95.73.78.80.85.84.95.54.95.84.89.80.69
-- absolute OID	: 1.3.6.1.4.1.7995.2.6.1.1.XX.16.65.69.83.95.73.78.80.85.84.95.54.95.84.89.80.69
-- Vary			: YES
--
-- Value(s)		: Unknown
--				: NONPCM
--              : PCM
--              : WARN: No Input
-- Comments		:
--
---------------------------------------------------------------------------------------------------
-- Header		: AES_INPUT_7_TYPE
--
-- MIB ref		: swCardEventLogSlotXX       .16.65.69.83.95.73.78.80.85.84.95.55.95.84.89.80.69
-- absolute OID	: 1.3.6.1.4.1.7995.2.6.1.1.XX.16.65.69.83.95.73.78.80.85.84.95.55.95.84.89.80.69
-- Vary			: YES
--
-- Value(s)		: Unknown
--				: NONPCM
--              : PCM
--              : WARN: No Input
-- Comments		:
--
---------------------------------------------------------------------------------------------------
-- Header		: AES_INPUT_8_TYPE
--
-- MIB ref		: swCardEventLogSlotXX       .16.65.69.83.95.73.78.80.85.84.95.56.95.84.89.80.69
-- absolute OID	: 1.3.6.1.4.1.7995.2.6.1.1.XX.16.65.69.83.95.73.78.80.85.84.95.56.95.84.89.80.69
-- Vary			: YES
--
-- Value(s)		: Unknown
--				: NONPCM
--              : PCM
--              : WARN: No Input
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 2.193
--				:
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: RDAUD1Y.001
--				:
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: NONE
--              : WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_INPUT_1_STATE
--
-- MIB ref		: swCardEventLogSlotXX       .17.65.69.83.95.73.78.80.85.84.95.49.95.83.84.65.84.69
-- absolute OID	: 1.3.6.1.4.1.7995.2.6.1.1.XX.17.65.69.83.95.73.78.80.85.84.95.49.95.83.84.65.84.69
-- Vary			: YES
--
-- Value(s)		: LOST
--				: FAIL:Lost
--              : OK
--              : Unknown
-- Comments		:
--
---------------------------------------------------------------------------------------------------
-- Header		: AES_INPUT_2_STATE
--
-- MIB ref		: swCardEventLogSlotXX       .17.65.69.83.95.73.78.80.85.84.95.50.95.83.84.65.84.69
-- absolute OID	: 1.3.6.1.4.1.7995.2.6.1.1.XX.17.65.69.83.95.73.78.80.85.84.95.50.95.83.84.65.84.69
-- Vary			: YES
--
-- Value(s)		: LOST
--				: FAIL:Lost
--              : OK
--              : Unknown
-- Comments		:
--
---------------------------------------------------------------------------------------------------
-- Header		: AES_INPUT_3_STATE
--
-- MIB ref		: swCardEventLogSlotXX       .17.65.69.83.95.73.78.80.85.84.95.51.95.83.84.65.84.69
-- absolute OID	: 1.3.6.1.4.1.7995.2.6.1.1.XX.17.65.69.83.95.73.78.80.85.84.95.51.95.83.84.65.84.69
-- Vary			: YES
--
-- Value(s)		: LOST
--				: FAIL:Lost
--              : OK
--              : Unknown
-- Comments		:
--
---------------------------------------------------------------------------------------------------
-- Header		: AES_INPUT_4_STATE
--
-- MIB ref		: swCardEventLogSlotXX       .17.65.69.83.95.73.78.80.85.84.95.52.95.83.84.65.84.69
-- absolute OID	: 1.3.6.1.4.1.7995.2.6.1.1.XX.17.65.69.83.95.73.78.80.85.84.95.52.95.83.84.65.84.69
-- Vary			: YES
--
-- Value(s)		: LOST
--				: FAIL:Lost
--              : OK
--              : Unknown
-- Comments		:
--
---------------------------------------------------------------------------------------------------
-- Header		: AES_INPUT_5_STATE
--
-- MIB ref		: swCardEventLogSlotXX       .17.65.69.83.95.73.78.80.85.84.95.53.95.83.84.65.84.69
-- absolute OID	: 1.3.6.1.4.1.7995.2.6.1.1.XX.17.65.69.83.95.73.78.80.85.84.95.53.95.83.84.65.84.69
-- Vary			: YES
--
-- Value(s)		: LOST
--				: FAIL:Lost
--              : OK
--              : Unknown
-- Comments		:
--
---------------------------------------------------------------------------------------------------
-- Header		: AES_INPUT_6_STATE
--
-- MIB ref		: swCardEventLogSlotXX       .17.65.69.83.95.73.78.80.85.84.95.54.95.83.84.65.84.69
-- absolute OID	: 1.3.6.1.4.1.7995.2.6.1.1.XX.17.65.69.83.95.73.78.80.85.84.95.54.95.83.84.65.84.69
-- Vary			: YES
--
-- Value(s)		: LOST
--				: FAIL:Lost
--              : OK
--              : Unknown
-- Comments		:
--
---------------------------------------------------------------------------------------------------
-- Header		: AES_INPUT_7_STATE
--
-- MIB ref		: swCardEventLogSlotXX       .17.65.69.83.95.73.78.80.85.84.95.55.95.83.84.65.84.69
-- absolute OID	: 1.3.6.1.4.1.7995.2.6.1.1.XX.17.65.69.83.95.73.78.80.85.84.95.55.95.83.84.65.84.69
-- Vary			: YES
--
-- Value(s)		: LOST
--				: FAIL:Lost
--              : OK
--              : Unknown
-- Comments		:
--
---------------------------------------------------------------------------------------------------
-- Header		: AES_INPUT_8_STATE
--
-- MIB ref		: swCardEventLogSlotXX       .17.65.69.83.95.73.78.80.85.84.95.56.95.83.84.65.84.69
-- absolute OID	: 1.3.6.1.4.1.7995.2.6.1.1.XX.17.65.69.83.95.73.78.80.85.84.95.56.95.83.84.65.84.69
-- Vary			: YES
--
-- Value(s)		: LOST
--				: FAIL:Lost
--              : OK
--              : Unknown
-- Comments		:
--
---------------------------------------------------------------------------------------------------
-- Header		: AES_OUTPUT_1_TYPE
--
-- MIB ref		: swCardEventLogSlotXX       .17.65.69.83.95.79.85.84.80.85.84.95.49.95.84.89.80.69
-- absolute OID	: 1.3.6.1.4.1.7995.2.6.1.1.XX.17.65.69.83.95.79.85.84.80.85.84.95.49.95.84.89.80.69
-- Vary			: YES
--
-- Value(s)		: Unknown
--				: PCM
--              : NONPCM
--              : WARN: No Input
-- Comments		:
--
---------------------------------------------------------------------------------------------------
-- Header		: AES_OUTPUT_2_TYPE
--
-- MIB ref		: swCardEventLogSlotXX       .17.65.69.83.95.79.85.84.80.85.84.95.50.95.84.89.80.69
-- absolute OID	: 1.3.6.1.4.1.7995.2.6.1.1.XX.17.65.69.83.95.79.85.84.80.85.84.95.50.95.84.89.80.69
-- Vary			: YES
--
-- Value(s)		: Unknown
--				: PCM
--              : NONPCM
--              : WARN: No Input
-- Comments		:
--
---------------------------------------------------------------------------------------------------
-- Header		: AES_OUTPUT_3_TYPE
--
-- MIB ref		: swCardEventLogSlotXX       .17.65.69.83.95.79.85.84.80.85.84.95.51.95.84.89.80.69
-- absolute OID	: 1.3.6.1.4.1.7995.2.6.1.1.XX.17.65.69.83.95.79.85.84.80.85.84.95.51.95.84.89.80.69
-- Vary			: YES
--
-- Value(s)		: Unknown
--				: PCM
--              : NONPCM
--              : WARN: No Input
-- Comments		:
--
---------------------------------------------------------------------------------------------------
-- Header		: AES_OUTPUT_4_TYPE
--
-- MIB ref		: swCardEventLogSlotXX       .17.65.69.83.95.79.85.84.80.85.84.95.52.95.84.89.80.69
-- absolute OID	: 1.3.6.1.4.1.7995.2.6.1.1.XX.17.65.69.83.95.79.85.84.80.85.84.95.52.95.84.89.80.69
-- Vary			: YES
--
-- Value(s)		: Unknown
--				: PCM
--              : NONPCM
--              : WARN: No Input
-- Comments		:
--
---------------------------------------------------------------------------------------------------
-- Header		: AES_OUTPUT_5_TYPE
--
-- MIB ref		: swCardEventLogSlotXX       .17.65.69.83.95.79.85.84.80.85.84.95.53.95.84.89.80.69
-- absolute OID	: 1.3.6.1.4.1.7995.2.6.1.1.XX.17.65.69.83.95.79.85.84.80.85.84.95.53.95.84.89.80.69
-- Vary			: YES
--
-- Value(s)		: Unknown
--				: PCM
--              : NONPCM
--              : WARN: No Input
-- Comments		:
--
---------------------------------------------------------------------------------------------------
-- Header		: AES_OUTPUT_6_TYPE
--
-- MIB ref		: swCardEventLogSlotXX       .17.65.69.83.95.79.85.84.80.85.84.95.54.95.84.89.80.69
-- absolute OID	: 1.3.6.1.4.1.7995.2.6.1.1.XX.17.65.69.83.95.79.85.84.80.85.84.95.54.95.84.89.80.69
-- Vary			: YES
--
-- Value(s)		: Unknown
--				: PCM
--              : NONPCM
--              : WARN: No Input
-- Comments		:
--
---------------------------------------------------------------------------------------------------
-- Header		: AES_OUTPUT_7_TYPE
--
-- MIB ref		: swCardEventLogSlotXX       .17.65.69.83.95.79.85.84.80.85.84.95.55.95.84.89.80.69
-- absolute OID	: 1.3.6.1.4.1.7995.2.6.1.1.XX.17.65.69.83.95.79.85.84.80.85.84.95.55.95.84.89.80.69
-- Vary			: YES
--
-- Value(s)		: Unknown
--				: PCM
--              : NONPCM
--              : WARN: No Input
-- Comments		:
--
---------------------------------------------------------------------------------------------------
-- Header		: AES_OUTPUT_8_TYPE
--
-- MIB ref		: swCardEventLogSlotXX       .17.65.69.83.95.79.85.84.80.85.84.95.56.95.84.89.80.69
-- absolute OID	: 1.3.6.1.4.1.7995.2.6.1.1.XX.17.65.69.83.95.79.85.84.80.85.84.95.56.95.84.89.80.69
-- Vary			: YES
--
-- Value(s)		: Unknown
--				: PCM
--              : NONPCM
--              : WARN: No Input
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_OUTPUT_1_STATE
--
-- MIB ref		: swCardEventLogSlotXX       .18.65.69.83.95.79.85.84.80.85.84.95.49.95.83.84.65.84.69
-- absolute OID	: 1.3.6.1.4.1.7995.2.6.1.1.XX.18.65.69.83.95.79.85.84.80.85.84.95.49.95.83.84.65.84.69
-- Vary			: YES
--
-- Value(s)		: LOST
--				: FAIL:Lost
--              : OK
--              : Unknown
-- Comments		:
--
---------------------------------------------------------------------------------------------------
-- Header		: AES_OUTPUT_2_STATE
--
-- MIB ref		: swCardEventLogSlotXX       .18.65.69.83.95.79.85.84.80.85.84.95.50.95.83.84.65.84.69
-- absolute OID	: 1.3.6.1.4.1.7995.2.6.1.1.XX.18.65.69.83.95.79.85.84.80.85.84.95.50.95.83.84.65.84.69
-- Vary			: YES
--
-- Value(s)		: LOST
--				: FAIL:Lost
--              : OK
--              : Unknown
-- Comments		:
--
---------------------------------------------------------------------------------------------------
-- Header		: AES_OUTPUT_3_STATE
--
-- MIB ref		: swCardEventLogSlotXX       .18.65.69.83.95.79.85.84.80.85.84.95.51.95.83.84.65.84.69
-- absolute OID	: 1.3.6.1.4.1.7995.2.6.1.1.XX.18.65.69.83.95.79.85.84.80.85.84.95.51.95.83.84.65.84.69
-- Vary			: YES
--
-- Value(s)		: LOST
--				: FAIL:Lost
--              : OK
--              : Unknown
-- Comments		:
--
---------------------------------------------------------------------------------------------------
-- Header		: AES_OUTPUT_4_STATE
--
-- MIB ref		: swCardEventLogSlotXX       .18.65.69.83.95.79.85.84.80.85.84.95.52.95.83.84.65.84.69
-- absolute OID	: 1.3.6.1.4.1.7995.2.6.1.1.XX.18.65.69.83.95.79.85.84.80.85.84.95.52.95.83.84.65.84.69
-- Vary			: YES
--
-- Value(s)		: LOST
--				: FAIL:Lost
--              : OK
--              : Unknown
-- Comments		:
--
---------------------------------------------------------------------------------------------------
-- Header		: AES_OUTPUT_5_STATE
--
-- MIB ref		: swCardEventLogSlotXX       .18.65.69.83.95.79.85.84.80.85.84.95.53.95.83.84.65.84.69
-- absolute OID	: 1.3.6.1.4.1.7995.2.6.1.1.XX.18.65.69.83.95.79.85.84.80.85.84.95.53.95.83.84.65.84.69
-- Vary			: YES
--
-- Value(s)		: LOST
--				: FAIL:Lost
--              : OK
--              : Unknown
-- Comments		:
--
---------------------------------------------------------------------------------------------------
-- Header		: AES_OUTPUT_6_STATE
--
-- MIB ref		: swCardEventLogSlotXX       .18.65.69.83.95.79.85.84.80.85.84.95.54.95.83.84.65.84.69
-- absolute OID	: 1.3.6.1.4.1.7995.2.6.1.1.XX.18.65.69.83.95.79.85.84.80.85.84.95.54.95.83.84.65.84.69
-- Vary			: YES
--
-- Value(s)		: LOST
--				: FAIL:Lost
--              : OK
--              : Unknown
-- Comments		:
--
---------------------------------------------------------------------------------------------------
-- Header		: AES_OUTPUT_7_STATE
--
-- MIB ref		: swCardEventLogSlotXX       .18.65.69.83.95.79.85.84.80.85.84.95.55.95.83.84.65.84.69
-- absolute OID	: 1.3.6.1.4.1.7995.2.6.1.1.XX.18.65.69.83.95.79.85.84.80.85.84.95.55.95.83.84.65.84.69
-- Vary			: YES
--
-- Value(s)		: LOST
--				: FAIL:Lost
--              : OK
--              : Unknown
-- Comments		:
--
---------------------------------------------------------------------------------------------------
-- Header		: AES_OUTPUT_8_STATE
--
-- MIB ref		: swCardEventLogSlotXX       .18.65.69.83.95.79.85.84.80.85.84.95.56.95.83.84.65.84.69
-- absolute OID	: 1.3.6.1.4.1.7995.2.6.1.1.XX.18.65.69.83.95.79.85.84.80.85.84.95.56.95.83.84.65.84.69
-- Vary			: YES
--
-- Value(s)		: LOST
--				: FAIL:Lost
--              : OK
--              : Unknown
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
-- Vary			: YES
--
-- Value(s)		: 0
--				:
-- Comments		: Number
--
---------------------------------------------------------------------------------------------------
-- Header		: OUTPUT_1_ANC_STATE
--
-- MIB ref		: swCardEventLogSlotXX       .18.79.85.84.80.85.84.95.49.95.65.78.67.95.83.84.65.84.69
-- absolute OID	: 1.3.6.1.4.1.7995.2.6.1.1.XX.18.79.85.84.80.85.84.95.49.95.65.78.67.95.83.84.65.84.69
-- Vary			: YES
--
-- Value(s)		:
--				: ANC FULL
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: NONE
--              : WARN
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
-- Vary			: YES
--
-- Value(s)		: 0
--				:
-- Comments		: Number
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: LOST
--				: FAIL:Lost
--              : OK
--              : Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: LOST
--				: FAIL:Lost
--              : OK
--              : Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: LOST
--				: FAIL:Lost
--              : OK
--              : Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: OUTPUT_1_EMBEDDED_AUDIO_2_DOLBY
--
-- MIB ref		: swCardEventLogSlotXX       .31.79.85.84.80.85.84.95.49.95.69.77.66.69.68.68.69.68.95.65.85.68.73.79.95.50.95.68.79.76.66.89
-- absolute OID	: 1.3.6.1.4.1.7995.2.6.1.1.XX.31.79.85.84.80.85.84.95.49.95.69.77.66.69.68.68.69.68.95.65.85.68.73.79.95.50.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: OUTPUT_1_EMBEDDED_AUDIO_3_DOLBY
--
-- MIB ref		: swCardEventLogSlotXX       .31.79.85.84.80.85.84.95.49.95.69.77.66.69.68.68.69.68.95.65.85.68.73.79.95.51.95.68.79.76.66.89
-- absolute OID	: 1.3.6.1.4.1.7995.2.6.1.1.XX.31.79.85.84.80.85.84.95.49.95.69.77.66.69.68.68.69.68.95.65.85.68.73.79.95.51.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: OUTPUT_1_EMBEDDED_AUDIO_4_DOLBY
--
-- MIB ref		: swCardEventLogSlotXX       .31.79.85.84.80.85.84.95.49.95.69.77.66.69.68.68.69.68.95.65.85.68.73.79.95.52.95.68.79.76.66.89
-- absolute OID	: 1.3.6.1.4.1.7995.2.6.1.1.XX.31.79.85.84.80.85.84.95.49.95.69.77.66.69.68.68.69.68.95.65.85.68.73.79.95.52.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: LOST
--				: FAIL:Lost
--              : OK
--              : Unknown
-- Comments		:
-- Comments		:
--
---------------------------------------------------------------------------------------------------
-- Header		: OUTPUT_1_EMBEDDED_AUDIO_5_DOLBY
--
-- MIB ref		: swCardEventLogSlotXX       .31.79.85.84.80.85.84.95.49.95.69.77.66.69.68.68.69.68.95.65.85.68.73.79.95.53.95.68.79.76.66.89
-- absolute OID	: 1.3.6.1.4.1.7995.2.6.1.1.XX.31.79.85.84.80.85.84.95.49.95.69.77.66.69.68.68.69.68.95.65.85.68.73.79.95.53.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: OUTPUT_1_EMBEDDED_AUDIO_6_DOLBY
--
-- MIB ref		: swCardEventLogSlotXX       .31.79.85.84.80.85.84.95.49.95.69.77.66.69.68.68.69.68.95.65.85.68.73.79.95.54.95.68.79.76.66.89
-- absolute OID	: 1.3.6.1.4.1.7995.2.6.1.1.XX.31.79.85.84.80.85.84.95.49.95.69.77.66.69.68.68.69.68.95.65.85.68.73.79.95.54.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
--				: FAIL:Lost
--              : OK
--              : Unknown
-- Comments		:
-- Comments		:
--
---------------------------------------------------------------------------------------------------
-- Header		: OUTPUT_1_EMBEDDED_AUDIO_7_DOLBY
--
-- MIB ref		: swCardEventLogSlotXX       .31.79.85.84.80.85.84.95.49.95.69.77.66.69.68.68.69.68.95.65.85.68.73.79.95.55.95.68.79.76.66.89
-- absolute OID	: 1.3.6.1.4.1.7995.2.6.1.1.XX.31.79.85.84.80.85.84.95.49.95.69.77.66.69.68.68.69.68.95.65.85.68.73.79.95.55.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: LOST
--				: FAIL:Lost
--              : OK
--              : Unknown
-- Comments		:
---------------------------------------------------------------------------------------------------
-- Header		: OUTPUT_1_EMBEDDED_AUDIO_8_DOLBY
--
-- MIB ref		: swCardEventLogSlotXX       .31.79.85.84.80.85.84.95.49.95.69.77.66.69.68.68.69.68.95.65.85.68.73.79.95.56.95.68.79.76.66.89
-- absolute OID	: 1.3.6.1.4.1.7995.2.6.1.1.XX.31.79.85.84.80.85.84.95.49.95.69.77.66.69.68.68.69.68.95.65.85.68.73.79.95.56.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_1_LEVEL
--
-- MIB ref		: swCardEventLogSlotXX       .33.79.85.84.80.85.84.95.49.95.69.77.66.69.68.68.69.68.95.65.85.68.73.79.95.49.95.49.95.76.69.86.69.76
-- absolute OID	: 1.3.6.1.4.1.7995.2.6.1.1.XX.33.79.85.84.80.85.84.95.49.95.69.77.66.69.68.68.69.68.95.65.85.68.73.79.95.49.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_1_2_LEVEL
--
-- MIB ref		: swCardEventLogSlotXX       .33.79.85.84.80.85.84.95.49.95.69.77.66.69.68.68.69.68.95.65.85.68.73.79.95.49.95.50.95.76.69.86.69.76
-- absolute OID	: 1.3.6.1.4.1.7995.2.6.1.1.XX.33.79.85.84.80.85.84.95.49.95.69.77.66.69.68.68.69.68.95.65.85.68.73.79.95.49.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_1_LEVEL
--
-- MIB ref		: swCardEventLogSlotXX       .33.79.85.84.80.85.84.95.49.95.69.77.66.69.68.68.69.68.95.65.85.68.73.79.95.50.95.49.95.76.69.86.69.76
-- absolute OID	: 1.3.6.1.4.1.7995.2.6.1.1.XX.33.79.85.84.80.85.84.95.49.95.69.77.66.69.68.68.69.68.95.65.85.68.73.79.95.50.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_2_LEVEL
--
-- MIB ref		: swCardEventLogSlotXX       .33.79.85.84.80.85.84.95.49.95.69.77.66.69.68.68.69.68.95.65.85.68.73.79.95.50.95.50.95.76.69.86.69.76
-- absolute OID	: 1.3.6.1.4.1.7995.2.6.1.1.XX.33.79.85.84.80.85.84.95.49.95.69.77.66.69.68.68.69.68.95.65.85.68.73.79.95.50.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_1_LEVEL
--
-- MIB ref		: swCardEventLogSlotXX       .33.79.85.84.80.85.84.95.49.95.69.77.66.69.68.68.69.68.95.65.85.68.73.79.95.51.95.49.95.76.69.86.69.76
-- absolute OID	: 1.3.6.1.4.1.7995.2.6.1.1.XX.33.79.85.84.80.85.84.95.49.95.69.77.66.69.68.68.69.68.95.65.85.68.73.79.95.51.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_2_LEVEL
--
-- MIB ref		: swCardEventLogSlotXX       .33.79.85.84.80.85.84.95.49.95.69.77.66.69.68.68.69.68.95.65.85.68.73.79.95.51.95.50.95.76.69.86.69.76
-- absolute OID	: 1.3.6.1.4.1.7995.2.6.1.1.XX.33.79.85.84.80.85.84.95.49.95.69.77.66.69.68.68.69.68.95.65.85.68.73.79.95.51.95.50.95.76.69.86.69.76
-- Vary			: YES
--
-- Value(s)		: OK
--				:
-- Comments		:
--
---------------------------------------------------------------------------------------------------
-- Header		: OUTPUT_1_EMBEDDED_AUDIO_4_1_LEVEL
--
-- MIB ref		: swCardEventLogSlotXX       .33.79.85.84.80.85.84.95.49.95.69.77.66.69.68.68.69.68.95.65.85.68.73.79.95.52.95.49.95.76.69.86.69.76
-- absolute OID	: 1.3.6.1.4.1.7995.2.6.1.1.XX.33.79.85.84.80.85.84.95.49.95.69.77.66.69.68.68.69.68.95.65.85.68.73.79.95.52.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_4_2_LEVEL
--
-- MIB ref		: swCardEventLogSlotXX       .33.79.85.84.80.85.84.95.49.95.69.77.66.69.68.68.69.68.95.65.85.68.73.79.95.52.95.50.95.76.69.86.69.76
-- absolute OID	: 1.3.6.1.4.1.7995.2.6.1.1.XX.33.79.85.84.80.85.84.95.49.95.69.77.66.69.68.68.69.68.95.65.85.68.73.79.95.52.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_5_1_LEVEL
--
-- MIB ref		: swCardEventLogSlotXX       .33.79.85.84.80.85.84.95.49.95.69.77.66.69.68.68.69.68.95.65.85.68.73.79.95.53.95.49.95.76.69.86.69.76
-- absolute OID	: 1.3.6.1.4.1.7995.2.6.1.1.XX.33.79.85.84.80.85.84.95.49.95.69.77.66.69.68.68.69.68.95.65.85.68.73.79.95.53.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_5_2_LEVEL
--
-- MIB ref		: swCardEventLogSlotXX       .33.79.85.84.80.85.84.95.49.95.69.77.66.69.68.68.69.68.95.65.85.68.73.79.95.53.95.50.95.76.69.86.69.76
-- absolute OID	: 1.3.6.1.4.1.7995.2.6.1.1.XX.33.79.85.84.80.85.84.95.49.95.69.77.66.69.68.68.69.68.95.65.85.68.73.79.95.53.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_1_LEVEL
--
-- MIB ref		: swCardEventLogSlotXX       .33.79.85.84.80.85.84.95.49.95.69.77.66.69.68.68.69.68.95.65.85.68.73.79.95.54.95.49.95.76.69.86.69.76
-- absolute OID	: 1.3.6.1.4.1.7995.2.6.1.1.XX.33.79.85.84.80.85.84.95.49.95.69.77.66.69.68.68.69.68.95.65.85.68.73.79.95.54.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_2_LEVEL
--
-- MIB ref		: swCardEventLogSlotXX       .33.79.85.84.80.85.84.95.49.95.69.77.66.69.68.68.69.68.95.65.85.68.73.79.95.54.95.50.95.76.69.86.69.76
-- absolute OID	: 1.3.6.1.4.1.7995.2.6.1.1.XX.33.79.85.84.80.85.84.95.49.95.69.77.66.69.68.68.69.68.95.65.85.68.73.79.95.54.95.50.95.76.69.86.69.76
-- Vary			: YES
--
-- Value(s)		: OK
--				:
-- Comments		:
--
---------------------------------------------------------------------------------------------------
-- Header		: OUTPUT_1_EMBEDDED_AUDIO_7_1_LEVEL
--
-- MIB ref		: swCardEventLogSlotXX       .33.79.85.84.80.85.84.95.49.95.69.77.66.69.68.68.69.68.95.65.85.68.73.79.95.55.95.49.95.76.69.86.69.76
-- absolute OID	: 1.3.6.1.4.1.7995.2.6.1.1.XX.33.79.85.84.80.85.84.95.49.95.69.77.66.69.68.68.69.68.95.65.85.68.73.79.95.55.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_7_2_LEVEL
--
-- MIB ref		: swCardEventLogSlotXX       .33.79.85.84.80.85.84.95.49.95.69.77.66.69.68.68.69.68.95.65.85.68.73.79.95.55.95.50.95.76.69.86.69.76
-- absolute OID	: 1.3.6.1.4.1.7995.2.6.1.1.XX.33.79.85.84.80.85.84.95.49.95.69.77.66.69.68.68.69.68.95.65.85.68.73.79.95.55.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_1_LEVEL
--
-- MIB ref		: swCardEventLogSlotXX       .33.79.85.84.80.85.84.95.49.95.69.77.66.69.68.68.69.68.95.65.85.68.73.79.95.56.95.49.95.76.69.86.69.76
-- absolute OID	: 1.3.6.1.4.1.7995.2.6.1.1.XX.33.79.85.84.80.85.84.95.49.95.69.77.66.69.68.68.69.68.95.65.85.68.73.79.95.56.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_2_LEVEL
--
-- MIB ref		: swCardEventLogSlotXX       .33.79.85.84.80.85.84.95.49.95.69.77.66.69.68.68.69.68.95.65.85.68.73.79.95.56.95.50.95.76.69.86.69.76
-- absolute OID	: 1.3.6.1.4.1.7995.2.6.1.1.XX.33.79.85.84.80.85.84.95.49.95.69.77.66.69.68.68.69.68.95.65.85.68.73.79.95.56.95.50.95.76.69.86.69.76
-- Vary			: YES
--
-- Value(s)		: OK
--				: WARN:Silent
--              : WARN:Quiet
--              : WARN:Loud
--              : WARN:Overflow
-- Comments		:
--
---------------------------------------------------------------------------------------------------
