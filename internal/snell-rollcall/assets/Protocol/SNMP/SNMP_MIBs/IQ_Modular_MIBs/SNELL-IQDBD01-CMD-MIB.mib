-- ************************************************************************************
-- Snell Card:IQDBD01
--        Module Id#:499
--       Command Set:6
--          Filename:SNELL-IQDBD01-CMD-MIB.mib
--            Author:Jonathan Riches
--              Date:22/04/2010
--              Time:15:56
--
-- Copyright (c) 2010 Snell Ltd
-- All rights reserved.
--
-- ************************************************************************************

SNELL-IQDBD01-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDBD01,
    moduleIQDBD01MIB
        FROM SNELL-WILCOX-PRODUCT-REG;

 moduleIQDBD01CmdMi MODULE-IDENTITY
    LAST-UPDATED "1004221556Z"
    ORGANIZATION "Snell Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell card, command set  translations."
    ::= { moduleIQDBD01MIB 1 }




--********************************************************************************
--*
--*  Snell Card:
--*  command set:
--*  list commands/menus:
--*
--******************************************************************************
	iqdbd01CmdTable OBJECT-TYPE
		SYNTAX			SEQUENCE OF Iqdbd01CmdEntry
		MAX-ACCESS		not-accessible
		STATUS			current
		DESCRIPTION
				"Note the instance of this table is relected in the command set Version"
		::= { moduleIQDBD01 1 }

	iqdbd01CmdEntry OBJECT-TYPE
		SYNTAX		Iqdbd01CmdEntry
		MAX-ACCESS		not-accessible
		STATUS			current
		DESCRIPTION
				"Entry in command table."
		INDEX	{ iqdbd01SlotIndex }
		::= { iqdbd01CmdTable 1 }

	Iqdbd01CmdEntry ::=
		SEQUENCE {
			iqdbd01SlotIndex
				Unsigned32,
			iqdbd01InputIPLoss
				INTEGER,
			iqdbd01InputValidStdsAllValid
				INTEGER,
			iqdbd01InputValidStdsAllInvalid
				INTEGER,
			iqdbd01InputValidStds108023sF
				INTEGER,
			iqdbd01InputValidStds108023p
				INTEGER,
			iqdbd01InputValidStds108024sF
				INTEGER,
			iqdbd01InputValidStds108024p
				INTEGER,
			iqdbd01InputValidStds108025i
				INTEGER,
			iqdbd01InputValidStds108025p
				INTEGER,
			iqdbd01InputValidStds103529i
				INTEGER,
			iqdbd01InputValidStds108029i
				INTEGER,
			iqdbd01InputValidStds108029p
				INTEGER,
			iqdbd01InputValidStds103530i
				INTEGER,
			iqdbd01InputValidStds108030i
				INTEGER,
			iqdbd01InputValidStds108030p
				INTEGER,
			iqdbd01InputValidStds72050p
				INTEGER,
			iqdbd01InputValidStds72059p
				INTEGER,
			iqdbd01InputValidStds72060p
				INTEGER,
			iqdbd01InputValidStds62525i
				INTEGER,
			iqdbd01InputValidStds52529i
				INTEGER,
			iqdbd01InputErrorsCRCErrs
				RollCallString,
			iqdbd01InputErrorsCRCErrSec
				RollCallString,
			iqdbd01InputErrorsANCErrs
				RollCallString,
			iqdbd01InputErrorsANCErrSec
				RollCallString,
			iqdbd01InputErrorsResetSec
				RollCallString,
			iqdbd01InputErrorsErrorReset
				INTEGER,
			iqdbd01OutputOutputStandard
				INTEGER,
			iqdbd01OutputSelectStandard
				INTEGER,
			iqdbd01OutputVideoProcAmpsMasterGain
				INTEGER,
			iqdbd01OutputVideoProcAmpsYGain
				INTEGER,
			iqdbd01OutputVideoProcAmpsCGain
				INTEGER,
			iqdbd01OutputVideoProcAmpsBlackLevel
				INTEGER,
			iqdbd01OutputDefaultOutput
				INTEGER,
			iqdbd01OutputDefaultOPStd
				INTEGER,
			iqdbd01AudioDelayASourcesManual
				INTEGER,
			iqdbd01AudioDelayASourcesGPIPWM
				INTEGER,
			iqdbd01AudioDelayASourcesRollTrack14
				INTEGER,
			iqdbd01AudioDelayASourcesRollTrack15
				INTEGER,
			iqdbd01AudioDelayASourcesRollTrack16
				INTEGER,
			iqdbd01AudioDelayASourcesRollTrack17
				INTEGER,
			iqdbd01AudDelaysAudioDelayAAdjustCoarseDelay
				INTEGER,
			iqdbd01AudDelaysAudioDelayACurrentAudioDelay
				RollCallString,
			iqdbd01AudioDelayBSourcesManual
				INTEGER,
			iqdbd01AudioDelayBSourcesGPIPWM
				INTEGER,
			iqdbd01AudioDelayBSourcesRollTrack14
				INTEGER,
			iqdbd01AudioDelayBSourcesRollTrack15
				INTEGER,
			iqdbd01AudioDelayBSourcesRollTrack16
				INTEGER,
			iqdbd01AudioDelayBSourcesRollTrack17
				INTEGER,
			iqdbd01AudDelaysAudioDelayBAdjustCoarseDelay
				INTEGER,
			iqdbd01AudDelaysAudioDelayBCurrentAudioDelay
				RollCallString,
			iqdbd01AudDelaysAESDelaySelectDelay1
				INTEGER,
			iqdbd01AudDelaysAESDelaySelectInternal1
				INTEGER,
			iqdbd01AudDelaysAESDelaySelectAutoDolbyEPhase1
				INTEGER,
			iqdbd01AudDelaysAESDelaySelectDelayLimit1
				RollCallString,
			iqdbd01AudDelaysAESDelaySelectAES1FineDelay
				INTEGER,
			iqdbd01AudDelaysAESDelaySelectDelay2
				INTEGER,
			iqdbd01AudDelaysAESDelaySelectInternal2
				INTEGER,
			iqdbd01AudDelaysAESDelaySelectAutoDolbyEPhase2
				INTEGER,
			iqdbd01AudDelaysAESDelaySelectDelayLimit2
				RollCallString,
			iqdbd01AudDelaysAESDelaySelectAES2FineDelay
				INTEGER,
			iqdbd01AudDelaysAESDelaySelectDelay3
				INTEGER,
			iqdbd01AudDelaysAESDelaySelectInternal3
				INTEGER,
			iqdbd01AudDelaysAESDelaySelectAutoDolbyEPhase3
				INTEGER,
			iqdbd01AudDelaysAESDelaySelectDelayLimit3
				RollCallString,
			iqdbd01AudDelaysAESDelaySelectAES3FineDelay
				INTEGER,
			iqdbd01AudDelaysAESDelaySelectDelay4
				INTEGER,
			iqdbd01AudDelaysAESDelaySelectInternal4
				INTEGER,
			iqdbd01AudDelaysAESDelaySelectAutoDolbyEPhase4
				INTEGER,
			iqdbd01AudDelaysAESDelaySelectDelayLimit4
				RollCallString,
			iqdbd01AudDelaysAESDelaySelectAES4FineDelay
				INTEGER,
			iqdbd01AudDelaysAESDelaySelectDelay5
				INTEGER,
			iqdbd01AudDelaysAESDelaySelectInternal5
				INTEGER,
			iqdbd01AudDelaysAESDelaySelectAutoDolbyEPhase5
				INTEGER,
			iqdbd01AudDelaysAESDelaySelectDelayLimit5
				RollCallString,
			iqdbd01AudDelaysAESDelaySelectAES5FineDelay
				INTEGER,
			iqdbd01AudDelaysAESDelaySelectDelay6
				INTEGER,
			iqdbd01AudDelaysAESDelaySelectInternal6
				INTEGER,
			iqdbd01AudDelaysAESDelaySelectAutoDolbyEPhase6
				INTEGER,
			iqdbd01AudDelaysAESDelaySelectDelayLimit6
				RollCallString,
			iqdbd01AudDelaysAESDelaySelectAES6FineDelay
				INTEGER,
			iqdbd01AudDelaysAESDelaySelectDelay7
				INTEGER,
			iqdbd01AudDelaysAESDelaySelectInternal7
				INTEGER,
			iqdbd01AudDelaysAESDelaySelectAutoDolbyEPhase7
				INTEGER,
			iqdbd01AudDelaysAESDelaySelectDelayLimit7
				RollCallString,
			iqdbd01AudDelaysAESDelaySelectAES7FineDelay
				INTEGER,
			iqdbd01AudDelaysAESDelaySelectDelay8
				INTEGER,
			iqdbd01AudDelaysAESDelaySelectInternal8
				INTEGER,
			iqdbd01AudDelaysAESDelaySelectAutoDolbyEPhase8
				INTEGER,
			iqdbd01AudDelaysAESDelaySelectDelayLimit8
				RollCallString,
			iqdbd01AudDelaysAESDelaySelectAES8FineDelay
				INTEGER,
			iqdbd01AudDelaysEMBDelaySelectDelay1
				INTEGER,
			iqdbd01AudDelaysEMBDelaySelectInternal1
				INTEGER,
			iqdbd01AudDelaysEMBDelaySelectAutoDolbyEPhase1
				INTEGER,
			iqdbd01AudDelaysEMBDelaySelectDelayLimit1
				RollCallString,
			iqdbd01AudDelaysEMBDelaySelectEMB1FineDelay
				INTEGER,
			iqdbd01AudDelaysEMBDelaySelectDelay2
				INTEGER,
			iqdbd01AudDelaysEMBDelaySelectInternal2
				INTEGER,
			iqdbd01AudDelaysEMBDelaySelectAutoDolbyEPhase2
				INTEGER,
			iqdbd01AudDelaysEMBDelaySelectDelayLimit2
				RollCallString,
			iqdbd01AudDelaysEMBDelaySelectEMB2FineDelay
				INTEGER,
			iqdbd01AudDelaysEMBDelaySelectDelay3
				INTEGER,
			iqdbd01AudDelaysEMBDelaySelectInternal3
				INTEGER,
			iqdbd01AudDelaysEMBDelaySelectAutoDolbyEPhase3
				INTEGER,
			iqdbd01AudDelaysEMBDelaySelectDelayLimit3
				RollCallString,
			iqdbd01AudDelaysEMBDelaySelectEMB3FineDelay
				INTEGER,
			iqdbd01AudDelaysEMBDelaySelectDelay4
				INTEGER,
			iqdbd01AudDelaysEMBDelaySelectInternal4
				INTEGER,
			iqdbd01AudDelaysEMBDelaySelectAutoDolbyEPhase4
				INTEGER,
			iqdbd01AudDelaysEMBDelaySelectDelayLimit4
				RollCallString,
			iqdbd01AudDelaysEMBDelaySelectEMB4FineDelay
				INTEGER,
			iqdbd01AudDelaysEMBDelaySelectDelay5
				INTEGER,
			iqdbd01AudDelaysEMBDelaySelectInternal5
				INTEGER,
			iqdbd01AudDelaysEMBDelaySelectAutoDolbyEPhase5
				INTEGER,
			iqdbd01AudDelaysEMBDelaySelectDelayLimit5
				RollCallString,
			iqdbd01AudDelaysEMBDelaySelectEMB5FineDelay
				INTEGER,
			iqdbd01AudDelaysEMBDelaySelectDelay6
				INTEGER,
			iqdbd01AudDelaysEMBDelaySelectInternal6
				INTEGER,
			iqdbd01AudDelaysEMBDelaySelectAutoDolbyEPhase6
				INTEGER,
			iqdbd01AudDelaysEMBDelaySelectDelayLimit6
				RollCallString,
			iqdbd01AudDelaysEMBDelaySelectEMB6FineDelay
				INTEGER,
			iqdbd01AudDelaysEMBDelaySelectDelay7
				INTEGER,
			iqdbd01AudDelaysEMBDelaySelectInternal7
				INTEGER,
			iqdbd01AudDelaysEMBDelaySelectAutoDolbyEPhase7
				INTEGER,
			iqdbd01AudDelaysEMBDelaySelectDelayLimit7
				RollCallString,
			iqdbd01AudDelaysEMBDelaySelectEMB7FineDelay
				INTEGER,
			iqdbd01AudDelaysEMBDelaySelectDelay8
				INTEGER,
			iqdbd01AudDelaysEMBDelaySelectInternal8
				INTEGER,
			iqdbd01AudDelaysEMBDelaySelectDelayLimit8
				RollCallString,
			iqdbd01AudDelaysEMBDelaySelectAutoDolbyEPhase8
				INTEGER,
			iqdbd01AudDelaysEMBDelaySelectEMB8FineDelay
				INTEGER,
			iqdbd01AudioAudDelaysRollTrack14
				RollCallString,
			iqdbd01AudioAudDelaysRollTrack15
				RollCallString,
			iqdbd01AudioAudDelaysRollTrack16
				RollCallString,
			iqdbd01AudioAudDelaysRollTrack17
				RollCallString,
			iqdbd01EmbCtrlGroupGroup1Audio
				INTEGER,
			iqdbd01EmbCtrlGroupGroup2Audio
				INTEGER,
			iqdbd01EmbCtrlGroupGroup3Audio
				INTEGER,
			iqdbd01EmbCtrlGroupGroup4Audio
				INTEGER,
			iqdbd01EmbCtrlChannelPair1LActive
				INTEGER,
			iqdbd01EmbCtrlChannelPair1RActive
				INTEGER,
			iqdbd01EmbCtrlChannelPair2LActive
				INTEGER,
			iqdbd01EmbCtrlChannelPair2RActive
				INTEGER,
			iqdbd01EmbCtrlChannelPair3LActive
				INTEGER,
			iqdbd01EmbCtrlChannelPair3RActive
				INTEGER,
			iqdbd01EmbCtrlChannelPair4LActive
				INTEGER,
			iqdbd01EmbCtrlChannelPair4RActive
				INTEGER,
			iqdbd01EmbCtrlChannelPair5LActive
				INTEGER,
			iqdbd01EmbCtrlChannelPair5RActive
				INTEGER,
			iqdbd01EmbCtrlChannelPair6LActive
				INTEGER,
			iqdbd01EmbCtrlChannelPair6RActive
				INTEGER,
			iqdbd01EmbCtrlChannelPair7LActive
				INTEGER,
			iqdbd01EmbCtrlChannelPair7RActive
				INTEGER,
			iqdbd01EmbCtrlChannelPair8LActive
				INTEGER,
			iqdbd01EmbCtrlChannelPair8RActive
				INTEGER,
			iqdbd01AudioEmbCtrlEmbedderPriority
				INTEGER,
			iqdbd01EmbGainEmbedPair1Embed1MuteL
				INTEGER,
			iqdbd01EmbGainEmbedPair1Embed1MuteR
				INTEGER,
			iqdbd01EmbGainEmbedPair1Embed1LGain
				INTEGER,
			iqdbd01EmbGainEmbedPair1Embed1RGain
				INTEGER,
			iqdbd01EmbGainEmbedPair1Stereo
				INTEGER,
			iqdbd01EmbGainEmbedPair1Embed1InvertL
				INTEGER,
			iqdbd01EmbGainEmbedPair1Embed1InvertR
				INTEGER,
			iqdbd01EmbGainEmbedPair1Embed1LClip
				RollCallString,
			iqdbd01EmbGainEmbedPair1Embed1RClip
				RollCallString,
			iqdbd01EmbGainEmbedPair2Embed2MuteL
				INTEGER,
			iqdbd01EmbGainEmbedPair2Embed2MuteR
				INTEGER,
			iqdbd01EmbGainEmbedPair2Embed2LGain
				INTEGER,
			iqdbd01EmbGainEmbedPair2Embed2RGain
				INTEGER,
			iqdbd01EmbGainEmbedPair2Stereo
				INTEGER,
			iqdbd01EmbGainEmbedPair2Embed2InvertL
				INTEGER,
			iqdbd01EmbGainEmbedPair2Embed2InvertR
				INTEGER,
			iqdbd01EmbGainEmbedPair2Embed2LClip
				RollCallString,
			iqdbd01EmbGainEmbedPair2Embed2RClip
				RollCallString,
			iqdbd01EmbGainEmbedPair3Embed3MuteL
				INTEGER,
			iqdbd01EmbGainEmbedPair3Embed3MuteR
				INTEGER,
			iqdbd01EmbGainEmbedPair3Embed3LGain
				INTEGER,
			iqdbd01EmbGainEmbedPair3Embed3RGain
				INTEGER,
			iqdbd01EmbGainEmbedPair3Stereo
				INTEGER,
			iqdbd01EmbGainEmbedPair3Embed3InvertL
				INTEGER,
			iqdbd01EmbGainEmbedPair3Embed3InvertR
				INTEGER,
			iqdbd01EmbGainEmbedPair3Embed3LClip
				RollCallString,
			iqdbd01EmbGainEmbedPair3Embed3RClip
				RollCallString,
			iqdbd01EmbGainEmbedPair4Embed4MuteL
				INTEGER,
			iqdbd01EmbGainEmbedPair4Embed4MuteR
				INTEGER,
			iqdbd01EmbGainEmbedPair4Embed4LGain
				INTEGER,
			iqdbd01EmbGainEmbedPair4Embed4RGain
				INTEGER,
			iqdbd01EmbGainEmbedPair4Stereo
				INTEGER,
			iqdbd01EmbGainEmbedPair4Embed4InvertL
				INTEGER,
			iqdbd01EmbGainEmbedPair4Embed4InvertR
				INTEGER,
			iqdbd01EmbGainEmbedPair4Embed4LClip
				RollCallString,
			iqdbd01EmbGainEmbedPair4Embed4RClip
				RollCallString,
			iqdbd01EmbGainEmbedPair5Embed5MuteL
				INTEGER,
			iqdbd01EmbGainEmbedPair5Embed5MuteR
				INTEGER,
			iqdbd01EmbGainEmbedPair5Embed5LGain
				INTEGER,
			iqdbd01EmbGainEmbedPair5Embed5RGain
				INTEGER,
			iqdbd01EmbGainEmbedPair5Stereo
				INTEGER,
			iqdbd01EmbGainEmbedPair5Embed5InvertL
				INTEGER,
			iqdbd01EmbGainEmbedPair5Embed5InvertR
				INTEGER,
			iqdbd01EmbGainEmbedPair5Embed5LClip
				RollCallString,
			iqdbd01EmbGainEmbedPair5Embed5RClip
				RollCallString,
			iqdbd01EmbGainEmbedPair6Embed6MuteL
				INTEGER,
			iqdbd01EmbGainEmbedPair6Embed6MuteR
				INTEGER,
			iqdbd01EmbGainEmbedPair6Embed6LGain
				INTEGER,
			iqdbd01EmbGainEmbedPair6Embed6RGain
				INTEGER,
			iqdbd01EmbGainEmbedPair6Stereo
				INTEGER,
			iqdbd01EmbGainEmbedPair6Embed6InvertL
				INTEGER,
			iqdbd01EmbGainEmbedPair6Embed6InvertR
				INTEGER,
			iqdbd01EmbGainEmbedPair6Embed6LClip
				RollCallString,
			iqdbd01EmbGainEmbedPair6Embed6RClip
				RollCallString,
			iqdbd01EmbGainEmbedPair7Embed7MuteL
				INTEGER,
			iqdbd01EmbGainEmbedPair7Embed7MuteR
				INTEGER,
			iqdbd01EmbGainEmbedPair7Embed7LGain
				INTEGER,
			iqdbd01EmbGainEmbedPair7Embed7RGain
				INTEGER,
			iqdbd01EmbGainEmbedPair7Stereo
				INTEGER,
			iqdbd01EmbGainEmbedPair7Embed7InvertL
				INTEGER,
			iqdbd01EmbGainEmbedPair7Embed7InvertR
				INTEGER,
			iqdbd01EmbGainEmbedPair7Embed7LClip
				RollCallString,
			iqdbd01EmbGainEmbedPair7Embed7RClip
				RollCallString,
			iqdbd01EmbGainEmbedPair8Embed8MuteL
				INTEGER,
			iqdbd01EmbGainEmbedPair8Embed8MuteR
				INTEGER,
			iqdbd01EmbGainEmbedPair8Embed8LGain
				INTEGER,
			iqdbd01EmbGainEmbedPair8Embed8RGain
				INTEGER,
			iqdbd01EmbGainEmbedPair8Stereo
				INTEGER,
			iqdbd01EmbGainEmbedPair8Embed8InvertL
				INTEGER,
			iqdbd01EmbGainEmbedPair8Embed8InvertR
				INTEGER,
			iqdbd01EmbGainEmbedPair8Embed8LClip
				RollCallString,
			iqdbd01EmbGainEmbedPair8Embed8RClip
				RollCallString,
			iqdbd01EmbOutEmbedPair1Left
				INTEGER,
			iqdbd01EmbOutEmbedPair1Right
				INTEGER,
			iqdbd01EmbOutEmbedPair1LinkLRSelection
				INTEGER,
			iqdbd01EmbOutEmbedPair2Left
				INTEGER,
			iqdbd01EmbOutEmbedPair2Right
				INTEGER,
			iqdbd01EmbOutEmbedPair2LinkLRSelection
				INTEGER,
			iqdbd01EmbOutEmbedPair3Left
				INTEGER,
			iqdbd01EmbOutEmbedPair3Right
				INTEGER,
			iqdbd01EmbOutEmbedPair3LinkLRSelection
				INTEGER,
			iqdbd01EmbOutEmbedPair4Left
				INTEGER,
			iqdbd01EmbOutEmbedPair4Right
				INTEGER,
			iqdbd01EmbOutEmbedPair4LinkLRSelection
				INTEGER,
			iqdbd01EmbOutEmbedPair5Left
				INTEGER,
			iqdbd01EmbOutEmbedPair5Right
				INTEGER,
			iqdbd01EmbOutEmbedPair5LinkLRSelection
				INTEGER,
			iqdbd01EmbOutEmbedPair6Left
				INTEGER,
			iqdbd01EmbOutEmbedPair6Right
				INTEGER,
			iqdbd01EmbOutEmbedPair6LinkLRSelection
				INTEGER,
			iqdbd01EmbOutEmbedPair7Left
				INTEGER,
			iqdbd01EmbOutEmbedPair7Right
				INTEGER,
			iqdbd01EmbOutEmbedPair7LinkLRSelection
				INTEGER,
			iqdbd01EmbOutEmbedPair8Left
				INTEGER,
			iqdbd01EmbOutEmbedPair8Right
				INTEGER,
			iqdbd01EmbOutEmbedPair8LinkLRSelection
				INTEGER,
			iqdbd01AudioEmbModeInput1
				INTEGER,
			iqdbd01AudioEmbModeInput2
				INTEGER,
			iqdbd01AudioEmbModeInput3
				INTEGER,
			iqdbd01AudioEmbModeInput4
				INTEGER,
			iqdbd01AudioEmbModeInput5
				INTEGER,
			iqdbd01AudioEmbModeInput6
				INTEGER,
			iqdbd01AudioEmbModeInput7
				INTEGER,
			iqdbd01AudioEmbModeInput8
				INTEGER,
			iqdbd01EmbNamesDisembederNamesDisembed1
				RollCallString,
			iqdbd01EmbNamesDisembederNamesDisembed1R
				RollCallString,
			iqdbd01EmbNamesDisembederNamesDisembed2
				RollCallString,
			iqdbd01EmbNamesDisembederNamesDisembed2R
				RollCallString,
			iqdbd01EmbNamesDisembederNamesDisembed3
				RollCallString,
			iqdbd01EmbNamesDisembederNamesDisembed3R
				RollCallString,
			iqdbd01EmbNamesDisembederNamesDisembed4
				RollCallString,
			iqdbd01EmbNamesDisembederNamesDisembed4R
				RollCallString,
			iqdbd01EmbNamesDisembederNamesDisembed5
				RollCallString,
			iqdbd01EmbNamesDisembederNamesDisembed5R
				RollCallString,
			iqdbd01EmbNamesDisembederNamesDisembed6
				RollCallString,
			iqdbd01EmbNamesDisembederNamesDisembed6R
				RollCallString,
			iqdbd01EmbNamesDisembederNamesDisembed7
				RollCallString,
			iqdbd01EmbNamesDisembederNamesDisembed7R
				RollCallString,
			iqdbd01EmbNamesDisembederNamesDisembed8
				RollCallString,
			iqdbd01EmbNamesDisembederNamesDisembed8R
				RollCallString,
			iqdbd01EmbNamesEmbeddedOPNamesEmbed1
				RollCallString,
			iqdbd01EmbNamesEmbeddedOPNamesEmbed1R
				RollCallString,
			iqdbd01EmbNamesEmbeddedOPNamesEmbed2
				RollCallString,
			iqdbd01EmbNamesEmbeddedOPNamesEmbed2R
				RollCallString,
			iqdbd01EmbNamesEmbeddedOPNamesEmbed3
				RollCallString,
			iqdbd01EmbNamesEmbeddedOPNamesEmbed3R
				RollCallString,
			iqdbd01EmbNamesEmbeddedOPNamesEmbed4
				RollCallString,
			iqdbd01EmbNamesEmbeddedOPNamesEmbed4R
				RollCallString,
			iqdbd01EmbNamesEmbeddedOPNamesEmbed5
				RollCallString,
			iqdbd01EmbNamesEmbeddedOPNamesEmbed5R
				RollCallString,
			iqdbd01EmbNamesEmbeddedOPNamesEmbed6
				RollCallString,
			iqdbd01EmbNamesEmbeddedOPNamesEmbed6R
				RollCallString,
			iqdbd01EmbNamesEmbeddedOPNamesEmbed7
				RollCallString,
			iqdbd01EmbNamesEmbeddedOPNamesEmbed7R
				RollCallString,
			iqdbd01EmbNamesEmbeddedOPNamesEmbed8
				RollCallString,
			iqdbd01EmbNamesEmbeddedOPNamesEmbed8R
				RollCallString,
			iqdbd01EmbNamesIPNamesStereoDisemb1
				INTEGER,
			iqdbd01EmbNamesIPNamesStereoDisemb2
				INTEGER,
			iqdbd01EmbNamesIPNamesStereoDisemb3
				INTEGER,
			iqdbd01EmbNamesIPNamesStereoDisemb4
				INTEGER,
			iqdbd01EmbNamesIPNamesStereoDisemb5
				INTEGER,
			iqdbd01EmbNamesIPNamesStereoDisemb6
				INTEGER,
			iqdbd01EmbNamesIPNamesStereoDisemb7
				INTEGER,
			iqdbd01EmbNamesIPNamesStereoDisemb8
				INTEGER,
			iqdbd01EmbNamesOPNamesStereoEmbed1
				INTEGER,
			iqdbd01EmbNamesOPNamesStereoEmbed2
				INTEGER,
			iqdbd01EmbNamesOPNamesStereoEmbed3
				INTEGER,
			iqdbd01EmbNamesOPNamesStereoEmbed4
				INTEGER,
			iqdbd01EmbNamesOPNamesStereoEmbed5
				INTEGER,
			iqdbd01EmbNamesOPNamesStereoEmbed6
				INTEGER,
			iqdbd01EmbNamesOPNamesStereoEmbed7
				INTEGER,
			iqdbd01EmbNamesOPNamesStereoEmbed8
				INTEGER,
			iqdbd01AudioMixNamesMix1
				RollCallString,
			iqdbd01AudioMixNamesMix2
				RollCallString,
			iqdbd01AudioMixNamesMix3
				RollCallString,
			iqdbd01AudioMixNamesMix4
				RollCallString,
			iqdbd01Mix1RoutingSource1
				INTEGER,
			iqdbd01Mix1RoutingInvert1
				INTEGER,
			iqdbd01Mix1RoutingSource2
				INTEGER,
			iqdbd01Mix1RoutingInvert2
				INTEGER,
			iqdbd01Mix1RoutingSource3
				INTEGER,
			iqdbd01Mix1RoutingInvert3
				INTEGER,
			iqdbd01Mix1RoutingSource4
				INTEGER,
			iqdbd01Mix1RoutingInvert4
				INTEGER,
			iqdbd01Mix1GainGain1
				INTEGER,
			iqdbd01Mix1GainMute1
				INTEGER,
			iqdbd01Mix1GainGain2
				INTEGER,
			iqdbd01Mix1GainMute2
				INTEGER,
			iqdbd01Mix1GainGain3
				INTEGER,
			iqdbd01Mix1GainMute3
				INTEGER,
			iqdbd01Mix1GainGain4
				INTEGER,
			iqdbd01Mix1GainMute4
				INTEGER,
			iqdbd01Mix1GainInp1Clip
				RollCallString,
			iqdbd01Mix1GainInp2Clip
				RollCallString,
			iqdbd01Mix1GainInp3Clip
				RollCallString,
			iqdbd01Mix1GainInp4Clip
				RollCallString,
			iqdbd01Mix1GainOPClip
				RollCallString,
			iqdbd01Mix2RoutingSource1
				INTEGER,
			iqdbd01Mix2RoutingInvert1
				INTEGER,
			iqdbd01Mix2RoutingSource2
				INTEGER,
			iqdbd01Mix2RoutingInvert2
				INTEGER,
			iqdbd01Mix2RoutingSource3
				INTEGER,
			iqdbd01Mix2RoutingInvert3
				INTEGER,
			iqdbd01Mix2RoutingSource4
				INTEGER,
			iqdbd01Mix2RoutingInvert4
				INTEGER,
			iqdbd01Mix2GainGain1
				INTEGER,
			iqdbd01Mix2GainMute1
				INTEGER,
			iqdbd01Mix2GainGain2
				INTEGER,
			iqdbd01Mix2GainMute2
				INTEGER,
			iqdbd01Mix2GainGain3
				INTEGER,
			iqdbd01Mix2GainMute3
				INTEGER,
			iqdbd01Mix2GainGain4
				INTEGER,
			iqdbd01Mix2GainMute4
				INTEGER,
			iqdbd01Mix2GainInp1Clip
				RollCallString,
			iqdbd01Mix2GainInp2Clip
				RollCallString,
			iqdbd01Mix2GainInp3Clip
				RollCallString,
			iqdbd01Mix2GainInp4Clip
				RollCallString,
			iqdbd01Mix2GainOPClip
				RollCallString,
			iqdbd01Mix3RoutingSource1
				INTEGER,
			iqdbd01Mix3RoutingInvert1
				INTEGER,
			iqdbd01Mix3RoutingSource2
				INTEGER,
			iqdbd01Mix3RoutingInvert2
				INTEGER,
			iqdbd01Mix3RoutingSource3
				INTEGER,
			iqdbd01Mix3RoutingInvert3
				INTEGER,
			iqdbd01Mix3RoutingSource4
				INTEGER,
			iqdbd01Mix3RoutingInvert4
				INTEGER,
			iqdbd01Mix3GainGain1
				INTEGER,
			iqdbd01Mix3GainMute1
				INTEGER,
			iqdbd01Mix3GainGain2
				INTEGER,
			iqdbd01Mix3GainMute2
				INTEGER,
			iqdbd01Mix3GainGain3
				INTEGER,
			iqdbd01Mix3GainMute3
				INTEGER,
			iqdbd01Mix3GainGain4
				INTEGER,
			iqdbd01Mix3GainMute4
				INTEGER,
			iqdbd01Mix3GainInp1Clip
				RollCallString,
			iqdbd01Mix3GainInp2Clip
				RollCallString,
			iqdbd01Mix3GainInp3Clip
				RollCallString,
			iqdbd01Mix3GainInp4Clip
				RollCallString,
			iqdbd01Mix3GainOPClip
				RollCallString,
			iqdbd01Mix4RoutingSource1
				INTEGER,
			iqdbd01Mix4RoutingInvert1
				INTEGER,
			iqdbd01Mix4RoutingSource2
				INTEGER,
			iqdbd01Mix4RoutingInvert2
				INTEGER,
			iqdbd01Mix4RoutingSource3
				INTEGER,
			iqdbd01Mix4RoutingInvert3
				INTEGER,
			iqdbd01Mix4RoutingSource4
				INTEGER,
			iqdbd01Mix4RoutingInvert4
				INTEGER,
			iqdbd01Mix4GainGain1
				INTEGER,
			iqdbd01Mix4GainMute1
				INTEGER,
			iqdbd01Mix4GainGain2
				INTEGER,
			iqdbd01Mix4GainMute2
				INTEGER,
			iqdbd01Mix4GainGain3
				INTEGER,
			iqdbd01Mix4GainMute3
				INTEGER,
			iqdbd01Mix4GainGain4
				INTEGER,
			iqdbd01Mix4GainMute4
				INTEGER,
			iqdbd01Mix4GainInp1Clip
				RollCallString,
			iqdbd01Mix4GainInp2Clip
				RollCallString,
			iqdbd01Mix4GainInp3Clip
				RollCallString,
			iqdbd01Mix4GainInp4Clip
				RollCallString,
			iqdbd01Mix4GainOPClip
				RollCallString,
			iqdbd01AESGainAESOut1AESOut1MuteL
				INTEGER,
			iqdbd01AESGainAESOut1AESOut1MuteR
				INTEGER,
			iqdbd01AESGainAESOut1AESOut1LGain
				INTEGER,
			iqdbd01AESGainAESOut1AESOut1RGain
				INTEGER,
			iqdbd01AESGainAESOut1Stereo
				INTEGER,
			iqdbd01AESGainAESOut1AESOut1InvertL
				INTEGER,
			iqdbd01AESGainAESOut1AESOut1InvertR
				INTEGER,
			iqdbd01AESGainAESOut1AESOut1LClip
				RollCallString,
			iqdbd01AESGainAESOut1AESOut1RClip
				RollCallString,
			iqdbd01AESGainAESOut2AESOut2MuteL
				INTEGER,
			iqdbd01AESGainAESOut2AESOut2MuteR
				INTEGER,
			iqdbd01AESGainAESOut2AESOut2LGain
				INTEGER,
			iqdbd01AESGainAESOut2AESOut2RGain
				INTEGER,
			iqdbd01AESGainAESOut2Stereo
				INTEGER,
			iqdbd01AESGainAESOut2AESOut2InvertL
				INTEGER,
			iqdbd01AESGainAESOut2AESOut2InvertR
				INTEGER,
			iqdbd01AESGainAESOut2AESOut2LClip
				RollCallString,
			iqdbd01AESGainAESOut2AESOut2RClip
				RollCallString,
			iqdbd01AESGainAESOut3AESOut3MuteL
				INTEGER,
			iqdbd01AESGainAESOut3AESOut3MuteR
				INTEGER,
			iqdbd01AESGainAESOut3AESOut3LGain
				INTEGER,
			iqdbd01AESGainAESOut3AESOut3RGain
				INTEGER,
			iqdbd01AESGainAESOut3Stereo
				INTEGER,
			iqdbd01AESGainAESOut3AESOut3InvertL
				INTEGER,
			iqdbd01AESGainAESOut3AESOut3InvertR
				INTEGER,
			iqdbd01AESGainAESOut3AESOut3LClip
				RollCallString,
			iqdbd01AESGainAESOut3AESOut3RClip
				RollCallString,
			iqdbd01AESGainAESOut4AESOut4MuteL
				INTEGER,
			iqdbd01AESGainAESOut4AESOut4MuteR
				INTEGER,
			iqdbd01AESGainAESOut4AESOut4LGain
				INTEGER,
			iqdbd01AESGainAESOut4AESOut4RGain
				INTEGER,
			iqdbd01AESGainAESOut4Stereo
				INTEGER,
			iqdbd01AESGainAESOut4AESOut4InvertL
				INTEGER,
			iqdbd01AESGainAESOut4AESOut4InvertR
				INTEGER,
			iqdbd01AESGainAESOut4AESOut4LClip
				RollCallString,
			iqdbd01AESGainAESOut4AESOut4RClip
				RollCallString,
			iqdbd01AESGainAESOut5AESOut5MuteL
				INTEGER,
			iqdbd01AESGainAESOut5AESOut5MuteR
				INTEGER,
			iqdbd01AESGainAESOut5AESOut5LGain
				INTEGER,
			iqdbd01AESGainAESOut5AESOut5RGain
				INTEGER,
			iqdbd01AESGainAESOut5Stereo
				INTEGER,
			iqdbd01AESGainAESOut5AESOut5InvertL
				INTEGER,
			iqdbd01AESGainAESOut5AESOut5InvertR
				INTEGER,
			iqdbd01AESGainAESOut5AESOut5LClip
				RollCallString,
			iqdbd01AESGainAESOut5AESOut5RClip
				RollCallString,
			iqdbd01AESGainAESOut6AESOut6MuteL
				INTEGER,
			iqdbd01AESGainAESOut6AESOut6MuteR
				INTEGER,
			iqdbd01AESGainAESOut6AESOut6LGain
				INTEGER,
			iqdbd01AESGainAESOut6AESOut6RGain
				INTEGER,
			iqdbd01AESGainAESOut6Stereo
				INTEGER,
			iqdbd01AESGainAESOut6AESOut6InvertL
				INTEGER,
			iqdbd01AESGainAESOut6AESOut6InvertR
				INTEGER,
			iqdbd01AESGainAESOut6AESOut6LClip
				RollCallString,
			iqdbd01AESGainAESOut6AESOut6RClip
				RollCallString,
			iqdbd01AESGainAESOut7AESOut7MuteL
				INTEGER,
			iqdbd01AESGainAESOut7AESOut7MuteR
				INTEGER,
			iqdbd01AESGainAESOut7AESOut7LGain
				INTEGER,
			iqdbd01AESGainAESOut7AESOut7RGain
				INTEGER,
			iqdbd01AESGainAESOut7Stereo
				INTEGER,
			iqdbd01AESGainAESOut7AESOut7InvertL
				INTEGER,
			iqdbd01AESGainAESOut7AESOut7InvertR
				INTEGER,
			iqdbd01AESGainAESOut7AESOut7LClip
				RollCallString,
			iqdbd01AESGainAESOut7AESOut7RClip
				RollCallString,
			iqdbd01AESGainAESOut8AESOut8MuteL
				INTEGER,
			iqdbd01AESGainAESOut8AESOut8MuteR
				INTEGER,
			iqdbd01AESGainAESOut8AESOut8LGain
				INTEGER,
			iqdbd01AESGainAESOut8AESOut8RGain
				INTEGER,
			iqdbd01AESGainAESOut8Stereo
				INTEGER,
			iqdbd01AESGainAESOut8AESOut8InvertL
				INTEGER,
			iqdbd01AESGainAESOut8AESOut8InvertR
				INTEGER,
			iqdbd01AESGainAESOut8AESOut8LClip
				RollCallString,
			iqdbd01AESGainAESOut8AESOut8RClip
				RollCallString,
			iqdbd01AESOutAESOut1Left
				INTEGER,
			iqdbd01AESOutAESOut1Right
				INTEGER,
			iqdbd01AESOutAESOut1LinkLRSelection
				INTEGER,
			iqdbd01AESOutAESOut3Left
				INTEGER,
			iqdbd01AESOutAESOut3Right
				INTEGER,
			iqdbd01AESOutAESOut3LinkLRSelection
				INTEGER,
			iqdbd01AESOutAESOut4Left
				INTEGER,
			iqdbd01AESOutAESOut4Right
				INTEGER,
			iqdbd01AESOutAESOut4LinkLRSelection
				INTEGER,
			iqdbd01AESOutAESOut5Left
				INTEGER,
			iqdbd01AESOutAESOut5Right
				INTEGER,
			iqdbd01AESOutAESOut5LinkLRSelection
				INTEGER,
			iqdbd01AESOutAESOut6Left
				INTEGER,
			iqdbd01AESOutAESOut6Right
				INTEGER,
			iqdbd01AESOutAESOut6LinkLRSelection
				INTEGER,
			iqdbd01AESOutAESOut7Left
				INTEGER,
			iqdbd01AESOutAESOut7Right
				INTEGER,
			iqdbd01AESOutAESOut7LinkLRSelection
				INTEGER,
			iqdbd01AESOutAESOut8Left
				INTEGER,
			iqdbd01AESOutAESOut8Right
				INTEGER,
			iqdbd01AESOutAESOut8LinkLRSelection
				INTEGER,
			iqdbd01AESOutMonitoropLeft
				INTEGER,
			iqdbd01AESOutMonitoropRight
				INTEGER,
			iqdbd01AESOutMonitoropLinkLRSelection
				INTEGER,
			iqdbd01AESOutAESPortNamesAESPort1Stereo
				INTEGER,
			iqdbd01AESOutAESPortNamesAESPort1L
				RollCallString,
			iqdbd01AESOutAESPortNamesAESPort1R
				RollCallString,
			iqdbd01AESOutAESPortNamesAESPort2Stereo
				INTEGER,
			iqdbd01AESOutAESPortNamesAESPort2L
				RollCallString,
			iqdbd01AESOutAESPortNamesAESPort2R
				RollCallString,
			iqdbd01AESOutAESPortNamesAESPort3Stereo
				INTEGER,
			iqdbd01AESOutAESPortNamesAESPort3L
				RollCallString,
			iqdbd01AESOutAESPortNamesAESPort3R
				RollCallString,
			iqdbd01AESOutAESPortNamesAESPort4Stereo
				INTEGER,
			iqdbd01AESOutAESPortNamesAESPort4L
				RollCallString,
			iqdbd01AESOutAESPortNamesAESPort4R
				RollCallString,
			iqdbd01AESOutAESPortNamesAESPort5Stereo
				INTEGER,
			iqdbd01AESOutAESPortNamesAESPort5L
				RollCallString,
			iqdbd01AESOutAESPortNamesAESPort5R
				RollCallString,
			iqdbd01AESOutAESPortNamesAESPort6Stereo
				INTEGER,
			iqdbd01AESOutAESPortNamesAESPort6L
				RollCallString,
			iqdbd01AESOutAESPortNamesAESPort6R
				RollCallString,
			iqdbd01AESOutAESPortNamesAESPort7Stereo
				INTEGER,
			iqdbd01AESOutAESPortNamesAESPort7L
				RollCallString,
			iqdbd01AESOutAESPortNamesAESPort7R
				RollCallString,
			iqdbd01AESOutAESPortNamesAESPort8Stereo
				INTEGER,
			iqdbd01AESOutAESPortNamesAESPort8L
				RollCallString,
			iqdbd01AESOutAESPortNamesAESPort8R
				RollCallString,
			iqdbd01AESPortNamesAESOut2Left
				INTEGER,
			iqdbd01AESPortNamesAESOut2Right
				INTEGER,
			iqdbd01AESPortNamesAESOut2LinkLRSelection
				INTEGER,
			iqdbd01AESBusAESDataModeInput1
				INTEGER,
			iqdbd01AESBusAESDataModeInput2
				INTEGER,
			iqdbd01AESBusAESDataModeInput3
				INTEGER,
			iqdbd01AESBusAESDataModeInput4
				INTEGER,
			iqdbd01AESBusAESDataModeInput5
				INTEGER,
			iqdbd01AESBusAESDataModeInput6
				INTEGER,
			iqdbd01AESBusAESDataModeInput7
				INTEGER,
			iqdbd01AESBusAESDataModeInput8
				INTEGER,
			iqdbd01AESBusAESBusNamesAESBus1Stereo
				INTEGER,
			iqdbd01AESBusAESBusNamesAESBus1
				RollCallString,
			iqdbd01AESBusAESBusNamesAESBus1R
				RollCallString,
			iqdbd01AESBusAESBusNamesAESBus2Stereo
				INTEGER,
			iqdbd01AESBusAESBusNamesAESBus2
				RollCallString,
			iqdbd01AESBusAESBusNamesAESBus2R
				RollCallString,
			iqdbd01AESBusAESBusNamesAESBus3Stereo
				INTEGER,
			iqdbd01AESBusAESBusNamesAESBus3
				RollCallString,
			iqdbd01AESBusAESBusNamesAESBus3R
				RollCallString,
			iqdbd01AESBusAESBusNamesAESBus4Stereo
				INTEGER,
			iqdbd01AESBusAESBusNamesAESBus4
				RollCallString,
			iqdbd01AESBusAESBusNamesAESBus4R
				RollCallString,
			iqdbd01AESBusAESBusNamesAESBus5Stereo
				INTEGER,
			iqdbd01AESBusAESBusNamesAESBus5
				RollCallString,
			iqdbd01AESBusAESBusNamesAESBus5R
				RollCallString,
			iqdbd01AESBusAESBusNamesAESBus6Stereo
				INTEGER,
			iqdbd01AESBusAESBusNamesAESBus6
				RollCallString,
			iqdbd01AESBusAESBusNamesAESBus6R
				RollCallString,
			iqdbd01AESBusAESBusNamesAESBus7Stereo
				INTEGER,
			iqdbd01AESBusAESBusNamesAESBus7
				RollCallString,
			iqdbd01AESBusAESBusNamesAESBus7R
				RollCallString,
			iqdbd01AESBusAESBusNamesAESBus8Stereo
				INTEGER,
			iqdbd01AESBusAESBusNamesAESBus8
				RollCallString,
			iqdbd01AESBusAESBusNamesAESBus8R
				RollCallString,
			iqdbd01AESBusAESBusRoutingSource1
				INTEGER,
			iqdbd01AESBusAESBusRoutingSource2
				INTEGER,
			iqdbd01AESBusAESBusRoutingSource3
				INTEGER,
			iqdbd01AESBusAESBusRoutingSource4
				INTEGER,
			iqdbd01AESBusAESBusRoutingSource5
				INTEGER,
			iqdbd01AESBusAESBusRoutingSource6
				INTEGER,
			iqdbd01AESBusAESBusRoutingSource7
				INTEGER,
			iqdbd01AESBusAESBusRoutingSource8
				INTEGER,
			iqdbd01AESPortsAESDirectionAESPort1Dir
				INTEGER,
			iqdbd01AESPortsAESDirectionAESPort2Dir
				INTEGER,
			iqdbd01AESPortsAESDirectionAESPort3Dir
				INTEGER,
			iqdbd01AESPortsAESDirectionAESPort4Dir
				INTEGER,
			iqdbd01AESPortsAESDirectionAESPort5Dir
				INTEGER,
			iqdbd01AESPortsAESDirectionAESPort6Dir
				INTEGER,
			iqdbd01AESPortsAESDirectionAESPort7Dir
				INTEGER,
			iqdbd01AESPortsAESDirectionAESPort8Dir
				INTEGER,
			iqdbd01EngineerPageDolbyETimingSelAudioPair
				INTEGER,
			iqdbd01AudioDolbyETimingRelativeTiming
				RollCallString,
			iqdbd01AudioDolbyETimingStatus
				RollCallString,
			iqdbd01AudioDolbyETimingError
				RollCallString,
			iqdbd01DolbyETimingDolbyELineStandard
				INTEGER,
			iqdbd01DolbyETimingDolbyELineAutoLineNo
				INTEGER,
			iqdbd01DolbyELineUserDolbyELinePair1
				INTEGER,
			iqdbd01DolbyELineUserDolbyELinePair2
				INTEGER,
			iqdbd01DolbyELineUserDolbyELinePair3
				INTEGER,
			iqdbd01DolbyELineUserDolbyELinePair4
				INTEGER,
			iqdbd01DolbyELineUserDolbyELinePair5
				INTEGER,
			iqdbd01DolbyELineUserDolbyELinePair6
				INTEGER,
			iqdbd01DolbyELineUserDolbyELinePair7
				INTEGER,
			iqdbd01DolbyELineUserDolbyELinePair8
				INTEGER,
			iqdbd01AudioDolbyDecoderDecoderSourceSel
				INTEGER,
			iqdbd01AudioDolbyDecoderAESBus4SourceSel
				INTEGER,
			iqdbd01AudioDolbyDecoderMonitorSourceSel
				INTEGER,
			iqdbd01AudioDolbyDecoderBitstreamDetmode
				INTEGER,
			iqdbd01AudioDolbyDecoderDynamicRange
				INTEGER,
			iqdbd01AudioDolbyDecoderListeningModeDD
				INTEGER,
			iqdbd01AudioDolbyDecoderPCMLatency
				INTEGER,
			iqdbd01AudioDolbyDecoderDisplayLatency
				RollCallString,
			iqdbd01AudioDolbyDecoderAESChanSel
				INTEGER,
			iqdbd01AudioDolbyDecoderAuxChanOPMode
				INTEGER,
			iqdbd01AudioDolbyDecoderAuxChanPgmSel
				INTEGER,
			iqdbd01AudioDolbyDecoderAuxChanDynRange
				INTEGER,
			iqdbd01AudioDolbyDecoderSoftwareVersion
				RollCallString,
			iqdbd01AudioDolbyDecoderResetErrorCounts
				INTEGER,
			iqdbd01DolbyDecoderCenterMixLevelProgram1
				RollCallString,
			iqdbd01DolbyDecoderCenterMixLevelProgram2
				RollCallString,
			iqdbd01DolbyDecoderCenterMixLevelProgram3
				RollCallString,
			iqdbd01DolbyDecoderCenterMixLevelProgram4
				RollCallString,
			iqdbd01DolbyDecoderCenterMixLevelProgram5
				RollCallString,
			iqdbd01DolbyDecoderCenterMixLevelProgram6
				RollCallString,
			iqdbd01DolbyDecoderCenterMixLevelProgram7
				RollCallString,
			iqdbd01DolbyDecoderCenterMixLevelProgram8
				RollCallString,
			iqdbd01DolbyDecoderSurroundMixLevelProgram1
				RollCallString,
			iqdbd01DolbyDecoderSurroundMixLevelProgram2
				RollCallString,
			iqdbd01DolbyDecoderSurroundMixLevelProgram3
				RollCallString,
			iqdbd01DolbyDecoderSurroundMixLevelProgram4
				RollCallString,
			iqdbd01DolbyDecoderSurroundMixLevelProgram5
				RollCallString,
			iqdbd01DolbyDecoderSurroundMixLevelProgram6
				RollCallString,
			iqdbd01DolbyDecoderSurroundMixLevelProgram7
				RollCallString,
			iqdbd01DolbyDecoderSurroundMixLevelProgram8
				RollCallString,
			iqdbd01DolbyDecoderLtRtCMixLevelProgram1
				RollCallString,
			iqdbd01DolbyDecoderLtRtCMixLevelProgram2
				RollCallString,
			iqdbd01DolbyDecoderLtRtCMixLevelProgram3
				RollCallString,
			iqdbd01DolbyDecoderLtRtCMixLevelProgram4
				RollCallString,
			iqdbd01DolbyDecoderLtRtCMixLevelProgram5
				RollCallString,
			iqdbd01DolbyDecoderLtRtCMixLevelProgram6
				RollCallString,
			iqdbd01DolbyDecoderLtRtCMixLevelProgram7
				RollCallString,
			iqdbd01DolbyDecoderLtRtCMixLevelProgram8
				RollCallString,
			iqdbd01DolbyDecoderLtRtSMixLevelProgram1
				RollCallString,
			iqdbd01DolbyDecoderLtRtSMixLevelProgram2
				RollCallString,
			iqdbd01DolbyDecoderLtRtSMixLevelProgram3
				RollCallString,
			iqdbd01DolbyDecoderLtRtSMixLevelProgram4
				RollCallString,
			iqdbd01DolbyDecoderLtRtSMixLevelProgram5
				RollCallString,
			iqdbd01DolbyDecoderLtRtSMixLevelProgram6
				RollCallString,
			iqdbd01DolbyDecoderLtRtSMixLevelProgram7
				RollCallString,
			iqdbd01DolbyDecoderLtRtSMixLevelProgram8
				RollCallString,
			iqdbd01DolbyDecoderLoRoCMixLevelProgram1
				RollCallString,
			iqdbd01DolbyDecoderLoRoCMixLevelProgram2
				RollCallString,
			iqdbd01DolbyDecoderLoRoCMixLevelProgram3
				RollCallString,
			iqdbd01DolbyDecoderLoRoCMixLevelProgram4
				RollCallString,
			iqdbd01DolbyDecoderLoRoCMixLevelProgram5
				RollCallString,
			iqdbd01DolbyDecoderLoRoCMixLevelProgram6
				RollCallString,
			iqdbd01DolbyDecoderLoRoCMixLevelProgram7
				RollCallString,
			iqdbd01DolbyDecoderLoRoCMixLevelProgram8
				RollCallString,
			iqdbd01DolbyDecoderLoRoSMixLevelProgram1
				RollCallString,
			iqdbd01DolbyDecoderLoRoSMixLevelProgram2
				RollCallString,
			iqdbd01DolbyDecoderLoRoSMixLevelProgram3
				RollCallString,
			iqdbd01DolbyDecoderLoRoSMixLevelProgram4
				RollCallString,
			iqdbd01DolbyDecoderLoRoSMixLevelProgram5
				RollCallString,
			iqdbd01DolbyDecoderLoRoSMixLevelProgram6
				RollCallString,
			iqdbd01DolbyDecoderLoRoSMixLevelProgram7
				RollCallString,
			iqdbd01DolbyDecoderLoRoSMixLevelProgram8
				RollCallString,
			iqdbd01DolbyDecoderMetadataDisplayDisplaySelect
				INTEGER,
			iqdbd01DolbyDecoderMetadataDisplayDataSelect
				INTEGER,
			iqdbd01DolbyDecoderMetadataDisplayProgramSelect
				INTEGER,
			iqdbd01VidDelayInternalDelay
				RollCallString,
			iqdbd01VidDelayDelayMode
				INTEGER,
			iqdbd01VidDelaySetDelayDelayFrames
				INTEGER,
			iqdbd01VidDelaySetDelayVerticalTiming
				INTEGER,
			iqdbd01VidDelaySetDelayHorizontalTiming
				INTEGER,
			iqdbd01VidDelaySetDelayDelayms
				INTEGER,
			iqdbd01UtilsPatternsPatternEnable
				INTEGER,
			iqdbd01UtilsPatternsScrollPattern
				INTEGER,
			iqdbd01UtilsPatternsPatternType
				INTEGER,
			iqdbd01UtilsANCblankonMismat
				INTEGER,
			iqdbd01UtilsFreezeForceFreeze
				INTEGER,
			iqdbd01UtilsFreezeFreezeType
				INTEGER,
			iqdbd01UtilsMonochrome
				INTEGER,
			iqdbd01UtilsMonochromeMonochromeType
				INTEGER,
			iqdbd01UtilsVBIBlankingANCMode
				INTEGER,
			iqdbd01UtilsVBIBlankingStandard
				INTEGER,
			iqdbd01UtilsVBIBlankingBlankAll
				INTEGER,
			iqdbd01UtilsVBIBlankingPassAll
				INTEGER,
			iqdbd01UtilsVBIBlankingBlank1
				INTEGER,
			iqdbd01UtilsVBIBlankingBlank2
				INTEGER,
			iqdbd01UtilsVBIBlankingBlank3
				INTEGER,
			iqdbd01UtilsVBIBlankingBlank4
				INTEGER,
			iqdbd01UtilsVBIBlankingBlank5
				INTEGER,
			iqdbd01UtilsVBIBlankingBlank6
				INTEGER,
			iqdbd01UtilsVBIBlankingBlank7
				INTEGER,
			iqdbd01UtilsVBIBlankingBlank8
				INTEGER,
			iqdbd01UtilsVBIBlankingBlank9
				INTEGER,
			iqdbd01UtilsVBIBlankingBlank10
				INTEGER,
			iqdbd01UtilsVBIBlankingBlank11
				INTEGER,
			iqdbd01UtilsVBIBlankingBlank12
				INTEGER,
			iqdbd01UtilsVBIBlankingBlank13
				INTEGER,
			iqdbd01UtilsVBIBlankingBlank14
				INTEGER,
			iqdbd01UtilsVBIBlankingBlank15
				INTEGER,
			iqdbd01UtilsVBIBlankingBlank16
				INTEGER,
			iqdbd01UtilsVBIBlankingBlank17
				INTEGER,
			iqdbd01UtilsVBIBlankingBlank18
				INTEGER,
			iqdbd01UtilsVBIBlankingBlank19
				INTEGER,
			iqdbd01UtilsVBIBlankingBlank20
				INTEGER,
			iqdbd01UtilsVBIBlankingBlank21
				INTEGER,
			iqdbd01UtilsVBIBlankingBlank22
				INTEGER,
			iqdbd01UtilsVBIBlankingBlank23
				INTEGER,
			iqdbd01UtilsVBIBlankingBlank24
				INTEGER,
			iqdbd01UtilsVBIBlankingBlank25
				INTEGER,
			iqdbd01UtilsVBIBlankingBlank26
				INTEGER,
			iqdbd01UtilsVBIBlankingBlank27
				INTEGER,
			iqdbd01UtilsVBIBlankingBlank28
				INTEGER,
			iqdbd01UtilsVBIBlankingBlank29
				INTEGER,
			iqdbd01UtilsVBIBlankingBlank30
				INTEGER,
			iqdbd01UtilsVBIBlankingBlank31
				INTEGER,
			iqdbd01UtilsVBIBlankingBlank32
				INTEGER,
			iqdbd01UtilsVBIBlankingBlank33
				INTEGER,
			iqdbd01UtilsVBIBlankingBlank34
				INTEGER,
			iqdbd01RecallMemory
				INTEGER,
			iqdbd01SelMemory
				INTEGER,
			iqdbd01SaveMemory
				INTEGER,
			iqdbd01ClearMemory
				INTEGER,
			iqdbd01MemoryNameChangeName
				RollCallString,
			iqdbd01MemoryNameLastUserMemory
				RollCallString,
			iqdbd01MemoryName1
				RollCallString,
			iqdbd01MemoryName2
				RollCallString,
			iqdbd01MemoryName3
				RollCallString,
			iqdbd01MemoryName4
				RollCallString,
			iqdbd01MemoryName5
				RollCallString,
			iqdbd01MemoryName6
				RollCallString,
			iqdbd01MemoryName7
				RollCallString,
			iqdbd01MemoryName8
				RollCallString,
			iqdbd01MemoryName9
				RollCallString,
			iqdbd01MemoryName10
				RollCallString,
			iqdbd01MemoryName11
				RollCallString,
			iqdbd01MemoryName12
				RollCallString,
			iqdbd01MemoryName13
				RollCallString,
			iqdbd01MemoryName14
				RollCallString,
			iqdbd01MemoryName15
				RollCallString,
			iqdbd01MemoryName16
				RollCallString,
			iqdbd01LoggingVideoLoggingLogInput1Type
				INTEGER,
			iqdbd01LoggingVideoLoggingInput1Type
				RollCallString,
			iqdbd01LoggingVideoLoggingLogInput1Status
				INTEGER,
			iqdbd01LoggingVideoLoggingInput1Status
				RollCallString,
			iqdbd01LoggingVideoLoggingLogInput1Std
				INTEGER,
			iqdbd01LoggingVideoLoggingInput1Std
				RollCallString,
			iqdbd01LoggingVideoLoggingLogInput1Errors
				INTEGER,
			iqdbd01LoggingVideoLoggingInput1Errors
				RollCallString,
			iqdbd01LoggingVideoLoggingLogInput1ErrSecs
				INTEGER,
			iqdbd01LoggingVideoLoggingInput1ErrSecs
				RollCallString,
			iqdbd01LoggingVideoLoggingLogInput1ANCErr
				INTEGER,
			iqdbd01LoggingVideoLoggingInput1ANCErrors
				RollCallString,
			iqdbd01LoggingVideoLoggingLogInput1ANCErrSec
				INTEGER,
			iqdbd01LoggingVideoLoggingInput1ANCErrSecs
				RollCallString,
			iqdbd01LoggingVideoLoggingLogOutputState
				INTEGER,
			iqdbd01LoggingVideoLoggingOutputState
				RollCallString,
			iqdbd01LoggingVideoLoggingLogOutputType
				INTEGER,
			iqdbd01LoggingVideoLoggingOutputType
				RollCallString,
			iqdbd01LoggingVideoLoggingLogOutputStandard
				INTEGER,
			iqdbd01LoggingVideoLoggingOutputStandard
				RollCallString,
			iqdbd01LoggingVideoLoggingLogoutputANCstat
				INTEGER,
			iqdbd01LoggingVideoLoggingOutputANCstate
				RollCallString,
			iqdbd01LoggingEmbAudLoggingLogInp1Emb1stat
				INTEGER,
			iqdbd01LoggingEmbAudLoggingInp1Emb1state
				RollCallString,
			iqdbd01LoggingEmbAudLoggingLogInp1Emb2stat
				INTEGER,
			iqdbd01LoggingEmbAudLoggingInp1Emb2state
				RollCallString,
			iqdbd01LoggingEmbAudLoggingLogInp1Emb3stat
				INTEGER,
			iqdbd01LoggingEmbAudLoggingInp1Emb3state
				RollCallString,
			iqdbd01LoggingEmbAudLoggingLogInp1Emb4stat
				INTEGER,
			iqdbd01LoggingEmbAudLoggingInp1Emb4state
				RollCallString,
			iqdbd01LoggingEmbAudLoggingLogInp1Emb5stat
				INTEGER,
			iqdbd01LoggingEmbAudLoggingInp1Emb5state
				RollCallString,
			iqdbd01LoggingEmbAudLoggingLogInp1Emb6stat
				INTEGER,
			iqdbd01LoggingEmbAudLoggingInp1Emb6state
				RollCallString,
			iqdbd01LoggingEmbAudLoggingLogInp1Emb7stat
				INTEGER,
			iqdbd01LoggingEmbAudLoggingInp1Emb7state
				RollCallString,
			iqdbd01LoggingEmbAudLoggingLogInp1Emb8stat
				INTEGER,
			iqdbd01LoggingEmbAudLoggingInp1Emb8state
				RollCallString,
			iqdbd01LoggingEmbAudLoggingLogInp1Emb1type
				INTEGER,
			iqdbd01LoggingEmbAudLoggingInp1Emb1type
				RollCallString,
			iqdbd01LoggingEmbAudLoggingLogInp1Emb2type
				INTEGER,
			iqdbd01LoggingEmbAudLoggingInp1Emb2type
				RollCallString,
			iqdbd01LoggingEmbAudLoggingLogInp1Emb3type
				INTEGER,
			iqdbd01LoggingEmbAudLoggingInp1Emb3type
				RollCallString,
			iqdbd01LoggingEmbAudLoggingLogInp1Emb4type
				INTEGER,
			iqdbd01LoggingEmbAudLoggingInp1Emb4type
				RollCallString,
			iqdbd01LoggingEmbAudLoggingLogInp1Emb5type
				INTEGER,
			iqdbd01LoggingEmbAudLoggingInp1Emb5type
				RollCallString,
			iqdbd01LoggingEmbAudLoggingLogInp1Emb6type
				INTEGER,
			iqdbd01LoggingEmbAudLoggingInp1Emb6type
				RollCallString,
			iqdbd01LoggingEmbAudLoggingLogInp1Emb7type
				INTEGER,
			iqdbd01LoggingEmbAudLoggingInp1Emb7type
				RollCallString,
			iqdbd01LoggingEmbAudLoggingLogInp1Emb8type
				INTEGER,
			iqdbd01LoggingEmbAudLoggingInp1Emb8type
				RollCallString,
			iqdbd01LoggingOPAudLoggingLogOutEmb1state
				INTEGER,
			iqdbd01LoggingOPAudLoggingOutEmb1state
				RollCallString,
			iqdbd01LoggingOPAudLoggingLogOutEmb2state
				INTEGER,
			iqdbd01LoggingOPAudLoggingOutEmb2state
				RollCallString,
			iqdbd01LoggingOPAudLoggingLogOutEmb3state
				INTEGER,
			iqdbd01LoggingOPAudLoggingOutEmb3state
				RollCallString,
			iqdbd01LoggingOPAudLoggingLogOutEmb4state
				INTEGER,
			iqdbd01LoggingOPAudLoggingOutEmb4state
				RollCallString,
			iqdbd01LoggingOPAudLoggingLogOutEmb5state
				INTEGER,
			iqdbd01LoggingOPAudLoggingOutEmb5state
				RollCallString,
			iqdbd01LoggingOPAudLoggingLogOutEmb6state
				INTEGER,
			iqdbd01LoggingOPAudLoggingOutEmb6state
				RollCallString,
			iqdbd01LoggingOPAudLoggingLogOutEmb7state
				INTEGER,
			iqdbd01LoggingOPAudLoggingOutEmb7state
				RollCallString,
			iqdbd01LoggingOPAudLoggingLogOutEmb8state
				INTEGER,
			iqdbd01LoggingOPAudLoggingOutEmb8state
				RollCallString,
			iqdbd01LoggingOPAudLoggingLogOutEmb1type
				INTEGER,
			iqdbd01LoggingOPAudLoggingOutEmb1type
				RollCallString,
			iqdbd01LoggingOPAudLoggingLogOutEmb2type
				INTEGER,
			iqdbd01LoggingOPAudLoggingOutEmb2type
				RollCallString,
			iqdbd01LoggingOPAudLoggingLogOutEmb3type
				INTEGER,
			iqdbd01LoggingOPAudLoggingOutEmb3type
				RollCallString,
			iqdbd01LoggingOPAudLoggingLogOutEmb4type
				INTEGER,
			iqdbd01LoggingOPAudLoggingOutEmb4type
				RollCallString,
			iqdbd01LoggingOPAudLoggingLogOutEmb5type
				INTEGER,
			iqdbd01LoggingOPAudLoggingOutEmb5type
				RollCallString,
			iqdbd01LoggingOPAudLoggingLogOutEmb6type
				INTEGER,
			iqdbd01LoggingOPAudLoggingOutEmb6type
				RollCallString,
			iqdbd01LoggingOPAudLoggingLogOutEmb7type
				INTEGER,
			iqdbd01LoggingOPAudLoggingOutEmb7type
				RollCallString,
			iqdbd01LoggingOPAudLoggingLogOutEmb8type
				INTEGER,
			iqdbd01LoggingOPAudLoggingOutEmb8type
				RollCallString,
			iqdbd01LoggingOPAudLevelLoggiLogOutEmb1LLev
				INTEGER,
			iqdbd01LoggingOPAudLevelLoggiOutEmb1LLevel
				RollCallString,
			iqdbd01LoggingOPAudLevelLoggiLogOutEmb1RLev
				INTEGER,
			iqdbd01LoggingOPAudLevelLoggiOutEmb1RLevel
				RollCallString,
			iqdbd01LoggingOPAudLevelLoggiLogOutEmb2LLev
				INTEGER,
			iqdbd01LoggingOPAudLevelLoggiOutEmb2LLevel
				RollCallString,
			iqdbd01LoggingOPAudLevelLoggiLogOutEmb2RLev
				INTEGER,
			iqdbd01LoggingOPAudLevelLoggiOutEmb2RLevel
				RollCallString,
			iqdbd01LoggingOPAudLevelLoggiLogOutEmb3LLev
				INTEGER,
			iqdbd01LoggingOPAudLevelLoggiOutEmb3LLevel
				RollCallString,
			iqdbd01LoggingOPAudLevelLoggiLogOutEmb3RLev
				INTEGER,
			iqdbd01LoggingOPAudLevelLoggiOutEmb3RLevel
				RollCallString,
			iqdbd01LoggingOPAudLevelLoggiLogOutEmb4LLev
				INTEGER,
			iqdbd01LoggingOPAudLevelLoggiOutEmb4LLevel
				RollCallString,
			iqdbd01LoggingOPAudLevelLoggiLogOutEmb4RLev
				INTEGER,
			iqdbd01LoggingOPAudLevelLoggiOutEmb4RLevel
				RollCallString,
			iqdbd01LoggingOPAudLevelLoggiLogOutEmb5LLev
				INTEGER,
			iqdbd01LoggingOPAudLevelLoggiOutEmb5LLevel
				RollCallString,
			iqdbd01LoggingOPAudLevelLoggiLogOutEmb5RLev
				INTEGER,
			iqdbd01LoggingOPAudLevelLoggiOutEmb5RLevel
				RollCallString,
			iqdbd01LoggingOPAudLevelLoggiLogOutEmb6LLev
				INTEGER,
			iqdbd01LoggingOPAudLevelLoggiOutEmb6LLevel
				RollCallString,
			iqdbd01LoggingOPAudLevelLoggiLogOutEmb6RLev
				INTEGER,
			iqdbd01LoggingOPAudLevelLoggiOutEmb6RLevel
				RollCallString,
			iqdbd01LoggingOPAudLevelLoggiLogOutEmb7LLev
				INTEGER,
			iqdbd01LoggingOPAudLevelLoggiOutEmb7LLevel
				RollCallString,
			iqdbd01LoggingOPAudLevelLoggiLogOutEmb7RLev
				INTEGER,
			iqdbd01LoggingOPAudLevelLoggiOutEmb7RLevel
				RollCallString,
			iqdbd01LoggingOPAudLevelLoggiLogOutEmb8LLev
				INTEGER,
			iqdbd01LoggingOPAudLevelLoggiOutEmb8LLevel
				RollCallString,
			iqdbd01LoggingOPAudLevelLoggiLogOutEmb8RLev
				INTEGER,
			iqdbd01LoggingOPAudLevelLoggiOutEmb8RLevel
				RollCallString,
			iqdbd01LoggingOPDolbyELoggingLogEmbDolbyE1
				INTEGER,
			iqdbd01LoggingOPDolbyELoggingEmbDolbyE1
				RollCallString,
			iqdbd01LoggingOPDolbyELoggingLogEmbDolbyE2
				INTEGER,
			iqdbd01LoggingOPDolbyELoggingEmbDolbyE2
				RollCallString,
			iqdbd01LoggingOPDolbyELoggingLogEmbDolbyE3
				INTEGER,
			iqdbd01LoggingOPDolbyELoggingEmbDolbyE3
				RollCallString,
			iqdbd01LoggingOPDolbyELoggingLogEmbDolbyE4
				INTEGER,
			iqdbd01LoggingOPDolbyELoggingEmbDolbyE4
				RollCallString,
			iqdbd01LoggingOPDolbyELoggingLogEmbDolbyE5
				INTEGER,
			iqdbd01LoggingOPDolbyELoggingEmbDolbyE5
				RollCallString,
			iqdbd01LoggingOPDolbyELoggingLogEmbDolbyE6
				INTEGER,
			iqdbd01LoggingOPDolbyELoggingEmbDolbyE6
				RollCallString,
			iqdbd01LoggingOPDolbyELoggingLogEmbDolbyE7
				INTEGER,
			iqdbd01LoggingOPDolbyELoggingEmbDolbyE7
				RollCallString,
			iqdbd01LoggingOPDolbyELoggingLogEmbDolbyE8
				INTEGER,
			iqdbd01LoggingOPDolbyELoggingEmbDolbyE8
				RollCallString,
			iqdbd01LoggingAESInputLoggingLogAESInput1sta
				INTEGER,
			iqdbd01LoggingAESInputLoggingAESInput1state
				RollCallString,
			iqdbd01LoggingAESInputLoggingLogAESInput2sta
				INTEGER,
			iqdbd01LoggingAESInputLoggingAESInput2state
				RollCallString,
			iqdbd01LoggingAESInputLoggingLogAESInput3sta
				INTEGER,
			iqdbd01LoggingAESInputLoggingAESInput3state
				RollCallString,
			iqdbd01LoggingAESInputLoggingLogAESInput4sta
				INTEGER,
			iqdbd01LoggingAESInputLoggingAESInput4state
				RollCallString,
			iqdbd01LoggingAESInputLoggingLogAESInput5sta
				INTEGER,
			iqdbd01LoggingAESInputLoggingAESInput5state
				RollCallString,
			iqdbd01LoggingAESInputLoggingLogAESInput6sta
				INTEGER,
			iqdbd01LoggingAESInputLoggingAESInput6state
				RollCallString,
			iqdbd01LoggingAESInputLoggingLogAESInput7sta
				INTEGER,
			iqdbd01LoggingAESInputLoggingAESInput7state
				RollCallString,
			iqdbd01LoggingAESInputLoggingLogAESInput8sta
				INTEGER,
			iqdbd01LoggingAESInputLoggingAESInput8state
				RollCallString,
			iqdbd01LoggingAESInputLoggingLogAESInput1typ
				INTEGER,
			iqdbd01LoggingAESInputLoggingAESInput1type
				RollCallString,
			iqdbd01LoggingAESInputLoggingLogAESInput2typ
				INTEGER,
			iqdbd01LoggingAESInputLoggingAESInput2type
				RollCallString,
			iqdbd01LoggingAESInputLoggingLogAESInput3typ
				INTEGER,
			iqdbd01LoggingAESInputLoggingAESInput3type
				RollCallString,
			iqdbd01LoggingAESInputLoggingLogAESInput4typ
				INTEGER,
			iqdbd01LoggingAESInputLoggingAESInput4type
				RollCallString,
			iqdbd01LoggingAESInputLoggingLogAESInput5typ
				INTEGER,
			iqdbd01LoggingAESInputLoggingAESInput5type
				RollCallString,
			iqdbd01LoggingAESInputLoggingLogAESInput6typ
				INTEGER,
			iqdbd01LoggingAESInputLoggingAESInput6type
				RollCallString,
			iqdbd01LoggingAESInputLoggingLogAESInput7typ
				INTEGER,
			iqdbd01LoggingAESInputLoggingAESInput7type
				RollCallString,
			iqdbd01LoggingAESInputLoggingLogAESInput8typ
				INTEGER,
			iqdbd01LoggingAESInputLoggingAESInput8type
				RollCallString,
			iqdbd01LoggingAESOutputLoggingLogAESOutput1st
				INTEGER,
			iqdbd01LoggingAESOutputLoggingAESOutput1state
				RollCallString,
			iqdbd01LoggingAESOutputLoggingLogAESOutput2st
				INTEGER,
			iqdbd01LoggingAESOutputLoggingAESOutput2state
				RollCallString,
			iqdbd01LoggingAESOutputLoggingLogAESOutput3st
				INTEGER,
			iqdbd01LoggingAESOutputLoggingAESOutput3state
				RollCallString,
			iqdbd01LoggingAESOutputLoggingLogAESOutput4st
				INTEGER,
			iqdbd01LoggingAESOutputLoggingAESOutput4state
				RollCallString,
			iqdbd01LoggingAESOutputLoggingLogAESOutput5st
				INTEGER,
			iqdbd01LoggingAESOutputLoggingAESOutput5state
				RollCallString,
			iqdbd01LoggingAESOutputLoggingLogAESOutput6st
				INTEGER,
			iqdbd01LoggingAESOutputLoggingAESOutput6state
				RollCallString,
			iqdbd01LoggingAESOutputLoggingLogAESOutput7st
				INTEGER,
			iqdbd01LoggingAESOutputLoggingAESOutput7state
				RollCallString,
			iqdbd01LoggingAESOutputLoggingLogAESOutput8st
				INTEGER,
			iqdbd01LoggingAESOutputLoggingAESOutput8state
				RollCallString,
			iqdbd01LoggingAESOutputLoggingLogAESOutput1ty
				INTEGER,
			iqdbd01LoggingAESOutputLoggingAESOutput1type
				RollCallString,
			iqdbd01LoggingAESOutputLoggingLogAESOutput2ty
				INTEGER,
			iqdbd01LoggingAESOutputLoggingAESOutput2type
				RollCallString,
			iqdbd01LoggingAESOutputLoggingLogAESOutput3ty
				INTEGER,
			iqdbd01LoggingAESOutputLoggingAESOutput3type
				RollCallString,
			iqdbd01LoggingAESOutputLoggingLogAESOutput4ty
				INTEGER,
			iqdbd01LoggingAESOutputLoggingAESOutput4type
				RollCallString,
			iqdbd01LoggingAESOutputLoggingLogAESOutput5ty
				INTEGER,
			iqdbd01LoggingAESOutputLoggingAESOutput5type
				RollCallString,
			iqdbd01LoggingAESOutputLoggingLogAESOutput6ty
				INTEGER,
			iqdbd01LoggingAESOutputLoggingAESOutput6type
				RollCallString,
			iqdbd01LoggingAESOutputLoggingLogAESOutput7ty
				INTEGER,
			iqdbd01LoggingAESOutputLoggingAESOutput7type
				RollCallString,
			iqdbd01LoggingAESOutputLoggingLogAESOutput8ty
				INTEGER,
			iqdbd01LoggingAESOutputLoggingAESOutput8type
				RollCallString,
			iqdbd01LoggingMiscLoggingLogSerialNo
				INTEGER,
			iqdbd01LoggingMiscLoggingSerialNo
				RollCallString,
			iqdbd01LoggingMiscLoggingLogOSVersion
				INTEGER,
			iqdbd01LoggingMiscLoggingOSVersion
				RollCallString,
			iqdbd01LoggingMiscLoggingLogBuildNo
				INTEGER,
			iqdbd01LoggingMiscLoggingBuildNo
				RollCallString,
			iqdbd01LoggingMiscLoggingLogHardwareVer
				INTEGER,
			iqdbd01LoggingMiscLoggingHardwareVer
				RollCallString,
			iqdbd01LoggingMiscLoggingLogFirmwareVer
				INTEGER,
			iqdbd01LoggingMiscLoggingFirmwareVer
				RollCallString,
			iqdbd01LoggingMiscLoggingLogUpTime
				INTEGER,
			iqdbd01LoggingMiscLoggingUpTime
				RollCallString,
			iqdbd01LoggingDolbyDecMetadataLogInputFormat
				INTEGER,
			iqdbd01LoggingDolbyDecMetadataInputFormat
				RollCallString,
			iqdbd01LoggingDolbyDecMetadataLogInputBitDepth
				INTEGER,
			iqdbd01LoggingDolbyDecMetadataInputBitDepth
				RollCallString,
			iqdbd01LoggingDolbyDecMetadataLogInpFrameRate
				INTEGER,
			iqdbd01LoggingDolbyDecMetadataInputFrameRate
				RollCallString,
			iqdbd01LoggingDolbyDecMetadataLogInpProgConfig
				INTEGER,
			iqdbd01LoggingDolbyDecMetadataInputProgConfig
				RollCallString,
			iqdbd01LoggingDolbyDecMetadataLogDolbyEErrCnt
				INTEGER,
			iqdbd01LoggingDolbyDecMetadataDolbyEErrCnt
				RollCallString,
			iqdbd01LoggingDolbyDecMetadataLogDolbyDErrCnt
				INTEGER,
			iqdbd01LoggingDolbyDecMetadataDolbyDErrCnt
				RollCallString,
			iqdbd01LoggingDolbyDecMetadataLogInpState
				INTEGER,
			iqdbd01LoggingDolbyDecMetadataInputState
				RollCallString,
			iqdbd01LoggingDolbyDecMetadataLogInpFrmSync
				INTEGER,
			iqdbd01LoggingDolbyDecMetadataInputFrameSync
				RollCallString,
			iqdbd01LoggingDolbyDecMetadataLogDolbyDListnM
				INTEGER,
			iqdbd01LoggingDolbyDecMetadataDolbyDListeningM
				RollCallString,
			iqdbd01LoggingDolbyDecMetadataLogDolbyDRngM
				INTEGER,
			iqdbd01LoggingDolbyDecMetadataDolbyDDynRngM
				RollCallString,
			iqdbd01LoggingDolbyDecMetadataLogAuxRngMode
				INTEGER,
			iqdbd01LoggingDolbyDecMetadataAuxDynRngMode
				RollCallString,
			iqdbd01DolbyDecMetadataDescTextLoggingLogProg1DescTXT
				INTEGER,
			iqdbd01DolbyDecMetadataDescTextLoggingProg1DescText
				RollCallString,
			iqdbd01DolbyDecMetadataDescTextLoggingProg1DescTextPt2
				RollCallString,
			iqdbd01DolbyDecMetadataDescTextLoggingLogProg2DescTXT
				INTEGER,
			iqdbd01DolbyDecMetadataDescTextLoggingProg2DescText
				RollCallString,
			iqdbd01DolbyDecMetadataDescTextLoggingProg2DescTextPt2
				RollCallString,
			iqdbd01DolbyDecMetadataDescTextLoggingLogProg3DescTXT
				INTEGER,
			iqdbd01DolbyDecMetadataDescTextLoggingProg3DescText
				RollCallString,
			iqdbd01DolbyDecMetadataDescTextLoggingProg3DescTextPt2
				RollCallString,
			iqdbd01DolbyDecMetadataDescTextLoggingLogProg4DescTXT
				INTEGER,
			iqdbd01DolbyDecMetadataDescTextLoggingProg4DescTextPt2
				RollCallString,
			iqdbd01DolbyDecMetadataDescTextLoggingProg4DescText
				RollCallString,
			iqdbd01DolbyDecMetadataDescTextLoggingLogProg5DescTXT
				INTEGER,
			iqdbd01DolbyDecMetadataDescTextLoggingProg5DescText
				RollCallString,
			iqdbd01DolbyDecMetadataDescTextLoggingProg5DescTextPt2
				RollCallString,
			iqdbd01DolbyDecMetadataDescTextLoggingLogProg6DescTXT
				INTEGER,
			iqdbd01DolbyDecMetadataDescTextLoggingProg6DescText
				RollCallString,
			iqdbd01DolbyDecMetadataDescTextLoggingProg6DescTextPt2
				RollCallString,
			iqdbd01DolbyDecMetadataDescTextLoggingLogProg7DescTXT
				INTEGER,
			iqdbd01DolbyDecMetadataDescTextLoggingProg7DescText
				RollCallString,
			iqdbd01DolbyDecMetadataDescTextLoggingProg7DescTextPt2
				RollCallString,
			iqdbd01DolbyDecMetadataDescTextLoggingLogProg8DescTXT
				INTEGER,
			iqdbd01DolbyDecMetadataDescTextLoggingProg8DescText
				RollCallString,
			iqdbd01DolbyDecMetadataDescTextLoggingProg8DescTextPt2
				RollCallString,
			iqdbd01DolbyDecMetadataLFEChanLoggingLogProg1LFEChan
				INTEGER,
			iqdbd01DolbyDecMetadataLFEChanLoggingProg1LFEChan
				RollCallString,
			iqdbd01DolbyDecMetadataLFEChanLoggingLogProg2LFEChan
				INTEGER,
			iqdbd01DolbyDecMetadataLFEChanLoggingProg2LFEChan
				RollCallString,
			iqdbd01DolbyDecMetadataLFEChanLoggingLogProg3LFEChan
				INTEGER,
			iqdbd01DolbyDecMetadataLFEChanLoggingProg3LFEChan
				RollCallString,
			iqdbd01DolbyDecMetadataLFEChanLoggingLogProg4LFEChan
				INTEGER,
			iqdbd01DolbyDecMetadataLFEChanLoggingProg4LFEChan
				RollCallString,
			iqdbd01DolbyDecMetadataLFEChanLoggingLogProg5LFEChan
				INTEGER,
			iqdbd01DolbyDecMetadataLFEChanLoggingProg5LFEChan
				RollCallString,
			iqdbd01DolbyDecMetadataLFEChanLoggingLogProg6LFEChan
				INTEGER,
			iqdbd01DolbyDecMetadataLFEChanLoggingProg6LFEChan
				RollCallString,
			iqdbd01DolbyDecMetadataLFEChanLoggingLogProg7LFEChan
				INTEGER,
			iqdbd01DolbyDecMetadataLFEChanLoggingProg7LFEChan
				RollCallString,
			iqdbd01DolbyDecMetadataLFEChanLoggingLogProg8LFEChan
				INTEGER,
			iqdbd01DolbyDecMetadataLFEChanLoggingProg8LFEChan
				RollCallString,
			iqdbd01DolbyDecMetadataChanModeLoggingLogProg1ChanMod
				INTEGER,
			iqdbd01DolbyDecMetadataChanModeLoggingProg1ChanMode
				RollCallString,
			iqdbd01DolbyDecMetadataChanModeLoggingLogProg2ChanMod
				INTEGER,
			iqdbd01DolbyDecMetadataChanModeLoggingProg2ChanMode
				RollCallString,
			iqdbd01DolbyDecMetadataChanModeLoggingLogProg3ChanMod
				INTEGER,
			iqdbd01DolbyDecMetadataChanModeLoggingProg3ChanMode
				RollCallString,
			iqdbd01DolbyDecMetadataChanModeLoggingLogProg4ChanMod
				INTEGER,
			iqdbd01DolbyDecMetadataChanModeLoggingProg4ChanMode
				RollCallString,
			iqdbd01DolbyDecMetadataChanModeLoggingLogProg5ChanMod
				INTEGER,
			iqdbd01DolbyDecMetadataChanModeLoggingProg5ChanMode
				RollCallString,
			iqdbd01DolbyDecMetadataChanModeLoggingLogProg6ChanMod
				INTEGER,
			iqdbd01DolbyDecMetadataChanModeLoggingProg6ChanMode
				RollCallString,
			iqdbd01DolbyDecMetadataChanModeLoggingLogProg7ChanMod
				INTEGER,
			iqdbd01DolbyDecMetadataChanModeLoggingProg7ChanMode
				RollCallString,
			iqdbd01DolbyDecMetadataChanModeLoggingLogProg8ChanMod
				INTEGER,
			iqdbd01DolbyDecMetadataChanModeLoggingProg8ChanMode
				RollCallString,
			iqdbd01DolbyDecMetadataStereoDOWNMIXLoggLogPgm1StDNMIX
				INTEGER,
			iqdbd01DolbyDecMetadataStereoDOWNMIXLoggPgm1StereoDNMIX
				RollCallString,
			iqdbd01DolbyDecMetadataStereoDOWNMIXLoggLogPgm2StDNMIX
				INTEGER,
			iqdbd01DolbyDecMetadataStereoDOWNMIXLoggPgm2StereoDNMIX
				RollCallString,
			iqdbd01DolbyDecMetadataStereoDOWNMIXLoggLogPgm3StDNMIX
				INTEGER,
			iqdbd01DolbyDecMetadataStereoDOWNMIXLoggPgm3StereoDNMIX
				RollCallString,
			iqdbd01DolbyDecMetadataStereoDOWNMIXLoggLogPgm4StDNMIX
				INTEGER,
			iqdbd01DolbyDecMetadataStereoDOWNMIXLoggPgm4StereoDNMIX
				RollCallString,
			iqdbd01DolbyDecMetadataStereoDOWNMIXLoggLogPgm5StDNMIX
				INTEGER,
			iqdbd01DolbyDecMetadataStereoDOWNMIXLoggPgm5StereoDNMIX
				RollCallString,
			iqdbd01DolbyDecMetadataStereoDOWNMIXLoggLogPgm6StDNMIX
				INTEGER,
			iqdbd01DolbyDecMetadataStereoDOWNMIXLoggPgm6StereoDNMIX
				RollCallString,
			iqdbd01DolbyDecMetadataStereoDOWNMIXLoggLogPgm7StDNMIX
				INTEGER,
			iqdbd01DolbyDecMetadataStereoDOWNMIXLoggPgm7StereoDNMIX
				RollCallString,
			iqdbd01DolbyDecMetadataStereoDOWNMIXLoggLogPgm8StDNMIX
				INTEGER,
			iqdbd01DolbyDecMetadataStereoDOWNMIXLoggPgm8StereoDNMIX
				RollCallString,
			iqdbd01DolbyDecMetadataDialnormLoggingLogProg1Dialnorm
				INTEGER,
			iqdbd01DolbyDecMetadataDialnormLoggingProg1Dialnorm
				RollCallString,
			iqdbd01DolbyDecMetadataDialnormLoggingLogProg2Dialnorm
				INTEGER,
			iqdbd01DolbyDecMetadataDialnormLoggingProg2Dialnorm
				RollCallString,
			iqdbd01DolbyDecMetadataDialnormLoggingLogProg3Dialnorm
				INTEGER,
			iqdbd01DolbyDecMetadataDialnormLoggingProg3Dialnorm
				RollCallString,
			iqdbd01DolbyDecMetadataDialnormLoggingLogProg4Dialnorm
				INTEGER,
			iqdbd01DolbyDecMetadataDialnormLoggingProg4Dialnorm
				RollCallString,
			iqdbd01DolbyDecMetadataDialnormLoggingLogProg5Dialnorm
				INTEGER,
			iqdbd01DolbyDecMetadataDialnormLoggingProg5Dialnorm
				RollCallString,
			iqdbd01DolbyDecMetadataDialnormLoggingLogProg6Dialnorm
				INTEGER,
			iqdbd01DolbyDecMetadataDialnormLoggingProg6Dialnorm
				RollCallString,
			iqdbd01DolbyDecMetadataDialnormLoggingLogProg7Dialnorm
				INTEGER,
			iqdbd01DolbyDecMetadataDialnormLoggingProg7Dialnorm
				RollCallString,
			iqdbd01DolbyDecMetadataDialnormLoggingLogProg8Dialnorm
				INTEGER,
			iqdbd01DolbyDecMetadataDialnormLoggingProg8Dialnorm
				RollCallString,
			iqdbd01DolbyDecMetadataCompGainLoggingLogPgm1CompGain
				INTEGER,
			iqdbd01DolbyDecMetadataCompGainLoggingPgm1CompGain
				RollCallString,
			iqdbd01DolbyDecMetadataCompGainLoggingLogPgm2CompGain
				INTEGER,
			iqdbd01DolbyDecMetadataCompGainLoggingPgm2CompGain
				RollCallString,
			iqdbd01DolbyDecMetadataCompGainLoggingLogPgm3CompGain
				INTEGER,
			iqdbd01DolbyDecMetadataCompGainLoggingPgm3CompGain
				RollCallString,
			iqdbd01DolbyDecMetadataCompGainLoggingLogPgm4CompGain
				INTEGER,
			iqdbd01DolbyDecMetadataCompGainLoggingPgm4CompGain
				RollCallString,
			iqdbd01DolbyDecMetadataCompGainLoggingLogPgm5CompGain
				INTEGER,
			iqdbd01DolbyDecMetadataCompGainLoggingPgm5CompGain
				RollCallString,
			iqdbd01DolbyDecMetadataCompGainLoggingLogPgm6CompGain
				INTEGER,
			iqdbd01DolbyDecMetadataCompGainLoggingPgm6CompGain
				RollCallString,
			iqdbd01DolbyDecMetadataCompGainLoggingLogPgm7CompGain
				INTEGER,
			iqdbd01DolbyDecMetadataCompGainLoggingPgm7CompGain
				RollCallString,
			iqdbd01DolbyDecMetadataCompGainLoggingLogPgm8CompGain
				INTEGER,
			iqdbd01DolbyDecMetadataCompGainLoggingPgm8CompGain
				RollCallString,
			iqdbd01DolbyDecMetadataDynamicGainLogginLogProg1DynGain
				INTEGER,
			iqdbd01DolbyDecMetadataDynamicGainLogginProg1DynGain
				RollCallString,
			iqdbd01DolbyDecMetadataDynamicGainLogginLogProg2DynGain
				INTEGER,
			iqdbd01DolbyDecMetadataDynamicGainLogginProg2DynGain
				RollCallString,
			iqdbd01DolbyDecMetadataDynamicGainLogginLogProg3DynGain
				INTEGER,
			iqdbd01DolbyDecMetadataDynamicGainLogginProg3DynGain
				RollCallString,
			iqdbd01DolbyDecMetadataDynamicGainLogginLogProg4DynGain
				INTEGER,
			iqdbd01DolbyDecMetadataDynamicGainLogginProg4DynGain
				RollCallString,
			iqdbd01DolbyDecMetadataDynamicGainLogginLogProg5DynGain
				INTEGER,
			iqdbd01DolbyDecMetadataDynamicGainLogginProg5DynGain
				RollCallString,
			iqdbd01DolbyDecMetadataDynamicGainLogginLogProg6DynGain
				INTEGER,
			iqdbd01DolbyDecMetadataDynamicGainLogginProg6DynGain
				RollCallString,
			iqdbd01DolbyDecMetadataDynamicGainLogginLogProg7DynGain
				INTEGER,
			iqdbd01DolbyDecMetadataDynamicGainLogginProg7DynGain
				RollCallString,
			iqdbd01DolbyDecMetadataDynamicGainLogginLogProg8DynGain
				INTEGER,
			iqdbd01DolbyDecMetadataDynamicGainLogginProg8DynGain
				RollCallString,
			iqdbd01RollCallRollTrackDisableAll
				INTEGER,
			iqdbd01RollCallRollTrackIndex
				INTEGER,
			iqdbd01RollCallRollTrackSource
				INTEGER,
			iqdbd01RollCallRollTrackAddress
				RollCallString,
			iqdbd01RollCallRollTrackCommand
				RollCallString,
			iqdbd01RollCallRollTrackStatus
				RollCallString,
			iqdbd01RollCallRollTrackSending
				RollCallString,
			iqdbd01SetupProduct
				RollCallString,
			iqdbd01SetupRelease
				RollCallString,
			iqdbd01SetupBuild
				RollCallString,
			iqdbd01SetupKOS
				RollCallString,
			iqdbd01SetupSerialNo
				RollCallString,
			iqdbd01SetupFirmware
				RollCallString,
			iqdbd01SetupPCB
				RollCallString,
			iqdbd01SetupFactoryDefault
				INTEGER,
			iqdbd01SetupRestart
				INTEGER,
			iqdbd01SetupDefaultsSettings
				INTEGER,
			iqdbd01SetupDisplay
				INTEGER,
			iqdbd01SetupSerialNumber
				RollCallString,
			iqdbd01SetupBoardID
				INTEGER,
			iqdbd01SetupSaveID
				INTEGER,
			iqdbd01EngineerEngineerPassword
				RollCallString,
			iqdbd01EngineerShowEngineer
				INTEGER,
			iqdbd01EngineerPageOptions1
				INTEGER,
			iqdbd01EngineerPageOptions2
				INTEGER,
			iqdbd01EngineerPageOptions3
				INTEGER,
			iqdbd01OptionsDolbyModuleS1
				INTEGER,
			iqdbd01EngineerPageOptionsUndoChanges
				INTEGER,
			iqdbd01EngineerPageDolbyETimingLineNumber
				RollCallString,
			iqdbd01EngineerPageDolbyETimingSampleNumber
				RollCallString,
			iqdbd01EngineerPagePaAutoalignEmbeddedInputs
				INTEGER,
			iqdbd01EngineerPagePaAutoalignAESInputs
				INTEGER,
			iqdbd01EngineerShowEngineer2
				INTEGER,
			iqdbd01EngineerUseEmbDelayFbac
				INTEGER
		}

	iqdbd01SlotIndex OBJECT-TYPE
		SYNTAX		Unsigned32
		MAX-ACCESS		not-accessible
		STATUS			current
		DESCRIPTION
				"The unique Index value for each slot.  Its value
					ranges between 1 and the value of slotNumber."
		::= { iqdbd01CmdEntry 0 }


	iqdbd01InputIPLoss OBJECT-TYPE
		SYNTAX		INTEGER {
							val_No_Input(0),
							val_In_Out_Std_Mismatch(1)
							}
		MAX-ACCESS		read-write
		STATUS			current
		DESCRIPTION
				"TYPE: - RadiobuttonList
				 PAGE: - Input
					I/P Loss  cmdID= 33030
					No Input  value= 0
					In/Out Std.Mismatch  value= 1  "
		::= { iqdbd01CmdEntry 33030 }


	iqdbd01InputValidStdsAllValid OBJECT-TYPE
		SYNTAX		INTEGER { noAction(0),val_All_Valid(1) }
		MAX-ACCESS		read-write
		STATUS			current
		DESCRIPTION
				"TYPE: - Button
				 PAGE: - Input
					All Valid  cmdID= 32900  value= 1  "
		::= { iqdbd01CmdEntry 32900 }


	iqdbd01InputValidStdsAllInvalid OBJECT-TYPE
		SYNTAX		INTEGER { noAction(0),val_All_Invalid(1) }
		MAX-ACCESS		read-write
		STATUS			current
		DESCRIPTION
				"TYPE: - Button
				 PAGE: - Input
					All Invalid  cmdID= 32901  value= 1  "
		::= { iqdbd01CmdEntry 32901 }


	iqdbd01InputValidStds108023sF OBJECT-TYPE
		SYNTAX		INTEGER { disable(0), enable(1) }
		MAX-ACCESS		read-write
		STATUS			current
		DESCRIPTION
				"TYPE: - Checkbox
				 PAGE: - Input
					1080/23sF  cmdID= 32916 "
		::= { iqdbd01CmdEntry 32916 }


	iqdbd01InputValidStds108023p OBJECT-TYPE
		SYNTAX		INTEGER { disable(0), enable(1) }
		MAX-ACCESS		read-write
		STATUS			current
		DESCRIPTION
				"TYPE: - Checkbox
				 PAGE: - Input
					1080/23p  cmdID= 32915 "
		::= { iqdbd01CmdEntry 32915 }


	iqdbd01InputValidStds108024sF OBJECT-TYPE
		SYNTAX		INTEGER { disable(0), enable(1) }
		MAX-ACCESS		read-write
		STATUS			current
		DESCRIPTION
				"TYPE: - Checkbox
				 PAGE: - Input
					1080/24sF  cmdID= 32917 "
		::= { iqdbd01CmdEntry 32917 }


	iqdbd01InputValidStds108024p OBJECT-TYPE
		SYNTAX		INTEGER { disable(0), enable(1) }
		MAX-ACCESS		read-write
		STATUS			current
		DESCRIPTION
				"TYPE: - Checkbox
				 PAGE: - Input
					1080/24p  cmdID= 32914 "
		::= { iqdbd01CmdEntry 32914 }


	iqdbd01InputValidStds108025i OBJECT-TYPE
		SYNTAX		INTEGER { disable(0), enable(1) }
		MAX-ACCESS		read-write
		STATUS			current
		DESCRIPTION
				"TYPE: - Checkbox
				 PAGE: - Input
					1080/25i  cmdID= 32910 "
		::= { iqdbd01CmdEntry 32910 }


	iqdbd01InputValidStds108025p OBJECT-TYPE
		SYNTAX		INTEGER { disable(0), enable(1) }
		MAX-ACCESS		read-write
		STATUS			current
		DESCRIPTION
				"TYPE: - Checkbox
				 PAGE: - Input
					1080/25p  cmdID= 32911 "
		::= { iqdbd01CmdEntry 32911 }


	iqdbd01InputValidStds103529i OBJECT-TYPE
		SYNTAX		INTEGER { disable(0), enable(1) }
		MAX-ACCESS		read-write
		STATUS			current
		DESCRIPTION
				"TYPE: - Checkbox
				 PAGE: - Input
					1035/29i  cmdID= 32921 "
		::= { iqdbd01CmdEntry 32921 }


	iqdbd01InputValidStds108029i OBJECT-TYPE
		SYNTAX		INTEGER { disable(0), enable(1) }
		MAX-ACCESS		read-write
		STATUS			current
		DESCRIPTION
				"TYPE: - Checkbox
				 PAGE: - Input
					1080/29i  cmdID= 32919 "
		::= { iqdbd01CmdEntry 32919 }


	iqdbd01InputValidStds108029p OBJECT-TYPE
		SYNTAX		INTEGER { disable(0), enable(1) }
		MAX-ACCESS		read-write
		STATUS			current
		DESCRIPTION
				"TYPE: - Checkbox
				 PAGE: - Input
					1080/29p  cmdID= 32918 "
		::= { iqdbd01CmdEntry 32918 }


	iqdbd01InputValidStds103530i OBJECT-TYPE
		SYNTAX		INTEGER { disable(0), enable(1) }
		MAX-ACCESS		read-write
		STATUS			current
		DESCRIPTION
				"TYPE: - Checkbox
				 PAGE: - Input
					1035/30i  cmdID= 32920 "
		::= { iqdbd01CmdEntry 32920 }


	iqdbd01InputValidStds108030i OBJECT-TYPE
		SYNTAX		INTEGER { disable(0), enable(1) }
		MAX-ACCESS		read-write
		STATUS			current
		DESCRIPTION
				"TYPE: - Checkbox
				 PAGE: - Input
					1080/30i  cmdID= 32912 "
		::= { iqdbd01CmdEntry 32912 }


	iqdbd01InputValidStds108030p OBJECT-TYPE
		SYNTAX		INTEGER { disable(0), enable(1) }
		MAX-ACCESS		read-write
		STATUS			current
		DESCRIPTION
				"TYPE: - Checkbox
				 PAGE: - Input
					1080/30p  cmdID= 32913 "
		::= { iqdbd01CmdEntry 32913 }


	iqdbd01InputValidStds72050p OBJECT-TYPE
		SYNTAX		INTEGER { disable(0), enable(1) }
		MAX-ACCESS		read-write
		STATUS			current
		DESCRIPTION
				"TYPE: - Checkbox
				 PAGE: - Input
					720/50p  cmdID= 32922 "
		::= { iqdbd01CmdEntry 32922 }


	iqdbd01InputValidStds72059p OBJECT-TYPE
		SYNTAX		INTEGER { disable(0), enable(1) }
		MAX-ACCESS		read-write
		STATUS			current
		DESCRIPTION
				"TYPE: - Checkbox
				 PAGE: - Input
					720/59p  cmdID= 32924 "
		::= { iqdbd01CmdEntry 32924 }


	iqdbd01InputValidStds72060p OBJECT-TYPE
		SYNTAX		INTEGER { disable(0), enable(1) }
		MAX-ACCESS		read-write
		STATUS			current
		DESCRIPTION
				"TYPE: - Checkbox
				 PAGE: - Input
					720/60p  cmdID= 32923 "
		::= { iqdbd01CmdEntry 32923 }


	iqdbd01InputValidStds62525i OBJECT-TYPE
		SYNTAX		INTEGER { disable(0), enable(1) }
		MAX-ACCESS		read-write
		STATUS			current
		DESCRIPTION
				"TYPE: - Checkbox
				 PAGE: - Input
					625/25i  cmdID= 32925 "
		::= { iqdbd01CmdEntry 32925 }


	iqdbd01InputValidStds52529i OBJECT-TYPE
		SYNTAX		INTEGER { disable(0), enable(1) }
		MAX-ACCESS		read-write
		STATUS			current
		DESCRIPTION
				"TYPE: - Checkbox
				 PAGE: - Input
					525/29i  cmdID= 32926 "
		::= { iqdbd01CmdEntry 32926 }


	iqdbd01InputErrorsCRCErrs OBJECT-TYPE
		SYNTAX		RollCallString
		MAX-ACCESS		read-only
		STATUS			current
		DESCRIPTION
				"TYPE: - Display
				 PAGE: - Input
					CRC Errs  cmdID= 33050  format=   "
		::= { iqdbd01CmdEntry 33050 }


	iqdbd01InputErrorsCRCErrSec OBJECT-TYPE
		SYNTAX		RollCallString
		MAX-ACCESS		read-only
		STATUS			current
		DESCRIPTION
				"TYPE: - Display
				 PAGE: - Input
					CRC ErrSec  cmdID= 33051  format=   "
		::= { iqdbd01CmdEntry 33051 }


	iqdbd01InputErrorsANCErrs OBJECT-TYPE
		SYNTAX		RollCallString
		MAX-ACCESS		read-only
		STATUS			current
		DESCRIPTION
				"TYPE: - Display
				 PAGE: - Input
					ANC Errs  cmdID= 33053  format=   "
		::= { iqdbd01CmdEntry 33053 }


	iqdbd01InputErrorsANCErrSec OBJECT-TYPE
		SYNTAX		RollCallString
		MAX-ACCESS		read-only
		STATUS			current
		DESCRIPTION
				"TYPE: - Display
				 PAGE: - Input
					ANC ErrSec  cmdID= 33054  format=   "
		::= { iqdbd01CmdEntry 33054 }


	iqdbd01InputErrorsResetSec OBJECT-TYPE
		SYNTAX		RollCallString
		MAX-ACCESS		read-only
		STATUS			current
		DESCRIPTION
				"TYPE: - Display
				 PAGE: - Input
					ResetSec  cmdID= 33055  format=   "
		::= { iqdbd01CmdEntry 33055 }


	iqdbd01InputErrorsErrorReset OBJECT-TYPE
		SYNTAX		INTEGER { noAction(0),val_Error_Reset(1) }
		MAX-ACCESS		read-write
		STATUS			current
		DESCRIPTION
				"TYPE: - Button
				 PAGE: - Input
					Error Reset  cmdID= 33052  value= 1  "
		::= { iqdbd01CmdEntry 33052 }


	iqdbd01OutputOutputStandard OBJECT-TYPE
		SYNTAX		INTEGER {
							val_Manual(0),
							val_Follows_Input(1)
							}
		MAX-ACCESS		read-write
		STATUS			current
		DESCRIPTION
				"TYPE: - RadiobuttonList
					Output Standard  cmdID= 33011
					Manual  value= 0
					Follows Input  value= 1  "
		::= { iqdbd01CmdEntry 33011 }


	iqdbd01OutputSelectStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Select Standard  cmdID= 33010
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbd01CmdEntry 33010 }


	iqdbd01OutputVideoProcAmpsMasterGain OBJECT-TYPE
		SYNTAX		INTEGER
		MAX-ACCESS		read-write
		STATUS			current
		DESCRIPTION
				"TYPE: - Number
					Master Gain  cmdID= 33000  min= -600  max= 600  step= 10  format= %0.1f dB  div_scale= 100
					Min = -6.0 dB  Max = 6.0 dB  Step = 0.1 dB "
		::= { iqdbd01CmdEntry 33000 }


	iqdbd01OutputVideoProcAmpsYGain OBJECT-TYPE
		SYNTAX		INTEGER
		MAX-ACCESS		read-write
		STATUS			current
		DESCRIPTION
				"TYPE: - Number
					Y Gain  cmdID= 33001  min= -600  max= 600  step= 10  format= %0.1f dB  div_scale= 100
					Min = -6.0 dB  Max = 6.0 dB  Step = 0.1 dB "
		::= { iqdbd01CmdEntry 33001 }


	iqdbd01OutputVideoProcAmpsCGain OBJECT-TYPE
		SYNTAX		INTEGER
		MAX-ACCESS		read-write
		STATUS			current
		DESCRIPTION
				"TYPE: - Number
					C Gain  cmdID= 33003  min= -600  max= 600  step= 10  format= %0.1f dB  div_scale= 100
					Min = -6.0 dB  Max = 6.0 dB  Step = 0.1 dB "
		::= { iqdbd01CmdEntry 33003 }


	iqdbd01OutputVideoProcAmpsBlackLevel OBJECT-TYPE
		SYNTAX		INTEGER
		MAX-ACCESS		read-write
		STATUS			current
		DESCRIPTION
				"TYPE: - Number
					Black Level  cmdID= 33002  min= -200  max= 200  step= 1  format= %0.0f mV  div_scale= 1
					Min = -200 mV  Max = 200 mV  Step = 1 mV "
		::= { iqdbd01CmdEntry 33002 }


	iqdbd01OutputDefaultOutput OBJECT-TYPE
		SYNTAX		INTEGER {
							val_Freeze_Frame(1),
							val_Freeze_Field(5),
							val_Black(2),
							val_Input(3),
							val_Out_Pattern(4)
							}
		MAX-ACCESS		read-write
		STATUS			current
		DESCRIPTION
				"TYPE: - RadiobuttonList
					Default Output  cmdID= 33031
					Freeze Frame  value= 1
					Freeze Field  value= 5
					Black  value= 2
					Input  value= 3
					Out Pattern  value= 4  "
		::= { iqdbd01CmdEntry 33031 }


	iqdbd01OutputDefaultOPStd OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Default O/P Std.  cmdID= 33012
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbd01CmdEntry 33012 }


	iqdbd01AudioDelayASourcesManual OBJECT-TYPE
		SYNTAX		INTEGER { disable(0), enable(1) }
		MAX-ACCESS		read-write
		STATUS			current
		DESCRIPTION
				"TYPE: - Checkbox
				 PAGE: - Audio- Aud.Delays
					Manual  cmdID= 38041 "
		::= { iqdbd01CmdEntry 38041 }


	iqdbd01AudioDelayASourcesGPIPWM OBJECT-TYPE
		SYNTAX		INTEGER { disable(0), enable(1) }
		MAX-ACCESS		read-write
		STATUS			current
		DESCRIPTION
				"TYPE: - Checkbox
				 PAGE: - Audio- Aud.Delays
					GPI PWM  cmdID= 38042 "
		::= { iqdbd01CmdEntry 38042 }


	iqdbd01AudioDelayASourcesRollTrack14 OBJECT-TYPE
		SYNTAX		INTEGER { disable(0), enable(1) }
		MAX-ACCESS		read-write
		STATUS			current
		DESCRIPTION
				"TYPE: - Checkbox
				 PAGE: - Audio- Aud.Delays
					RollTrack14  cmdID= 38044 "
		::= { iqdbd01CmdEntry 38044 }


	iqdbd01AudioDelayASourcesRollTrack15 OBJECT-TYPE
		SYNTAX		INTEGER { disable(0), enable(1) }
		MAX-ACCESS		read-write
		STATUS			current
		DESCRIPTION
				"TYPE: - Checkbox
				 PAGE: - Audio- Aud.Delays
					RollTrack15  cmdID= 38045 "
		::= { iqdbd01CmdEntry 38045 }


	iqdbd01AudioDelayASourcesRollTrack16 OBJECT-TYPE
		SYNTAX		INTEGER { disable(0), enable(1) }
		MAX-ACCESS		read-write
		STATUS			current
		DESCRIPTION
				"TYPE: - Checkbox
				 PAGE: - Audio- Aud.Delays
					RollTrack16  cmdID= 38046 "
		::= { iqdbd01CmdEntry 38046 }


	iqdbd01AudioDelayASourcesRollTrack17 OBJECT-TYPE
		SYNTAX		INTEGER { disable(0), enable(1) }
		MAX-ACCESS		read-write
		STATUS			current
		DESCRIPTION
				"TYPE: - Checkbox
				 PAGE: - Audio- Aud.Delays
					RollTrack17  cmdID= 38047 "
		::= { iqdbd01CmdEntry 38047 }


	iqdbd01AudDelaysAudioDelayAAdjustCoarseDelay OBJECT-TYPE
		SYNTAX		INTEGER
		MAX-ACCESS		read-write
		STATUS			current
		DESCRIPTION
				"TYPE: - Number
				 PAGE: - Audio- Aud.Delays
					Adjust Coarse Delay  cmdID= 38043  min= -4000  max= 200000  step= 25  format= %0.2f ms  div_scale= 100
					Min = -40.00 ms  Max = 2000.00 ms  Step = 0.25 ms "
		::= { iqdbd01CmdEntry 38043 }


	iqdbd01AudDelaysAudioDelayACurrentAudioDelay OBJECT-TYPE
		SYNTAX		RollCallString
		MAX-ACCESS		read-only
		STATUS			current
		DESCRIPTION
				"TYPE: - Display
				 PAGE: - Audio- Aud.Delays
					Current Audio Delay  cmdID= 38048  format=   "
		::= { iqdbd01CmdEntry 38048 }


	iqdbd01AudioDelayBSourcesManual OBJECT-TYPE
		SYNTAX		INTEGER { disable(0), enable(1) }
		MAX-ACCESS		read-write
		STATUS			current
		DESCRIPTION
				"TYPE: - Checkbox
				 PAGE: - Audio- Aud.Delays
					Manual  cmdID= 38061 "
		::= { iqdbd01CmdEntry 38061 }


	iqdbd01AudioDelayBSourcesGPIPWM OBJECT-TYPE
		SYNTAX		INTEGER { disable(0), enable(1) }
		MAX-ACCESS		read-write
		STATUS			current
		DESCRIPTION
				"TYPE: - Checkbox
				 PAGE: - Audio- Aud.Delays
					GPI PWM  cmdID= 38062 "
		::= { iqdbd01CmdEntry 38062 }


	iqdbd01AudioDelayBSourcesRollTrack14 OBJECT-TYPE
		SYNTAX		INTEGER { disable(0), enable(1) }
		MAX-ACCESS		read-write
		STATUS			current
		DESCRIPTION
				"TYPE: - Checkbox
				 PAGE: - Audio- Aud.Delays
					RollTrack14  cmdID= 38064 "
		::= { iqdbd01CmdEntry 38064 }


	iqdbd01AudioDelayBSourcesRollTrack15 OBJECT-TYPE
		SYNTAX		INTEGER { disable(0), enable(1) }
		MAX-ACCESS		read-write
		STATUS			current
		DESCRIPTION
				"TYPE: - Checkbox
				 PAGE: - Audio- Aud.Delays
					RollTrack15  cmdID= 38065 "
		::= { iqdbd01CmdEntry 38065 }


	iqdbd01AudioDelayBSourcesRollTrack16 OBJECT-TYPE
		SYNTAX		INTEGER { disable(0), enable(1) }
		MAX-ACCESS		read-write
		STATUS			current
		DESCRIPTION
				"TYPE: - Checkbox
				 PAGE: - Audio- Aud.Delays
					RollTrack16  cmdID= 38066 "
		::= { iqdbd01CmdEntry 38066 }


	iqdbd01AudioDelayBSourcesRollTrack17 OBJECT-TYPE
		SYNTAX		INTEGER { disable(0), enable(1) }
		MAX-ACCESS		read-write
		STATUS			current
		DESCRIPTION
				"TYPE: - Checkbox
				 PAGE: - Audio- Aud.Delays
					RollTrack17  cmdID= 38067 "
		::= { iqdbd01CmdEntry 38067 }


	iqdbd01AudDelaysAudioDelayBAdjustCoarseDelay OBJECT-TYPE
		SYNTAX		INTEGER
		MAX-ACCESS		read-write
		STATUS			current
		DESCRIPTION
				"TYPE: - Number
				 PAGE: - Audio- Aud.Delays
					Adjust Coarse Delay  cmdID= 38063  min= -4000  max= 200000  step= 25  format= %0.2f ms  div_scale= 100
					Min = -40.00 ms  Max = 2000.00 ms  Step = 0.25 ms "
		::= { iqdbd01CmdEntry 38063 }


	iqdbd01AudDelaysAudioDelayBCurrentAudioDelay OBJECT-TYPE
		SYNTAX		RollCallString
		MAX-ACCESS		read-only
		STATUS			current
		DESCRIPTION
				"TYPE: - Display
				 PAGE: - Audio- Aud.Delays
					Current Audio Delay  cmdID= 38068  format=   "
		::= { iqdbd01CmdEntry 38068 }


	iqdbd01AudDelaysAESDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-1  cmdID= 38600
					Min  value= 0
					Delay A  value= 1
					Delay B  value= 2  "
		::= { iqdbd01CmdEntry 38600 }


	iqdbd01AudDelaysAESDelaySelectInternal1 OBJECT-TYPE
		SYNTAX		INTEGER { disable(0), enable(1) }
		MAX-ACCESS		read-write
		STATUS			current
		DESCRIPTION
				"TYPE: - Checkbox
				 PAGE: - Audio- Aud.Delays
					Internal-1  cmdID= 38620 "
		::= { iqdbd01CmdEntry 38620 }


	iqdbd01AudDelaysAESDelaySelectAutoDolbyEPhase1 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38118 "
		::= { iqdbd01CmdEntry 38118 }


	iqdbd01AudDelaysAESDelaySelectDelayLimit1 OBJECT-TYPE
		SYNTAX		RollCallString
		MAX-ACCESS		read-only
		STATUS			current
		DESCRIPTION
				"TYPE: - Display
				 PAGE: - Audio- Aud.Delays
					Delay Limit  cmdID= 38300  format=   "
		::= { iqdbd01CmdEntry 38300 }


	iqdbd01AudDelaysAESDelaySelectAES1FineDelay OBJECT-TYPE
		SYNTAX		INTEGER
		MAX-ACCESS		read-write
		STATUS			current
		DESCRIPTION
				"TYPE: - Number
				 PAGE: - Audio- Aud.Delays
					AES 1 Fine Delay  cmdID= 38130  min= -2450  max= 2450  step= 52  format= %0.3f ms  div_scale= 10000
					Min = -0.245 ms  Max = 0.245 ms  Step = 0.005 ms "
		::= { iqdbd01CmdEntry 38130 }


	iqdbd01AudDelaysAESDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-2  cmdID= 38601
					Min  value= 0
					Delay A  value= 1
					Delay B  value= 2  "
		::= { iqdbd01CmdEntry 38601 }


	iqdbd01AudDelaysAESDelaySelectInternal2 OBJECT-TYPE
		SYNTAX		INTEGER { disable(0), enable(1) }
		MAX-ACCESS		read-write
		STATUS			current
		DESCRIPTION
				"TYPE: - Checkbox
				 PAGE: - Audio- Aud.Delays
					Internal-2  cmdID= 38621 "
		::= { iqdbd01CmdEntry 38621 }


	iqdbd01AudDelaysAESDelaySelectAutoDolbyEPhase2 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38119 "
		::= { iqdbd01CmdEntry 38119 }


	iqdbd01AudDelaysAESDelaySelectDelayLimit2 OBJECT-TYPE
		SYNTAX		RollCallString
		MAX-ACCESS		read-only
		STATUS			current
		DESCRIPTION
				"TYPE: - Display
				 PAGE: - Audio- Aud.Delays
					Delay Limit  cmdID= 38301  format=   "
		::= { iqdbd01CmdEntry 38301 }


	iqdbd01AudDelaysAESDelaySelectAES2FineDelay OBJECT-TYPE
		SYNTAX		INTEGER
		MAX-ACCESS		read-write
		STATUS			current
		DESCRIPTION
				"TYPE: - Number
				 PAGE: - Audio- Aud.Delays
					AES 2 Fine Delay  cmdID= 38131  min= -2450  max= 2450  step= 52  format= %0.3f ms  div_scale= 10000
					Min = -0.245 ms  Max = 0.245 ms  Step = 0.005 ms "
		::= { iqdbd01CmdEntry 38131 }


	iqdbd01AudDelaysAESDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-3  cmdID= 38602
					Min  value= 0
					Delay A  value= 1
					Delay B  value= 2  "
		::= { iqdbd01CmdEntry 38602 }


	iqdbd01AudDelaysAESDelaySelectInternal3 OBJECT-TYPE
		SYNTAX		INTEGER { disable(0), enable(1) }
		MAX-ACCESS		read-write
		STATUS			current
		DESCRIPTION
				"TYPE: - Checkbox
				 PAGE: - Audio- Aud.Delays
					Internal-3  cmdID= 38622 "
		::= { iqdbd01CmdEntry 38622 }


	iqdbd01AudDelaysAESDelaySelectAutoDolbyEPhase3 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38120 "
		::= { iqdbd01CmdEntry 38120 }


	iqdbd01AudDelaysAESDelaySelectDelayLimit3 OBJECT-TYPE
		SYNTAX		RollCallString
		MAX-ACCESS		read-only
		STATUS			current
		DESCRIPTION
				"TYPE: - Display
				 PAGE: - Audio- Aud.Delays
					Delay Limit  cmdID= 38302  format=   "
		::= { iqdbd01CmdEntry 38302 }


	iqdbd01AudDelaysAESDelaySelectAES3FineDelay OBJECT-TYPE
		SYNTAX		INTEGER
		MAX-ACCESS		read-write
		STATUS			current
		DESCRIPTION
				"TYPE: - Number
				 PAGE: - Audio- Aud.Delays
					AES 3 Fine Delay  cmdID= 38132  min= -2450  max= 2450  step= 52  format= %0.3f ms  div_scale= 10000
					Min = -0.245 ms  Max = 0.245 ms  Step = 0.005 ms "
		::= { iqdbd01CmdEntry 38132 }


	iqdbd01AudDelaysAESDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-4  cmdID= 38603
					Min  value= 0
					Delay A  value= 1
					Delay B  value= 2  "
		::= { iqdbd01CmdEntry 38603 }


	iqdbd01AudDelaysAESDelaySelectInternal4 OBJECT-TYPE
		SYNTAX		INTEGER { disable(0), enable(1) }
		MAX-ACCESS		read-write
		STATUS			current
		DESCRIPTION
				"TYPE: - Checkbox
				 PAGE: - Audio- Aud.Delays
					Internal-4  cmdID= 38623 "
		::= { iqdbd01CmdEntry 38623 }


	iqdbd01AudDelaysAESDelaySelectAutoDolbyEPhase4 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38121 "
		::= { iqdbd01CmdEntry 38121 }


	iqdbd01AudDelaysAESDelaySelectDelayLimit4 OBJECT-TYPE
		SYNTAX		RollCallString
		MAX-ACCESS		read-only
		STATUS			current
		DESCRIPTION
				"TYPE: - Display
				 PAGE: - Audio- Aud.Delays
					Delay Limit  cmdID= 38303  format=   "
		::= { iqdbd01CmdEntry 38303 }


	iqdbd01AudDelaysAESDelaySelectAES4FineDelay OBJECT-TYPE
		SYNTAX		INTEGER
		MAX-ACCESS		read-write
		STATUS			current
		DESCRIPTION
				"TYPE: - Number
				 PAGE: - Audio- Aud.Delays
					AES 4 Fine Delay  cmdID= 38133  min= -2450  max= 2450  step= 52  format= %0.3f ms  div_scale= 10000
					Min = -0.245 ms  Max = 0.245 ms  Step = 0.005 ms "
		::= { iqdbd01CmdEntry 38133 }


	iqdbd01AudDelaysAESDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-5  cmdID= 38604
					Min  value= 0
					Delay A  value= 1
					Delay B  value= 2  "
		::= { iqdbd01CmdEntry 38604 }


	iqdbd01AudDelaysAESDelaySelectInternal5 OBJECT-TYPE
		SYNTAX		INTEGER { disable(0), enable(1) }
		MAX-ACCESS		read-write
		STATUS			current
		DESCRIPTION
				"TYPE: - Checkbox
				 PAGE: - Audio- Aud.Delays
					Internal-5  cmdID= 38624 "
		::= { iqdbd01CmdEntry 38624 }


	iqdbd01AudDelaysAESDelaySelectAutoDolbyEPhase5 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38122 "
		::= { iqdbd01CmdEntry 38122 }


	iqdbd01AudDelaysAESDelaySelectDelayLimit5 OBJECT-TYPE
		SYNTAX		RollCallString
		MAX-ACCESS		read-only
		STATUS			current
		DESCRIPTION
				"TYPE: - Display
				 PAGE: - Audio- Aud.Delays
					Delay Limit  cmdID= 38304  format=   "
		::= { iqdbd01CmdEntry 38304 }


	iqdbd01AudDelaysAESDelaySelectAES5FineDelay OBJECT-TYPE
		SYNTAX		INTEGER
		MAX-ACCESS		read-write
		STATUS			current
		DESCRIPTION
				"TYPE: - Number
				 PAGE: - Audio- Aud.Delays
					AES 5 Fine Delay  cmdID= 38134  min= -2450  max= 2450  step= 52  format= %0.3f ms  div_scale= 10000
					Min = -0.245 ms  Max = 0.245 ms  Step = 0.005 ms "
		::= { iqdbd01CmdEntry 38134 }


	iqdbd01AudDelaysAESDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-6  cmdID= 38605
					Min  value= 0
					Delay A  value= 1
					Delay B  value= 2  "
		::= { iqdbd01CmdEntry 38605 }


	iqdbd01AudDelaysAESDelaySelectInternal6 OBJECT-TYPE
		SYNTAX		INTEGER { disable(0), enable(1) }
		MAX-ACCESS		read-write
		STATUS			current
		DESCRIPTION
				"TYPE: - Checkbox
				 PAGE: - Audio- Aud.Delays
					Internal-6  cmdID= 38625 "
		::= { iqdbd01CmdEntry 38625 }


	iqdbd01AudDelaysAESDelaySelectAutoDolbyEPhase6 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38123 "
		::= { iqdbd01CmdEntry 38123 }


	iqdbd01AudDelaysAESDelaySelectDelayLimit6 OBJECT-TYPE
		SYNTAX		RollCallString
		MAX-ACCESS		read-only
		STATUS			current
		DESCRIPTION
				"TYPE: - Display
				 PAGE: - Audio- Aud.Delays
					Delay Limit  cmdID= 38305  format=   "
		::= { iqdbd01CmdEntry 38305 }


	iqdbd01AudDelaysAESDelaySelectAES6FineDelay OBJECT-TYPE
		SYNTAX		INTEGER
		MAX-ACCESS		read-write
		STATUS			current
		DESCRIPTION
				"TYPE: - Number
				 PAGE: - Audio- Aud.Delays
					AES 6 Fine Delay  cmdID= 38135  min= -2450  max= 2450  step= 52  format= %0.3f ms  div_scale= 10000
					Min = -0.245 ms  Max = 0.245 ms  Step = 0.005 ms "
		::= { iqdbd01CmdEntry 38135 }


	iqdbd01AudDelaysAESDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-7  cmdID= 38606
					Min  value= 0
					Delay A  value= 1
					Delay B  value= 2  "
		::= { iqdbd01CmdEntry 38606 }


	iqdbd01AudDelaysAESDelaySelectInternal7 OBJECT-TYPE
		SYNTAX		INTEGER { disable(0), enable(1) }
		MAX-ACCESS		read-write
		STATUS			current
		DESCRIPTION
				"TYPE: - Checkbox
				 PAGE: - Audio- Aud.Delays
					Internal-7  cmdID= 38626 "
		::= { iqdbd01CmdEntry 38626 }


	iqdbd01AudDelaysAESDelaySelectAutoDolbyEPhase7 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38124 "
		::= { iqdbd01CmdEntry 38124 }


	iqdbd01AudDelaysAESDelaySelectDelayLimit7 OBJECT-TYPE
		SYNTAX		RollCallString
		MAX-ACCESS		read-only
		STATUS			current
		DESCRIPTION
				"TYPE: - Display
				 PAGE: - Audio- Aud.Delays
					Delay Limit  cmdID= 38306  format=   "
		::= { iqdbd01CmdEntry 38306 }


	iqdbd01AudDelaysAESDelaySelectAES7FineDelay OBJECT-TYPE
		SYNTAX		INTEGER
		MAX-ACCESS		read-write
		STATUS			current
		DESCRIPTION
				"TYPE: - Number
				 PAGE: - Audio- Aud.Delays
					AES 7 Fine Delay  cmdID= 38136  min= -2450  max= 2450  step= 52  format= %0.3f ms  div_scale= 10000
					Min = -0.245 ms  Max = 0.245 ms  Step = 0.005 ms "
		::= { iqdbd01CmdEntry 38136 }


	iqdbd01AudDelaysAESDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-8  cmdID= 38607
					Min  value= 0
					Delay A  value= 1
					Delay B  value= 2  "
		::= { iqdbd01CmdEntry 38607 }


	iqdbd01AudDelaysAESDelaySelectInternal8 OBJECT-TYPE
		SYNTAX		INTEGER { disable(0), enable(1) }
		MAX-ACCESS		read-write
		STATUS			current
		DESCRIPTION
				"TYPE: - Checkbox
				 PAGE: - Audio- Aud.Delays
					Internal-8  cmdID= 38627 "
		::= { iqdbd01CmdEntry 38627 }


	iqdbd01AudDelaysAESDelaySelectAutoDolbyEPhase8 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38125 "
		::= { iqdbd01CmdEntry 38125 }


	iqdbd01AudDelaysAESDelaySelectDelayLimit8 OBJECT-TYPE
		SYNTAX		RollCallString
		MAX-ACCESS		read-only
		STATUS			current
		DESCRIPTION
				"TYPE: - Display
				 PAGE: - Audio- Aud.Delays
					Delay Limit  cmdID= 38307  format=   "
		::= { iqdbd01CmdEntry 38307 }


	iqdbd01AudDelaysAESDelaySelectAES8FineDelay OBJECT-TYPE
		SYNTAX		INTEGER
		MAX-ACCESS		read-write
		STATUS			current
		DESCRIPTION
				"TYPE: - Number
				 PAGE: - Audio- Aud.Delays
					AES 8 Fine Delay  cmdID= 38137  min= -2450  max= 2450  step= 52  format= %0.3f ms  div_scale= 10000
					Min = -0.245 ms  Max = 0.245 ms  Step = 0.005 ms "
		::= { iqdbd01CmdEntry 38137 }


	iqdbd01AudDelaysEMBDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-1  cmdID= 38080
					Min  value= 0
					Delay A  value= 1
					Delay B  value= 2  "
		::= { iqdbd01CmdEntry 38080 }


	iqdbd01AudDelaysEMBDelaySelectInternal1 OBJECT-TYPE
		SYNTAX		INTEGER { disable(0), enable(1) }
		MAX-ACCESS		read-write
		STATUS			current
		DESCRIPTION
				"TYPE: - Checkbox
				 PAGE: - Audio- Aud.Delays
					Internal-1  cmdID= 38100 "
		::= { iqdbd01CmdEntry 38100 }


	iqdbd01AudDelaysEMBDelaySelectAutoDolbyEPhase1 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38110 "
		::= { iqdbd01CmdEntry 38110 }


	iqdbd01AudDelaysEMBDelaySelectDelayLimit1 OBJECT-TYPE
		SYNTAX		RollCallString
		MAX-ACCESS		read-only
		STATUS			current
		DESCRIPTION
				"TYPE: - Display
				 PAGE: - Audio- Aud.Delays
					Delay Limit  cmdID= 38308  format=   "
		::= { iqdbd01CmdEntry 38308 }


	iqdbd01AudDelaysEMBDelaySelectEMB1FineDelay OBJECT-TYPE
		SYNTAX		INTEGER
		MAX-ACCESS		read-write
		STATUS			current
		DESCRIPTION
				"TYPE: - Number
				 PAGE: - Audio- Aud.Delays
					EMB 1 Fine Delay  cmdID= 38138  min= -2450  max= 2450  step= 52  format= %0.3f ms  div_scale= 10000
					Min = -0.245 ms  Max = 0.245 ms  Step = 0.005 ms "
		::= { iqdbd01CmdEntry 38138 }


	iqdbd01AudDelaysEMBDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-2  cmdID= 38081
					Min  value= 0
					Delay A  value= 1
					Delay B  value= 2  "
		::= { iqdbd01CmdEntry 38081 }


	iqdbd01AudDelaysEMBDelaySelectInternal2 OBJECT-TYPE
		SYNTAX		INTEGER { disable(0), enable(1) }
		MAX-ACCESS		read-write
		STATUS			current
		DESCRIPTION
				"TYPE: - Checkbox
				 PAGE: - Audio- Aud.Delays
					Internal-2  cmdID= 38101 "
		::= { iqdbd01CmdEntry 38101 }


	iqdbd01AudDelaysEMBDelaySelectAutoDolbyEPhase2 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38111 "
		::= { iqdbd01CmdEntry 38111 }


	iqdbd01AudDelaysEMBDelaySelectDelayLimit2 OBJECT-TYPE
		SYNTAX		RollCallString
		MAX-ACCESS		read-only
		STATUS			current
		DESCRIPTION
				"TYPE: - Display
				 PAGE: - Audio- Aud.Delays
					Delay Limit  cmdID= 38309  format=   "
		::= { iqdbd01CmdEntry 38309 }


	iqdbd01AudDelaysEMBDelaySelectEMB2FineDelay OBJECT-TYPE
		SYNTAX		INTEGER
		MAX-ACCESS		read-write
		STATUS			current
		DESCRIPTION
				"TYPE: - Number
				 PAGE: - Audio- Aud.Delays
					EMB 2 Fine Delay  cmdID= 38139  min= -2450  max= 2450  step= 52  format= %0.3f ms  div_scale= 10000
					Min = -0.245 ms  Max = 0.245 ms  Step = 0.005 ms "
		::= { iqdbd01CmdEntry 38139 }


	iqdbd01AudDelaysEMBDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-3  cmdID= 38082
					Min  value= 0
					Delay A  value= 1
					Delay B  value= 2  "
		::= { iqdbd01CmdEntry 38082 }


	iqdbd01AudDelaysEMBDelaySelectInternal3 OBJECT-TYPE
		SYNTAX		INTEGER { disable(0), enable(1) }
		MAX-ACCESS		read-write
		STATUS			current
		DESCRIPTION
				"TYPE: - Checkbox
				 PAGE: - Audio- Aud.Delays
					Internal-3  cmdID= 38102 "
		::= { iqdbd01CmdEntry 38102 }


	iqdbd01AudDelaysEMBDelaySelectAutoDolbyEPhase3 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38112 "
		::= { iqdbd01CmdEntry 38112 }


	iqdbd01AudDelaysEMBDelaySelectDelayLimit3 OBJECT-TYPE
		SYNTAX		RollCallString
		MAX-ACCESS		read-only
		STATUS			current
		DESCRIPTION
				"TYPE: - Display
				 PAGE: - Audio- Aud.Delays
					Delay Limit  cmdID= 38310  format=   "
		::= { iqdbd01CmdEntry 38310 }


	iqdbd01AudDelaysEMBDelaySelectEMB3FineDelay OBJECT-TYPE
		SYNTAX		INTEGER
		MAX-ACCESS		read-write
		STATUS			current
		DESCRIPTION
				"TYPE: - Number
				 PAGE: - Audio- Aud.Delays
					EMB 3 Fine Delay  cmdID= 38140  min= -2450  max= 2450  step= 52  format= %0.3f ms  div_scale= 10000
					Min = -0.245 ms  Max = 0.245 ms  Step = 0.005 ms "
		::= { iqdbd01CmdEntry 38140 }


	iqdbd01AudDelaysEMBDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-4  cmdID= 38083
					Min  value= 0
					Delay A  value= 1
					Delay B  value= 2  "
		::= { iqdbd01CmdEntry 38083 }


	iqdbd01AudDelaysEMBDelaySelectInternal4 OBJECT-TYPE
		SYNTAX		INTEGER { disable(0), enable(1) }
		MAX-ACCESS		read-write
		STATUS			current
		DESCRIPTION
				"TYPE: - Checkbox
				 PAGE: - Audio- Aud.Delays
					Internal-4  cmdID= 38103 "
		::= { iqdbd01CmdEntry 38103 }


	iqdbd01AudDelaysEMBDelaySelectAutoDolbyEPhase4 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38113 "
		::= { iqdbd01CmdEntry 38113 }


	iqdbd01AudDelaysEMBDelaySelectDelayLimit4 OBJECT-TYPE
		SYNTAX		RollCallString
		MAX-ACCESS		read-only
		STATUS			current
		DESCRIPTION
				"TYPE: - Display
				 PAGE: - Audio- Aud.Delays
					Delay Limit  cmdID= 38311  format=   "
		::= { iqdbd01CmdEntry 38311 }


	iqdbd01AudDelaysEMBDelaySelectEMB4FineDelay OBJECT-TYPE
		SYNTAX		INTEGER
		MAX-ACCESS		read-write
		STATUS			current
		DESCRIPTION
				"TYPE: - Number
				 PAGE: - Audio- Aud.Delays
					EMB 4 Fine Delay  cmdID= 38141  min= -2450  max= 2450  step= 52  format= %0.3f ms  div_scale= 10000
					Min = -0.245 ms  Max = 0.245 ms  Step = 0.005 ms "
		::= { iqdbd01CmdEntry 38141 }


	iqdbd01AudDelaysEMBDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-5  cmdID= 38084
					Min  value= 0
					Delay A  value= 1
					Delay B  value= 2  "
		::= { iqdbd01CmdEntry 38084 }


	iqdbd01AudDelaysEMBDelaySelectInternal5 OBJECT-TYPE
		SYNTAX		INTEGER { disable(0), enable(1) }
		MAX-ACCESS		read-write
		STATUS			current
		DESCRIPTION
				"TYPE: - Checkbox
				 PAGE: - Audio- Aud.Delays
					Internal-5  cmdID= 38104 "
		::= { iqdbd01CmdEntry 38104 }


	iqdbd01AudDelaysEMBDelaySelectAutoDolbyEPhase5 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38114 "
		::= { iqdbd01CmdEntry 38114 }


	iqdbd01AudDelaysEMBDelaySelectDelayLimit5 OBJECT-TYPE
		SYNTAX		RollCallString
		MAX-ACCESS		read-only
		STATUS			current
		DESCRIPTION
				"TYPE: - Display
				 PAGE: - Audio- Aud.Delays
					Delay Limit  cmdID= 38312  format=   "
		::= { iqdbd01CmdEntry 38312 }


	iqdbd01AudDelaysEMBDelaySelectEMB5FineDelay OBJECT-TYPE
		SYNTAX		INTEGER
		MAX-ACCESS		read-write
		STATUS			current
		DESCRIPTION
				"TYPE: - Number
				 PAGE: - Audio- Aud.Delays
					EMB 5 Fine Delay  cmdID= 38142  min= -2450  max= 2450  step= 52  format= %0.3f ms  div_scale= 10000
					Min = -0.245 ms  Max = 0.245 ms  Step = 0.005 ms "
		::= { iqdbd01CmdEntry 38142 }


	iqdbd01AudDelaysEMBDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-6  cmdID= 38085
					Min  value= 0
					Delay A  value= 1
					Delay B  value= 2  "
		::= { iqdbd01CmdEntry 38085 }


	iqdbd01AudDelaysEMBDelaySelectInternal6 OBJECT-TYPE
		SYNTAX		INTEGER { disable(0), enable(1) }
		MAX-ACCESS		read-write
		STATUS			current
		DESCRIPTION
				"TYPE: - Checkbox
				 PAGE: - Audio- Aud.Delays
					Internal-6  cmdID= 38105 "
		::= { iqdbd01CmdEntry 38105 }


	iqdbd01AudDelaysEMBDelaySelectAutoDolbyEPhase6 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38115 "
		::= { iqdbd01CmdEntry 38115 }


	iqdbd01AudDelaysEMBDelaySelectDelayLimit6 OBJECT-TYPE
		SYNTAX		RollCallString
		MAX-ACCESS		read-only
		STATUS			current
		DESCRIPTION
				"TYPE: - Display
				 PAGE: - Audio- Aud.Delays
					Delay Limit  cmdID= 38313  format=   "
		::= { iqdbd01CmdEntry 38313 }


	iqdbd01AudDelaysEMBDelaySelectEMB6FineDelay OBJECT-TYPE
		SYNTAX		INTEGER
		MAX-ACCESS		read-write
		STATUS			current
		DESCRIPTION
				"TYPE: - Number
				 PAGE: - Audio- Aud.Delays
					EMB 6 Fine Delay  cmdID= 38143  min= -2450  max= 2450  step= 52  format= %0.3f ms  div_scale= 10000
					Min = -0.245 ms  Max = 0.245 ms  Step = 0.005 ms "
		::= { iqdbd01CmdEntry 38143 }


	iqdbd01AudDelaysEMBDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-7  cmdID= 38086
					Min  value= 0
					Delay A  value= 1
					Delay B  value= 2  "
		::= { iqdbd01CmdEntry 38086 }


	iqdbd01AudDelaysEMBDelaySelectInternal7 OBJECT-TYPE
		SYNTAX		INTEGER { disable(0), enable(1) }
		MAX-ACCESS		read-write
		STATUS			current
		DESCRIPTION
				"TYPE: - Checkbox
				 PAGE: - Audio- Aud.Delays
					Internal-7  cmdID= 38106 "
		::= { iqdbd01CmdEntry 38106 }


	iqdbd01AudDelaysEMBDelaySelectAutoDolbyEPhase7 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38116 "
		::= { iqdbd01CmdEntry 38116 }


	iqdbd01AudDelaysEMBDelaySelectDelayLimit7 OBJECT-TYPE
		SYNTAX		RollCallString
		MAX-ACCESS		read-only
		STATUS			current
		DESCRIPTION
				"TYPE: - Display
				 PAGE: - Audio- Aud.Delays
					Delay Limit  cmdID= 38314  format=   "
		::= { iqdbd01CmdEntry 38314 }


	iqdbd01AudDelaysEMBDelaySelectEMB7FineDelay OBJECT-TYPE
		SYNTAX		INTEGER
		MAX-ACCESS		read-write
		STATUS			current
		DESCRIPTION
				"TYPE: - Number
				 PAGE: - Audio- Aud.Delays
					EMB 7 Fine Delay  cmdID= 38144  min= -2450  max= 2450  step= 52  format= %0.3f ms  div_scale= 10000
					Min = -0.245 ms  Max = 0.245 ms  Step = 0.005 ms "
		::= { iqdbd01CmdEntry 38144 }


	iqdbd01AudDelaysEMBDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-8  cmdID= 38087
					Min  value= 0
					Delay A  value= 1
					Delay B  value= 2  "
		::= { iqdbd01CmdEntry 38087 }


	iqdbd01AudDelaysEMBDelaySelectInternal8 OBJECT-TYPE
		SYNTAX		INTEGER { disable(0), enable(1) }
		MAX-ACCESS		read-write
		STATUS			current
		DESCRIPTION
				"TYPE: - Checkbox
				 PAGE: - Audio- Aud.Delays
					Internal-8  cmdID= 38107 "
		::= { iqdbd01CmdEntry 38107 }


	iqdbd01AudDelaysEMBDelaySelectDelayLimit8 OBJECT-TYPE
		SYNTAX		RollCallString
		MAX-ACCESS		read-only
		STATUS			current
		DESCRIPTION
				"TYPE: - Display
				 PAGE: - Audio- Aud.Delays
					Delay Limit  cmdID= 38315  format=   "
		::= { iqdbd01CmdEntry 38315 }


	iqdbd01AudDelaysEMBDelaySelectAutoDolbyEPhase8 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38117 "
		::= { iqdbd01CmdEntry 38117 }


	iqdbd01AudDelaysEMBDelaySelectEMB8FineDelay OBJECT-TYPE
		SYNTAX		INTEGER
		MAX-ACCESS		read-write
		STATUS			current
		DESCRIPTION
				"TYPE: - Number
				 PAGE: - Audio- Aud.Delays
					EMB 8 Fine Delay  cmdID= 38145  min= -2450  max= 2450  step= 52  format= %0.3f ms  div_scale= 10000
					Min = -0.245 ms  Max = 0.245 ms  Step = 0.005 ms "
		::= { iqdbd01CmdEntry 38145 }


	iqdbd01AudioAudDelaysRollTrack14 OBJECT-TYPE
		SYNTAX		RollCallString
		MAX-ACCESS		read-only
		STATUS			current
		DESCRIPTION
				"TYPE: - Display
				 PAGE: - Audio- Aud.Delays
					RollTrack14  cmdID= 14  format=   "
		::= { iqdbd01CmdEntry 14 }


	iqdbd01AudioAudDelaysRollTrack15 OBJECT-TYPE
		SYNTAX		RollCallString
		MAX-ACCESS		read-only
		STATUS			current
		DESCRIPTION
				"TYPE: - Display
				 PAGE: - Audio- Aud.Delays
					RollTrack15  cmdID= 15  format=   "
		::= { iqdbd01CmdEntry 15 }


	iqdbd01AudioAudDelaysRollTrack16 OBJECT-TYPE
		SYNTAX		RollCallString
		MAX-ACCESS		read-only
		STATUS			current
		DESCRIPTION
				"TYPE: - Display
				 PAGE: - Audio- Aud.Delays
					RollTrack16  cmdID= 16  format=   "
		::= { iqdbd01CmdEntry 16 }


	iqdbd01AudioAudDelaysRollTrack17 OBJECT-TYPE
		SYNTAX		RollCallString
		MAX-ACCESS		read-only
		STATUS			current
		DESCRIPTION
				"TYPE: - Display
				 PAGE: - Audio- Aud.Delays
					RollTrack17  cmdID= 17  format=   "
		::= { iqdbd01CmdEntry 17 }


	iqdbd01EmbCtrlGroupGroup1Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 1 Audio  cmdID= 37450
					Pass  value= 0
					Blank  value= 2
					Embed  value= 1  "
		::= { iqdbd01CmdEntry 37450 }


	iqdbd01EmbCtrlGroupGroup2Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 2 Audio  cmdID= 37451
					Pass  value= 0
					Blank  value= 2
					Embed  value= 1  "
		::= { iqdbd01CmdEntry 37451 }


	iqdbd01EmbCtrlGroupGroup3Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 3 Audio  cmdID= 37452
					Pass  value= 0
					Blank  value= 2
					Embed  value= 1  "
		::= { iqdbd01CmdEntry 37452 }


	iqdbd01EmbCtrlGroupGroup4Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 4 Audio  cmdID= 37453
					Pass  value= 0
					Blank  value= 2
					Embed  value= 1  "
		::= { iqdbd01CmdEntry 37453 }


	iqdbd01EmbCtrlChannelPair1LActive OBJECT-TYPE
		SYNTAX		INTEGER { disable(0), enable(1) }
		MAX-ACCESS		read-write
		STATUS			current
		DESCRIPTION
				"TYPE: - Checkbox
				 PAGE: - Audio- Emb.Ctrl
					Pair 1-L Active  cmdID= 37431 "
		::= { iqdbd01CmdEntry 37431 }


	iqdbd01EmbCtrlChannelPair1RActive OBJECT-TYPE
		SYNTAX		INTEGER { disable(0), enable(1) }
		MAX-ACCESS		read-write
		STATUS			current
		DESCRIPTION
				"TYPE: - Checkbox
				 PAGE: - Audio- Emb.Ctrl
					Pair 1-R Active  cmdID= 37432 "
		::= { iqdbd01CmdEntry 37432 }


	iqdbd01EmbCtrlChannelPair2LActive OBJECT-TYPE
		SYNTAX		INTEGER { disable(0), enable(1) }
		MAX-ACCESS		read-write
		STATUS			current
		DESCRIPTION
				"TYPE: - Checkbox
				 PAGE: - Audio- Emb.Ctrl
					Pair 2-L Active  cmdID= 37433 "
		::= { iqdbd01CmdEntry 37433 }


	iqdbd01EmbCtrlChannelPair2RActive OBJECT-TYPE
		SYNTAX		INTEGER { disable(0), enable(1) }
		MAX-ACCESS		read-write
		STATUS			current
		DESCRIPTION
				"TYPE: - Checkbox
				 PAGE: - Audio- Emb.Ctrl
					Pair 2-R Active  cmdID= 37434 "
		::= { iqdbd01CmdEntry 37434 }


	iqdbd01EmbCtrlChannelPair3LActive OBJECT-TYPE
		SYNTAX		INTEGER { disable(0), enable(1) }
		MAX-ACCESS		read-write
		STATUS			current
		DESCRIPTION
				"TYPE: - Checkbox
				 PAGE: - Audio- Emb.Ctrl
					Pair 3-L Active  cmdID= 37435 "
		::= { iqdbd01CmdEntry 37435 }


	iqdbd01EmbCtrlChannelPair3RActive OBJECT-TYPE
		SYNTAX		INTEGER { disable(0), enable(1) }
		MAX-ACCESS		read-write
		STATUS			current
		DESCRIPTION
				"TYPE: - Checkbox
				 PAGE: - Audio- Emb.Ctrl
					Pair 3-R Active  cmdID= 37436 "
		::= { iqdbd01CmdEntry 37436 }


	iqdbd01EmbCtrlChannelPair4LActive OBJECT-TYPE
		SYNTAX		INTEGER { disable(0), enable(1) }
		MAX-ACCESS		read-write
		STATUS			current
		DESCRIPTION
				"TYPE: - Checkbox
				 PAGE: - Audio- Emb.Ctrl
					Pair 4-L Active  cmdID= 37437 "
		::= { iqdbd01CmdEntry 37437 }


	iqdbd01EmbCtrlChannelPair4RActive OBJECT-TYPE
		SYNTAX		INTEGER { disable(0), enable(1) }
		MAX-ACCESS		read-write
		STATUS			current
		DESCRIPTION
				"TYPE: - Checkbox
				 PAGE: - Audio- Emb.Ctrl
					Pair 4-R Active  cmdID= 37438 "
		::= { iqdbd01CmdEntry 37438 }


	iqdbd01EmbCtrlChannelPair5LActive OBJECT-TYPE
		SYNTAX		INTEGER { disable(0), enable(1) }
		MAX-ACCESS		read-write
		STATUS			current
		DESCRIPTION
				"TYPE: - Checkbox
				 PAGE: - Audio- Emb.Ctrl
					Pair 5-L Active  cmdID= 37439 "
		::= { iqdbd01CmdEntry 37439 }


	iqdbd01EmbCtrlChannelPair5RActive OBJECT-TYPE
		SYNTAX		INTEGER { disable(0), enable(1) }
		MAX-ACCESS		read-write
		STATUS			current
		DESCRIPTION
				"TYPE: - Checkbox
				 PAGE: - Audio- Emb.Ctrl
					Pair 5-R Active  cmdID= 37440 "
		::= { iqdbd01CmdEntry 37440 }


	iqdbd01EmbCtrlChannelPair6LActive OBJECT-TYPE
		SYNTAX		INTEGER { disable(0), enable(1) }
		MAX-ACCESS		read-write
		STATUS			current
		DESCRIPTION
				"TYPE: - Checkbox
				 PAGE: - Audio- Emb.Ctrl
					Pair 6-L Active  cmdID= 37441 "
		::= { iqdbd01CmdEntry 37441 }


	iqdbd01EmbCtrlChannelPair6RActive OBJECT-TYPE
		SYNTAX		INTEGER { disable(0), enable(1) }
		MAX-ACCESS		read-write
		STATUS			current
		DESCRIPTION
				"TYPE: - Checkbox
				 PAGE: - Audio- Emb.Ctrl
					Pair 6-R Active  cmdID= 37442 "
		::= { iqdbd01CmdEntry 37442 }


	iqdbd01EmbCtrlChannelPair7LActive OBJECT-TYPE
		SYNTAX		INTEGER { disable(0), enable(1) }
		MAX-ACCESS		read-write
		STATUS			current
		DESCRIPTION
				"TYPE: - Checkbox
				 PAGE: - Audio- Emb.Ctrl
					Pair 7-L Active  cmdID= 37443 "
		::= { iqdbd01CmdEntry 37443 }


	iqdbd01EmbCtrlChannelPair7RActive OBJECT-TYPE
		SYNTAX		INTEGER { disable(0), enable(1) }
		MAX-ACCESS		read-write
		STATUS			current
		DESCRIPTION
				"TYPE: - Checkbox
				 PAGE: - Audio- Emb.Ctrl
					Pair 7-R Active  cmdID= 37444 "
		::= { iqdbd01CmdEntry 37444 }


	iqdbd01EmbCtrlChannelPair8LActive OBJECT-TYPE
		SYNTAX		INTEGER { disable(0), enable(1) }
		MAX-ACCESS		read-write
		STATUS			current
		DESCRIPTION
				"TYPE: - Checkbox
				 PAGE: - Audio- Emb.Ctrl
					Pair 8-L Active  cmdID= 37445 "
		::= { iqdbd01CmdEntry 37445 }


	iqdbd01EmbCtrlChannelPair8RActive OBJECT-TYPE
		SYNTAX		INTEGER { disable(0), enable(1) }
		MAX-ACCESS		read-write
		STATUS			current
		DESCRIPTION
				"TYPE: - Checkbox
				 PAGE: - Audio- Emb.Ctrl
					Pair 8-R Active  cmdID= 37446 "
		::= { iqdbd01CmdEntry 37446 }


	iqdbd01AudioEmbCtrlEmbedderPriority OBJECT-TYPE
		SYNTAX		INTEGER {
							val_Normal(0),
							val_Audio_Dolby_E(1)
							}
		MAX-ACCESS		read-write
		STATUS			current
		DESCRIPTION
				"TYPE: - RadiobuttonList
				 PAGE: - Audio- Emb.Ctrl
					Embedder Priority  cmdID= 37460
					Normal  value= 0
					Audio (Dolby-E)  value= 1  "
		::= { iqdbd01CmdEntry 37460 }


	iqdbd01EmbGainEmbedPair1Embed1MuteL OBJECT-TYPE
		SYNTAX		INTEGER { disable(0), enable(1) }
		MAX-ACCESS		read-write
		STATUS			current
		DESCRIPTION
				"TYPE: - Checkbox
				 PAGE: - Audio
					Embed 1 Mute L  cmdID= 37340 "
		::= { iqdbd01CmdEntry 37340 }


	iqdbd01EmbGainEmbedPair1Embed1MuteR OBJECT-TYPE
		SYNTAX		INTEGER { disable(0), enable(1) }
		MAX-ACCESS		read-write
		STATUS			current
		DESCRIPTION
				"TYPE: - Checkbox
				 PAGE: - Audio
					Embed 1 Mute R  cmdID= 37341 "
		::= { iqdbd01CmdEntry 37341 }


	iqdbd01EmbGainEmbedPair1Embed1LGain OBJECT-TYPE
		SYNTAX		INTEGER
		MAX-ACCESS		read-write
		STATUS			current
		DESCRIPTION
				"TYPE: - Number
				 PAGE: - Audio
					Embed 1 L Gain  cmdID= 37320  min= -661  max= 120  step= 1  format= %0.1f dB  div_scale= 10
					Min = -66.1 dB  Max = 12.0 dB  Step = 0.1 dB "
		::= { iqdbd01CmdEntry 37320 }


	iqdbd01EmbGainEmbedPair1Embed1RGain OBJECT-TYPE
		SYNTAX		INTEGER
		MAX-ACCESS		read-write
		STATUS			current
		DESCRIPTION
				"TYPE: - Number
				 PAGE: - Audio
					Embed 1 R Gain  cmdID= 37321  min= -661  max= 120  step= 1  format= %0.1f dB  div_scale= 10
					Min = -66.1 dB  Max = 12.0 dB  Step = 0.1 dB "
		::= { iqdbd01CmdEntry 37321 }


	iqdbd01EmbGainEmbedPair1Stereo OBJECT-TYPE
		SYNTAX		INTEGER { disable(0), enable(1) }
		MAX-ACCESS		read-write
		STATUS			current
		DESCRIPTION
				"TYPE: - Checkbox
				 PAGE: - Audio
					Stereo  cmdID= 37380 "
		::= { iqdbd01CmdEntry 37380 }


	iqdbd01EmbGainEmbedPair1Embed1InvertL OBJECT-TYPE
		SYNTAX		INTEGER { disable(0), enable(1) }
		MAX-ACCESS		read-write
		STATUS			current
		DESCRIPTION
				"TYPE: - Checkbox
				 PAGE: - Audio
					Embed 1 Invert L  cmdID= 37360 "
		::= { iqdbd01CmdEntry 37360 }


	iqdbd01EmbGainEmbedPair1Embed1InvertR OBJECT-TYPE
		SYNTAX		INTEGER { disable(0), enable(1) }
		MAX-ACCESS		read-write
		STATUS			current
		DESCRIPTION
				"TYPE: - Checkbox
				 PAGE: - Audio
					Embed 1 Invert R  cmdID= 37361 "
		::= { iqdbd01CmdEntry 37361 }


	iqdbd01EmbGainEmbedPair1Embed1LClip OBJECT-TYPE
		SYNTAX		RollCallString
		MAX-ACCESS		read-only
		STATUS			current
		DESCRIPTION
				"TYPE: - Display
				 PAGE: - Audio
					Embed 1-L Clip  cmdID= 37540  format=   "
		::= { iqdbd01CmdEntry 37540 }


	iqdbd01EmbGainEmbedPair1Embed1RClip OBJECT-TYPE
		SYNTAX		RollCallString
		MAX-ACCESS		read-only
		STATUS			current
		DESCRIPTION
				"TYPE: - Display
				 PAGE: - Audio
					Embed 1-R Clip  cmdID= 37541  format=   "
		::= { iqdbd01CmdEntry 37541 }


	iqdbd01EmbGainEmbedPair2Embed2MuteL OBJECT-TYPE
		SYNTAX		INTEGER { disable(0), enable(1) }
		MAX-ACCESS		read-write
		STATUS			current
		DESCRIPTION
				"TYPE: - Checkbox
				 PAGE: - Audio
					Embed 2 Mute L  cmdID= 37342 "
		::= { iqdbd01CmdEntry 37342 }


	iqdbd01EmbGainEmbedPair2Embed2MuteR OBJECT-TYPE
		SYNTAX		INTEGER { disable(0), enable(1) }
		MAX-ACCESS		read-write
		STATUS			current
		DESCRIPTION
				"TYPE: - Checkbox
				 PAGE: - Audio
					Embed 2 Mute R  cmdID= 37343 "
		::= { iqdbd01CmdEntry 37343 }


	iqdbd01EmbGainEmbedPair2Embed2LGain OBJECT-TYPE
		SYNTAX		INTEGER
		MAX-ACCESS		read-write
		STATUS			current
		DESCRIPTION
				"TYPE: - Number
				 PAGE: - Audio
					Embed 2 L Gain  cmdID= 37322  min= -661  max= 120  step= 1  format= %0.1f dB  div_scale= 10
					Min = -66.1 dB  Max = 12.0 dB  Step = 0.1 dB "
		::= { iqdbd01CmdEntry 37322 }


	iqdbd01EmbGainEmbedPair2Embed2RGain OBJECT-TYPE
		SYNTAX		INTEGER
		MAX-ACCESS		read-write
		STATUS			current
		DESCRIPTION
				"TYPE: - Number
				 PAGE: - Audio
					Embed 2 R Gain  cmdID= 37323  min= -661  max= 120  step= 1  format= %0.1f dB  div_scale= 10
					Min = -66.1 dB  Max = 12.0 dB  Step = 0.1 dB "
		::= { iqdbd01CmdEntry 37323 }


	iqdbd01EmbGainEmbedPair2Stereo OBJECT-TYPE
		SYNTAX		INTEGER { disable(0), enable(1) }
		MAX-ACCESS		read-write
		STATUS			current
		DESCRIPTION
				"TYPE: - Checkbox
				 PAGE: - Audio
					Stereo  cmdID= 37381 "
		::= { iqdbd01CmdEntry 37381 }


	iqdbd01EmbGainEmbedPair2Embed2InvertL OBJECT-TYPE
		SYNTAX		INTEGER { disable(0), enable(1) }
		MAX-ACCESS		read-write
		STATUS			current
		DESCRIPTION
				"TYPE: - Checkbox
				 PAGE: - Audio
					Embed 2 Invert L  cmdID= 37362 "
		::= { iqdbd01CmdEntry 37362 }


	iqdbd01EmbGainEmbedPair2Embed2InvertR OBJECT-TYPE
		SYNTAX		INTEGER { disable(0), enable(1) }
		MAX-ACCESS		read-write
		STATUS			current
		DESCRIPTION
				"TYPE: - Checkbox
				 PAGE: - Audio
					Embed 2 Invert R  cmdID= 37363 "
		::= { iqdbd01CmdEntry 37363 }


	iqdbd01EmbGainEmbedPair2Embed2LClip OBJECT-TYPE
		SYNTAX		RollCallString
		MAX-ACCESS		read-only
		STATUS			current
		DESCRIPTION
				"TYPE: - Display
				 PAGE: - Audio
					Embed 2-L Clip  cmdID= 37542  format=   "
		::= { iqdbd01CmdEntry 37542 }


	iqdbd01EmbGainEmbedPair2Embed2RClip OBJECT-TYPE
		SYNTAX		RollCallString
		MAX-ACCESS		read-only
		STATUS			current
		DESCRIPTION
				"TYPE: - Display
				 PAGE: - Audio
					Embed 2-R Clip  cmdID= 37543  format=   "
		::= { iqdbd01CmdEntry 37543 }


	iqdbd01EmbGainEmbedPair3Embed3MuteL OBJECT-TYPE
		SYNTAX		INTEGER { disable(0), enable(1) }
		MAX-ACCESS		read-write
		STATUS			current
		DESCRIPTION
				"TYPE: - Checkbox
				 PAGE: - Audio
					Embed 3 Mute L  cmdID= 37344 "
		::= { iqdbd01CmdEntry 37344 }


	iqdbd01EmbGainEmbedPair3Embed3MuteR OBJECT-TYPE
		SYNTAX		INTEGER { disable(0), enable(1) }
		MAX-ACCESS		read-write
		STATUS			current
		DESCRIPTION
				"TYPE: - Checkbox
				 PAGE: - Audio
					Embed 3 Mute R  cmdID= 37345 "
		::= { iqdbd01CmdEntry 37345 }


	iqdbd01EmbGainEmbedPair3Embed3LGain OBJECT-TYPE
		SYNTAX		INTEGER
		MAX-ACCESS		read-write
		STATUS			current
		DESCRIPTION
				"TYPE: - Number
				 PAGE: - Audio
					Embed 3 L Gain  cmdID= 37324  min= -661  max= 120  step= 1  format= %0.1f dB  div_scale= 10
					Min = -66.1 dB  Max = 12.0 dB  Step = 0.1 dB "
		::= { iqdbd01CmdEntry 37324 }


	iqdbd01EmbGainEmbedPair3Embed3RGain OBJECT-TYPE
		SYNTAX		INTEGER
		MAX-ACCESS		read-write
		STATUS			current
		DESCRIPTION
				"TYPE: - Number
				 PAGE: - Audio
					Embed 3 R Gain  cmdID= 37325  min= -661  max= 120  step= 1  format= %0.1f dB  div_scale= 10
					Min = -66.1 dB  Max = 12.0 dB  Step = 0.1 dB "
		::= { iqdbd01CmdEntry 37325 }


	iqdbd01EmbGainEmbedPair3Stereo OBJECT-TYPE
		SYNTAX		INTEGER { disable(0), enable(1) }
		MAX-ACCESS		read-write
		STATUS			current
		DESCRIPTION
				"TYPE: - Checkbox
				 PAGE: - Audio
					Stereo  cmdID= 37382 "
		::= { iqdbd01CmdEntry 37382 }


	iqdbd01EmbGainEmbedPair3Embed3InvertL OBJECT-TYPE
		SYNTAX		INTEGER { disable(0), enable(1) }
		MAX-ACCESS		read-write
		STATUS			current
		DESCRIPTION
				"TYPE: - Checkbox
				 PAGE: - Audio
					Embed 3 Invert L  cmdID= 37364 "
		::= { iqdbd01CmdEntry 37364 }


	iqdbd01EmbGainEmbedPair3Embed3InvertR OBJECT-TYPE
		SYNTAX		INTEGER { disable(0), enable(1) }
		MAX-ACCESS		read-write
		STATUS			current
		DESCRIPTION
				"TYPE: - Checkbox
				 PAGE: - Audio
					Embed 3 Invert R  cmdID= 37365 "
		::= { iqdbd01CmdEntry 37365 }


	iqdbd01EmbGainEmbedPair3Embed3LClip OBJECT-TYPE
		SYNTAX		RollCallString
		MAX-ACCESS		read-only
		STATUS			current
		DESCRIPTION
				"TYPE: - Display
				 PAGE: - Audio
					Embed 3-L Clip  cmdID= 37544  format=   "
		::= { iqdbd01CmdEntry 37544 }


	iqdbd01EmbGainEmbedPair3Embed3RClip OBJECT-TYPE
		SYNTAX		RollCallString
		MAX-ACCESS		read-only
		STATUS			current
		DESCRIPTION
				"TYPE: - Display
				 PAGE: - Audio
					Embed 3-R Clip  cmdID= 37545  format=   "
		::= { iqdbd01CmdEntry 37545 }


	iqdbd01EmbGainEmbedPair4Embed4MuteL OBJECT-TYPE
		SYNTAX		INTEGER { disable(0), enable(1) }
		MAX-ACCESS		read-write
		STATUS			current
		DESCRIPTION
				"TYPE: - Checkbox
				 PAGE: - Audio
					Embed 4 Mute L  cmdID= 37346 "
		::= { iqdbd01CmdEntry 37346 }


	iqdbd01EmbGainEmbedPair4Embed4MuteR OBJECT-TYPE
		SYNTAX		INTEGER { disable(0), enable(1) }
		MAX-ACCESS		read-write
		STATUS			current
		DESCRIPTION
				"TYPE: - Checkbox
				 PAGE: - Audio
					Embed 4 Mute R  cmdID= 37347 "
		::= { iqdbd01CmdEntry 37347 }


	iqdbd01EmbGainEmbedPair4Embed4LGain OBJECT-TYPE
		SYNTAX		INTEGER
		MAX-ACCESS		read-write
		STATUS			current
		DESCRIPTION
				"TYPE: - Number
				 PAGE: - Audio
					Embed 4 L Gain  cmdID= 37326  min= -661  max= 120  step= 1  format= %0.1f dB  div_scale= 10
					Min = -66.1 dB  Max = 12.0 dB  Step = 0.1 dB "
		::= { iqdbd01CmdEntry 37326 }


	iqdbd01EmbGainEmbedPair4Embed4RGain OBJECT-TYPE
		SYNTAX		INTEGER
		MAX-ACCESS		read-write
		STATUS			current
		DESCRIPTION
				"TYPE: - Number
				 PAGE: - Audio
					Embed 4 R Gain  cmdID= 37327  min= -661  max= 120  step= 1  format= %0.1f dB  div_scale= 10
					Min = -66.1 dB  Max = 12.0 dB  Step = 0.1 dB "
		::= { iqdbd01CmdEntry 37327 }


	iqdbd01EmbGainEmbedPair4Stereo OBJECT-TYPE
		SYNTAX		INTEGER { disable(0), enable(1) }
		MAX-ACCESS		read-write
		STATUS			current
		DESCRIPTION
				"TYPE: - Checkbox
				 PAGE: - Audio
					Stereo  cmdID= 37383 "
		::= { iqdbd01CmdEntry 37383 }


	iqdbd01EmbGainEmbedPair4Embed4InvertL OBJECT-TYPE
		SYNTAX		INTEGER { disable(0), enable(1) }
		MAX-ACCESS		read-write
		STATUS			current
		DESCRIPTION
				"TYPE: - Checkbox
				 PAGE: - Audio
					Embed 4 Invert L  cmdID= 37366 "
		::= { iqdbd01CmdEntry 37366 }


	iqdbd01EmbGainEmbedPair4Embed4InvertR OBJECT-TYPE
		SYNTAX		INTEGER { disable(0), enable(1) }
		MAX-ACCESS		read-write
		STATUS			current
		DESCRIPTION
				"TYPE: - Checkbox
				 PAGE: - Audio
					Embed 4 Invert R  cmdID= 37367 "
		::= { iqdbd01CmdEntry 37367 }


	iqdbd01EmbGainEmbedPair4Embed4LClip OBJECT-TYPE
		SYNTAX		RollCallString
		MAX-ACCESS		read-only
		STATUS			current
		DESCRIPTION
				"TYPE: - Display
				 PAGE: - Audio
					Embed 4-L Clip  cmdID= 37546  format=   "
		::= { iqdbd01CmdEntry 37546 }


	iqdbd01EmbGainEmbedPair4Embed4RClip OBJECT-TYPE
		SYNTAX		RollCallString
		MAX-ACCESS		read-only
		STATUS			current
		DESCRIPTION
				"TYPE: - Display
				 PAGE: - Audio
					Embed 4-R Clip  cmdID= 37547  format=   "
		::= { iqdbd01CmdEntry 37547 }


	iqdbd01EmbGainEmbedPair5Embed5MuteL OBJECT-TYPE
		SYNTAX		INTEGER { disable(0), enable(1) }
		MAX-ACCESS		read-write
		STATUS			current
		DESCRIPTION
				"TYPE: - Checkbox
				 PAGE: - Audio
					Embed 5 Mute L  cmdID= 37348 "
		::= { iqdbd01CmdEntry 37348 }


	iqdbd01EmbGainEmbedPair5Embed5MuteR OBJECT-TYPE
		SYNTAX		INTEGER { disable(0), enable(1) }
		MAX-ACCESS		read-write
		STATUS			current
		DESCRIPTION
				"TYPE: - Checkbox
				 PAGE: - Audio
					Embed 5 Mute R  cmdID= 37349 "
		::= { iqdbd01CmdEntry 37349 }


	iqdbd01EmbGainEmbedPair5Embed5LGain OBJECT-TYPE
		SYNTAX		INTEGER
		MAX-ACCESS		read-write
		STATUS			current
		DESCRIPTION
				"TYPE: - Number
				 PAGE: - Audio
					Embed 5 L Gain  cmdID= 37328  min= -661  max= 120  step= 1  format= %0.1f dB  div_scale= 10
					Min = -66.1 dB  Max = 12.0 dB  Step = 0.1 dB "
		::= { iqdbd01CmdEntry 37328 }


	iqdbd01EmbGainEmbedPair5Embed5RGain OBJECT-TYPE
		SYNTAX		INTEGER
		MAX-ACCESS		read-write
		STATUS			current
		DESCRIPTION
				"TYPE: - Number
				 PAGE: - Audio
					Embed 5 R Gain  cmdID= 37329  min= -661  max= 120  step= 1  format= %0.1f dB  div_scale= 10
					Min = -66.1 dB  Max = 12.0 dB  Step = 0.1 dB "
		::= { iqdbd01CmdEntry 37329 }


	iqdbd01EmbGainEmbedPair5Stereo OBJECT-TYPE
		SYNTAX		INTEGER { disable(0), enable(1) }
		MAX-ACCESS		read-write
		STATUS			current
		DESCRIPTION
				"TYPE: - Checkbox
				 PAGE: - Audio
					Stereo  cmdID= 37384 "
		::= { iqdbd01CmdEntry 37384 }


	iqdbd01EmbGainEmbedPair5Embed5InvertL OBJECT-TYPE
		SYNTAX		INTEGER { disable(0), enable(1) }
		MAX-ACCESS		read-write
		STATUS			current
		DESCRIPTION
				"TYPE: - Checkbox
				 PAGE: - Audio
					Embed 5 Invert L  cmdID= 37368 "
		::= { iqdbd01CmdEntry 37368 }


	iqdbd01EmbGainEmbedPair5Embed5InvertR OBJECT-TYPE
		SYNTAX		INTEGER { disable(0), enable(1) }
		MAX-ACCESS		read-write
		STATUS			current
		DESCRIPTION
				"TYPE: - Checkbox
				 PAGE: - Audio
					Embed 5 Invert R  cmdID= 37369 "
		::= { iqdbd01CmdEntry 37369 }


	iqdbd01EmbGainEmbedPair5Embed5LClip OBJECT-TYPE
		SYNTAX		RollCallString
		MAX-ACCESS		read-only
		STATUS			current
		DESCRIPTION
				"TYPE: - Display
				 PAGE: - Audio
					Embed 5-L Clip  cmdID= 37548  format=   "
		::= { iqdbd01CmdEntry 37548 }


	iqdbd01EmbGainEmbedPair5Embed5RClip OBJECT-TYPE
		SYNTAX		RollCallString
		MAX-ACCESS		read-only
		STATUS			current
		DESCRIPTION
				"TYPE: - Display
				 PAGE: - Audio
					Embed 5-R Clip  cmdID= 37549  format=   "
		::= { iqdbd01CmdEntry 37549 }


	iqdbd01EmbGainEmbedPair6Embed6MuteL OBJECT-TYPE
		SYNTAX		INTEGER { disable(0), enable(1) }
		MAX-ACCESS		read-write
		STATUS			current
		DESCRIPTION
				"TYPE: - Checkbox
				 PAGE: - Audio
					Embed 6 Mute L  cmdID= 37350 "
		::= { iqdbd01CmdEntry 37350 }


	iqdbd01EmbGainEmbedPair6Embed6MuteR OBJECT-TYPE
		SYNTAX		INTEGER { disable(0), enable(1) }
		MAX-ACCESS		read-write
		STATUS			current
		DESCRIPTION
				"TYPE: - Checkbox
				 PAGE: - Audio
					Embed 6 Mute R  cmdID= 37351 "
		::= { iqdbd01CmdEntry 37351 }


	iqdbd01EmbGainEmbedPair6Embed6LGain OBJECT-TYPE
		SYNTAX		INTEGER
		MAX-ACCESS		read-write
		STATUS			current
		DESCRIPTION
				"TYPE: - Number
				 PAGE: - Audio
					Embed 6 L Gain  cmdID= 37330  min= -661  max= 120  step= 1  format= %0.1f dB  div_scale= 10
					Min = -66.1 dB  Max = 12.0 dB  Step = 0.1 dB "
		::= { iqdbd01CmdEntry 37330 }


	iqdbd01EmbGainEmbedPair6Embed6RGain OBJECT-TYPE
		SYNTAX		INTEGER
		MAX-ACCESS		read-write
		STATUS			current
		DESCRIPTION
				"TYPE: - Number
				 PAGE: - Audio
					Embed 6 R Gain  cmdID= 37331  min= -661  max= 120  step= 1  format= %0.1f dB  div_scale= 10
					Min = -66.1 dB  Max = 12.0 dB  Step = 0.1 dB "
		::= { iqdbd01CmdEntry 37331 }


	iqdbd01EmbGainEmbedPair6Stereo OBJECT-TYPE
		SYNTAX		INTEGER { disable(0), enable(1) }
		MAX-ACCESS		read-write
		STATUS			current
		DESCRIPTION
				"TYPE: - Checkbox
				 PAGE: - Audio
					Stereo  cmdID= 37385 "
		::= { iqdbd01CmdEntry 37385 }


	iqdbd01EmbGainEmbedPair6Embed6InvertL OBJECT-TYPE
		SYNTAX		INTEGER { disable(0), enable(1) }
		MAX-ACCESS		read-write
		STATUS			current
		DESCRIPTION
				"TYPE: - Checkbox
				 PAGE: - Audio
					Embed 6 Invert L  cmdID= 37370 "
		::= { iqdbd01CmdEntry 37370 }


	iqdbd01EmbGainEmbedPair6Embed6InvertR OBJECT-TYPE
		SYNTAX		INTEGER { disable(0), enable(1) }
		MAX-ACCESS		read-write
		STATUS			current
		DESCRIPTION
				"TYPE: - Checkbox
				 PAGE: - Audio
					Embed 6 Invert R  cmdID= 37371 "
		::= { iqdbd01CmdEntry 37371 }


	iqdbd01EmbGainEmbedPair6Embed6LClip OBJECT-TYPE
		SYNTAX		RollCallString
		MAX-ACCESS		read-only
		STATUS			current
		DESCRIPTION
				"TYPE: - Display
				 PAGE: - Audio
					Embed 6-L Clip  cmdID= 37550  format=   "
		::= { iqdbd01CmdEntry 37550 }


	iqdbd01EmbGainEmbedPair6Embed6RClip OBJECT-TYPE
		SYNTAX		RollCallString
		MAX-ACCESS		read-only
		STATUS			current
		DESCRIPTION
				"TYPE: - Display
				 PAGE: - Audio
					Embed 6-R Clip  cmdID= 37551  format=   "
		::= { iqdbd01CmdEntry 37551 }


	iqdbd01EmbGainEmbedPair7Embed7MuteL OBJECT-TYPE
		SYNTAX		INTEGER { disable(0), enable(1) }
		MAX-ACCESS		read-write
		STATUS			current
		DESCRIPTION
				"TYPE: - Checkbox
				 PAGE: - Audio
					Embed 7 Mute L  cmdID= 37352 "
		::= { iqdbd01CmdEntry 37352 }


	iqdbd01EmbGainEmbedPair7Embed7MuteR OBJECT-TYPE
		SYNTAX		INTEGER { disable(0), enable(1) }
		MAX-ACCESS		read-write
		STATUS			current
		DESCRIPTION
				"TYPE: - Checkbox
				 PAGE: - Audio
					Embed 7 Mute R  cmdID= 37353 "
		::= { iqdbd01CmdEntry 37353 }


	iqdbd01EmbGainEmbedPair7Embed7LGain OBJECT-TYPE
		SYNTAX		INTEGER
		MAX-ACCESS		read-write
		STATUS			current
		DESCRIPTION
				"TYPE: - Number
				 PAGE: - Audio
					Embed 7 L Gain  cmdID= 37332  min= -661  max= 120  step= 1  format= %0.1f dB  div_scale= 10
					Min = -66.1 dB  Max = 12.0 dB  Step = 0.1 dB "
		::= { iqdbd01CmdEntry 37332 }


	iqdbd01EmbGainEmbedPair7Embed7RGain OBJECT-TYPE
		SYNTAX		INTEGER
		MAX-ACCESS		read-write
		STATUS			current
		DESCRIPTION
				"TYPE: - Number
				 PAGE: - Audio
					Embed 7 R Gain  cmdID= 37333  min= -661  max= 120  step= 1  format= %0.1f dB  div_scale= 10
					Min = -66.1 dB  Max = 12.0 dB  Step = 0.1 dB "
		::= { iqdbd01CmdEntry 37333 }


	iqdbd01EmbGainEmbedPair7Stereo OBJECT-TYPE
		SYNTAX		INTEGER { disable(0), enable(1) }
		MAX-ACCESS		read-write
		STATUS			current
		DESCRIPTION
				"TYPE: - Checkbox
				 PAGE: - Audio
					Stereo  cmdID= 37386 "
		::= { iqdbd01CmdEntry 37386 }


	iqdbd01EmbGainEmbedPair7Embed7InvertL OBJECT-TYPE
		SYNTAX		INTEGER { disable(0), enable(1) }
		MAX-ACCESS		read-write
		STATUS			current
		DESCRIPTION
				"TYPE: - Checkbox
				 PAGE: - Audio
					Embed 7 Invert L  cmdID= 37372 "
		::= { iqdbd01CmdEntry 37372 }


	iqdbd01EmbGainEmbedPair7Embed7InvertR OBJECT-TYPE
		SYNTAX		INTEGER { disable(0), enable(1) }
		MAX-ACCESS		read-write
		STATUS			current
		DESCRIPTION
				"TYPE: - Checkbox
				 PAGE: - Audio
					Embed 7 Invert R  cmdID= 37373 "
		::= { iqdbd01CmdEntry 37373 }


	iqdbd01EmbGainEmbedPair7Embed7LClip OBJECT-TYPE
		SYNTAX		RollCallString
		MAX-ACCESS		read-only
		STATUS			current
		DESCRIPTION
				"TYPE: - Display
				 PAGE: - Audio
					Embed 7-L Clip  cmdID= 37552  format=   "
		::= { iqdbd01CmdEntry 37552 }


	iqdbd01EmbGainEmbedPair7Embed7RClip OBJECT-TYPE
		SYNTAX		RollCallString
		MAX-ACCESS		read-only
		STATUS			current
		DESCRIPTION
				"TYPE: - Display
				 PAGE: - Audio
					Embed 7-R Clip  cmdID= 37553  format=   "
		::= { iqdbd01CmdEntry 37553 }


	iqdbd01EmbGainEmbedPair8Embed8MuteL OBJECT-TYPE
		SYNTAX		INTEGER { disable(0), enable(1) }
		MAX-ACCESS		read-write
		STATUS			current
		DESCRIPTION
				"TYPE: - Checkbox
				 PAGE: - Audio
					Embed 8 Mute L  cmdID= 37354 "
		::= { iqdbd01CmdEntry 37354 }


	iqdbd01EmbGainEmbedPair8Embed8MuteR OBJECT-TYPE
		SYNTAX		INTEGER { disable(0), enable(1) }
		MAX-ACCESS		read-write
		STATUS			current
		DESCRIPTION
				"TYPE: - Checkbox
				 PAGE: - Audio
					Embed 8 Mute R  cmdID= 37355 "
		::= { iqdbd01CmdEntry 37355 }


	iqdbd01EmbGainEmbedPair8Embed8LGain OBJECT-TYPE
		SYNTAX		INTEGER
		MAX-ACCESS		read-write
		STATUS			current
		DESCRIPTION
				"TYPE: - Number
				 PAGE: - Audio
					Embed 8 L Gain  cmdID= 37334  min= -661  max= 120  step= 1  format= %0.1f dB  div_scale= 10
					Min = -66.1 dB  Max = 12.0 dB  Step = 0.1 dB "
		::= { iqdbd01CmdEntry 37334 }


	iqdbd01EmbGainEmbedPair8Embed8RGain OBJECT-TYPE
		SYNTAX		INTEGER
		MAX-ACCESS		read-write
		STATUS			current
		DESCRIPTION
				"TYPE: - Number
				 PAGE: - Audio
					Embed 8 R Gain  cmdID= 37335  min= -661  max= 120  step= 1  format= %0.1f dB  div_scale= 10
					Min = -66.1 dB  Max = 12.0 dB  Step = 0.1 dB "
		::= { iqdbd01CmdEntry 37335 }


	iqdbd01EmbGainEmbedPair8Stereo OBJECT-TYPE
		SYNTAX		INTEGER { disable(0), enable(1) }
		MAX-ACCESS		read-write
		STATUS			current
		DESCRIPTION
				"TYPE: - Checkbox
				 PAGE: - Audio
					Stereo  cmdID= 37387 "
		::= { iqdbd01CmdEntry 37387 }


	iqdbd01EmbGainEmbedPair8Embed8InvertL OBJECT-TYPE
		SYNTAX		INTEGER { disable(0), enable(1) }
		MAX-ACCESS		read-write
		STATUS			current
		DESCRIPTION
				"TYPE: - Checkbox
				 PAGE: - Audio
					Embed 8 Invert L  cmdID= 37374 "
		::= { iqdbd01CmdEntry 37374 }


	iqdbd01EmbGainEmbedPair8Embed8InvertR OBJECT-TYPE
		SYNTAX		INTEGER { disable(0), enable(1) }
		MAX-ACCESS		read-write
		STATUS			current
		DESCRIPTION
				"TYPE: - Checkbox
				 PAGE: - Audio
					Embed 8 Invert R  cmdID= 37375 "
		::= { iqdbd01CmdEntry 37375 }


	iqdbd01EmbGainEmbedPair8Embed8LClip OBJECT-TYPE
		SYNTAX		RollCallString
		MAX-ACCESS		read-only
		STATUS			current
		DESCRIPTION
				"TYPE: - Display
				 PAGE: - Audio
					Embed 8-L Clip  cmdID= 37554  format=   "
		::= { iqdbd01CmdEntry 37554 }


	iqdbd01EmbGainEmbedPair8Embed8RClip OBJECT-TYPE
		SYNTAX		RollCallString
		MAX-ACCESS		read-only
		STATUS			current
		DESCRIPTION
				"TYPE: - Display
				 PAGE: - Audio
					Embed 8-R Clip  cmdID= 37555  format=   "
		::= { iqdbd01CmdEntry 37555 }


	iqdbd01EmbOutEmbedPair1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 1
					Left  cmdID= 37300
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37300 }


	iqdbd01EmbOutEmbedPair1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 1
					Right  cmdID= 37301
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37301 }


	iqdbd01EmbOutEmbedPair1LinkLRSelection OBJECT-TYPE
		SYNTAX		INTEGER { disable(0), enable(1) }
		MAX-ACCESS		read-write
		STATUS			current
		DESCRIPTION
				"TYPE: - Checkbox
				 PAGE: - Audio- Embed Pair 1
					Link L+R Selection  cmdID= 37390 "
		::= { iqdbd01CmdEntry 37390 }


	iqdbd01EmbOutEmbedPair2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 2
					Left  cmdID= 37302
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37302 }


	iqdbd01EmbOutEmbedPair2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 2
					Right  cmdID= 37303
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37303 }


	iqdbd01EmbOutEmbedPair2LinkLRSelection OBJECT-TYPE
		SYNTAX		INTEGER { disable(0), enable(1) }
		MAX-ACCESS		read-write
		STATUS			current
		DESCRIPTION
				"TYPE: - Checkbox
				 PAGE: - Audio- Embed Pair 2
					Link L+R Selection  cmdID= 37391 "
		::= { iqdbd01CmdEntry 37391 }


	iqdbd01EmbOutEmbedPair3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 3
					Left  cmdID= 37304
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37304 }


	iqdbd01EmbOutEmbedPair3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 3
					Right  cmdID= 37305
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37305 }


	iqdbd01EmbOutEmbedPair3LinkLRSelection OBJECT-TYPE
		SYNTAX		INTEGER { disable(0), enable(1) }
		MAX-ACCESS		read-write
		STATUS			current
		DESCRIPTION
				"TYPE: - Checkbox
				 PAGE: - Audio- Embed Pair 3
					Link L+R Selection  cmdID= 37392 "
		::= { iqdbd01CmdEntry 37392 }


	iqdbd01EmbOutEmbedPair4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 4
					Left  cmdID= 37306
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37306 }


	iqdbd01EmbOutEmbedPair4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 4
					Right  cmdID= 37307
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37307 }


	iqdbd01EmbOutEmbedPair4LinkLRSelection OBJECT-TYPE
		SYNTAX		INTEGER { disable(0), enable(1) }
		MAX-ACCESS		read-write
		STATUS			current
		DESCRIPTION
				"TYPE: - Checkbox
				 PAGE: - Audio- Embed Pair 4
					Link L+R Selection  cmdID= 37393 "
		::= { iqdbd01CmdEntry 37393 }


	iqdbd01EmbOutEmbedPair5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 5
					Left  cmdID= 37308
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37308 }


	iqdbd01EmbOutEmbedPair5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 5
					Right  cmdID= 37309
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37309 }


	iqdbd01EmbOutEmbedPair5LinkLRSelection OBJECT-TYPE
		SYNTAX		INTEGER { disable(0), enable(1) }
		MAX-ACCESS		read-write
		STATUS			current
		DESCRIPTION
				"TYPE: - Checkbox
				 PAGE: - Audio- Embed Pair 5
					Link L+R Selection  cmdID= 37394 "
		::= { iqdbd01CmdEntry 37394 }


	iqdbd01EmbOutEmbedPair6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 6
					Left  cmdID= 37310
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37310 }


	iqdbd01EmbOutEmbedPair6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 6
					Right  cmdID= 37311
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37311 }


	iqdbd01EmbOutEmbedPair6LinkLRSelection OBJECT-TYPE
		SYNTAX		INTEGER { disable(0), enable(1) }
		MAX-ACCESS		read-write
		STATUS			current
		DESCRIPTION
				"TYPE: - Checkbox
				 PAGE: - Audio- Embed Pair 6
					Link L+R Selection  cmdID= 37395 "
		::= { iqdbd01CmdEntry 37395 }


	iqdbd01EmbOutEmbedPair7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 7
					Left  cmdID= 37312
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37312 }


	iqdbd01EmbOutEmbedPair7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 7
					Right  cmdID= 37313
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37313 }


	iqdbd01EmbOutEmbedPair7LinkLRSelection OBJECT-TYPE
		SYNTAX		INTEGER { disable(0), enable(1) }
		MAX-ACCESS		read-write
		STATUS			current
		DESCRIPTION
				"TYPE: - Checkbox
				 PAGE: - Audio- Embed Pair 7
					Link L+R Selection  cmdID= 37396 "
		::= { iqdbd01CmdEntry 37396 }


	iqdbd01EmbOutEmbedPair8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 8
					Left  cmdID= 37314
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37314 }


	iqdbd01EmbOutEmbedPair8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 8
					Right  cmdID= 37315
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37315 }


	iqdbd01EmbOutEmbedPair8LinkLRSelection OBJECT-TYPE
		SYNTAX		INTEGER { disable(0), enable(1) }
		MAX-ACCESS		read-write
		STATUS			current
		DESCRIPTION
				"TYPE: - Checkbox
				 PAGE: - Audio- Embed Pair 8
					Link L+R Selection  cmdID= 37397 "
		::= { iqdbd01CmdEntry 37397 }


	iqdbd01AudioEmbModeInput1 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 1  cmdID= 37420
					PCM  value= 0
					Data  value= 1
					Mixed  value= 2  "
		::= { iqdbd01CmdEntry 37420 }


	iqdbd01AudioEmbModeInput2 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 2  cmdID= 37421
					PCM  value= 0
					Data  value= 1
					Mixed  value= 2  "
		::= { iqdbd01CmdEntry 37421 }


	iqdbd01AudioEmbModeInput3 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 3  cmdID= 37422
					PCM  value= 0
					Data  value= 1
					Mixed  value= 2  "
		::= { iqdbd01CmdEntry 37422 }


	iqdbd01AudioEmbModeInput4 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 4  cmdID= 37423
					PCM  value= 0
					Data  value= 1
					Mixed  value= 2  "
		::= { iqdbd01CmdEntry 37423 }


	iqdbd01AudioEmbModeInput5 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 5  cmdID= 37424
					PCM  value= 0
					Data  value= 1
					Mixed  value= 2  "
		::= { iqdbd01CmdEntry 37424 }


	iqdbd01AudioEmbModeInput6 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 6  cmdID= 37425
					PCM  value= 0
					Data  value= 1
					Mixed  value= 2  "
		::= { iqdbd01CmdEntry 37425 }


	iqdbd01AudioEmbModeInput7 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 7  cmdID= 37426
					PCM  value= 0
					Data  value= 1
					Mixed  value= 2  "
		::= { iqdbd01CmdEntry 37426 }


	iqdbd01AudioEmbModeInput8 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 8  cmdID= 37427
					PCM  value= 0
					Data  value= 1
					Mixed  value= 2  "
		::= { iqdbd01CmdEntry 37427 }


	iqdbd01EmbNamesDisembederNamesDisembed1 OBJECT-TYPE
		SYNTAX		RollCallString
		MAX-ACCESS		read-write
		STATUS			current
		DESCRIPTION
				"TYPE: - Editstring
				 PAGE: - Audio- Emb.Names
					Disembed 1  cmdID= 37500  "
		::= { iqdbd01CmdEntry 37500 }


	iqdbd01EmbNamesDisembederNamesDisembed1R OBJECT-TYPE
		SYNTAX		RollCallString
		MAX-ACCESS		read-write
		STATUS			current
		DESCRIPTION
				"TYPE: - Editstring
				 PAGE: - Audio- Emb.Names
					Disembed 1-R  cmdID= 37501  "
		::= { iqdbd01CmdEntry 37501 }


	iqdbd01EmbNamesDisembederNamesDisembed2 OBJECT-TYPE
		SYNTAX		RollCallString
		MAX-ACCESS		read-write
		STATUS			current
		DESCRIPTION
				"TYPE: - Editstring
				 PAGE: - Audio- Emb.Names
					Disembed 2  cmdID= 37502  "
		::= { iqdbd01CmdEntry 37502 }


	iqdbd01EmbNamesDisembederNamesDisembed2R OBJECT-TYPE
		SYNTAX		RollCallString
		MAX-ACCESS		read-write
		STATUS			current
		DESCRIPTION
				"TYPE: - Editstring
				 PAGE: - Audio- Emb.Names
					Disembed 2-R  cmdID= 37503  "
		::= { iqdbd01CmdEntry 37503 }


	iqdbd01EmbNamesDisembederNamesDisembed3 OBJECT-TYPE
		SYNTAX		RollCallString
		MAX-ACCESS		read-write
		STATUS			current
		DESCRIPTION
				"TYPE: - Editstring
				 PAGE: - Audio- Emb.Names
					Disembed 3  cmdID= 37504  "
		::= { iqdbd01CmdEntry 37504 }


	iqdbd01EmbNamesDisembederNamesDisembed3R OBJECT-TYPE
		SYNTAX		RollCallString
		MAX-ACCESS		read-write
		STATUS			current
		DESCRIPTION
				"TYPE: - Editstring
				 PAGE: - Audio- Emb.Names
					Disembed 3-R  cmdID= 37505  "
		::= { iqdbd01CmdEntry 37505 }


	iqdbd01EmbNamesDisembederNamesDisembed4 OBJECT-TYPE
		SYNTAX		RollCallString
		MAX-ACCESS		read-write
		STATUS			current
		DESCRIPTION
				"TYPE: - Editstring
				 PAGE: - Audio- Emb.Names
					Disembed 4  cmdID= 37506  "
		::= { iqdbd01CmdEntry 37506 }


	iqdbd01EmbNamesDisembederNamesDisembed4R OBJECT-TYPE
		SYNTAX		RollCallString
		MAX-ACCESS		read-write
		STATUS			current
		DESCRIPTION
				"TYPE: - Editstring
				 PAGE: - Audio- Emb.Names
					Disembed 4-R  cmdID= 37507  "
		::= { iqdbd01CmdEntry 37507 }


	iqdbd01EmbNamesDisembederNamesDisembed5 OBJECT-TYPE
		SYNTAX		RollCallString
		MAX-ACCESS		read-write
		STATUS			current
		DESCRIPTION
				"TYPE: - Editstring
				 PAGE: - Audio- Emb.Names
					Disembed 5  cmdID= 37508  "
		::= { iqdbd01CmdEntry 37508 }


	iqdbd01EmbNamesDisembederNamesDisembed5R OBJECT-TYPE
		SYNTAX		RollCallString
		MAX-ACCESS		read-write
		STATUS			current
		DESCRIPTION
				"TYPE: - Editstring
				 PAGE: - Audio- Emb.Names
					Disembed 5-R  cmdID= 37509  "
		::= { iqdbd01CmdEntry 37509 }


	iqdbd01EmbNamesDisembederNamesDisembed6 OBJECT-TYPE
		SYNTAX		RollCallString
		MAX-ACCESS		read-write
		STATUS			current
		DESCRIPTION
				"TYPE: - Editstring
				 PAGE: - Audio- Emb.Names
					Disembed 6  cmdID= 37510  "
		::= { iqdbd01CmdEntry 37510 }


	iqdbd01EmbNamesDisembederNamesDisembed6R OBJECT-TYPE
		SYNTAX		RollCallString
		MAX-ACCESS		read-write
		STATUS			current
		DESCRIPTION
				"TYPE: - Editstring
				 PAGE: - Audio- Emb.Names
					Disembed 6-R  cmdID= 37511  "
		::= { iqdbd01CmdEntry 37511 }


	iqdbd01EmbNamesDisembederNamesDisembed7 OBJECT-TYPE
		SYNTAX		RollCallString
		MAX-ACCESS		read-write
		STATUS			current
		DESCRIPTION
				"TYPE: - Editstring
				 PAGE: - Audio- Emb.Names
					Disembed 7  cmdID= 37512  "
		::= { iqdbd01CmdEntry 37512 }


	iqdbd01EmbNamesDisembederNamesDisembed7R OBJECT-TYPE
		SYNTAX		RollCallString
		MAX-ACCESS		read-write
		STATUS			current
		DESCRIPTION
				"TYPE: - Editstring
				 PAGE: - Audio- Emb.Names
					Disembed 7-R  cmdID= 37513  "
		::= { iqdbd01CmdEntry 37513 }


	iqdbd01EmbNamesDisembederNamesDisembed8 OBJECT-TYPE
		SYNTAX		RollCallString
		MAX-ACCESS		read-write
		STATUS			current
		DESCRIPTION
				"TYPE: - Editstring
				 PAGE: - Audio- Emb.Names
					Disembed 8  cmdID= 37514  "
		::= { iqdbd01CmdEntry 37514 }


	iqdbd01EmbNamesDisembederNamesDisembed8R OBJECT-TYPE
		SYNTAX		RollCallString
		MAX-ACCESS		read-write
		STATUS			current
		DESCRIPTION
				"TYPE: - Editstring
				 PAGE: - Audio- Emb.Names
					Disembed 8-R  cmdID= 37515  "
		::= { iqdbd01CmdEntry 37515 }


	iqdbd01EmbNamesEmbeddedOPNamesEmbed1 OBJECT-TYPE
		SYNTAX		RollCallString
		MAX-ACCESS		read-write
		STATUS			current
		DESCRIPTION
				"TYPE: - Editstring
				 PAGE: - Audio- Emb.Names
					Embed 1  cmdID= 37520  "
		::= { iqdbd01CmdEntry 37520 }


	iqdbd01EmbNamesEmbeddedOPNamesEmbed1R OBJECT-TYPE
		SYNTAX		RollCallString
		MAX-ACCESS		read-write
		STATUS			current
		DESCRIPTION
				"TYPE: - Editstring
				 PAGE: - Audio- Emb.Names
					Embed 1-R  cmdID= 37521  "
		::= { iqdbd01CmdEntry 37521 }


	iqdbd01EmbNamesEmbeddedOPNamesEmbed2 OBJECT-TYPE
		SYNTAX		RollCallString
		MAX-ACCESS		read-write
		STATUS			current
		DESCRIPTION
				"TYPE: - Editstring
				 PAGE: - Audio- Emb.Names
					Embed 2  cmdID= 37522  "
		::= { iqdbd01CmdEntry 37522 }


	iqdbd01EmbNamesEmbeddedOPNamesEmbed2R OBJECT-TYPE
		SYNTAX		RollCallString
		MAX-ACCESS		read-write
		STATUS			current
		DESCRIPTION
				"TYPE: - Editstring
				 PAGE: - Audio- Emb.Names
					Embed 2-R  cmdID= 37523  "
		::= { iqdbd01CmdEntry 37523 }


	iqdbd01EmbNamesEmbeddedOPNamesEmbed3 OBJECT-TYPE
		SYNTAX		RollCallString
		MAX-ACCESS		read-write
		STATUS			current
		DESCRIPTION
				"TYPE: - Editstring
				 PAGE: - Audio- Emb.Names
					Embed 3  cmdID= 37524  "
		::= { iqdbd01CmdEntry 37524 }


	iqdbd01EmbNamesEmbeddedOPNamesEmbed3R OBJECT-TYPE
		SYNTAX		RollCallString
		MAX-ACCESS		read-write
		STATUS			current
		DESCRIPTION
				"TYPE: - Editstring
				 PAGE: - Audio- Emb.Names
					Embed 3-R  cmdID= 37525  "
		::= { iqdbd01CmdEntry 37525 }


	iqdbd01EmbNamesEmbeddedOPNamesEmbed4 OBJECT-TYPE
		SYNTAX		RollCallString
		MAX-ACCESS		read-write
		STATUS			current
		DESCRIPTION
				"TYPE: - Editstring
				 PAGE: - Audio- Emb.Names
					Embed 4  cmdID= 37526  "
		::= { iqdbd01CmdEntry 37526 }


	iqdbd01EmbNamesEmbeddedOPNamesEmbed4R OBJECT-TYPE
		SYNTAX		RollCallString
		MAX-ACCESS		read-write
		STATUS			current
		DESCRIPTION
				"TYPE: - Editstring
				 PAGE: - Audio- Emb.Names
					Embed 4-R  cmdID= 37527  "
		::= { iqdbd01CmdEntry 37527 }


	iqdbd01EmbNamesEmbeddedOPNamesEmbed5 OBJECT-TYPE
		SYNTAX		RollCallString
		MAX-ACCESS		read-write
		STATUS			current
		DESCRIPTION
				"TYPE: - Editstring
				 PAGE: - Audio- Emb.Names
					Embed 5  cmdID= 37528  "
		::= { iqdbd01CmdEntry 37528 }


	iqdbd01EmbNamesEmbeddedOPNamesEmbed5R OBJECT-TYPE
		SYNTAX		RollCallString
		MAX-ACCESS		read-write
		STATUS			current
		DESCRIPTION
				"TYPE: - Editstring
				 PAGE: - Audio- Emb.Names
					Embed 5-R  cmdID= 37529  "
		::= { iqdbd01CmdEntry 37529 }


	iqdbd01EmbNamesEmbeddedOPNamesEmbed6 OBJECT-TYPE
		SYNTAX		RollCallString
		MAX-ACCESS		read-write
		STATUS			current
		DESCRIPTION
				"TYPE: - Editstring
				 PAGE: - Audio- Emb.Names
					Embed 6  cmdID= 37530  "
		::= { iqdbd01CmdEntry 37530 }


	iqdbd01EmbNamesEmbeddedOPNamesEmbed6R OBJECT-TYPE
		SYNTAX		RollCallString
		MAX-ACCESS		read-write
		STATUS			current
		DESCRIPTION
				"TYPE: - Editstring
				 PAGE: - Audio- Emb.Names
					Embed 6-R  cmdID= 37531  "
		::= { iqdbd01CmdEntry 37531 }


	iqdbd01EmbNamesEmbeddedOPNamesEmbed7 OBJECT-TYPE
		SYNTAX		RollCallString
		MAX-ACCESS		read-write
		STATUS			current
		DESCRIPTION
				"TYPE: - Editstring
				 PAGE: - Audio- Emb.Names
					Embed 7  cmdID= 37532  "
		::= { iqdbd01CmdEntry 37532 }


	iqdbd01EmbNamesEmbeddedOPNamesEmbed7R OBJECT-TYPE
		SYNTAX		RollCallString
		MAX-ACCESS		read-write
		STATUS			current
		DESCRIPTION
				"TYPE: - Editstring
				 PAGE: - Audio- Emb.Names
					Embed 7-R  cmdID= 37533  "
		::= { iqdbd01CmdEntry 37533 }


	iqdbd01EmbNamesEmbeddedOPNamesEmbed8 OBJECT-TYPE
		SYNTAX		RollCallString
		MAX-ACCESS		read-write
		STATUS			current
		DESCRIPTION
				"TYPE: - Editstring
				 PAGE: - Audio- Emb.Names
					Embed 8  cmdID= 37534  "
		::= { iqdbd01CmdEntry 37534 }


	iqdbd01EmbNamesEmbeddedOPNamesEmbed8R OBJECT-TYPE
		SYNTAX		RollCallString
		MAX-ACCESS		read-write
		STATUS			current
		DESCRIPTION
				"TYPE: - Editstring
				 PAGE: - Audio- Emb.Names
					Embed 8-R  cmdID= 37535  "
		::= { iqdbd01CmdEntry 37535 }


	iqdbd01EmbNamesIPNamesStereoDisemb1 OBJECT-TYPE
		SYNTAX		INTEGER { disable(0), enable(1) }
		MAX-ACCESS		read-write
		STATUS			current
		DESCRIPTION
				"TYPE: - Checkbox
				 PAGE: - Audio- Emb.Names
					Disemb 1  cmdID= 37400 "
		::= { iqdbd01CmdEntry 37400 }


	iqdbd01EmbNamesIPNamesStereoDisemb2 OBJECT-TYPE
		SYNTAX		INTEGER { disable(0), enable(1) }
		MAX-ACCESS		read-write
		STATUS			current
		DESCRIPTION
				"TYPE: - Checkbox
				 PAGE: - Audio- Emb.Names
					Disemb 2  cmdID= 37401 "
		::= { iqdbd01CmdEntry 37401 }


	iqdbd01EmbNamesIPNamesStereoDisemb3 OBJECT-TYPE
		SYNTAX		INTEGER { disable(0), enable(1) }
		MAX-ACCESS		read-write
		STATUS			current
		DESCRIPTION
				"TYPE: - Checkbox
				 PAGE: - Audio- Emb.Names
					Disemb 3  cmdID= 37402 "
		::= { iqdbd01CmdEntry 37402 }


	iqdbd01EmbNamesIPNamesStereoDisemb4 OBJECT-TYPE
		SYNTAX		INTEGER { disable(0), enable(1) }
		MAX-ACCESS		read-write
		STATUS			current
		DESCRIPTION
				"TYPE: - Checkbox
				 PAGE: - Audio- Emb.Names
					Disemb 4  cmdID= 37403 "
		::= { iqdbd01CmdEntry 37403 }


	iqdbd01EmbNamesIPNamesStereoDisemb5 OBJECT-TYPE
		SYNTAX		INTEGER { disable(0), enable(1) }
		MAX-ACCESS		read-write
		STATUS			current
		DESCRIPTION
				"TYPE: - Checkbox
				 PAGE: - Audio- Emb.Names
					Disemb 5  cmdID= 37404 "
		::= { iqdbd01CmdEntry 37404 }


	iqdbd01EmbNamesIPNamesStereoDisemb6 OBJECT-TYPE
		SYNTAX		INTEGER { disable(0), enable(1) }
		MAX-ACCESS		read-write
		STATUS			current
		DESCRIPTION
				"TYPE: - Checkbox
				 PAGE: - Audio- Emb.Names
					Disemb 6  cmdID= 37405 "
		::= { iqdbd01CmdEntry 37405 }


	iqdbd01EmbNamesIPNamesStereoDisemb7 OBJECT-TYPE
		SYNTAX		INTEGER { disable(0), enable(1) }
		MAX-ACCESS		read-write
		STATUS			current
		DESCRIPTION
				"TYPE: - Checkbox
				 PAGE: - Audio- Emb.Names
					Disemb 7  cmdID= 37406 "
		::= { iqdbd01CmdEntry 37406 }


	iqdbd01EmbNamesIPNamesStereoDisemb8 OBJECT-TYPE
		SYNTAX		INTEGER { disable(0), enable(1) }
		MAX-ACCESS		read-write
		STATUS			current
		DESCRIPTION
				"TYPE: - Checkbox
				 PAGE: - Audio- Emb.Names
					Disemb 8  cmdID= 37407 "
		::= { iqdbd01CmdEntry 37407 }


	iqdbd01EmbNamesOPNamesStereoEmbed1 OBJECT-TYPE
		SYNTAX		INTEGER { disable(0), enable(1) }
		MAX-ACCESS		read-write
		STATUS			current
		DESCRIPTION
				"TYPE: - Checkbox
				 PAGE: - Audio- Emb.Names
					Embed 1  cmdID= 37410 "
		::= { iqdbd01CmdEntry 37410 }


	iqdbd01EmbNamesOPNamesStereoEmbed2 OBJECT-TYPE
		SYNTAX		INTEGER { disable(0), enable(1) }
		MAX-ACCESS		read-write
		STATUS			current
		DESCRIPTION
				"TYPE: - Checkbox
				 PAGE: - Audio- Emb.Names
					Embed 2  cmdID= 37411 "
		::= { iqdbd01CmdEntry 37411 }


	iqdbd01EmbNamesOPNamesStereoEmbed3 OBJECT-TYPE
		SYNTAX		INTEGER { disable(0), enable(1) }
		MAX-ACCESS		read-write
		STATUS			current
		DESCRIPTION
				"TYPE: - Checkbox
				 PAGE: - Audio- Emb.Names
					Embed 3  cmdID= 37412 "
		::= { iqdbd01CmdEntry 37412 }


	iqdbd01EmbNamesOPNamesStereoEmbed4 OBJECT-TYPE
		SYNTAX		INTEGER { disable(0), enable(1) }
		MAX-ACCESS		read-write
		STATUS			current
		DESCRIPTION
				"TYPE: - Checkbox
				 PAGE: - Audio- Emb.Names
					Embed 4  cmdID= 37413 "
		::= { iqdbd01CmdEntry 37413 }


	iqdbd01EmbNamesOPNamesStereoEmbed5 OBJECT-TYPE
		SYNTAX		INTEGER { disable(0), enable(1) }
		MAX-ACCESS		read-write
		STATUS			current
		DESCRIPTION
				"TYPE: - Checkbox
				 PAGE: - Audio- Emb.Names
					Embed 5  cmdID= 37414 "
		::= { iqdbd01CmdEntry 37414 }


	iqdbd01EmbNamesOPNamesStereoEmbed6 OBJECT-TYPE
		SYNTAX		INTEGER { disable(0), enable(1) }
		MAX-ACCESS		read-write
		STATUS			current
		DESCRIPTION
				"TYPE: - Checkbox
				 PAGE: - Audio- Emb.Names
					Embed 6  cmdID= 37415 "
		::= { iqdbd01CmdEntry 37415 }


	iqdbd01EmbNamesOPNamesStereoEmbed7 OBJECT-TYPE
		SYNTAX		INTEGER { disable(0), enable(1) }
		MAX-ACCESS		read-write
		STATUS			current
		DESCRIPTION
				"TYPE: - Checkbox
				 PAGE: - Audio- Emb.Names
					Embed 7  cmdID= 37416 "
		::= { iqdbd01CmdEntry 37416 }


	iqdbd01EmbNamesOPNamesStereoEmbed8 OBJECT-TYPE
		SYNTAX		INTEGER { disable(0), enable(1) }
		MAX-ACCESS		read-write
		STATUS			current
		DESCRIPTION
				"TYPE: - Checkbox
				 PAGE: - Audio- Emb.Names
					Embed 8  cmdID= 37417 "
		::= { iqdbd01CmdEntry 37417 }


	iqdbd01AudioMixNamesMix1 OBJECT-TYPE
		SYNTAX		RollCallString
		MAX-ACCESS		read-write
		STATUS			current
		DESCRIPTION
				"TYPE: - Editstring
				 PAGE: - Audio
					Mix 1  cmdID= 37810  "
		::= { iqdbd01CmdEntry 37810 }


	iqdbd01AudioMixNamesMix2 OBJECT-TYPE
		SYNTAX		RollCallString
		MAX-ACCESS		read-write
		STATUS			current
		DESCRIPTION
				"TYPE: - Editstring
				 PAGE: - Audio
					Mix 2  cmdID= 37811  "
		::= { iqdbd01CmdEntry 37811 }


	iqdbd01AudioMixNamesMix3 OBJECT-TYPE
		SYNTAX		RollCallString
		MAX-ACCESS		read-write
		STATUS			current
		DESCRIPTION
				"TYPE: - Editstring
				 PAGE: - Audio
					Mix 3  cmdID= 37812  "
		::= { iqdbd01CmdEntry 37812 }


	iqdbd01AudioMixNamesMix4 OBJECT-TYPE
		SYNTAX		RollCallString
		MAX-ACCESS		read-write
		STATUS			current
		DESCRIPTION
				"TYPE: - Editstring
				 PAGE: - Audio
					Mix 4  cmdID= 37813  "
		::= { iqdbd01CmdEntry 37813 }


	iqdbd01Mix1RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 1  cmdID= 37600
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37600 }


	iqdbd01Mix1RoutingInvert1 OBJECT-TYPE
		SYNTAX		INTEGER { disable(0), enable(1) }
		MAX-ACCESS		read-write
		STATUS			current
		DESCRIPTION
				"TYPE: - Checkbox
				 PAGE: - Audio- Mix 1
					Invert 1  cmdID= 37720 "
		::= { iqdbd01CmdEntry 37720 }


	iqdbd01Mix1RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 2  cmdID= 37601
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37601 }


	iqdbd01Mix1RoutingInvert2 OBJECT-TYPE
		SYNTAX		INTEGER { disable(0), enable(1) }
		MAX-ACCESS		read-write
		STATUS			current
		DESCRIPTION
				"TYPE: - Checkbox
				 PAGE: - Audio- Mix 1
					Invert 2  cmdID= 37721 "
		::= { iqdbd01CmdEntry 37721 }


	iqdbd01Mix1RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 3  cmdID= 37602
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37602 }


	iqdbd01Mix1RoutingInvert3 OBJECT-TYPE
		SYNTAX		INTEGER { disable(0), enable(1) }
		MAX-ACCESS		read-write
		STATUS			current
		DESCRIPTION
				"TYPE: - Checkbox
				 PAGE: - Audio- Mix 1
					Invert 3  cmdID= 37722 "
		::= { iqdbd01CmdEntry 37722 }


	iqdbd01Mix1RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 4  cmdID= 37603
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37603 }


	iqdbd01Mix1RoutingInvert4 OBJECT-TYPE
		SYNTAX		INTEGER { disable(0), enable(1) }
		MAX-ACCESS		read-write
		STATUS			current
		DESCRIPTION
				"TYPE: - Checkbox
				 PAGE: - Audio- Mix 1
					Invert 4  cmdID= 37723 "
		::= { iqdbd01CmdEntry 37723 }


	iqdbd01Mix1GainGain1 OBJECT-TYPE
		SYNTAX		INTEGER
		MAX-ACCESS		read-write
		STATUS			current
		DESCRIPTION
				"TYPE: - Number
				 PAGE: - Audio- Mix 1
					Gain 1  cmdID= 37640  min= -360  max= 120  step= 1  format= %0.1f dB  div_scale= 10
					Min = -36.0 dB  Max = 12.0 dB  Step = 0.1 dB "
		::= { iqdbd01CmdEntry 37640 }


	iqdbd01Mix1GainMute1 OBJECT-TYPE
		SYNTAX		INTEGER { disable(0), enable(1) }
		MAX-ACCESS		read-write
		STATUS			current
		DESCRIPTION
				"TYPE: - Checkbox
				 PAGE: - Audio- Mix 1
					Mute 1  cmdID= 37680 "
		::= { iqdbd01CmdEntry 37680 }


	iqdbd01Mix1GainGain2 OBJECT-TYPE
		SYNTAX		INTEGER
		MAX-ACCESS		read-write
		STATUS			current
		DESCRIPTION
				"TYPE: - Number
				 PAGE: - Audio- Mix 1
					Gain 2  cmdID= 37641  min= -360  max= 120  step= 1  format= %0.1f dB  div_scale= 10
					Min = -36.0 dB  Max = 12.0 dB  Step = 0.1 dB "
		::= { iqdbd01CmdEntry 37641 }


	iqdbd01Mix1GainMute2 OBJECT-TYPE
		SYNTAX		INTEGER { disable(0), enable(1) }
		MAX-ACCESS		read-write
		STATUS			current
		DESCRIPTION
				"TYPE: - Checkbox
				 PAGE: - Audio- Mix 1
					Mute 2  cmdID= 37681 "
		::= { iqdbd01CmdEntry 37681 }


	iqdbd01Mix1GainGain3 OBJECT-TYPE
		SYNTAX		INTEGER
		MAX-ACCESS		read-write
		STATUS			current
		DESCRIPTION
				"TYPE: - Number
				 PAGE: - Audio- Mix 1
					Gain 3  cmdID= 37642  min= -360  max= 120  step= 1  format= %0.1f dB  div_scale= 10
					Min = -36.0 dB  Max = 12.0 dB  Step = 0.1 dB "
		::= { iqdbd01CmdEntry 37642 }


	iqdbd01Mix1GainMute3 OBJECT-TYPE
		SYNTAX		INTEGER { disable(0), enable(1) }
		MAX-ACCESS		read-write
		STATUS			current
		DESCRIPTION
				"TYPE: - Checkbox
				 PAGE: - Audio- Mix 1
					Mute 3  cmdID= 37682 "
		::= { iqdbd01CmdEntry 37682 }


	iqdbd01Mix1GainGain4 OBJECT-TYPE
		SYNTAX		INTEGER
		MAX-ACCESS		read-write
		STATUS			current
		DESCRIPTION
				"TYPE: - Number
				 PAGE: - Audio- Mix 1
					Gain 4  cmdID= 37643  min= -360  max= 120  step= 1  format= %0.1f dB  div_scale= 10
					Min = -36.0 dB  Max = 12.0 dB  Step = 0.1 dB "
		::= { iqdbd01CmdEntry 37643 }


	iqdbd01Mix1GainMute4 OBJECT-TYPE
		SYNTAX		INTEGER { disable(0), enable(1) }
		MAX-ACCESS		read-write
		STATUS			current
		DESCRIPTION
				"TYPE: - Checkbox
				 PAGE: - Audio- Mix 1
					Mute 4  cmdID= 37683 "
		::= { iqdbd01CmdEntry 37683 }


	iqdbd01Mix1GainInp1Clip OBJECT-TYPE
		SYNTAX		RollCallString
		MAX-ACCESS		read-only
		STATUS			current
		DESCRIPTION
				"TYPE: - Display
				 PAGE: - Audio- Mix 1
					Inp1 Clip  cmdID= 37760  format=   "
		::= { iqdbd01CmdEntry 37760 }


	iqdbd01Mix1GainInp2Clip OBJECT-TYPE
		SYNTAX		RollCallString
		MAX-ACCESS		read-only
		STATUS			current
		DESCRIPTION
				"TYPE: - Display
				 PAGE: - Audio- Mix 1
					Inp2 Clip  cmdID= 37761  format=   "
		::= { iqdbd01CmdEntry 37761 }


	iqdbd01Mix1GainInp3Clip OBJECT-TYPE
		SYNTAX		RollCallString
		MAX-ACCESS		read-only
		STATUS			current
		DESCRIPTION
				"TYPE: - Display
				 PAGE: - Audio- Mix 1
					Inp3 Clip  cmdID= 37762  format=   "
		::= { iqdbd01CmdEntry 37762 }


	iqdbd01Mix1GainInp4Clip OBJECT-TYPE
		SYNTAX		RollCallString
		MAX-ACCESS		read-only
		STATUS			current
		DESCRIPTION
				"TYPE: - Display
				 PAGE: - Audio- Mix 1
					Inp4 Clip  cmdID= 37763  format=   "
		::= { iqdbd01CmdEntry 37763 }


	iqdbd01Mix1GainOPClip OBJECT-TYPE
		SYNTAX		RollCallString
		MAX-ACCESS		read-only
		STATUS			current
		DESCRIPTION
				"TYPE: - Display
				 PAGE: - Audio- Mix 1
					O/P Clip  cmdID= 37800  format=   "
		::= { iqdbd01CmdEntry 37800 }


	iqdbd01Mix2RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 1  cmdID= 37604
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37604 }


	iqdbd01Mix2RoutingInvert1 OBJECT-TYPE
		SYNTAX		INTEGER { disable(0), enable(1) }
		MAX-ACCESS		read-write
		STATUS			current
		DESCRIPTION
				"TYPE: - Checkbox
				 PAGE: - Audio- Mix 2
					Invert 1  cmdID= 37724 "
		::= { iqdbd01CmdEntry 37724 }


	iqdbd01Mix2RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 2  cmdID= 37605
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37605 }


	iqdbd01Mix2RoutingInvert2 OBJECT-TYPE
		SYNTAX		INTEGER { disable(0), enable(1) }
		MAX-ACCESS		read-write
		STATUS			current
		DESCRIPTION
				"TYPE: - Checkbox
				 PAGE: - Audio- Mix 2
					Invert 2  cmdID= 37725 "
		::= { iqdbd01CmdEntry 37725 }


	iqdbd01Mix2RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 3  cmdID= 37606
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37606 }


	iqdbd01Mix2RoutingInvert3 OBJECT-TYPE
		SYNTAX		INTEGER { disable(0), enable(1) }
		MAX-ACCESS		read-write
		STATUS			current
		DESCRIPTION
				"TYPE: - Checkbox
				 PAGE: - Audio- Mix 2
					Invert 3  cmdID= 37726 "
		::= { iqdbd01CmdEntry 37726 }


	iqdbd01Mix2RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 4  cmdID= 37607
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37607 }


	iqdbd01Mix2RoutingInvert4 OBJECT-TYPE
		SYNTAX		INTEGER { disable(0), enable(1) }
		MAX-ACCESS		read-write
		STATUS			current
		DESCRIPTION
				"TYPE: - Checkbox
				 PAGE: - Audio- Mix 2
					Invert 4  cmdID= 37727 "
		::= { iqdbd01CmdEntry 37727 }


	iqdbd01Mix2GainGain1 OBJECT-TYPE
		SYNTAX		INTEGER
		MAX-ACCESS		read-write
		STATUS			current
		DESCRIPTION
				"TYPE: - Number
				 PAGE: - Audio- Mix 2
					Gain 1  cmdID= 37644  min= -360  max= 120  step= 1  format= %0.1f dB  div_scale= 10
					Min = -36.0 dB  Max = 12.0 dB  Step = 0.1 dB "
		::= { iqdbd01CmdEntry 37644 }


	iqdbd01Mix2GainMute1 OBJECT-TYPE
		SYNTAX		INTEGER { disable(0), enable(1) }
		MAX-ACCESS		read-write
		STATUS			current
		DESCRIPTION
				"TYPE: - Checkbox
				 PAGE: - Audio- Mix 2
					Mute 1  cmdID= 37684 "
		::= { iqdbd01CmdEntry 37684 }


	iqdbd01Mix2GainGain2 OBJECT-TYPE
		SYNTAX		INTEGER
		MAX-ACCESS		read-write
		STATUS			current
		DESCRIPTION
				"TYPE: - Number
				 PAGE: - Audio- Mix 2
					Gain 2  cmdID= 37645  min= -360  max= 120  step= 1  format= %0.1f dB  div_scale= 10
					Min = -36.0 dB  Max = 12.0 dB  Step = 0.1 dB "
		::= { iqdbd01CmdEntry 37645 }


	iqdbd01Mix2GainMute2 OBJECT-TYPE
		SYNTAX		INTEGER { disable(0), enable(1) }
		MAX-ACCESS		read-write
		STATUS			current
		DESCRIPTION
				"TYPE: - Checkbox
				 PAGE: - Audio- Mix 2
					Mute 2  cmdID= 37685 "
		::= { iqdbd01CmdEntry 37685 }


	iqdbd01Mix2GainGain3 OBJECT-TYPE
		SYNTAX		INTEGER
		MAX-ACCESS		read-write
		STATUS			current
		DESCRIPTION
				"TYPE: - Number
				 PAGE: - Audio- Mix 2
					Gain 3  cmdID= 37646  min= -360  max= 120  step= 1  format= %0.1f dB  div_scale= 10
					Min = -36.0 dB  Max = 12.0 dB  Step = 0.1 dB "
		::= { iqdbd01CmdEntry 37646 }


	iqdbd01Mix2GainMute3 OBJECT-TYPE
		SYNTAX		INTEGER { disable(0), enable(1) }
		MAX-ACCESS		read-write
		STATUS			current
		DESCRIPTION
				"TYPE: - Checkbox
				 PAGE: - Audio- Mix 2
					Mute 3  cmdID= 37686 "
		::= { iqdbd01CmdEntry 37686 }


	iqdbd01Mix2GainGain4 OBJECT-TYPE
		SYNTAX		INTEGER
		MAX-ACCESS		read-write
		STATUS			current
		DESCRIPTION
				"TYPE: - Number
				 PAGE: - Audio- Mix 2
					Gain 4  cmdID= 37647  min= -360  max= 120  step= 1  format= %0.1f dB  div_scale= 10
					Min = -36.0 dB  Max = 12.0 dB  Step = 0.1 dB "
		::= { iqdbd01CmdEntry 37647 }


	iqdbd01Mix2GainMute4 OBJECT-TYPE
		SYNTAX		INTEGER { disable(0), enable(1) }
		MAX-ACCESS		read-write
		STATUS			current
		DESCRIPTION
				"TYPE: - Checkbox
				 PAGE: - Audio- Mix 2
					Mute 4  cmdID= 37687 "
		::= { iqdbd01CmdEntry 37687 }


	iqdbd01Mix2GainInp1Clip OBJECT-TYPE
		SYNTAX		RollCallString
		MAX-ACCESS		read-only
		STATUS			current
		DESCRIPTION
				"TYPE: - Display
				 PAGE: - Audio- Mix 2
					Inp1 Clip  cmdID= 37764  format=   "
		::= { iqdbd01CmdEntry 37764 }


	iqdbd01Mix2GainInp2Clip OBJECT-TYPE
		SYNTAX		RollCallString
		MAX-ACCESS		read-only
		STATUS			current
		DESCRIPTION
				"TYPE: - Display
				 PAGE: - Audio- Mix 2
					Inp2 Clip  cmdID= 37765  format=   "
		::= { iqdbd01CmdEntry 37765 }


	iqdbd01Mix2GainInp3Clip OBJECT-TYPE
		SYNTAX		RollCallString
		MAX-ACCESS		read-only
		STATUS			current
		DESCRIPTION
				"TYPE: - Display
				 PAGE: - Audio- Mix 2
					Inp3 Clip  cmdID= 37766  format=   "
		::= { iqdbd01CmdEntry 37766 }


	iqdbd01Mix2GainInp4Clip OBJECT-TYPE
		SYNTAX		RollCallString
		MAX-ACCESS		read-only
		STATUS			current
		DESCRIPTION
				"TYPE: - Display
				 PAGE: - Audio- Mix 2
					Inp4 Clip  cmdID= 37767  format=   "
		::= { iqdbd01CmdEntry 37767 }


	iqdbd01Mix2GainOPClip OBJECT-TYPE
		SYNTAX		RollCallString
		MAX-ACCESS		read-only
		STATUS			current
		DESCRIPTION
				"TYPE: - Display
				 PAGE: - Audio- Mix 2
					O/P Clip  cmdID= 37801  format=   "
		::= { iqdbd01CmdEntry 37801 }


	iqdbd01Mix3RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 1  cmdID= 37608
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37608 }


	iqdbd01Mix3RoutingInvert1 OBJECT-TYPE
		SYNTAX		INTEGER { disable(0), enable(1) }
		MAX-ACCESS		read-write
		STATUS			current
		DESCRIPTION
				"TYPE: - Checkbox
				 PAGE: - Audio- Mix 3
					Invert 1  cmdID= 37728 "
		::= { iqdbd01CmdEntry 37728 }


	iqdbd01Mix3RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 2  cmdID= 37609
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37609 }


	iqdbd01Mix3RoutingInvert2 OBJECT-TYPE
		SYNTAX		INTEGER { disable(0), enable(1) }
		MAX-ACCESS		read-write
		STATUS			current
		DESCRIPTION
				"TYPE: - Checkbox
				 PAGE: - Audio- Mix 3
					Invert 2  cmdID= 37729 "
		::= { iqdbd01CmdEntry 37729 }


	iqdbd01Mix3RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 3  cmdID= 37610
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37610 }


	iqdbd01Mix3RoutingInvert3 OBJECT-TYPE
		SYNTAX		INTEGER { disable(0), enable(1) }
		MAX-ACCESS		read-write
		STATUS			current
		DESCRIPTION
				"TYPE: - Checkbox
				 PAGE: - Audio- Mix 3
					Invert 3  cmdID= 37730 "
		::= { iqdbd01CmdEntry 37730 }


	iqdbd01Mix3RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 4  cmdID= 37611
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37611 }


	iqdbd01Mix3RoutingInvert4 OBJECT-TYPE
		SYNTAX		INTEGER { disable(0), enable(1) }
		MAX-ACCESS		read-write
		STATUS			current
		DESCRIPTION
				"TYPE: - Checkbox
				 PAGE: - Audio- Mix 3
					Invert 4  cmdID= 37731 "
		::= { iqdbd01CmdEntry 37731 }


	iqdbd01Mix3GainGain1 OBJECT-TYPE
		SYNTAX		INTEGER
		MAX-ACCESS		read-write
		STATUS			current
		DESCRIPTION
				"TYPE: - Number
				 PAGE: - Audio- Mix 3
					Gain 1  cmdID= 37648  min= -360  max= 120  step= 1  format= %0.1f dB  div_scale= 10
					Min = -36.0 dB  Max = 12.0 dB  Step = 0.1 dB "
		::= { iqdbd01CmdEntry 37648 }


	iqdbd01Mix3GainMute1 OBJECT-TYPE
		SYNTAX		INTEGER { disable(0), enable(1) }
		MAX-ACCESS		read-write
		STATUS			current
		DESCRIPTION
				"TYPE: - Checkbox
				 PAGE: - Audio- Mix 3
					Mute 1  cmdID= 37688 "
		::= { iqdbd01CmdEntry 37688 }


	iqdbd01Mix3GainGain2 OBJECT-TYPE
		SYNTAX		INTEGER
		MAX-ACCESS		read-write
		STATUS			current
		DESCRIPTION
				"TYPE: - Number
				 PAGE: - Audio- Mix 3
					Gain 2  cmdID= 37649  min= -360  max= 120  step= 1  format= %0.1f dB  div_scale= 10
					Min = -36.0 dB  Max = 12.0 dB  Step = 0.1 dB "
		::= { iqdbd01CmdEntry 37649 }


	iqdbd01Mix3GainMute2 OBJECT-TYPE
		SYNTAX		INTEGER { disable(0), enable(1) }
		MAX-ACCESS		read-write
		STATUS			current
		DESCRIPTION
				"TYPE: - Checkbox
				 PAGE: - Audio- Mix 3
					Mute 2  cmdID= 37689 "
		::= { iqdbd01CmdEntry 37689 }


	iqdbd01Mix3GainGain3 OBJECT-TYPE
		SYNTAX		INTEGER
		MAX-ACCESS		read-write
		STATUS			current
		DESCRIPTION
				"TYPE: - Number
				 PAGE: - Audio- Mix 3
					Gain 3  cmdID= 37650  min= -360  max= 120  step= 1  format= %0.1f dB  div_scale= 10
					Min = -36.0 dB  Max = 12.0 dB  Step = 0.1 dB "
		::= { iqdbd01CmdEntry 37650 }


	iqdbd01Mix3GainMute3 OBJECT-TYPE
		SYNTAX		INTEGER { disable(0), enable(1) }
		MAX-ACCESS		read-write
		STATUS			current
		DESCRIPTION
				"TYPE: - Checkbox
				 PAGE: - Audio- Mix 3
					Mute 3  cmdID= 37690 "
		::= { iqdbd01CmdEntry 37690 }


	iqdbd01Mix3GainGain4 OBJECT-TYPE
		SYNTAX		INTEGER
		MAX-ACCESS		read-write
		STATUS			current
		DESCRIPTION
				"TYPE: - Number
				 PAGE: - Audio- Mix 3
					Gain 4  cmdID= 37651  min= -360  max= 120  step= 1  format= %0.1f dB  div_scale= 10
					Min = -36.0 dB  Max = 12.0 dB  Step = 0.1 dB "
		::= { iqdbd01CmdEntry 37651 }


	iqdbd01Mix3GainMute4 OBJECT-TYPE
		SYNTAX		INTEGER { disable(0), enable(1) }
		MAX-ACCESS		read-write
		STATUS			current
		DESCRIPTION
				"TYPE: - Checkbox
				 PAGE: - Audio- Mix 3
					Mute 4  cmdID= 37691 "
		::= { iqdbd01CmdEntry 37691 }


	iqdbd01Mix3GainInp1Clip OBJECT-TYPE
		SYNTAX		RollCallString
		MAX-ACCESS		read-only
		STATUS			current
		DESCRIPTION
				"TYPE: - Display
				 PAGE: - Audio- Mix 3
					Inp1 Clip  cmdID= 37768  format=   "
		::= { iqdbd01CmdEntry 37768 }


	iqdbd01Mix3GainInp2Clip OBJECT-TYPE
		SYNTAX		RollCallString
		MAX-ACCESS		read-only
		STATUS			current
		DESCRIPTION
				"TYPE: - Display
				 PAGE: - Audio- Mix 3
					Inp2 Clip  cmdID= 37769  format=   "
		::= { iqdbd01CmdEntry 37769 }


	iqdbd01Mix3GainInp3Clip OBJECT-TYPE
		SYNTAX		RollCallString
		MAX-ACCESS		read-only
		STATUS			current
		DESCRIPTION
				"TYPE: - Display
				 PAGE: - Audio- Mix 3
					Inp3 Clip  cmdID= 37770  format=   "
		::= { iqdbd01CmdEntry 37770 }


	iqdbd01Mix3GainInp4Clip OBJECT-TYPE
		SYNTAX		RollCallString
		MAX-ACCESS		read-only
		STATUS			current
		DESCRIPTION
				"TYPE: - Display
				 PAGE: - Audio- Mix 3
					Inp4 Clip  cmdID= 37771  format=   "
		::= { iqdbd01CmdEntry 37771 }


	iqdbd01Mix3GainOPClip OBJECT-TYPE
		SYNTAX		RollCallString
		MAX-ACCESS		read-only
		STATUS			current
		DESCRIPTION
				"TYPE: - Display
				 PAGE: - Audio- Mix 3
					O/P Clip  cmdID= 37802  format=   "
		::= { iqdbd01CmdEntry 37802 }


	iqdbd01Mix4RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 1  cmdID= 37612
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37612 }


	iqdbd01Mix4RoutingInvert1 OBJECT-TYPE
		SYNTAX		INTEGER { disable(0), enable(1) }
		MAX-ACCESS		read-write
		STATUS			current
		DESCRIPTION
				"TYPE: - Checkbox
				 PAGE: - Audio- Mix 4
					Invert 1  cmdID= 37732 "
		::= { iqdbd01CmdEntry 37732 }


	iqdbd01Mix4RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 2  cmdID= 37613
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37613 }


	iqdbd01Mix4RoutingInvert2 OBJECT-TYPE
		SYNTAX		INTEGER { disable(0), enable(1) }
		MAX-ACCESS		read-write
		STATUS			current
		DESCRIPTION
				"TYPE: - Checkbox
				 PAGE: - Audio- Mix 4
					Invert 2  cmdID= 37733 "
		::= { iqdbd01CmdEntry 37733 }


	iqdbd01Mix4RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 3  cmdID= 37614
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37614 }


	iqdbd01Mix4RoutingInvert3 OBJECT-TYPE
		SYNTAX		INTEGER { disable(0), enable(1) }
		MAX-ACCESS		read-write
		STATUS			current
		DESCRIPTION
				"TYPE: - Checkbox
				 PAGE: - Audio- Mix 4
					Invert 3  cmdID= 37734 "
		::= { iqdbd01CmdEntry 37734 }


	iqdbd01Mix4RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 4  cmdID= 37615
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 37615 }


	iqdbd01Mix4RoutingInvert4 OBJECT-TYPE
		SYNTAX		INTEGER { disable(0), enable(1) }
		MAX-ACCESS		read-write
		STATUS			current
		DESCRIPTION
				"TYPE: - Checkbox
				 PAGE: - Audio- Mix 4
					Invert 4  cmdID= 37735 "
		::= { iqdbd01CmdEntry 37735 }


	iqdbd01Mix4GainGain1 OBJECT-TYPE
		SYNTAX		INTEGER
		MAX-ACCESS		read-write
		STATUS			current
		DESCRIPTION
				"TYPE: - Number
				 PAGE: - Audio- Mix 4
					Gain 1  cmdID= 37652  min= -360  max= 120  step= 1  format= %0.1f dB  div_scale= 10
					Min = -36.0 dB  Max = 12.0 dB  Step = 0.1 dB "
		::= { iqdbd01CmdEntry 37652 }


	iqdbd01Mix4GainMute1 OBJECT-TYPE
		SYNTAX		INTEGER { disable(0), enable(1) }
		MAX-ACCESS		read-write
		STATUS			current
		DESCRIPTION
				"TYPE: - Checkbox
				 PAGE: - Audio- Mix 4
					Mute 1  cmdID= 37692 "
		::= { iqdbd01CmdEntry 37692 }


	iqdbd01Mix4GainGain2 OBJECT-TYPE
		SYNTAX		INTEGER
		MAX-ACCESS		read-write
		STATUS			current
		DESCRIPTION
				"TYPE: - Number
				 PAGE: - Audio- Mix 4
					Gain 2  cmdID= 37653  min= -360  max= 120  step= 1  format= %0.1f dB  div_scale= 10
					Min = -36.0 dB  Max = 12.0 dB  Step = 0.1 dB "
		::= { iqdbd01CmdEntry 37653 }


	iqdbd01Mix4GainMute2 OBJECT-TYPE
		SYNTAX		INTEGER { disable(0), enable(1) }
		MAX-ACCESS		read-write
		STATUS			current
		DESCRIPTION
				"TYPE: - Checkbox
				 PAGE: - Audio- Mix 4
					Mute 2  cmdID= 37693 "
		::= { iqdbd01CmdEntry 37693 }


	iqdbd01Mix4GainGain3 OBJECT-TYPE
		SYNTAX		INTEGER
		MAX-ACCESS		read-write
		STATUS			current
		DESCRIPTION
				"TYPE: - Number
				 PAGE: - Audio- Mix 4
					Gain 3  cmdID= 37654  min= -360  max= 120  step= 1  format= %0.1f dB  div_scale= 10
					Min = -36.0 dB  Max = 12.0 dB  Step = 0.1 dB "
		::= { iqdbd01CmdEntry 37654 }


	iqdbd01Mix4GainMute3 OBJECT-TYPE
		SYNTAX		INTEGER { disable(0), enable(1) }
		MAX-ACCESS		read-write
		STATUS			current
		DESCRIPTION
				"TYPE: - Checkbox
				 PAGE: - Audio- Mix 4
					Mute 3  cmdID= 37694 "
		::= { iqdbd01CmdEntry 37694 }


	iqdbd01Mix4GainGain4 OBJECT-TYPE
		SYNTAX		INTEGER
		MAX-ACCESS		read-write
		STATUS			current
		DESCRIPTION
				"TYPE: - Number
				 PAGE: - Audio- Mix 4
					Gain 4  cmdID= 37655  min= -360  max= 120  step= 1  format= %0.1f dB  div_scale= 10
					Min = -36.0 dB  Max = 12.0 dB  Step = 0.1 dB "
		::= { iqdbd01CmdEntry 37655 }


	iqdbd01Mix4GainMute4 OBJECT-TYPE
		SYNTAX		INTEGER { disable(0), enable(1) }
		MAX-ACCESS		read-write
		STATUS			current
		DESCRIPTION
				"TYPE: - Checkbox
				 PAGE: - Audio- Mix 4
					Mute 4  cmdID= 37695 "
		::= { iqdbd01CmdEntry 37695 }


	iqdbd01Mix4GainInp1Clip OBJECT-TYPE
		SYNTAX		RollCallString
		MAX-ACCESS		read-only
		STATUS			current
		DESCRIPTION
				"TYPE: - Display
				 PAGE: - Audio- Mix 4
					Inp1 Clip  cmdID= 37772  format=   "
		::= { iqdbd01CmdEntry 37772 }


	iqdbd01Mix4GainInp2Clip OBJECT-TYPE
		SYNTAX		RollCallString
		MAX-ACCESS		read-only
		STATUS			current
		DESCRIPTION
				"TYPE: - Display
				 PAGE: - Audio- Mix 4
					Inp2 Clip  cmdID= 37773  format=   "
		::= { iqdbd01CmdEntry 37773 }


	iqdbd01Mix4GainInp3Clip OBJECT-TYPE
		SYNTAX		RollCallString
		MAX-ACCESS		read-only
		STATUS			current
		DESCRIPTION
				"TYPE: - Display
				 PAGE: - Audio- Mix 4
					Inp3 Clip  cmdID= 37774  format=   "
		::= { iqdbd01CmdEntry 37774 }


	iqdbd01Mix4GainInp4Clip OBJECT-TYPE
		SYNTAX		RollCallString
		MAX-ACCESS		read-only
		STATUS			current
		DESCRIPTION
				"TYPE: - Display
				 PAGE: - Audio- Mix 4
					Inp4 Clip  cmdID= 37775  format=   "
		::= { iqdbd01CmdEntry 37775 }


	iqdbd01Mix4GainOPClip OBJECT-TYPE
		SYNTAX		RollCallString
		MAX-ACCESS		read-only
		STATUS			current
		DESCRIPTION
				"TYPE: - Display
				 PAGE: - Audio- Mix 4
					O/P Clip  cmdID= 37803  format=   "
		::= { iqdbd01CmdEntry 37803 }


	iqdbd01AESGainAESOut1AESOut1MuteL OBJECT-TYPE
		SYNTAX		INTEGER { disable(0), enable(1) }
		MAX-ACCESS		read-write
		STATUS			current
		DESCRIPTION
				"TYPE: - Checkbox
				 PAGE: - Audio- AES Ports- AES Gain
					AES Out 1 Mute L  cmdID= 38280 "
		::= { iqdbd01CmdEntry 38280 }


	iqdbd01AESGainAESOut1AESOut1MuteR OBJECT-TYPE
		SYNTAX		INTEGER { disable(0), enable(1) }
		MAX-ACCESS		read-write
		STATUS			current
		DESCRIPTION
				"TYPE: - Checkbox
				 PAGE: - Audio- AES Ports- AES Gain
					AES Out 1 Mute R  cmdID= 38281 "
		::= { iqdbd01CmdEntry 38281 }


	iqdbd01AESGainAESOut1AESOut1LGain OBJECT-TYPE
		SYNTAX		INTEGER
		MAX-ACCESS		read-write
		STATUS			current
		DESCRIPTION
				"TYPE: - Number
				 PAGE: - Audio- AES Ports- AES Gain
					AES Out 1 L Gain  cmdID= 38240  min= -661  max= 120  step= 1  format= %0.1f dB  div_scale= 10
					Min = -66.1 dB  Max = 12.0 dB  Step = 0.1 dB "
		::= { iqdbd01CmdEntry 38240 }


	iqdbd01AESGainAESOut1AESOut1RGain OBJECT-TYPE
		SYNTAX		INTEGER
		MAX-ACCESS		read-write
		STATUS			current
		DESCRIPTION
				"TYPE: - Number
				 PAGE: - Audio- AES Ports- AES Gain
					AES Out 1 R Gain  cmdID= 38241  min= -661  max= 120  step= 1  format= %0.1f dB  div_scale= 10
					Min = -66.1 dB  Max = 12.0 dB  Step = 0.1 dB "
		::= { iqdbd01CmdEntry 38241 }


	iqdbd01AESGainAESOut1Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38360 "
		::= { iqdbd01CmdEntry 38360 }


	iqdbd01AESGainAESOut1AESOut1InvertL OBJECT-TYPE
		SYNTAX		INTEGER { disable(0), enable(1) }
		MAX-ACCESS		read-write
		STATUS			current
		DESCRIPTION
				"TYPE: - Checkbox
				 PAGE: - Audio- AES Ports- AES Gain
					AES Out 1 Invert L  cmdID= 38320 "
		::= { iqdbd01CmdEntry 38320 }


	iqdbd01AESGainAESOut1AESOut1InvertR OBJECT-TYPE
		SYNTAX		INTEGER { disable(0), enable(1) }
		MAX-ACCESS		read-write
		STATUS			current
		DESCRIPTION
				"TYPE: - Checkbox
				 PAGE: - Audio- AES Ports- AES Gain
					AES Out 1 Invert R  cmdID= 38321 "
		::= { iqdbd01CmdEntry 38321 }


	iqdbd01AESGainAESOut1AESOut1LClip OBJECT-TYPE
		SYNTAX		RollCallString
		MAX-ACCESS		read-only
		STATUS			current
		DESCRIPTION
				"TYPE: - Display
				 PAGE: - Audio- AES Ports- AES Gain
					AES Out 1-L Clip  cmdID= 38520  format=   "
		::= { iqdbd01CmdEntry 38520 }


	iqdbd01AESGainAESOut1AESOut1RClip OBJECT-TYPE
		SYNTAX		RollCallString
		MAX-ACCESS		read-only
		STATUS			current
		DESCRIPTION
				"TYPE: - Display
				 PAGE: - Audio- AES Ports- AES Gain
					AES Out 1-R Clip  cmdID= 38521  format=   "
		::= { iqdbd01CmdEntry 38521 }


	iqdbd01AESGainAESOut2AESOut2MuteL OBJECT-TYPE
		SYNTAX		INTEGER { disable(0), enable(1) }
		MAX-ACCESS		read-write
		STATUS			current
		DESCRIPTION
				"TYPE: - Checkbox
				 PAGE: - Audio- AES Ports- AES Gain
					AES Out 2 Mute L  cmdID= 38282 "
		::= { iqdbd01CmdEntry 38282 }


	iqdbd01AESGainAESOut2AESOut2MuteR OBJECT-TYPE
		SYNTAX		INTEGER { disable(0), enable(1) }
		MAX-ACCESS		read-write
		STATUS			current
		DESCRIPTION
				"TYPE: - Checkbox
				 PAGE: - Audio- AES Ports- AES Gain
					AES Out 2 Mute R  cmdID= 38283 "
		::= { iqdbd01CmdEntry 38283 }


	iqdbd01AESGainAESOut2AESOut2LGain OBJECT-TYPE
		SYNTAX		INTEGER
		MAX-ACCESS		read-write
		STATUS			current
		DESCRIPTION
				"TYPE: - Number
				 PAGE: - Audio- AES Ports- AES Gain
					AES Out 2 L Gain  cmdID= 38242  min= -661  max= 120  step= 1  format= %0.1f dB  div_scale= 10
					Min = -66.1 dB  Max = 12.0 dB  Step = 0.1 dB "
		::= { iqdbd01CmdEntry 38242 }


	iqdbd01AESGainAESOut2AESOut2RGain OBJECT-TYPE
		SYNTAX		INTEGER
		MAX-ACCESS		read-write
		STATUS			current
		DESCRIPTION
				"TYPE: - Number
				 PAGE: - Audio- AES Ports- AES Gain
					AES Out 2 R Gain  cmdID= 38243  min= -661  max= 120  step= 1  format= %0.1f dB  div_scale= 10
					Min = -66.1 dB  Max = 12.0 dB  Step = 0.1 dB "
		::= { iqdbd01CmdEntry 38243 }


	iqdbd01AESGainAESOut2Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38361 "
		::= { iqdbd01CmdEntry 38361 }


	iqdbd01AESGainAESOut2AESOut2InvertL OBJECT-TYPE
		SYNTAX		INTEGER { disable(0), enable(1) }
		MAX-ACCESS		read-write
		STATUS			current
		DESCRIPTION
				"TYPE: - Checkbox
				 PAGE: - Audio- AES Ports- AES Gain
					AES Out 2 Invert L  cmdID= 38322 "
		::= { iqdbd01CmdEntry 38322 }


	iqdbd01AESGainAESOut2AESOut2InvertR OBJECT-TYPE
		SYNTAX		INTEGER { disable(0), enable(1) }
		MAX-ACCESS		read-write
		STATUS			current
		DESCRIPTION
				"TYPE: - Checkbox
				 PAGE: - Audio- AES Ports- AES Gain
					AES Out 2 Invert R  cmdID= 38323 "
		::= { iqdbd01CmdEntry 38323 }


	iqdbd01AESGainAESOut2AESOut2LClip OBJECT-TYPE
		SYNTAX		RollCallString
		MAX-ACCESS		read-only
		STATUS			current
		DESCRIPTION
				"TYPE: - Display
				 PAGE: - Audio- AES Ports- AES Gain
					AES Out 2-L Clip  cmdID= 38522  format=   "
		::= { iqdbd01CmdEntry 38522 }


	iqdbd01AESGainAESOut2AESOut2RClip OBJECT-TYPE
		SYNTAX		RollCallString
		MAX-ACCESS		read-only
		STATUS			current
		DESCRIPTION
				"TYPE: - Display
				 PAGE: - Audio- AES Ports- AES Gain
					AES Out 2-R Clip  cmdID= 38523  format=   "
		::= { iqdbd01CmdEntry 38523 }


	iqdbd01AESGainAESOut3AESOut3MuteL OBJECT-TYPE
		SYNTAX		INTEGER { disable(0), enable(1) }
		MAX-ACCESS		read-write
		STATUS			current
		DESCRIPTION
				"TYPE: - Checkbox
				 PAGE: - Audio- AES Ports- AES Gain
					AES Out 3 Mute L  cmdID= 38284 "
		::= { iqdbd01CmdEntry 38284 }


	iqdbd01AESGainAESOut3AESOut3MuteR OBJECT-TYPE
		SYNTAX		INTEGER { disable(0), enable(1) }
		MAX-ACCESS		read-write
		STATUS			current
		DESCRIPTION
				"TYPE: - Checkbox
				 PAGE: - Audio- AES Ports- AES Gain
					AES Out 3 Mute R  cmdID= 38285 "
		::= { iqdbd01CmdEntry 38285 }


	iqdbd01AESGainAESOut3AESOut3LGain OBJECT-TYPE
		SYNTAX		INTEGER
		MAX-ACCESS		read-write
		STATUS			current
		DESCRIPTION
				"TYPE: - Number
				 PAGE: - Audio- AES Ports- AES Gain
					AES Out 3 L Gain  cmdID= 38244  min= -661  max= 120  step= 1  format= %0.1f dB  div_scale= 10
					Min = -66.1 dB  Max = 12.0 dB  Step = 0.1 dB "
		::= { iqdbd01CmdEntry 38244 }


	iqdbd01AESGainAESOut3AESOut3RGain OBJECT-TYPE
		SYNTAX		INTEGER
		MAX-ACCESS		read-write
		STATUS			current
		DESCRIPTION
				"TYPE: - Number
				 PAGE: - Audio- AES Ports- AES Gain
					AES Out 3 R Gain  cmdID= 38245  min= -661  max= 120  step= 1  format= %0.1f dB  div_scale= 10
					Min = -66.1 dB  Max = 12.0 dB  Step = 0.1 dB "
		::= { iqdbd01CmdEntry 38245 }


	iqdbd01AESGainAESOut3Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38362 "
		::= { iqdbd01CmdEntry 38362 }


	iqdbd01AESGainAESOut3AESOut3InvertL OBJECT-TYPE
		SYNTAX		INTEGER { disable(0), enable(1) }
		MAX-ACCESS		read-write
		STATUS			current
		DESCRIPTION
				"TYPE: - Checkbox
				 PAGE: - Audio- AES Ports- AES Gain
					AES Out 3 Invert L  cmdID= 38324 "
		::= { iqdbd01CmdEntry 38324 }


	iqdbd01AESGainAESOut3AESOut3InvertR OBJECT-TYPE
		SYNTAX		INTEGER { disable(0), enable(1) }
		MAX-ACCESS		read-write
		STATUS			current
		DESCRIPTION
				"TYPE: - Checkbox
				 PAGE: - Audio- AES Ports- AES Gain
					AES Out 3 Invert R  cmdID= 38325 "
		::= { iqdbd01CmdEntry 38325 }


	iqdbd01AESGainAESOut3AESOut3LClip OBJECT-TYPE
		SYNTAX		RollCallString
		MAX-ACCESS		read-only
		STATUS			current
		DESCRIPTION
				"TYPE: - Display
				 PAGE: - Audio- AES Ports- AES Gain
					AES Out 3-L Clip  cmdID= 38524  format=   "
		::= { iqdbd01CmdEntry 38524 }


	iqdbd01AESGainAESOut3AESOut3RClip OBJECT-TYPE
		SYNTAX		RollCallString
		MAX-ACCESS		read-only
		STATUS			current
		DESCRIPTION
				"TYPE: - Display
				 PAGE: - Audio- AES Ports- AES Gain
					AES Out 3-R Clip  cmdID= 38525  format=   "
		::= { iqdbd01CmdEntry 38525 }


	iqdbd01AESGainAESOut4AESOut4MuteL OBJECT-TYPE
		SYNTAX		INTEGER { disable(0), enable(1) }
		MAX-ACCESS		read-write
		STATUS			current
		DESCRIPTION
				"TYPE: - Checkbox
				 PAGE: - Audio- AES Ports- AES Gain
					AES Out 4 Mute L  cmdID= 38286 "
		::= { iqdbd01CmdEntry 38286 }


	iqdbd01AESGainAESOut4AESOut4MuteR OBJECT-TYPE
		SYNTAX		INTEGER { disable(0), enable(1) }
		MAX-ACCESS		read-write
		STATUS			current
		DESCRIPTION
				"TYPE: - Checkbox
				 PAGE: - Audio- AES Ports- AES Gain
					AES Out 4 Mute R  cmdID= 38287 "
		::= { iqdbd01CmdEntry 38287 }


	iqdbd01AESGainAESOut4AESOut4LGain OBJECT-TYPE
		SYNTAX		INTEGER
		MAX-ACCESS		read-write
		STATUS			current
		DESCRIPTION
				"TYPE: - Number
				 PAGE: - Audio- AES Ports- AES Gain
					AES Out 4 L Gain  cmdID= 38246  min= -661  max= 120  step= 1  format= %0.1f dB  div_scale= 10
					Min = -66.1 dB  Max = 12.0 dB  Step = 0.1 dB "
		::= { iqdbd01CmdEntry 38246 }


	iqdbd01AESGainAESOut4AESOut4RGain OBJECT-TYPE
		SYNTAX		INTEGER
		MAX-ACCESS		read-write
		STATUS			current
		DESCRIPTION
				"TYPE: - Number
				 PAGE: - Audio- AES Ports- AES Gain
					AES Out 4 R Gain  cmdID= 38247  min= -661  max= 120  step= 1  format= %0.1f dB  div_scale= 10
					Min = -66.1 dB  Max = 12.0 dB  Step = 0.1 dB "
		::= { iqdbd01CmdEntry 38247 }


	iqdbd01AESGainAESOut4Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38363 "
		::= { iqdbd01CmdEntry 38363 }


	iqdbd01AESGainAESOut4AESOut4InvertL OBJECT-TYPE
		SYNTAX		INTEGER { disable(0), enable(1) }
		MAX-ACCESS		read-write
		STATUS			current
		DESCRIPTION
				"TYPE: - Checkbox
				 PAGE: - Audio- AES Ports- AES Gain
					AES Out 4 Invert L  cmdID= 38326 "
		::= { iqdbd01CmdEntry 38326 }


	iqdbd01AESGainAESOut4AESOut4InvertR OBJECT-TYPE
		SYNTAX		INTEGER { disable(0), enable(1) }
		MAX-ACCESS		read-write
		STATUS			current
		DESCRIPTION
				"TYPE: - Checkbox
				 PAGE: - Audio- AES Ports- AES Gain
					AES Out 4 Invert R  cmdID= 38327 "
		::= { iqdbd01CmdEntry 38327 }


	iqdbd01AESGainAESOut4AESOut4LClip OBJECT-TYPE
		SYNTAX		RollCallString
		MAX-ACCESS		read-only
		STATUS			current
		DESCRIPTION
				"TYPE: - Display
				 PAGE: - Audio- AES Ports- AES Gain
					AES Out 4-L Clip  cmdID= 38526  format=   "
		::= { iqdbd01CmdEntry 38526 }


	iqdbd01AESGainAESOut4AESOut4RClip OBJECT-TYPE
		SYNTAX		RollCallString
		MAX-ACCESS		read-only
		STATUS			current
		DESCRIPTION
				"TYPE: - Display
				 PAGE: - Audio- AES Ports- AES Gain
					AES Out 4-R Clip  cmdID= 38527  format=   "
		::= { iqdbd01CmdEntry 38527 }


	iqdbd01AESGainAESOut5AESOut5MuteL OBJECT-TYPE
		SYNTAX		INTEGER { disable(0), enable(1) }
		MAX-ACCESS		read-write
		STATUS			current
		DESCRIPTION
				"TYPE: - Checkbox
				 PAGE: - Audio- AES Ports- AES Gain
					AES Out 5 Mute L  cmdID= 38288 "
		::= { iqdbd01CmdEntry 38288 }


	iqdbd01AESGainAESOut5AESOut5MuteR OBJECT-TYPE
		SYNTAX		INTEGER { disable(0), enable(1) }
		MAX-ACCESS		read-write
		STATUS			current
		DESCRIPTION
				"TYPE: - Checkbox
				 PAGE: - Audio- AES Ports- AES Gain
					AES Out 5 Mute R  cmdID= 38289 "
		::= { iqdbd01CmdEntry 38289 }


	iqdbd01AESGainAESOut5AESOut5LGain OBJECT-TYPE
		SYNTAX		INTEGER
		MAX-ACCESS		read-write
		STATUS			current
		DESCRIPTION
				"TYPE: - Number
				 PAGE: - Audio- AES Ports- AES Gain
					AES Out 5 L Gain  cmdID= 38248  min= -661  max= 120  step= 1  format= %0.1f dB  div_scale= 10
					Min = -66.1 dB  Max = 12.0 dB  Step = 0.1 dB "
		::= { iqdbd01CmdEntry 38248 }


	iqdbd01AESGainAESOut5AESOut5RGain OBJECT-TYPE
		SYNTAX		INTEGER
		MAX-ACCESS		read-write
		STATUS			current
		DESCRIPTION
				"TYPE: - Number
				 PAGE: - Audio- AES Ports- AES Gain
					AES Out 5 R Gain  cmdID= 38249  min= -661  max= 120  step= 1  format= %0.1f dB  div_scale= 10
					Min = -66.1 dB  Max = 12.0 dB  Step = 0.1 dB "
		::= { iqdbd01CmdEntry 38249 }


	iqdbd01AESGainAESOut5Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38364 "
		::= { iqdbd01CmdEntry 38364 }


	iqdbd01AESGainAESOut5AESOut5InvertL OBJECT-TYPE
		SYNTAX		INTEGER { disable(0), enable(1) }
		MAX-ACCESS		read-write
		STATUS			current
		DESCRIPTION
				"TYPE: - Checkbox
				 PAGE: - Audio- AES Ports- AES Gain
					AES Out 5 Invert L  cmdID= 38328 "
		::= { iqdbd01CmdEntry 38328 }


	iqdbd01AESGainAESOut5AESOut5InvertR OBJECT-TYPE
		SYNTAX		INTEGER { disable(0), enable(1) }
		MAX-ACCESS		read-write
		STATUS			current
		DESCRIPTION
				"TYPE: - Checkbox
				 PAGE: - Audio- AES Ports- AES Gain
					AES Out 5 Invert R  cmdID= 38329 "
		::= { iqdbd01CmdEntry 38329 }


	iqdbd01AESGainAESOut5AESOut5LClip OBJECT-TYPE
		SYNTAX		RollCallString
		MAX-ACCESS		read-only
		STATUS			current
		DESCRIPTION
				"TYPE: - Display
				 PAGE: - Audio- AES Ports- AES Gain
					AES Out 5-L Clip  cmdID= 38528  format=   "
		::= { iqdbd01CmdEntry 38528 }


	iqdbd01AESGainAESOut5AESOut5RClip OBJECT-TYPE
		SYNTAX		RollCallString
		MAX-ACCESS		read-only
		STATUS			current
		DESCRIPTION
				"TYPE: - Display
				 PAGE: - Audio- AES Ports- AES Gain
					AES Out 5-R Clip  cmdID= 38529  format=   "
		::= { iqdbd01CmdEntry 38529 }


	iqdbd01AESGainAESOut6AESOut6MuteL OBJECT-TYPE
		SYNTAX		INTEGER { disable(0), enable(1) }
		MAX-ACCESS		read-write
		STATUS			current
		DESCRIPTION
				"TYPE: - Checkbox
				 PAGE: - Audio- AES Ports- AES Gain
					AES Out 6 Mute L  cmdID= 38290 "
		::= { iqdbd01CmdEntry 38290 }


	iqdbd01AESGainAESOut6AESOut6MuteR OBJECT-TYPE
		SYNTAX		INTEGER { disable(0), enable(1) }
		MAX-ACCESS		read-write
		STATUS			current
		DESCRIPTION
				"TYPE: - Checkbox
				 PAGE: - Audio- AES Ports- AES Gain
					AES Out 6 Mute R  cmdID= 38291 "
		::= { iqdbd01CmdEntry 38291 }


	iqdbd01AESGainAESOut6AESOut6LGain OBJECT-TYPE
		SYNTAX		INTEGER
		MAX-ACCESS		read-write
		STATUS			current
		DESCRIPTION
				"TYPE: - Number
				 PAGE: - Audio- AES Ports- AES Gain
					AES Out 6 L Gain  cmdID= 38250  min= -661  max= 120  step= 1  format= %0.1f dB  div_scale= 10
					Min = -66.1 dB  Max = 12.0 dB  Step = 0.1 dB "
		::= { iqdbd01CmdEntry 38250 }


	iqdbd01AESGainAESOut6AESOut6RGain OBJECT-TYPE
		SYNTAX		INTEGER
		MAX-ACCESS		read-write
		STATUS			current
		DESCRIPTION
				"TYPE: - Number
				 PAGE: - Audio- AES Ports- AES Gain
					AES Out 6 R Gain  cmdID= 38251  min= -661  max= 120  step= 1  format= %0.1f dB  div_scale= 10
					Min = -66.1 dB  Max = 12.0 dB  Step = 0.1 dB "
		::= { iqdbd01CmdEntry 38251 }


	iqdbd01AESGainAESOut6Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38365 "
		::= { iqdbd01CmdEntry 38365 }


	iqdbd01AESGainAESOut6AESOut6InvertL OBJECT-TYPE
		SYNTAX		INTEGER { disable(0), enable(1) }
		MAX-ACCESS		read-write
		STATUS			current
		DESCRIPTION
				"TYPE: - Checkbox
				 PAGE: - Audio- AES Ports- AES Gain
					AES Out 6 Invert L  cmdID= 38330 "
		::= { iqdbd01CmdEntry 38330 }


	iqdbd01AESGainAESOut6AESOut6InvertR OBJECT-TYPE
		SYNTAX		INTEGER { disable(0), enable(1) }
		MAX-ACCESS		read-write
		STATUS			current
		DESCRIPTION
				"TYPE: - Checkbox
				 PAGE: - Audio- AES Ports- AES Gain
					AES Out 6 Invert R  cmdID= 38331 "
		::= { iqdbd01CmdEntry 38331 }


	iqdbd01AESGainAESOut6AESOut6LClip OBJECT-TYPE
		SYNTAX		RollCallString
		MAX-ACCESS		read-only
		STATUS			current
		DESCRIPTION
				"TYPE: - Display
				 PAGE: - Audio- AES Ports- AES Gain
					AES Out 6-L Clip  cmdID= 38530  format=   "
		::= { iqdbd01CmdEntry 38530 }


	iqdbd01AESGainAESOut6AESOut6RClip OBJECT-TYPE
		SYNTAX		RollCallString
		MAX-ACCESS		read-only
		STATUS			current
		DESCRIPTION
				"TYPE: - Display
				 PAGE: - Audio- AES Ports- AES Gain
					AES Out 6-R Clip  cmdID= 38531  format=   "
		::= { iqdbd01CmdEntry 38531 }


	iqdbd01AESGainAESOut7AESOut7MuteL OBJECT-TYPE
		SYNTAX		INTEGER { disable(0), enable(1) }
		MAX-ACCESS		read-write
		STATUS			current
		DESCRIPTION
				"TYPE: - Checkbox
				 PAGE: - Audio- AES Ports- AES Gain
					AES Out 7 Mute L  cmdID= 38292 "
		::= { iqdbd01CmdEntry 38292 }


	iqdbd01AESGainAESOut7AESOut7MuteR OBJECT-TYPE
		SYNTAX		INTEGER { disable(0), enable(1) }
		MAX-ACCESS		read-write
		STATUS			current
		DESCRIPTION
				"TYPE: - Checkbox
				 PAGE: - Audio- AES Ports- AES Gain
					AES Out 7 Mute R  cmdID= 38293 "
		::= { iqdbd01CmdEntry 38293 }


	iqdbd01AESGainAESOut7AESOut7LGain OBJECT-TYPE
		SYNTAX		INTEGER
		MAX-ACCESS		read-write
		STATUS			current
		DESCRIPTION
				"TYPE: - Number
				 PAGE: - Audio- AES Ports- AES Gain
					AES Out 7 L Gain  cmdID= 38252  min= -661  max= 120  step= 1  format= %0.1f dB  div_scale= 10
					Min = -66.1 dB  Max = 12.0 dB  Step = 0.1 dB "
		::= { iqdbd01CmdEntry 38252 }


	iqdbd01AESGainAESOut7AESOut7RGain OBJECT-TYPE
		SYNTAX		INTEGER
		MAX-ACCESS		read-write
		STATUS			current
		DESCRIPTION
				"TYPE: - Number
				 PAGE: - Audio- AES Ports- AES Gain
					AES Out 7 R Gain  cmdID= 38253  min= -661  max= 120  step= 1  format= %0.1f dB  div_scale= 10
					Min = -66.1 dB  Max = 12.0 dB  Step = 0.1 dB "
		::= { iqdbd01CmdEntry 38253 }


	iqdbd01AESGainAESOut7Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38366 "
		::= { iqdbd01CmdEntry 38366 }


	iqdbd01AESGainAESOut7AESOut7InvertL OBJECT-TYPE
		SYNTAX		INTEGER { disable(0), enable(1) }
		MAX-ACCESS		read-write
		STATUS			current
		DESCRIPTION
				"TYPE: - Checkbox
				 PAGE: - Audio- AES Ports- AES Gain
					AES Out 7 Invert L  cmdID= 38332 "
		::= { iqdbd01CmdEntry 38332 }


	iqdbd01AESGainAESOut7AESOut7InvertR OBJECT-TYPE
		SYNTAX		INTEGER { disable(0), enable(1) }
		MAX-ACCESS		read-write
		STATUS			current
		DESCRIPTION
				"TYPE: - Checkbox
				 PAGE: - Audio- AES Ports- AES Gain
					AES Out 7 Invert R  cmdID= 38333 "
		::= { iqdbd01CmdEntry 38333 }


	iqdbd01AESGainAESOut7AESOut7LClip OBJECT-TYPE
		SYNTAX		RollCallString
		MAX-ACCESS		read-only
		STATUS			current
		DESCRIPTION
				"TYPE: - Display
				 PAGE: - Audio- AES Ports- AES Gain
					AES Out 7-L Clip  cmdID= 38532  format=   "
		::= { iqdbd01CmdEntry 38532 }


	iqdbd01AESGainAESOut7AESOut7RClip OBJECT-TYPE
		SYNTAX		RollCallString
		MAX-ACCESS		read-only
		STATUS			current
		DESCRIPTION
				"TYPE: - Display
				 PAGE: - Audio- AES Ports- AES Gain
					AES Out 7-R Clip  cmdID= 38533  format=   "
		::= { iqdbd01CmdEntry 38533 }


	iqdbd01AESGainAESOut8AESOut8MuteL OBJECT-TYPE
		SYNTAX		INTEGER { disable(0), enable(1) }
		MAX-ACCESS		read-write
		STATUS			current
		DESCRIPTION
				"TYPE: - Checkbox
				 PAGE: - Audio- AES Ports- AES Gain
					AES Out 8 Mute L  cmdID= 38294 "
		::= { iqdbd01CmdEntry 38294 }


	iqdbd01AESGainAESOut8AESOut8MuteR OBJECT-TYPE
		SYNTAX		INTEGER { disable(0), enable(1) }
		MAX-ACCESS		read-write
		STATUS			current
		DESCRIPTION
				"TYPE: - Checkbox
				 PAGE: - Audio- AES Ports- AES Gain
					AES Out 8 Mute R  cmdID= 38295 "
		::= { iqdbd01CmdEntry 38295 }


	iqdbd01AESGainAESOut8AESOut8LGain OBJECT-TYPE
		SYNTAX		INTEGER
		MAX-ACCESS		read-write
		STATUS			current
		DESCRIPTION
				"TYPE: - Number
				 PAGE: - Audio- AES Ports- AES Gain
					AES Out 8 L Gain  cmdID= 38254  min= -661  max= 120  step= 1  format= %0.1f dB  div_scale= 10
					Min = -66.1 dB  Max = 12.0 dB  Step = 0.1 dB "
		::= { iqdbd01CmdEntry 38254 }


	iqdbd01AESGainAESOut8AESOut8RGain OBJECT-TYPE
		SYNTAX		INTEGER
		MAX-ACCESS		read-write
		STATUS			current
		DESCRIPTION
				"TYPE: - Number
				 PAGE: - Audio- AES Ports- AES Gain
					AES Out 8 R Gain  cmdID= 38255  min= -661  max= 120  step= 1  format= %0.1f dB  div_scale= 10
					Min = -66.1 dB  Max = 12.0 dB  Step = 0.1 dB "
		::= { iqdbd01CmdEntry 38255 }


	iqdbd01AESGainAESOut8Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38367 "
		::= { iqdbd01CmdEntry 38367 }


	iqdbd01AESGainAESOut8AESOut8InvertL OBJECT-TYPE
		SYNTAX		INTEGER { disable(0), enable(1) }
		MAX-ACCESS		read-write
		STATUS			current
		DESCRIPTION
				"TYPE: - Checkbox
				 PAGE: - Audio- AES Ports- AES Gain
					AES Out 8 Invert L  cmdID= 38334 "
		::= { iqdbd01CmdEntry 38334 }


	iqdbd01AESGainAESOut8AESOut8InvertR OBJECT-TYPE
		SYNTAX		INTEGER { disable(0), enable(1) }
		MAX-ACCESS		read-write
		STATUS			current
		DESCRIPTION
				"TYPE: - Checkbox
				 PAGE: - Audio- AES Ports- AES Gain
					AES Out 8 Invert R  cmdID= 38335 "
		::= { iqdbd01CmdEntry 38335 }


	iqdbd01AESGainAESOut8AESOut8LClip OBJECT-TYPE
		SYNTAX		RollCallString
		MAX-ACCESS		read-only
		STATUS			current
		DESCRIPTION
				"TYPE: - Display
				 PAGE: - Audio- AES Ports- AES Gain
					AES Out 8-L Clip  cmdID= 38534  format=   "
		::= { iqdbd01CmdEntry 38534 }


	iqdbd01AESGainAESOut8AESOut8RClip OBJECT-TYPE
		SYNTAX		RollCallString
		MAX-ACCESS		read-only
		STATUS			current
		DESCRIPTION
				"TYPE: - Display
				 PAGE: - Audio- AES Ports- AES Gain
					AES Out 8-R Clip  cmdID= 38535  format=   "
		::= { iqdbd01CmdEntry 38535 }


	iqdbd01AESOutAESOut1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 1
					Left  cmdID= 38200
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38200 }


	iqdbd01AESOutAESOut1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 1
					Right  cmdID= 38201
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38201 }


	iqdbd01AESOutAESOut1LinkLRSelection OBJECT-TYPE
		SYNTAX		INTEGER { disable(0), enable(1) }
		MAX-ACCESS		read-write
		STATUS			current
		DESCRIPTION
				"TYPE: - Checkbox
				 PAGE: - Audio- AES Ports- AES Out 1
					Link L+R Selection  cmdID= 38380 "
		::= { iqdbd01CmdEntry 38380 }


	iqdbd01AESOutAESOut3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 3
					Left  cmdID= 38204
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38204 }


	iqdbd01AESOutAESOut3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 3
					Right  cmdID= 38205
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38205 }


	iqdbd01AESOutAESOut3LinkLRSelection OBJECT-TYPE
		SYNTAX		INTEGER { disable(0), enable(1) }
		MAX-ACCESS		read-write
		STATUS			current
		DESCRIPTION
				"TYPE: - Checkbox
				 PAGE: - Audio- AES Ports- AES Out 3
					Link L+R Selection  cmdID= 38382 "
		::= { iqdbd01CmdEntry 38382 }


	iqdbd01AESOutAESOut4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 4
					Left  cmdID= 38206
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38206 }


	iqdbd01AESOutAESOut4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 4
					Right  cmdID= 38207
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38207 }


	iqdbd01AESOutAESOut4LinkLRSelection OBJECT-TYPE
		SYNTAX		INTEGER { disable(0), enable(1) }
		MAX-ACCESS		read-write
		STATUS			current
		DESCRIPTION
				"TYPE: - Checkbox
				 PAGE: - Audio- AES Ports- AES Out 4
					Link L+R Selection  cmdID= 38383 "
		::= { iqdbd01CmdEntry 38383 }


	iqdbd01AESOutAESOut5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 5
					Left  cmdID= 38208
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38208 }


	iqdbd01AESOutAESOut5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 5
					Right  cmdID= 38209
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38209 }


	iqdbd01AESOutAESOut5LinkLRSelection OBJECT-TYPE
		SYNTAX		INTEGER { disable(0), enable(1) }
		MAX-ACCESS		read-write
		STATUS			current
		DESCRIPTION
				"TYPE: - Checkbox
				 PAGE: - Audio- AES Ports- AES Out 5
					Link L+R Selection  cmdID= 38384 "
		::= { iqdbd01CmdEntry 38384 }


	iqdbd01AESOutAESOut6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 6
					Left  cmdID= 38210
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38210 }


	iqdbd01AESOutAESOut6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 6
					Right  cmdID= 38211
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38211 }


	iqdbd01AESOutAESOut6LinkLRSelection OBJECT-TYPE
		SYNTAX		INTEGER { disable(0), enable(1) }
		MAX-ACCESS		read-write
		STATUS			current
		DESCRIPTION
				"TYPE: - Checkbox
				 PAGE: - Audio- AES Ports- AES Out 6
					Link L+R Selection  cmdID= 38385 "
		::= { iqdbd01CmdEntry 38385 }


	iqdbd01AESOutAESOut7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 7
					Left  cmdID= 38212
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38212 }


	iqdbd01AESOutAESOut7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 7
					Right  cmdID= 38213
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38213 }


	iqdbd01AESOutAESOut7LinkLRSelection OBJECT-TYPE
		SYNTAX		INTEGER { disable(0), enable(1) }
		MAX-ACCESS		read-write
		STATUS			current
		DESCRIPTION
				"TYPE: - Checkbox
				 PAGE: - Audio- AES Ports- AES Out 7
					Link L+R Selection  cmdID= 38386 "
		::= { iqdbd01CmdEntry 38386 }


	iqdbd01AESOutAESOut8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 8
					Left  cmdID= 38214
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38214 }


	iqdbd01AESOutAESOut8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 8
					Right  cmdID= 38215
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38215 }


	iqdbd01AESOutAESOut8LinkLRSelection OBJECT-TYPE
		SYNTAX		INTEGER { disable(0), enable(1) }
		MAX-ACCESS		read-write
		STATUS			current
		DESCRIPTION
				"TYPE: - Checkbox
				 PAGE: - Audio- AES Ports- AES Out 8
					Link L+R Selection  cmdID= 38387 "
		::= { iqdbd01CmdEntry 38387 }


	iqdbd01AESOutMonitoropLeft OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_Dolby_Aux_Ch_L(43),
							val_Dolby_Aux_Ch_R(44),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- Monitor o/p
					Left  cmdID= 38641
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					Dolby Aux Ch L  value= 43
					Dolby Aux Ch R  value= 44
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38641 }


	iqdbd01AESOutMonitoropRight OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_Dolby_Aux_Ch_L(43),
							val_Dolby_Aux_Ch_R(44),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- Monitor o/p
					Right  cmdID= 38642
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					Dolby Aux Ch L  value= 43
					Dolby Aux Ch R  value= 44
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38642 }


	iqdbd01AESOutMonitoropLinkLRSelection OBJECT-TYPE
		SYNTAX		INTEGER { disable(0), enable(1) }
		MAX-ACCESS		read-write
		STATUS			current
		DESCRIPTION
				"TYPE: - Checkbox
				 PAGE: - Audio- AES Ports- Monitor o/p
					Link L+R Selection  cmdID= 38640 "
		::= { iqdbd01CmdEntry 38640 }


	iqdbd01AESOutAESPortNamesAESPort1Stereo OBJECT-TYPE
		SYNTAX		INTEGER { disable(0), enable(1) }
		MAX-ACCESS		read-write
		STATUS			current
		DESCRIPTION
				"TYPE: - Checkbox
				 PAGE: - Audio- AES Ports- AES Port Names
					AES Port 1 Stereo  cmdID= 38448 "
		::= { iqdbd01CmdEntry 38448 }


	iqdbd01AESOutAESPortNamesAESPort1L OBJECT-TYPE
		SYNTAX		RollCallString
		MAX-ACCESS		read-write
		STATUS			current
		DESCRIPTION
				"TYPE: - Editstring
				 PAGE: - Audio- AES Ports- AES Port Names
					AES Port 1-L  cmdID= 38496  "
		::= { iqdbd01CmdEntry 38496 }


	iqdbd01AESOutAESPortNamesAESPort1R OBJECT-TYPE
		SYNTAX		RollCallString
		MAX-ACCESS		read-write
		STATUS			current
		DESCRIPTION
				"TYPE: - Editstring
				 PAGE: - Audio- AES Ports- AES Port Names
					AES Port 1-R  cmdID= 38497  "
		::= { iqdbd01CmdEntry 38497 }


	iqdbd01AESOutAESPortNamesAESPort2Stereo OBJECT-TYPE
		SYNTAX		INTEGER { disable(0), enable(1) }
		MAX-ACCESS		read-write
		STATUS			current
		DESCRIPTION
				"TYPE: - Checkbox
				 PAGE: - Audio- AES Ports- AES Port Names
					AES Port 2 Stereo  cmdID= 38449 "
		::= { iqdbd01CmdEntry 38449 }


	iqdbd01AESOutAESPortNamesAESPort2L OBJECT-TYPE
		SYNTAX		RollCallString
		MAX-ACCESS		read-write
		STATUS			current
		DESCRIPTION
				"TYPE: - Editstring
				 PAGE: - Audio- AES Ports- AES Port Names
					AES Port 2-L  cmdID= 38498  "
		::= { iqdbd01CmdEntry 38498 }


	iqdbd01AESOutAESPortNamesAESPort2R OBJECT-TYPE
		SYNTAX		RollCallString
		MAX-ACCESS		read-write
		STATUS			current
		DESCRIPTION
				"TYPE: - Editstring
				 PAGE: - Audio- AES Ports- AES Port Names
					AES Port 2-R  cmdID= 38499  "
		::= { iqdbd01CmdEntry 38499 }


	iqdbd01AESOutAESPortNamesAESPort3Stereo OBJECT-TYPE
		SYNTAX		INTEGER { disable(0), enable(1) }
		MAX-ACCESS		read-write
		STATUS			current
		DESCRIPTION
				"TYPE: - Checkbox
				 PAGE: - Audio- AES Ports- AES Port Names
					AES Port 3 Stereo  cmdID= 38450 "
		::= { iqdbd01CmdEntry 38450 }


	iqdbd01AESOutAESPortNamesAESPort3L OBJECT-TYPE
		SYNTAX		RollCallString
		MAX-ACCESS		read-write
		STATUS			current
		DESCRIPTION
				"TYPE: - Editstring
				 PAGE: - Audio- AES Ports- AES Port Names
					AES Port 3-L  cmdID= 38500  "
		::= { iqdbd01CmdEntry 38500 }


	iqdbd01AESOutAESPortNamesAESPort3R OBJECT-TYPE
		SYNTAX		RollCallString
		MAX-ACCESS		read-write
		STATUS			current
		DESCRIPTION
				"TYPE: - Editstring
				 PAGE: - Audio- AES Ports- AES Port Names
					AES Port 3-R  cmdID= 38501  "
		::= { iqdbd01CmdEntry 38501 }


	iqdbd01AESOutAESPortNamesAESPort4Stereo OBJECT-TYPE
		SYNTAX		INTEGER { disable(0), enable(1) }
		MAX-ACCESS		read-write
		STATUS			current
		DESCRIPTION
				"TYPE: - Checkbox
				 PAGE: - Audio- AES Ports- AES Port Names
					AES Port 4 Stereo  cmdID= 38451 "
		::= { iqdbd01CmdEntry 38451 }


	iqdbd01AESOutAESPortNamesAESPort4L OBJECT-TYPE
		SYNTAX		RollCallString
		MAX-ACCESS		read-write
		STATUS			current
		DESCRIPTION
				"TYPE: - Editstring
				 PAGE: - Audio- AES Ports- AES Port Names
					AES Port 4-L  cmdID= 38502  "
		::= { iqdbd01CmdEntry 38502 }


	iqdbd01AESOutAESPortNamesAESPort4R OBJECT-TYPE
		SYNTAX		RollCallString
		MAX-ACCESS		read-write
		STATUS			current
		DESCRIPTION
				"TYPE: - Editstring
				 PAGE: - Audio- AES Ports- AES Port Names
					AES Port 4-R  cmdID= 38503  "
		::= { iqdbd01CmdEntry 38503 }


	iqdbd01AESOutAESPortNamesAESPort5Stereo OBJECT-TYPE
		SYNTAX		INTEGER { disable(0), enable(1) }
		MAX-ACCESS		read-write
		STATUS			current
		DESCRIPTION
				"TYPE: - Checkbox
				 PAGE: - Audio- AES Ports- AES Port Names
					AES Port 5 Stereo  cmdID= 38452 "
		::= { iqdbd01CmdEntry 38452 }


	iqdbd01AESOutAESPortNamesAESPort5L OBJECT-TYPE
		SYNTAX		RollCallString
		MAX-ACCESS		read-write
		STATUS			current
		DESCRIPTION
				"TYPE: - Editstring
				 PAGE: - Audio- AES Ports- AES Port Names
					AES Port 5-L  cmdID= 38504  "
		::= { iqdbd01CmdEntry 38504 }


	iqdbd01AESOutAESPortNamesAESPort5R OBJECT-TYPE
		SYNTAX		RollCallString
		MAX-ACCESS		read-write
		STATUS			current
		DESCRIPTION
				"TYPE: - Editstring
				 PAGE: - Audio- AES Ports- AES Port Names
					AES Port 5-R  cmdID= 38505  "
		::= { iqdbd01CmdEntry 38505 }


	iqdbd01AESOutAESPortNamesAESPort6Stereo OBJECT-TYPE
		SYNTAX		INTEGER { disable(0), enable(1) }
		MAX-ACCESS		read-write
		STATUS			current
		DESCRIPTION
				"TYPE: - Checkbox
				 PAGE: - Audio- AES Ports- AES Port Names
					AES Port 6 Stereo  cmdID= 38453 "
		::= { iqdbd01CmdEntry 38453 }


	iqdbd01AESOutAESPortNamesAESPort6L OBJECT-TYPE
		SYNTAX		RollCallString
		MAX-ACCESS		read-write
		STATUS			current
		DESCRIPTION
				"TYPE: - Editstring
				 PAGE: - Audio- AES Ports- AES Port Names
					AES Port 6-L  cmdID= 38506  "
		::= { iqdbd01CmdEntry 38506 }


	iqdbd01AESOutAESPortNamesAESPort6R OBJECT-TYPE
		SYNTAX		RollCallString
		MAX-ACCESS		read-write
		STATUS			current
		DESCRIPTION
				"TYPE: - Editstring
				 PAGE: - Audio- AES Ports- AES Port Names
					AES Port 6-R  cmdID= 38507  "
		::= { iqdbd01CmdEntry 38507 }


	iqdbd01AESOutAESPortNamesAESPort7Stereo OBJECT-TYPE
		SYNTAX		INTEGER { disable(0), enable(1) }
		MAX-ACCESS		read-write
		STATUS			current
		DESCRIPTION
				"TYPE: - Checkbox
				 PAGE: - Audio- AES Ports- AES Port Names
					AES Port 7 Stereo  cmdID= 38454 "
		::= { iqdbd01CmdEntry 38454 }


	iqdbd01AESOutAESPortNamesAESPort7L OBJECT-TYPE
		SYNTAX		RollCallString
		MAX-ACCESS		read-write
		STATUS			current
		DESCRIPTION
				"TYPE: - Editstring
				 PAGE: - Audio- AES Ports- AES Port Names
					AES Port 7-L  cmdID= 38508  "
		::= { iqdbd01CmdEntry 38508 }


	iqdbd01AESOutAESPortNamesAESPort7R OBJECT-TYPE
		SYNTAX		RollCallString
		MAX-ACCESS		read-write
		STATUS			current
		DESCRIPTION
				"TYPE: - Editstring
				 PAGE: - Audio- AES Ports- AES Port Names
					AES Port 7-R  cmdID= 38509  "
		::= { iqdbd01CmdEntry 38509 }


	iqdbd01AESOutAESPortNamesAESPort8Stereo OBJECT-TYPE
		SYNTAX		INTEGER { disable(0), enable(1) }
		MAX-ACCESS		read-write
		STATUS			current
		DESCRIPTION
				"TYPE: - Checkbox
				 PAGE: - Audio- AES Ports- AES Port Names
					AES Port 8 Stereo  cmdID= 38455 "
		::= { iqdbd01CmdEntry 38455 }


	iqdbd01AESOutAESPortNamesAESPort8L OBJECT-TYPE
		SYNTAX		RollCallString
		MAX-ACCESS		read-write
		STATUS			current
		DESCRIPTION
				"TYPE: - Editstring
				 PAGE: - Audio- AES Ports- AES Port Names
					AES Port 8-L  cmdID= 38510  "
		::= { iqdbd01CmdEntry 38510 }


	iqdbd01AESOutAESPortNamesAESPort8R OBJECT-TYPE
		SYNTAX		RollCallString
		MAX-ACCESS		read-write
		STATUS			current
		DESCRIPTION
				"TYPE: - Editstring
				 PAGE: - Audio- AES Ports- AES Port Names
					AES Port 8-R  cmdID= 38511  "
		::= { iqdbd01CmdEntry 38511 }


	iqdbd01AESPortNamesAESOut2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Port Names- AES Out 2
					Left  cmdID= 38202
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38202 }


	iqdbd01AESPortNamesAESOut2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Port Names- AES Out 2
					Right  cmdID= 38203
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbd01CmdEntry 38203 }


	iqdbd01AESPortNamesAESOut2LinkLRSelection OBJECT-TYPE
		SYNTAX		INTEGER { disable(0), enable(1) }
		MAX-ACCESS		read-write
		STATUS			current
		DESCRIPTION
				"TYPE: - Checkbox
				 PAGE: - Audio- AES Ports- AES Port Names- AES Out 2
					Link L+R Selection  cmdID= 38381 "
		::= { iqdbd01CmdEntry 38381 }


	iqdbd01AESBusAESDataModeInput1 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 1  cmdID= 38400
					PCM  value= 0
					Data  value= 1
					Mixed  value= 2  "
		::= { iqdbd01CmdEntry 38400 }


	iqdbd01AESBusAESDataModeInput2 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 2  cmdID= 38401
					PCM  value= 0
					Data  value= 1
					Mixed  value= 2  "
		::= { iqdbd01CmdEntry 38401 }


	iqdbd01AESBusAESDataModeInput3 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 3  cmdID= 38402
					PCM  value= 0
					Data  value= 1
					Mixed  value= 2  "
		::= { iqdbd01CmdEntry 38402 }


	iqdbd01AESBusAESDataModeInput4 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 4  cmdID= 38403
					PCM  value= 0
					Data  value= 1
					Mixed  value= 2  "
		::= { iqdbd01CmdEntry 38403 }


	iqdbd01AESBusAESDataModeInput5 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 5  cmdID= 38404
					PCM  value= 0
					Data  value= 1
					Mixed  value= 2  "
		::= { iqdbd01CmdEntry 38404 }


	iqdbd01AESBusAESDataModeInput6 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 6  cmdID= 38405
					PCM  value= 0
					Data  value= 1
					Mixed  value= 2  "
		::= { iqdbd01CmdEntry 38405 }


	iqdbd01AESBusAESDataModeInput7 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 7  cmdID= 38406
					PCM  value= 0
					Data  value= 1
					Mixed  value= 2  "
		::= { iqdbd01CmdEntry 38406 }


	iqdbd01AESBusAESDataModeInput8 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 8  cmdID= 38407
					PCM  value= 0
					Data  value= 1
					Mixed  value= 2  "
		::= { iqdbd01CmdEntry 38407 }


	iqdbd01AESBusAESBusNamesAESBus1Stereo OBJECT-TYPE
		SYNTAX		INTEGER { disable(0), enable(1) }
		MAX-ACCESS		read-write
		STATUS			current
		DESCRIPTION
				"TYPE: - Checkbox
				 PAGE: - Audio- AES Ports- AES Bus
					AES Bus 1 Stereo  cmdID= 38440 "
		::= { iqdbd01CmdEntry 38440 }


	iqdbd01AESBusAESBusNamesAESBus1 OBJECT-TYPE
		SYNTAX		RollCallString
		MAX-ACCESS		read-write
		STATUS			current
		DESCRIPTION
				"TYPE: - Editstring
				 PAGE: - Audio- AES Ports- AES Bus
					AES Bus 1  cmdID= 38480  "
		::= { iqdbd01CmdEntry 38480 }


	iqdbd01AESBusAESBusNamesAESBus1R OBJECT-TYPE
		SYNTAX		RollCallString
		MAX-ACCESS		read-write
		STATUS			current
		DESCRIPTION
				"TYPE: - Editstring
				 PAGE: - Audio- AES Ports- AES Bus
					AES Bus 1-R  cmdID= 38481  "
		::= { iqdbd01CmdEntry 38481 }


	iqdbd01AESBusAESBusNamesAESBus2Stereo OBJECT-TYPE
		SYNTAX		INTEGER { disable(0), enable(1) }
		MAX-ACCESS		read-write
		STATUS			current
		DESCRIPTION
				"TYPE: - Checkbox
				 PAGE: - Audio- AES Ports- AES Bus
					AES Bus 2 Stereo  cmdID= 38441 "
		::= { iqdbd01CmdEntry 38441 }


	iqdbd01AESBusAESBusNamesAESBus2 OBJECT-TYPE
		SYNTAX		RollCallString
		MAX-ACCESS		read-write
		STATUS			current
		DESCRIPTION
				"TYPE: - Editstring
				 PAGE: - Audio- AES Ports- AES Bus
					AES Bus 2  cmdID= 38482  "
		::= { iqdbd01CmdEntry 38482 }


	iqdbd01AESBusAESBusNamesAESBus2R OBJECT-TYPE
		SYNTAX		RollCallString
		MAX-ACCESS		read-write
		STATUS			current
		DESCRIPTION
				"TYPE: - Editstring
				 PAGE: - Audio- AES Ports- AES Bus
					AES Bus 2-R  cmdID= 38483  "
		::= { iqdbd01CmdEntry 38483 }


	iqdbd01AESBusAESBusNamesAESBus3Stereo OBJECT-TYPE
		SYNTAX		INTEGER { disable(0), enable(1) }
		MAX-ACCESS		read-write
		STATUS			current
		DESCRIPTION
				"TYPE: - Checkbox
				 PAGE: - Audio- AES Ports- AES Bus
					AES Bus 3 Stereo  cmdID= 38442 "
		::= { iqdbd01CmdEntry 38442 }


	iqdbd01AESBusAESBusNamesAESBus3 OBJECT-TYPE
		SYNTAX		RollCallString
		MAX-ACCESS		read-write
		STATUS			current
		DESCRIPTION
				"TYPE: - Editstring
				 PAGE: - Audio- AES Ports- AES Bus
					AES Bus 3  cmdID= 38484  "
		::= { iqdbd01CmdEntry 38484 }


	iqdbd01AESBusAESBusNamesAESBus3R OBJECT-TYPE
		SYNTAX		RollCallString
		MAX-ACCESS		read-write
		STATUS			current
		DESCRIPTION
				"TYPE: - Editstring
				 PAGE: - Audio- AES Ports- AES Bus
					AES Bus 3-R  cmdID= 38485  "
		::= { iqdbd01CmdEntry 38485 }


	iqdbd01AESBusAESBusNamesAESBus4Stereo OBJECT-TYPE
		SYNTAX		INTEGER { disable(0), enable(1) }
		MAX-ACCESS		read-write
		STATUS			current
		DESCRIPTION
				"TYPE: - Checkbox
				 PAGE: - Audio- AES Ports- AES Bus
					AES Bus 4 Stereo  cmdID= 38443 "
		::= { iqdbd01CmdEntry 38443 }


	iqdbd01AESBusAESBusNamesAESBus4 OBJECT-TYPE
		SYNTAX		RollCallString
		MAX-ACCESS		read-write
		STATUS			current
		DESCRIPTION
				"TYPE: - Editstring
				 PAGE: - Audio- AES Ports- AES Bus
					AES Bus 4  cmdID= 38486  "
		::= { iqdbd01CmdEntry 38486 }


	iqdbd01AESBusAESBusNamesAESBus4R OBJECT-TYPE
		SYNTAX		RollCallString
		MAX-ACCESS		read-write
		STATUS			current
		DESCRIPTION
				"TYPE: - Editstring
				 PAGE: - Audio- AES Ports- AES Bus
					AES Bus 4-R  cmdID= 38487  "
		::= { iqdbd01CmdEntry 38487 }


	iqdbd01AESBusAESBusNamesAESBus5Stereo OBJECT-TYPE
		SYNTAX		INTEGER { disable(0), enable(1) }
		MAX-ACCESS		read-write
		STATUS			current
		DESCRIPTION
				"TYPE: - Checkbox
				 PAGE: - Audio- AES Ports- AES Bus
					AES Bus 5 Stereo  cmdID= 38444 "
		::= { iqdbd01CmdEntry 38444 }


	iqdbd01AESBusAESBusNamesAESBus5 OBJECT-TYPE
		SYNTAX		RollCallString
		MAX-ACCESS		read-write
		STATUS			current
		DESCRIPTION
				"TYPE: - Editstring
				 PAGE: - Audio- AES Ports- AES Bus
					AES Bus 5  cmdID= 38488  "
		::= { iqdbd01CmdEntry 38488 }


	iqdbd01AESBusAESBusNamesAESBus5R OBJECT-TYPE
		SYNTAX		RollCallString
		MAX-ACCESS		read-write
		STATUS			current
		DESCRIPTION
				"TYPE: - Editstring
				 PAGE: - Audio- AES Ports- AES Bus
					AES Bus 5-R  cmdID= 38489  "
		::= { iqdbd01CmdEntry 38489 }


	iqdbd01AESBusAESBusNamesAESBus6Stereo OBJECT-TYPE
		SYNTAX		INTEGER { disable(0), enable(1) }
		MAX-ACCESS		read-write
		STATUS			current
		DESCRIPTION
				"TYPE: - Checkbox
				 PAGE: - Audio- AES Ports- AES Bus
					AES Bus 6 Stereo  cmdID= 38445 "
		::= { iqdbd01CmdEntry 38445 }


	iqdbd01AESBusAESBusNamesAESBus6 OBJECT-TYPE
		SYNTAX		RollCallString
		MAX-ACCESS		read-write
		STATUS			current
		DESCRIPTION
				"TYPE: - Editstring
				 PAGE: - Audio- AES Ports- AES Bus
					AES Bus 6  cmdID= 38490  "
		::= { iqdbd01CmdEntry 38490 }


	iqdbd01AESBusAESBusNamesAESBus6R OBJECT-TYPE
		SYNTAX		RollCallString
		MAX-ACCESS		read-write
		STATUS			current
		DESCRIPTION
				"TYPE: - Editstring
				 PAGE: - Audio- AES Ports- AES Bus
					AES Bus 6-R  cmdID= 38491  "
		::= { iqdbd01CmdEntry 38491 }


	iqdbd01AESBusAESBusNamesAESBus7Stereo OBJECT-TYPE
		SYNTAX		INTEGER { disable(0), enable(1) }
		MAX-ACCESS		read-write
		STATUS			current
		DESCRIPTION
				"TYPE: - Checkbox
				 PAGE: - Audio- AES Ports- AES Bus
					AES Bus 7 Stereo  cmdID= 38446 "
		::= { iqdbd01CmdEntry 38446 }


	iqdbd01AESBusAESBusNamesAESBus7 OBJECT-TYPE
		SYNTAX		RollCallString
		MAX-ACCESS		read-write
		STATUS			current
		DESCRIPTION
				"TYPE: - Editstring
				 PAGE: - Audio- AES Ports- AES Bus
					AES Bus 7  cmdID= 38492  "
		::= { iqdbd01CmdEntry 38492 }


	iqdbd01AESBusAESBusNamesAESBus7R OBJECT-TYPE
		SYNTAX		RollCallString
		MAX-ACCESS		read-write
		STATUS			current
		DESCRIPTION
				"TYPE: - Editstring
				 PAGE: - Audio- AES Ports- AES Bus
					AES Bus 7-R  cmdID= 38493  "
		::= { iqdbd01CmdEntry 38493 }


	iqdbd01AESBusAESBusNamesAESBus8Stereo OBJECT-TYPE
		SYNTAX		INTEGER { disable(0), enable(1) }
		MAX-ACCESS		read-write
		STATUS			current
		DESCRIPTION
				"TYPE: - Checkbox
				 PAGE: - Audio- AES Ports- AES Bus
					AES Bus 8 Stereo  cmdID= 38447 "
		::= { iqdbd01CmdEntry 38447 }


	iqdbd01AESBusAESBusNamesAESBus8 OBJECT-TYPE
		SYNTAX		RollCallString
		MAX-ACCESS		read-write
		STATUS			current
		DESCRIPTION
				"TYPE: - Editstring
				 PAGE: - Audio- AES Ports- AES Bus
					AES Bus 8  cmdID= 38494  "
		::= { iqdbd01CmdEntry 38494 }


	iqdbd01AESBusAESBusNamesAESBus8R OBJECT-TYPE
		SYNTAX		RollCallString
		MAX-ACCESS		read-write
		STATUS			current
		DESCRIPTION
				"TYPE: - Editstring
				 PAGE: - Audio- AES Ports- AES Bus
					AES Bus 8-R  cmdID= 38495  "
		::= { iqdbd01CmdEntry 38495 }


	iqdbd01AESBusAESBusRoutingSource1 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 1  cmdID= 38560
					AES Port 1  value= 1
					AES Port 2  value= 2
					AES Port 3  value= 3
					AES Port 4  value= 4
					AES Port 5  value= 5
					AES Port 6  value= 6
					AES Port 7  value= 7
					AES Port 8  value= 8  "
		::= { iqdbd01CmdEntry 38560 }


	iqdbd01AESBusAESBusRoutingSource2 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 2  cmdID= 38561
					AES Port 1  value= 1
					AES Port 2  value= 2
					AES Port 3  value= 3
					AES Port 4  value= 4
					AES Port 5  value= 5
					AES Port 6  value= 6
					AES Port 7  value= 7
					AES Port 8  value= 8  "
		::= { iqdbd01CmdEntry 38561 }


	iqdbd01AESBusAESBusRoutingSource3 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 3  cmdID= 38562
					AES Port 1  value= 1
					AES Port 2  value= 2
					AES Port 3  value= 3
					AES Port 4  value= 4
					AES Port 5  value= 5
					AES Port 6  value= 6
					AES Port 7  value= 7
					AES Port 8  value= 8  "
		::= { iqdbd01CmdEntry 38562 }


	iqdbd01AESBusAESBusRoutingSource4 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 4  cmdID= 38563
					AES Port 1  value= 1
					AES Port 2  value= 2
					AES Port 3  value= 3
					AES Port 4  value= 4
					AES Port 5  value= 5
					AES Port 6  value= 6
					AES Port 7  value= 7
					AES Port 8  value= 8  "
		::= { iqdbd01CmdEntry 38563 }


	iqdbd01AESBusAESBusRoutingSource5 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 5  cmdID= 38564
					AES Port 1  value= 1
					AES Port 2  value= 2
					AES Port 3  value= 3
					AES Port 4  value= 4
					AES Port 5  value= 5
					AES Port 6  value= 6
					AES Port 7  value= 7
					AES Port 8  value= 8  "
		::= { iqdbd01CmdEntry 38564 }


	iqdbd01AESBusAESBusRoutingSource6 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 6  cmdID= 38565
					AES Port 1  value= 1
					AES Port 2  value= 2
					AES Port 3  value= 3
					AES Port 4  value= 4
					AES Port 5  value= 5
					AES Port 6  value= 6
					AES Port 7  value= 7
					AES Port 8  value= 8  "
		::= { iqdbd01CmdEntry 38565 }


	iqdbd01AESBusAESBusRoutingSource7 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 7  cmdID= 38566
					AES Port 1  value= 1
					AES Port 2  value= 2
					AES Port 3  value= 3
					AES Port 4  value= 4
					AES Port 5  value= 5
					AES Port 6  value= 6
					AES Port 7  value= 7
					AES Port 8  value= 8  "
		::= { iqdbd01CmdEntry 38566 }


	iqdbd01AESBusAESBusRoutingSource8 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 8  cmdID= 38567
					AES Port 1  value= 1
					AES Port 2  value= 2
					AES Port 3  value= 3
					AES Port 4  value= 4
					AES Port 5  value= 5
					AES Port 6  value= 6
					AES Port 7  value= 7
					AES Port 8  value= 8  "
		::= { iqdbd01CmdEntry 38567 }


	iqdbd01AESPortsAESDirectionAESPort1Dir OBJECT-TYPE
		SYNTAX		INTEGER {
							val_Input(0),
							val_Output(1)
							}
		MAX-ACCESS		read-write
		STATUS			current
		DESCRIPTION
				"TYPE: - RadiobuttonList
				 PAGE: - Audio- AES Ports
					AES Port 1 Dir  cmdID= 38420
					Input  value= 0
					Output  value= 1  "
		::= { iqdbd01CmdEntry 38420 }


	iqdbd01AESPortsAESDirectionAESPort2Dir OBJECT-TYPE
		SYNTAX		INTEGER {
							val_Input(0),
							val_Output(1)
							}
		MAX-ACCESS		read-write
		STATUS			current
		DESCRIPTION
				"TYPE: - RadiobuttonList
				 PAGE: - Audio- AES Ports
					AES Port 2 Dir  cmdID= 38421
					Input  value= 0
					Output  value= 1  "
		::= { iqdbd01CmdEntry 38421 }


	iqdbd01AESPortsAESDirectionAESPort3Dir OBJECT-TYPE
		SYNTAX		INTEGER {
							val_Input(0),
							val_Output(1)
							}
		MAX-ACCESS		read-write
		STATUS			current
		DESCRIPTION
				"TYPE: - RadiobuttonList
				 PAGE: - Audio- AES Ports
					AES Port 3 Dir  cmdID= 38422
					Input  value= 0
					Output  value= 1  "
		::= { iqdbd01CmdEntry 38422 }


	iqdbd01AESPortsAESDirectionAESPort4Dir OBJECT-TYPE
		SYNTAX		INTEGER {
							val_Input(0),
							val_Output(1)
							}
		MAX-ACCESS		read-write
		STATUS			current
		DESCRIPTION
				"TYPE: - RadiobuttonList
				 PAGE: - Audio- AES Ports
					AES Port 4 Dir  cmdID= 38423
					Input  value= 0
					Output  value= 1  "
		::= { iqdbd01CmdEntry 38423 }


	iqdbd01AESPortsAESDirectionAESPort5Dir OBJECT-TYPE
		SYNTAX		INTEGER {
							val_Input(0),
							val_Output(1)
							}
		MAX-ACCESS		read-write
		STATUS			current
		DESCRIPTION
				"TYPE: - RadiobuttonList
				 PAGE: - Audio- AES Ports
					AES Port 5 Dir  cmdID= 38424
					Input  value= 0
					Output  value= 1  "
		::= { iqdbd01CmdEntry 38424 }


	iqdbd01AESPortsAESDirectionAESPort6Dir OBJECT-TYPE
		SYNTAX		INTEGER {
							val_Input(0),
							val_Output(1)
							}
		MAX-ACCESS		read-write
		STATUS			current
		DESCRIPTION
				"TYPE: - RadiobuttonList
				 PAGE: - Audio- AES Ports
					AES Port 6 Dir  cmdID= 38425
					Input  value= 0
					Output  value= 1  "
		::= { iqdbd01CmdEntry 38425 }


	iqdbd01AESPortsAESDirectionAESPort7Dir OBJECT-TYPE
		SYNTAX		INTEGER {
							val_Input(0),
							val_Output(1)
							}
		MAX-ACCESS		read-write
		STATUS			current
		DESCRIPTION
				"TYPE: - RadiobuttonList
				 PAGE: - Audio- AES Ports
					AES Port 7 Dir  cmdID= 38426
					Input  value= 0
					Output  value= 1  "
		::= { iqdbd01CmdEntry 38426 }


	iqdbd01AESPortsAESDirectionAESPort8Dir OBJECT-TYPE
		SYNTAX		INTEGER {
							val_Input(0),
							val_Output(1)
							}
		MAX-ACCESS		read-write
		STATUS			current
		DESCRIPTION
				"TYPE: - RadiobuttonList
				 PAGE: - Audio- AES Ports
					AES Port 8 Dir  cmdID= 38427
					Input  value= 0
					Output  value= 1  "
		::= { iqdbd01CmdEntry 38427 }


	iqdbd01EngineerPageDolbyETimingSelAudioPair OBJECT-TYPE
		SYNTAX		INTEGER
		MAX-ACCESS		read-write
		STATUS			current
		DESCRIPTION
				"TYPE: - Number
				 PAGE: - Audio
					Sel Audio Pair  cmdID= 38650  min= 1  max= 8  step= 1  format= %0.0f  div_scale= 1
					Min = 1  Max = 8  Step = 1 "
		::= { iqdbd01CmdEntry 38650 }


	iqdbd01AudioDolbyETimingRelativeTiming OBJECT-TYPE
		SYNTAX		RollCallString
		MAX-ACCESS		read-only
		STATUS			current
		DESCRIPTION
				"TYPE: - Display
				 PAGE: - Audio
					Relative Timing  cmdID= 38653  format=   "
		::= { iqdbd01CmdEntry 38653 }


	iqdbd01AudioDolbyETimingStatus OBJECT-TYPE
		SYNTAX		RollCallString
		MAX-ACCESS		read-only
		STATUS			current
		DESCRIPTION
				"TYPE: - Display
				 PAGE: - Audio
					Status  cmdID= 38652  format=   "
		::= { iqdbd01CmdEntry 38652 }


	iqdbd01AudioDolbyETimingError OBJECT-TYPE
		SYNTAX		RollCallString
		MAX-ACCESS		read-only
		STATUS			current
		DESCRIPTION
				"TYPE: - Display
				 PAGE: - Audio
					Error  cmdID= 38654  format=   "
		::= { iqdbd01CmdEntry 38654 }


	iqdbd01DolbyETimingDolbyELineStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
				 PAGE: - Audio
					Standard  cmdID= 38655
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbd01CmdEntry 38655 }


	iqdbd01DolbyETimingDolbyELineAutoLineNo OBJECT-TYPE
		SYNTAX		INTEGER
		MAX-ACCESS		read-write
		STATUS			current
		DESCRIPTION
				"TYPE: - Number
				 PAGE: - Audio
					Auto Line No.  cmdID= 38656  min= 1  max= 10000  step= 1  format= %0.0f  div_scale= 1
					Min = 1  Max = 10000  Step = 1 "
		::= { iqdbd01CmdEntry 38656 }


	iqdbd01DolbyELineUserDolbyELinePair1 OBJECT-TYPE
		SYNTAX		INTEGER {
							val_User_Line(1),
							val_Standard_Line(0)
							}
		MAX-ACCESS		read-write
		STATUS			current
		DESCRIPTION
				"TYPE: - RadiobuttonList
				 PAGE: - Audio
					Pair 1  cmdID= 38670
					User Line  value= 1
					Standard Line  value= 0  "
		::= { iqdbd01CmdEntry 38670 }


	iqdbd01DolbyELineUserDolbyELinePair2 OBJECT-TYPE
		SYNTAX		INTEGER {
							val_User_Line(1),
							val_Standard_Line(0)
							}
		MAX-ACCESS		read-write
		STATUS			current
		DESCRIPTION
				"TYPE: - RadiobuttonList
				 PAGE: - Audio
					Pair 2  cmdID= 38671
					User Line  value= 1
					Standard Line  value= 0  "
		::= { iqdbd01CmdEntry 38671 }


	iqdbd01DolbyELineUserDolbyELinePair3 OBJECT-TYPE
		SYNTAX		INTEGER {
							val_User_Line(1),
							val_Standard_Line(0)
							}
		MAX-ACCESS		read-write
		STATUS			current
		DESCRIPTION
				"TYPE: - RadiobuttonList
				 PAGE: - Audio
					Pair 3  cmdID= 38672
					User Line  value= 1
					Standard Line  value= 0  "
		::= { iqdbd01CmdEntry 38672 }


	iqdbd01DolbyELineUserDolbyELinePair4 OBJECT-TYPE
		SYNTAX		INTEGER {
							val_User_Line(1),
							val_Standard_Line(0)
							}
		MAX-ACCESS		read-write
		STATUS			current
		DESCRIPTION
				"TYPE: - RadiobuttonList
				 PAGE: - Audio
					Pair 4  cmdID= 38673
					User Line  value= 1
					Standard Line  value= 0  "
		::= { iqdbd01CmdEntry 38673 }


	iqdbd01DolbyELineUserDolbyELinePair5 OBJECT-TYPE
		SYNTAX		INTEGER {
							val_User_Line(1),
							val_Standard_Line(0)
							}
		MAX-ACCESS		read-write
		STATUS			current
		DESCRIPTION
				"TYPE: - RadiobuttonList
				 PAGE: - Audio
					Pair 5  cmdID= 38674
					User Line  value= 1
					Standard Line  value= 0  "
		::= { iqdbd01CmdEntry 38674 }


	iqdbd01DolbyELineUserDolbyELinePair6 OBJECT-TYPE
		SYNTAX		INTEGER {
							val_User_Line(1),
							val_Standard_Line(0)
							}
		MAX-ACCESS		read-write
		STATUS			current
		DESCRIPTION
				"TYPE: - RadiobuttonList
				 PAGE: - Audio
					Pair 6  cmdID= 38675
					User Line  value= 1
					Standard Line  value= 0  "
		::= { iqdbd01CmdEntry 38675 }


	iqdbd01DolbyELineUserDolbyELinePair7 OBJECT-TYPE
		SYNTAX		INTEGER {
							val_User_Line(1),
							val_Standard_Line(0)
							}
		MAX-ACCESS		read-write
		STATUS			current
		DESCRIPTION
				"TYPE: - RadiobuttonList
				 PAGE: - Audio
					Pair 7  cmdID= 38676
					User Line  value= 1
					Standard Line  value= 0  "
		::= { iqdbd01CmdEntry 38676 }


	iqdbd01DolbyELineUserDolbyELinePair8 OBJECT-TYPE
		SYNTAX		INTEGER {
							val_User_Line(1),
							val_Standard_Line(0)
							}
		MAX-ACCESS		read-write
		STATUS			current
		DESCRIPTION
				"TYPE: - RadiobuttonList
				 PAGE: - Audio
					Pair 8  cmdID= 38677
					User Line  value= 1
					Standard Line  value= 0  "
		::= { iqdbd01CmdEntry 38677 }


	iqdbd01AudioDolbyDecoderDecoderSourceSel OBJECT-TYPE
		SYNTAX		INTEGER {
							val_AES_Input_5(0),
							val_AES_Input_6(1),
							val_AES_Input_7(2),
							val_AES_Input_8(3),
							val_Disembedded_1(4),
							val_Disembedded_2(5),
							val_Disembedded_3(6),
							val_Disembedded_4(7),
							val_Disembedded_5(8),
							val_Disembedded_6(9),
							val_Disembedded_7(10),
							val_Disembedded_8(11)
							}
		MAX-ACCESS		read-write
		STATUS			current
		DESCRIPTION
				"TYPE: - RadiobuttonList
				 PAGE: - Audio- Dolby Decoder
					Decoder Source Sel  cmdID= 38680
					AES Input 5  value= 0
					AES Input 6  value= 1
					AES Input 7  value= 2
					AES Input 8  value= 3
					Disembedded 1  value= 4
					Disembedded 2  value= 5
					Disembedded 3  value= 6
					Disembedded 4  value= 7
					Disembedded 5  value= 8
					Disembedded 6  value= 9
					Disembedded 7  value= 10
					Disembedded 8  value= 11  "
		::= { iqdbd01CmdEntry 38680 }


	iqdbd01AudioDolbyDecoderAESBus4SourceSel OBJECT-TYPE
		SYNTAX		INTEGER {
							val_Decoder_Chan_4(0),
							val_Decoder_Aux_Chan(1)
							}
		MAX-ACCESS		read-write
		STATUS			current
		DESCRIPTION
				"TYPE: - RadiobuttonList
				 PAGE: - Audio- Dolby Decoder
					AES Bus4 Source Sel  cmdID= 38689
					Decoder Chan 4  value= 0
					Decoder Aux Chan  value= 1  "
		::= { iqdbd01CmdEntry 38689 }


	iqdbd01AudioDolbyDecoderMonitorSourceSel OBJECT-TYPE
		SYNTAX		INTEGER {
							val_Decoder_Aux_Chan(0),
							val_Decoder_Chan_4(1)
							}
		MAX-ACCESS		read-write
		STATUS			current
		DESCRIPTION
				"TYPE: - RadiobuttonList
				 PAGE: - Audio- Dolby Decoder
					Monitor Source Sel  cmdID= 38690
					Decoder Aux Chan  value= 0
					Decoder Chan 4  value= 1  "
		::= { iqdbd01CmdEntry 38690 }


	iqdbd01AudioDolbyDecoderBitstreamDetmode OBJECT-TYPE
		SYNTAX		INTEGER {
							val_Auto(3),
							val_Dolby_E_or_Mute(2),
							val_Dolby_D_or_Mute(1),
							val_Mute(0)
							}
		MAX-ACCESS		read-write
		STATUS			current
		DESCRIPTION
				"TYPE: - RadiobuttonList
				 PAGE: - Audio- Dolby Decoder
					Bitstream Det mode  cmdID= 38681
					Auto  value= 3
					Dolby E or Mute  value= 2
					Dolby D or Mute  value= 1
					Mute  value= 0  "
		::= { iqdbd01CmdEntry 38681 }


	iqdbd01AudioDolbyDecoderDynamicRange OBJECT-TYPE
		SYNTAX		INTEGER {
							val_Line_Mode(3),
							val_RF_Mode(2),
							val_Bypass_Mode(0)
							}
		MAX-ACCESS		read-write
		STATUS			current
		DESCRIPTION
				"TYPE: - RadiobuttonList
				 PAGE: - Audio- Dolby Decoder
					Dynamic Range  cmdID= 38682
					Line Mode  value= 3
					RF Mode  value= 2
					Bypass Mode  value= 0  "
		::= { iqdbd01CmdEntry 38682 }


	iqdbd01AudioDolbyDecoderListeningModeDD OBJECT-TYPE
		SYNTAX		INTEGER {
							val_Full(7),
							val_EX(6),
							val_3_Stereo(5),
							val_Phantom(4),
							val_Stereo(3),
							val_Mono(2)
							}
		MAX-ACCESS		read-write
		STATUS			current
		DESCRIPTION
				"TYPE: - RadiobuttonList
				 PAGE: - Audio- Dolby Decoder
					Listening Mode DD  cmdID= 38683
					Full  value= 7
					EX  value= 6
					3 Stereo  value= 5
					Phantom  value= 4
					Stereo  value= 3
					Mono  value= 2  "
		::= { iqdbd01CmdEntry 38683 }


	iqdbd01AudioDolbyDecoderPCMLatency OBJECT-TYPE
		SYNTAX		INTEGER {
							val_Single_Frame(1),
							val_Minimum(0)
							}
		MAX-ACCESS		read-write
		STATUS			current
		DESCRIPTION
				"TYPE: - RadiobuttonList
				 PAGE: - Audio- Dolby Decoder
					PCM Latency  cmdID= 38684
					Single Frame  value= 1
					Minimum  value= 0  "
		::= { iqdbd01CmdEntry 38684 }


	iqdbd01AudioDolbyDecoderDisplayLatency OBJECT-TYPE
		SYNTAX		RollCallString
		MAX-ACCESS		read-only
		STATUS			current
		DESCRIPTION
				"TYPE: - Display
				 PAGE: - Audio- Dolby Decoder
					Display Latency  cmdID= 38692  format=   "
		::= { iqdbd01CmdEntry 38692 }


	iqdbd01AudioDolbyDecoderAESChanSel OBJECT-TYPE
		SYNTAX		INTEGER {
							val_Channel_1(1),
							val_Channel_2(0)
							}
		MAX-ACCESS		read-write
		STATUS			current
		DESCRIPTION
				"TYPE: - RadiobuttonList
				 PAGE: - Audio- Dolby Decoder
					AES Chan Sel  cmdID= 38685
					Channel 1  value= 1
					Channel 2  value= 0  "
		::= { iqdbd01CmdEntry 38685 }


	iqdbd01AudioDolbyDecoderAuxChanOPMode OBJECT-TYPE
		SYNTAX		INTEGER {
							val_Mode_3(3),
							val_Mode_2(2),
							val_Mode_1(1),
							val_Mute(0)
							}
		MAX-ACCESS		read-write
		STATUS			current
		DESCRIPTION
				"TYPE: - RadiobuttonList
				 PAGE: - Audio- Dolby Decoder
					Aux Chan O/P Mode  cmdID= 38686
					Mode 3  value= 3
					Mode 2  value= 2
					Mode 1  value= 1
					Mute  value= 0  "
		::= { iqdbd01CmdEntry 38686 }


	iqdbd01AudioDolbyDecoderAuxChanPgmSel OBJECT-TYPE
		SYNTAX		INTEGER {
							val_Program_1(0),
							val_Program_2(1),
							val_Program_3(2),
							val_Program_4(3),
							val_Program_5(4),
							val_Program_6(5),
							val_Program_7(6),
							val_Program_8(7)
							}
		MAX-ACCESS		read-write
		STATUS			current
		DESCRIPTION
				"TYPE: - RadiobuttonList
				 PAGE: - Audio- Dolby Decoder
					Aux Chan Pgm Sel  cmdID= 38687
					Program 1  value= 0
					Program 2  value= 1
					Program 3  value= 2
					Program 4  value= 3
					Program 5  value= 4
					Program 6  value= 5
					Program 7  value= 6
					Program 8  value= 7  "
		::= { iqdbd01CmdEntry 38687 }


	iqdbd01AudioDolbyDecoderAuxChanDynRange OBJECT-TYPE
		SYNTAX		INTEGER {
							val_Line_Mode(1),
							val_RF_Mode(0)
							}
		MAX-ACCESS		read-write
		STATUS			current
		DESCRIPTION
				"TYPE: - RadiobuttonList
				 PAGE: - Audio- Dolby Decoder
					Aux Chan Dyn Range  cmdID= 38688
					Line Mode  value= 1
					RF Mode  value= 0  "
		::= { iqdbd01CmdEntry 38688 }


	iqdbd01AudioDolbyDecoderSoftwareVersion OBJECT-TYPE
		SYNTAX		RollCallString
		MAX-ACCESS		read-only
		STATUS			current
		DESCRIPTION
				"TYPE: - Display
				 PAGE: - Audio- Dolby Decoder
					Software Version  cmdID= 38700  format=   "
		::= { iqdbd01CmdEntry 38700 }


	iqdbd01AudioDolbyDecoderResetErrorCounts OBJECT-TYPE
		SYNTAX		INTEGER {
							val_Reset_Dolby_E_Count(1),
							val_Reset_Dolby_D_Count(2)
							}
		MAX-ACCESS		read-write
		STATUS			current
		DESCRIPTION
				"TYPE: - RadiobuttonList
				 PAGE: - Audio- Dolby Decoder
					Reset Error Counts  cmdID= 38691
					Reset Dolby E Count  value= 1
					Reset Dolby D Count  value= 2  "
		::= { iqdbd01CmdEntry 38691 }


	iqdbd01DolbyDecoderCenterMixLevelProgram1 OBJECT-TYPE
		SYNTAX		RollCallString
		MAX-ACCESS		read-only
		STATUS			current
		DESCRIPTION
				"TYPE: - Display
				 PAGE: - Audio- Dolby Decoder
					Program 1  cmdID= 38701  format=   "
		::= { iqdbd01CmdEntry 38701 }


	iqdbd01DolbyDecoderCenterMixLevelProgram2 OBJECT-TYPE
		SYNTAX		RollCallString
		MAX-ACCESS		read-only
		STATUS			current
		DESCRIPTION
				"TYPE: - Display
				 PAGE: - Audio- Dolby Decoder
					Program 2  cmdID= 38702  format=   "
		::= { iqdbd01CmdEntry 38702 }


	iqdbd01DolbyDecoderCenterMixLevelProgram3 OBJECT-TYPE
		SYNTAX		RollCallString
		MAX-ACCESS		read-only
		STATUS			current
		DESCRIPTION
				"TYPE: - Display
				 PAGE: - Audio- Dolby Decoder
					Program 3  cmdID= 38703  format=   "
		::= { iqdbd01CmdEntry 38703 }


	iqdbd01DolbyDecoderCenterMixLevelProgram4 OBJECT-TYPE
		SYNTAX		RollCallString
		MAX-ACCESS		read-only
		STATUS			current
		DESCRIPTION
				"TYPE: - Display
				 PAGE: - Audio- Dolby Decoder
					Program 4  cmdID= 38704  format=   "
		::= { iqdbd01CmdEntry 38704 }


	iqdbd01DolbyDecoderCenterMixLevelProgram5 OBJECT-TYPE
		SYNTAX		RollCallString
		MAX-ACCESS		read-only
		STATUS			current
		DESCRIPTION
				"TYPE: - Display
				 PAGE: - Audio- Dolby Decoder
					Program 5  cmdID= 38705  format=   "
		::= { iqdbd01CmdEntry 38705 }


	iqdbd01DolbyDecoderCenterMixLevelProgram6 OBJECT-TYPE
		SYNTAX		RollCallString
		MAX-ACCESS		read-only
		STATUS			current
		DESCRIPTION
				"TYPE: - Display
				 PAGE: - Audio- Dolby Decoder
					Program 6  cmdID= 38706  format=   "
		::= { iqdbd01CmdEntry 38706 }


	iqdbd01DolbyDecoderCenterMixLevelProgram7 OBJECT-TYPE
		SYNTAX		RollCallString
		MAX-ACCESS		read-only
		STATUS			current
		DESCRIPTION
				"TYPE: - Display
				 PAGE: - Audio- Dolby Decoder
					Program 7  cmdID= 38707  format=   "
		::= { iqdbd01CmdEntry 38707 }


	iqdbd01DolbyDecoderCenterMixLevelProgram8 OBJECT-TYPE
		SYNTAX		RollCallString
		MAX-ACCESS		read-only
		STATUS			current
		DESCRIPTION
				"TYPE: - Display
				 PAGE: - Audio- Dolby Decoder
					Program 8  cmdID= 38708  format=   "
		::= { iqdbd01CmdEntry 38708 }


	iqdbd01DolbyDecoderSurroundMixLevelProgram1 OBJECT-TYPE
		SYNTAX		RollCallString
		MAX-ACCESS		read-only
		STATUS			current
		DESCRIPTION
				"TYPE: - Display
				 PAGE: - Audio- Dolby Decoder
					Program 1  cmdID= 38709  format=   "
		::= { iqdbd01CmdEntry 38709 }


	iqdbd01DolbyDecoderSurroundMixLevelProgram2 OBJECT-TYPE
		SYNTAX		RollCallString
		MAX-ACCESS		read-only
		STATUS			current
		DESCRIPTION
				"TYPE: - Display
				 PAGE: - Audio- Dolby Decoder
					Program 2  cmdID= 38710  format=   "
		::= { iqdbd01CmdEntry 38710 }


	iqdbd01DolbyDecoderSurroundMixLevelProgram3 OBJECT-TYPE
		SYNTAX		RollCallString
		MAX-ACCESS		read-only
		STATUS			current
		DESCRIPTION
				"TYPE: - Display
				 PAGE: - Audio- Dolby Decoder
					Program 3  cmdID= 38711  format=   "
		::= { iqdbd01CmdEntry 38711 }


	iqdbd01DolbyDecoderSurroundMixLevelProgram4 OBJECT-TYPE
		SYNTAX		RollCallString
		MAX-ACCESS		read-only
		STATUS			current
		DESCRIPTION
				"TYPE: - Display
				 PAGE: - Audio- Dolby Decoder
					Program 4  cmdID= 38712  format=   "
		::= { iqdbd01CmdEntry 38712 }


	iqdbd01DolbyDecoderSurroundMixLevelProgram5 OBJECT-TYPE
		SYNTAX		RollCallString
		MAX-ACCESS		read-only
		STATUS			current
		DESCRIPTION
				"TYPE: - Display
				 PAGE: - Audio- Dolby Decoder
					Program 5  cmdID= 38713  format=   "
		::= { iqdbd01CmdEntry 38713 }


	iqdbd01DolbyDecoderSurroundMixLevelProgram6 OBJECT-TYPE
		SYNTAX		RollCallString
		MAX-ACCESS		read-only
		STATUS			current
		DESCRIPTION
				"TYPE: - Display
				 PAGE: - Audio- Dolby Decoder
					Program 6  cmdID= 38714  format=   "
		::= { iqdbd01CmdEntry 38714 }


	iqdbd01DolbyDecoderSurroundMixLevelProgram7 OBJECT-TYPE
		SYNTAX		RollCallString
		MAX-ACCESS		read-only
		STATUS			current
		DESCRIPTION
				"TYPE: - Display
				 PAGE: - Audio- Dolby Decoder
					Program 7  cmdID= 38715  format=   "
		::= { iqdbd01CmdEntry 38715 }


	iqdbd01DolbyDecoderSurroundMixLevelProgram8 OBJECT-TYPE
		SYNTAX		RollCallString
		MAX-ACCESS		read-only
		STATUS			current
		DESCRIPTION
				"TYPE: - Display
				 PAGE: - Audio- Dolby Decoder
					Program 8  cmdID= 38716  format=   "
		::= { iqdbd01CmdEntry 38716 }


	iqdbd01DolbyDecoderLtRtCMixLevelProgram1 OBJECT-TYPE
		SYNTAX		RollCallString
		MAX-ACCESS		read-only
		STATUS			current
		DESCRIPTION
				"TYPE: - Display
				 PAGE: - Audio- Dolby Decoder
					Program 1  cmdID= 38717  format=   "
		::= { iqdbd01CmdEntry 38717 }


	iqdbd01DolbyDecoderLtRtCMixLevelProgram2 OBJECT-TYPE
		SYNTAX		RollCallString
		MAX-ACCESS		read-only
		STATUS			current
		DESCRIPTION
				"TYPE: - Display
				 PAGE: - Audio- Dolby Decoder
					Program 2  cmdID= 38718  format=   "
		::= { iqdbd01CmdEntry 38718 }


	iqdbd01DolbyDecoderLtRtCMixLevelProgram3 OBJECT-TYPE
		SYNTAX		RollCallString
		MAX-ACCESS		read-only
		STATUS			current
		DESCRIPTION
				"TYPE: - Display
				 PAGE: - Audio- Dolby Decoder
					Program 3  cmdID= 38719  format=   "
		::= { iqdbd01CmdEntry 38719 }


	iqdbd01DolbyDecoderLtRtCMixLevelProgram4 OBJECT-TYPE
		SYNTAX		RollCallString
		MAX-ACCESS		read-only
		STATUS			current
		DESCRIPTION
				"TYPE: - Display
				 PAGE: - Audio- Dolby Decoder
					Program 4  cmdID= 38720  format=   "
		::= { iqdbd01CmdEntry 38720 }


	iqdbd01DolbyDecoderLtRtCMixLevelProgram5 OBJECT-TYPE
		SYNTAX		RollCallString
		MAX-ACCESS		read-only
		STATUS			current
		DESCRIPTION
				"TYPE: - Display
				 PAGE: - Audio- Dolby Decoder
					Program 5  cmdID= 38721  format=   "
		::= { iqdbd01CmdEntry 38721 }


	iqdbd01DolbyDecoderLtRtCMixLevelProgram6 OBJECT-TYPE
		SYNTAX		RollCallString
		MAX-ACCESS		read-only
		STATUS			current
		DESCRIPTION
				"TYPE: - Display
				 PAGE: - Audio- Dolby Decoder
					Program 6  cmdID= 38722  format=   "
		::= { iqdbd01CmdEntry 38722 }


	iqdbd01DolbyDecoderLtRtCMixLevelProgram7 OBJECT-TYPE
		SYNTAX		RollCallString
		MAX-ACCESS		read-only
		STATUS			current
		DESCRIPTION
				"TYPE: - Display
				 PAGE: - Audio- Dolby Decoder
					Program 7  cmdID= 38723  format=   "
		::= { iqdbd01CmdEntry 38723 }


	iqdbd01DolbyDecoderLtRtCMixLevelProgram8 OBJECT-TYPE
		SYNTAX		RollCallString
		MAX-ACCESS		read-only
		STATUS			current
		DESCRIPTION
				"TYPE: - Display
				 PAGE: - Audio- Dolby Decoder
					Program 8  cmdID= 38724  format=   "
		::= { iqdbd01CmdEntry 38724 }


	iqdbd01DolbyDecoderLtRtSMixLevelProgram1 OBJECT-TYPE
		SYNTAX		RollCallString
		MAX-ACCESS		read-only
		STATUS			current
		DESCRIPTION
				"TYPE: - Display
				 PAGE: - Audio- Dolby Decoder
					Program 1  cmdID= 38725  format=   "
		::= { iqdbd01CmdEntry 38725 }


	iqdbd01DolbyDecoderLtRtSMixLevelProgram2 OBJECT-TYPE
		SYNTAX		RollCallString
		MAX-ACCESS		read-only
		STATUS			current
		DESCRIPTION
				"TYPE: - Display
				 PAGE: - Audio- Dolby Decoder
					Program 2  cmdID= 38726  format=   "
		::= { iqdbd01CmdEntry 38726 }


	iqdbd01DolbyDecoderLtRtSMixLevelProgram3 OBJECT-TYPE
		SYNTAX		RollCallString
		MAX-ACCESS		read-only
		STATUS			current
		DESCRIPTION
				"TYPE: - Display
				 PAGE: - Audio- Dolby Decoder
					Program 3  cmdID= 38727  format=   "
		::= { iqdbd01CmdEntry 38727 }


	iqdbd01DolbyDecoderLtRtSMixLevelProgram4 OBJECT-TYPE
		SYNTAX		RollCallString
		MAX-ACCESS		read-only
		STATUS			current
		DESCRIPTION
				"TYPE: - Display
				 PAGE: - Audio- Dolby Decoder
					Program 4  cmdID= 38728  format=   "
		::= { iqdbd01CmdEntry 38728 }


	iqdbd01DolbyDecoderLtRtSMixLevelProgram5 OBJECT-TYPE
		SYNTAX		RollCallString
		MAX-ACCESS		read-only
		STATUS			current
		DESCRIPTION
				"TYPE: - Display
				 PAGE: - Audio- Dolby Decoder
					Program 5  cmdID= 38729  format=   "
		::= { iqdbd01CmdEntry 38729 }


	iqdbd01DolbyDecoderLtRtSMixLevelProgram6 OBJECT-TYPE
		SYNTAX		RollCallString
		MAX-ACCESS		read-only
		STATUS			current
		DESCRIPTION
				"TYPE: - Display
				 PAGE: - Audio- Dolby Decoder
					Program 6  cmdID= 38730  format=   "
		::= { iqdbd01CmdEntry 38730 }


	iqdbd01DolbyDecoderLtRtSMixLevelProgram7 OBJECT-TYPE
		SYNTAX		RollCallString
		MAX-ACCESS		read-only
		STATUS			current
		DESCRIPTION
				"TYPE: - Display
				 PAGE: - Audio- Dolby Decoder
					Program 7  cmdID= 38731  format=   "
		::= { iqdbd01CmdEntry 38731 }


	iqdbd01DolbyDecoderLtRtSMixLevelProgram8 OBJECT-TYPE
		SYNTAX		RollCallString
		MAX-ACCESS		read-only
		STATUS			current
		DESCRIPTION
				"TYPE: - Display
				 PAGE: - Audio- Dolby Decoder
					Program 8  cmdID= 38732  format=   "
		::= { iqdbd01CmdEntry 38732 }


	iqdbd01DolbyDecoderLoRoCMixLevelProgram1 OBJECT-TYPE
		SYNTAX		RollCallString
		MAX-ACCESS		read-only
		STATUS			current
		DESCRIPTION
				"TYPE: - Display
				 PAGE: - Audio- Dolby Decoder
					Program 1  cmdID= 38733  format=   "
		::= { iqdbd01CmdEntry 38733 }


	iqdbd01DolbyDecoderLoRoCMixLevelProgram2 OBJECT-TYPE
		SYNTAX		RollCallString
		MAX-ACCESS		read-only
		STATUS			current
		DESCRIPTION
				"TYPE: - Display
				 PAGE: - Audio- Dolby Decoder
					Program 2  cmdID= 38734  format=   "
		::= { iqdbd01CmdEntry 38734 }


	iqdbd01DolbyDecoderLoRoCMixLevelProgram3 OBJECT-TYPE
		SYNTAX		RollCallString
		MAX-ACCESS		read-only
		STATUS			current
		DESCRIPTION
				"TYPE: - Display
				 PAGE: - Audio- Dolby Decoder
					Program 3  cmdID= 38735  format=   "
		::= { iqdbd01CmdEntry 38735 }


	iqdbd01DolbyDecoderLoRoCMixLevelProgram4 OBJECT-TYPE
		SYNTAX		RollCallString
		MAX-ACCESS		read-only
		STATUS			current
		DESCRIPTION
				"TYPE: - Display
				 PAGE: - Audio- Dolby Decoder
					Program 4  cmdID= 38736  format=   "
		::= { iqdbd01CmdEntry 38736 }


	iqdbd01DolbyDecoderLoRoCMixLevelProgram5 OBJECT-TYPE
		SYNTAX		RollCallString
		MAX-ACCESS		read-only
		STATUS			current
		DESCRIPTION
				"TYPE: - Display
				 PAGE: - Audio- Dolby Decoder
					Program 5  cmdID= 38737  format=   "
		::= { iqdbd01CmdEntry 38737 }


	iqdbd01DolbyDecoderLoRoCMixLevelProgram6 OBJECT-TYPE
		SYNTAX		RollCallString
		MAX-ACCESS		read-only
		STATUS			current
		DESCRIPTION
				"TYPE: - Display
				 PAGE: - Audio- Dolby Decoder
					Program 6  cmdID= 38738  format=   "
		::= { iqdbd01CmdEntry 38738 }


	iqdbd01DolbyDecoderLoRoCMixLevelProgram7 OBJECT-TYPE
		SYNTAX		RollCallString
		MAX-ACCESS		read-only
		STATUS			current
		DESCRIPTION
				"TYPE: - Display
				 PAGE: - Audio- Dolby Decoder
					Program 7  cmdID= 38739  format=   "
		::= { iqdbd01CmdEntry 38739 }


	iqdbd01DolbyDecoderLoRoCMixLevelProgram8 OBJECT-TYPE
		SYNTAX		RollCallString
		MAX-ACCESS		read-only
		STATUS			current
		DESCRIPTION
				"TYPE: - Display
				 PAGE: - Audio- Dolby Decoder
					Program 8  cmdID= 38740  format=   "
		::= { iqdbd01CmdEntry 38740 }


	iqdbd01DolbyDecoderLoRoSMixLevelProgram1 OBJECT-TYPE
		SYNTAX		RollCallString
		MAX-ACCESS		read-only
		STATUS			current
		DESCRIPTION
				"TYPE: - Display
				 PAGE: - Audio- Dolby Decoder
					Program 1  cmdID= 38741  format=   "
		::= { iqdbd01CmdEntry 38741 }


	iqdbd01DolbyDecoderLoRoSMixLevelProgram2 OBJECT-TYPE
		SYNTAX		RollCallString
		MAX-ACCESS		read-only
		STATUS			current
		DESCRIPTION
				"TYPE: - Display
				 PAGE: - Audio- Dolby Decoder
					Program 2  cmdID= 38742  format=   "
		::= { iqdbd01CmdEntry 38742 }


	iqdbd01DolbyDecoderLoRoSMixLevelProgram3 OBJECT-TYPE
		SYNTAX		RollCallString
		MAX-ACCESS		read-only
		STATUS			current
		DESCRIPTION
				"TYPE: - Display
				 PAGE: - Audio- Dolby Decoder
					Program 3  cmdID= 38743  format=   "
		::= { iqdbd01CmdEntry 38743 }


	iqdbd01DolbyDecoderLoRoSMixLevelProgram4 OBJECT-TYPE
		SYNTAX		RollCallString
		MAX-ACCESS		read-only
		STATUS			current
		DESCRIPTION
				"TYPE: - Display
				 PAGE: - Audio- Dolby Decoder
					Program 4  cmdID= 38744  format=   "
		::= { iqdbd01CmdEntry 38744 }


	iqdbd01DolbyDecoderLoRoSMixLevelProgram5 OBJECT-TYPE
		SYNTAX		RollCallString
		MAX-ACCESS		read-only
		STATUS			current
		DESCRIPTION
				"TYPE: - Display
				 PAGE: - Audio- Dolby Decoder
					Program 5  cmdID= 38745  format=   "
		::= { iqdbd01CmdEntry 38745 }


	iqdbd01DolbyDecoderLoRoSMixLevelProgram6 OBJECT-TYPE
		SYNTAX		RollCallString
		MAX-ACCESS		read-only
		STATUS			current
		DESCRIPTION
				"TYPE: - Display
				 PAGE: - Audio- Dolby Decoder
					Program 6  cmdID= 38746  format=   "
		::= { iqdbd01CmdEntry 38746 }


	iqdbd01DolbyDecoderLoRoSMixLevelProgram7 OBJECT-TYPE
		SYNTAX		RollCallString
		MAX-ACCESS		read-only
		STATUS			current
		DESCRIPTION
				"TYPE: - Display
				 PAGE: - Audio- Dolby Decoder
					Program 7  cmdID= 38747  format=   "
		::= { iqdbd01CmdEntry 38747 }


	iqdbd01DolbyDecoderLoRoSMixLevelProgram8 OBJECT-TYPE
		SYNTAX		RollCallString
		MAX-ACCESS		read-only
		STATUS			current
		DESCRIPTION
				"TYPE: - Display
				 PAGE: - Audio- Dolby Decoder
					Program 8  cmdID= 38748  format=   "
		::= { iqdbd01CmdEntry 38748 }


	iqdbd01DolbyDecoderMetadataDisplayDisplaySelect OBJECT-TYPE
		SYNTAX		INTEGER {
							val_Data_Words(0),
							val_Parameters(1)
							}
		MAX-ACCESS		read-write
		STATUS			current
		DESCRIPTION
				"TYPE: - RadiobuttonList
				 PAGE: - Audio- Dolby Decoder
					Display Select  cmdID= 38750
					Data Words  value= 0
					Parameters  value= 1  "
		::= { iqdbd01CmdEntry 38750 }


	iqdbd01DolbyDecoderMetadataDisplayDataSelect OBJECT-TYPE
		SYNTAX		INTEGER
		MAX-ACCESS		read-write
		STATUS			current
		DESCRIPTION
				"TYPE: - Number
				 PAGE: - Audio- Dolby Decoder
					Data Select  cmdID= 38751  min= 0  max= 69  step= 1  format= %0.0f  div_scale= 1
					Min = 0  Max = 69  Step = 1 "
		::= { iqdbd01CmdEntry 38751 }


	iqdbd01DolbyDecoderMetadataDisplayProgramSelect OBJECT-TYPE
		SYNTAX		INTEGER
		MAX-ACCESS		read-write
		STATUS			current
		DESCRIPTION
				"TYPE: - Number
				 PAGE: - Audio- Dolby Decoder
					Program Select  cmdID= 38752  min= 0  max= 7  step= 1  format= %0.0f  div_scale= 1
					Min = 0  Max = 7  Step = 1 "
		::= { iqdbd01CmdEntry 38752 }


	iqdbd01VidDelayInternalDelay OBJECT-TYPE
		SYNTAX		RollCallString
		MAX-ACCESS		read-only
		STATUS			current
		DESCRIPTION
				"TYPE: - Display
				 PAGE: - Vid. Delay
					Internal Delay  cmdID= 33025  format=   "
		::= { iqdbd01CmdEntry 33025 }


	iqdbd01VidDelayDelayMode OBJECT-TYPE
		SYNTAX		INTEGER {
							val_Minimum_Audio(3),
							val_Frames(4),
							val_Manual_H_V(5),
							val_Manual_ms(6)
							}
		MAX-ACCESS		read-write
		STATUS			current
		DESCRIPTION
				"TYPE: - RadiobuttonList
				 PAGE: - Vid. Delay
					Delay Mode  cmdID= 33026
					Minimum Audio  value= 3
					Frames  value= 4
					Manual H/V  value= 5
					Manual ms  value= 6  "
		::= { iqdbd01CmdEntry 33026 }


	iqdbd01VidDelaySetDelayDelayFrames OBJECT-TYPE
		SYNTAX		INTEGER
		MAX-ACCESS		read-write
		STATUS			current
		DESCRIPTION
				"TYPE: - Number
				 PAGE: - Vid. Delay
					Delay Frames  cmdID= 33024  min= 0  max= 11  step= 1  format= %0.0f frames  div_scale= 1
					Min = 0 frames  Max = 11 frames  Step = 1 frames "
		::= { iqdbd01CmdEntry 33024 }


	iqdbd01VidDelaySetDelayVerticalTiming OBJECT-TYPE
		SYNTAX		INTEGER
		MAX-ACCESS		read-write
		STATUS			current
		DESCRIPTION
				"TYPE: - Number
				 PAGE: - Vid. Delay
					Vertical Timing  cmdID= 33022  min= -1500  max= 1500  step= 1  format= %0.0f lines  div_scale= 1
					Min = -1500 lines  Max = 1500 lines  Step = 1 lines "
		::= { iqdbd01CmdEntry 33022 }


	iqdbd01VidDelaySetDelayHorizontalTiming OBJECT-TYPE
		SYNTAX		INTEGER
		MAX-ACCESS		read-write
		STATUS			current
		DESCRIPTION
				"TYPE: - Number
				 PAGE: - Vid. Delay
					Horizontal Timing  cmdID= 33021  min= -3000  max= 3000  step= 1  format= %0.0f pixels  div_scale= 1
					Min = -3000 pixels  Max = 3000 pixels  Step = 1 pixels "
		::= { iqdbd01CmdEntry 33021 }


	iqdbd01VidDelaySetDelayDelayms OBJECT-TYPE
		SYNTAX		INTEGER
		MAX-ACCESS		read-write
		STATUS			current
		DESCRIPTION
				"TYPE: - Number
				 PAGE: - Vid. Delay
					Delay ms  cmdID= 33027  min= -48000  max= 48000  step= 5  format= %0.2f ms  div_scale= 100
					Min = -480.00 ms  Max = 480.00 ms  Step = 0.05 ms "
		::= { iqdbd01CmdEntry 33027 }


	iqdbd01UtilsPatternsPatternEnable OBJECT-TYPE
		SYNTAX		INTEGER { disable(0), enable(1) }
		MAX-ACCESS		read-write
		STATUS			current
		DESCRIPTION
				"TYPE: - Checkbox
				 PAGE: - Utils
					Pattern Enable  cmdID= 33038 "
		::= { iqdbd01CmdEntry 33038 }


	iqdbd01UtilsPatternsScrollPattern OBJECT-TYPE
		SYNTAX		INTEGER { disable(0), enable(1) }
		MAX-ACCESS		read-write
		STATUS			current
		DESCRIPTION
				"TYPE: - Checkbox
				 PAGE: - Utils
					Scroll Pattern  cmdID= 33040 "
		::= { iqdbd01CmdEntry 33040 }


	iqdbd01UtilsPatternsPatternType OBJECT-TYPE
		SYNTAX		INTEGER {
							val_100_Color_Bars(1),
							val_75_Color_Bars(2),
							val_SMPTE_Bars(3),
							val_Tartan_Bars(4),
							val_Pluge(5),
							val_Ramp(6),
							val_Sweep(7),
							val_Pulse_Bar(8),
							val_Burst(9),
							val_Black(10)
							}
		MAX-ACCESS		read-write
		STATUS			current
		DESCRIPTION
				"TYPE: - RadiobuttonList
				 PAGE: - Utils
					Pattern Type  cmdID= 33039
					100% Color Bars  value= 1
					75% Color Bars  value= 2
					SMPTE Bars  value= 3
					Tartan Bars  value= 4
					Pluge  value= 5
					Ramp  value= 6
					Sweep  value= 7
					Pulse & Bar  value= 8
					Burst  value= 9
					Black  value= 10  "
		::= { iqdbd01CmdEntry 33039 }


	iqdbd01UtilsANCblankonMismat OBJECT-TYPE
		SYNTAX		INTEGER { disable(0), enable(1) }
		MAX-ACCESS		read-write
		STATUS			current
		DESCRIPTION
				"TYPE: - Checkbox
				 PAGE: - Utils
					ANC blank on Mismat  cmdID= 33036 "
		::= { iqdbd01CmdEntry 33036 }


	iqdbd01UtilsFreezeForceFreeze OBJECT-TYPE
		SYNTAX		INTEGER { disable(0), enable(1) }
		MAX-ACCESS		read-write
		STATUS			current
		DESCRIPTION
				"TYPE: - Checkbox
				 PAGE: - Utils
					Force Freeze  cmdID= 33032 "
		::= { iqdbd01CmdEntry 33032 }


	iqdbd01UtilsFreezeFreezeType OBJECT-TYPE
		SYNTAX		INTEGER {
							val_Frame(0),
							val_Field(1)
							}
		MAX-ACCESS		read-write
		STATUS			current
		DESCRIPTION
				"TYPE: - RadiobuttonList
				 PAGE: - Utils
					Freeze Type  cmdID= 33033
					Frame  value= 0
					Field  value= 1  "
		::= { iqdbd01CmdEntry 33033 }


	iqdbd01UtilsMonochrome OBJECT-TYPE
		SYNTAX		INTEGER { disable(0), enable(1) }
		MAX-ACCESS		read-write
		STATUS			current
		DESCRIPTION
				"TYPE: - Checkbox
				 PAGE: - Utils
					Monochrome  cmdID= 33034 "
		::= { iqdbd01CmdEntry 33034 }


	iqdbd01UtilsMonochromeMonochromeType OBJECT-TYPE
		SYNTAX		INTEGER {
							val_Y_only(0),
							val_C_only(1)
							}
		MAX-ACCESS		read-write
		STATUS			current
		DESCRIPTION
				"TYPE: - RadiobuttonList
				 PAGE: - Utils
					Monochrome Type  cmdID= 33035
					Y only  value= 0
					C only  value= 1  "
		::= { iqdbd01CmdEntry 33035 }


	iqdbd01UtilsVBIBlankingANCMode OBJECT-TYPE
		SYNTAX		INTEGER {
							val_Pass_Input_ANC(0),
							val_Blank_HANC(2),
							val_Blank_All_ANC(1)
							}
		MAX-ACCESS		read-write
		STATUS			current
		DESCRIPTION
				"TYPE: - RadiobuttonList
				 PAGE: - Utils
					ANC Mode  cmdID= 33037
					Pass Input ANC  value= 0
					Blank HANC  value= 2
					Blank All ANC  value= 1  "
		::= { iqdbd01CmdEntry 33037 }


	iqdbd01UtilsVBIBlankingStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
				 PAGE: - Utils
					Standard  cmdID= 37200
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbd01CmdEntry 37200 }


	iqdbd01UtilsVBIBlankingBlankAll OBJECT-TYPE
		SYNTAX		INTEGER { noAction(0),val_Blank_All(1) }
		MAX-ACCESS		read-write
		STATUS			current
		DESCRIPTION
				"TYPE: - Button
				 PAGE: - Utils
					Blank All  cmdID= 37201  value= 1  "
		::= { iqdbd01CmdEntry 37201 }


	iqdbd01UtilsVBIBlankingPassAll OBJECT-TYPE
		SYNTAX		INTEGER { noAction(0),val_Pass_All(1) }
		MAX-ACCESS		read-write
		STATUS			current
		DESCRIPTION
				"TYPE: - Button
				 PAGE: - Utils
					Pass All  cmdID= 37202  value= 1  "
		::= { iqdbd01CmdEntry 37202 }


	iqdbd01UtilsVBIBlankingBlank1 OBJECT-TYPE
		SYNTAX		INTEGER { disable(0), enable(1) }
		MAX-ACCESS		read-write
		STATUS			current
		DESCRIPTION
				"TYPE: - Checkbox
				 PAGE: - Utils
					Blank 1  cmdID= 37210 "
		::= { iqdbd01CmdEntry 37210 }


	iqdbd01UtilsVBIBlankingBlank2 OBJECT-TYPE
		SYNTAX		INTEGER { disable(0), enable(1) }
		MAX-ACCESS		read-write
		STATUS			current
		DESCRIPTION
				"TYPE: - Checkbox
				 PAGE: - Utils
					Blank 2  cmdID= 37211 "
		::= { iqdbd01CmdEntry 37211 }


	iqdbd01UtilsVBIBlankingBlank3 OBJECT-TYPE
		SYNTAX		INTEGER { disable(0), enable(1) }
		MAX-ACCESS		read-write
		STATUS			current
		DESCRIPTION
				"TYPE: - Checkbox
				 PAGE: - Utils
					Blank 3  cmdID= 37212 "
		::= { iqdbd01CmdEntry 37212 }


	iqdbd01UtilsVBIBlankingBlank4 OBJECT-TYPE
		SYNTAX		INTEGER { disable(0), enable(1) }
		MAX-ACCESS		read-write
		STATUS			current
		DESCRIPTION
				"TYPE: - Checkbox
				 PAGE: - Utils
					Blank 4  cmdID= 37213 "
		::= { iqdbd01CmdEntry 37213 }


	iqdbd01UtilsVBIBlankingBlank5 OBJECT-TYPE
		SYNTAX		INTEGER { disable(0), enable(1) }
		MAX-ACCESS		read-write
		STATUS			current
		DESCRIPTION
				"TYPE: - Checkbox
				 PAGE: - Utils
					Blank 5  cmdID= 37214 "
		::= { iqdbd01CmdEntry 37214 }


	iqdbd01UtilsVBIBlankingBlank6 OBJECT-TYPE
		SYNTAX		INTEGER { disable(0), enable(1) }
		MAX-ACCESS		read-write
		STATUS			current
		DESCRIPTION
				"TYPE: - Checkbox
				 PAGE: - Utils
					Blank 6  cmdID= 37215 "
		::= { iqdbd01CmdEntry 37215 }


	iqdbd01UtilsVBIBlankingBlank7 OBJECT-TYPE
		SYNTAX		INTEGER { disable(0), enable(1) }
		MAX-ACCESS		read-write
		STATUS			current
		DESCRIPTION
				"TYPE: - Checkbox
				 PAGE: - Utils
					Blank 7  cmdID= 37216 "
		::= { iqdbd01CmdEntry 37216 }


	iqdbd01UtilsVBIBlankingBlank8 OBJECT-TYPE
		SYNTAX		INTEGER { disable(0), enable(1) }
		MAX-ACCESS		read-write
		STATUS			current
		DESCRIPTION
				"TYPE: - Checkbox
				 PAGE: - Utils
					Blank 8  cmdID= 37217 "
		::= { iqdbd01CmdEntry 37217 }


	iqdbd01UtilsVBIBlankingBlank9 OBJECT-TYPE
		SYNTAX		INTEGER { disable(0), enable(1) }
		MAX-ACCESS		read-write
		STATUS			current
		DESCRIPTION
				"TYPE: - Checkbox
				 PAGE: - Utils
					Blank 9  cmdID= 37218 "
		::= { iqdbd01CmdEntry 37218 }


	iqdbd01UtilsVBIBlankingBlank10 OBJECT-TYPE
		SYNTAX		INTEGER { disable(0), enable(1) }
		MAX-ACCESS		read-write
		STATUS			current
		DESCRIPTION
				"TYPE: - Checkbox
				 PAGE: - Utils
					Blank 10  cmdID= 37219 "
		::= { iqdbd01CmdEntry 37219 }


	iqdbd01UtilsVBIBlankingBlank11 OBJECT-TYPE
		SYNTAX		INTEGER { disable(0), enable(1) }
		MAX-ACCESS		read-write
		STATUS			current
		DESCRIPTION
				"TYPE: - Checkbox
				 PAGE: - Utils
					Blank 11  cmdID= 37220 "
		::= { iqdbd01CmdEntry 37220 }


	iqdbd01UtilsVBIBlankingBlank12 OBJECT-TYPE
		SYNTAX		INTEGER { disable(0), enable(1) }
		MAX-ACCESS		read-write
		STATUS			current
		DESCRIPTION
				"TYPE: - Checkbox
				 PAGE: - Utils
					Blank 12  cmdID= 37221 "
		::= { iqdbd01CmdEntry 37221 }


	iqdbd01UtilsVBIBlankingBlank13 OBJECT-TYPE
		SYNTAX		INTEGER { disable(0), enable(1) }
		MAX-ACCESS		read-write
		STATUS			current
		DESCRIPTION
				"TYPE: - Checkbox
				 PAGE: - Utils
					Blank 13  cmdID= 37222 "
		::= { iqdbd01CmdEntry 37222 }


	iqdbd01UtilsVBIBlankingBlank14 OBJECT-TYPE
		SYNTAX		INTEGER { disable(0), enable(1) }
		MAX-ACCESS		read-write
		STATUS			current
		DESCRIPTION
				"TYPE: - Checkbox
				 PAGE: - Utils
					Blank 14  cmdID= 37223 "
		::= { iqdbd01CmdEntry 37223 }


	iqdbd01UtilsVBIBlankingBlank15 OBJECT-TYPE
		SYNTAX		INTEGER { disable(0), enable(1) }
		MAX-ACCESS		read-write
		STATUS			current
		DESCRIPTION
				"TYPE: - Checkbox
				 PAGE: - Utils
					Blank 15  cmdID= 37224 "
		::= { iqdbd01CmdEntry 37224 }


	iqdbd01UtilsVBIBlankingBlank16 OBJECT-TYPE
		SYNTAX		INTEGER { disable(0), enable(1) }
		MAX-ACCESS		read-write
		STATUS			current
		DESCRIPTION
				"TYPE: - Checkbox
				 PAGE: - Utils
					Blank 16  cmdID= 37225 "
		::= { iqdbd01CmdEntry 37225 }


	iqdbd01UtilsVBIBlankingBlank17 OBJECT-TYPE
		SYNTAX		INTEGER { disable(0), enable(1) }
		MAX-ACCESS		read-write
		STATUS			current
		DESCRIPTION
				"TYPE: - Checkbox
				 PAGE: - Utils
					Blank 17  cmdID= 37226 "
		::= { iqdbd01CmdEntry 37226 }


	iqdbd01UtilsVBIBlankingBlank18 OBJECT-TYPE
		SYNTAX		INTEGER { disable(0), enable(1) }
		MAX-ACCESS		read-write
		STATUS			current
		DESCRIPTION
				"TYPE: - Checkbox
				 PAGE: - Utils
					Blank 18  cmdID= 37227 "
		::= { iqdbd01CmdEntry 37227 }


	iqdbd01UtilsVBIBlankingBlank19 OBJECT-TYPE
		SYNTAX		INTEGER { disable(0), enable(1) }
		MAX-ACCESS		read-write
		STATUS			current
		DESCRIPTION
				"TYPE: - Checkbox
				 PAGE: - Utils
					Blank 19  cmdID= 37228 "
		::= { iqdbd01CmdEntry 37228 }


	iqdbd01UtilsVBIBlankingBlank20 OBJECT-TYPE
		SYNTAX		INTEGER { disable(0), enable(1) }
		MAX-ACCESS		read-write
		STATUS			current
		DESCRIPTION
				"TYPE: - Checkbox
				 PAGE: - Utils
					Blank 20  cmdID= 37229 "
		::= { iqdbd01CmdEntry 37229 }


	iqdbd01UtilsVBIBlankingBlank21 OBJECT-TYPE
		SYNTAX		INTEGER { disable(0), enable(1) }
		MAX-ACCESS		read-write
		STATUS			current
		DESCRIPTION
				"TYPE: - Checkbox
				 PAGE: - Utils
					Blank 21  cmdID= 37230 "
		::= { iqdbd01CmdEntry 37230 }


	iqdbd01UtilsVBIBlankingBlank22 OBJECT-TYPE
		SYNTAX		INTEGER { disable(0), enable(1) }
		MAX-ACCESS		read-write
		STATUS			current
		DESCRIPTION
				"TYPE: - Checkbox
				 PAGE: - Utils
					Blank 22  cmdID= 37231 "
		::= { iqdbd01CmdEntry 37231 }


	iqdbd01UtilsVBIBlankingBlank23 OBJECT-TYPE
		SYNTAX		INTEGER { disable(0), enable(1) }
		MAX-ACCESS		read-write
		STATUS			current
		DESCRIPTION
				"TYPE: - Checkbox
				 PAGE: - Utils
					Blank 23  cmdID= 37232 "
		::= { iqdbd01CmdEntry 37232 }


	iqdbd01UtilsVBIBlankingBlank24 OBJECT-TYPE
		SYNTAX		INTEGER { disable(0), enable(1) }
		MAX-ACCESS		read-write
		STATUS			current
		DESCRIPTION
				"TYPE: - Checkbox
				 PAGE: - Utils
					Blank 24  cmdID= 37233 "
		::= { iqdbd01CmdEntry 37233 }


	iqdbd01UtilsVBIBlankingBlank25 OBJECT-TYPE
		SYNTAX		INTEGER { disable(0), enable(1) }
		MAX-ACCESS		read-write
		STATUS			current
		DESCRIPTION
				"TYPE: - Checkbox
				 PAGE: - Utils
					Blank 25  cmdID= 37234 "
		::= { iqdbd01CmdEntry 37234 }


	iqdbd01UtilsVBIBlankingBlank26 OBJECT-TYPE
		SYNTAX		INTEGER { disable(0), enable(1) }
		MAX-ACCESS		read-write
		STATUS			current
		DESCRIPTION
				"TYPE: - Checkbox
				 PAGE: - Utils
					Blank 26  cmdID= 37235 "
		::= { iqdbd01CmdEntry 37235 }


	iqdbd01UtilsVBIBlankingBlank27 OBJECT-TYPE
		SYNTAX		INTEGER { disable(0), enable(1) }
		MAX-ACCESS		read-write
		STATUS			current
		DESCRIPTION
				"TYPE: - Checkbox
				 PAGE: - Utils
					Blank 27  cmdID= 37236 "
		::= { iqdbd01CmdEntry 37236 }


	iqdbd01UtilsVBIBlankingBlank28 OBJECT-TYPE
		SYNTAX		INTEGER { disable(0), enable(1) }
		MAX-ACCESS		read-write
		STATUS			current
		DESCRIPTION
				"TYPE: - Checkbox
				 PAGE: - Utils
					Blank 28  cmdID= 37237 "
		::= { iqdbd01CmdEntry 37237 }


	iqdbd01UtilsVBIBlankingBlank29 OBJECT-TYPE
		SYNTAX		INTEGER { disable(0), enable(1) }
		MAX-ACCESS		read-write
		STATUS			current
		DESCRIPTION
				"TYPE: - Checkbox
				 PAGE: - Utils
					Blank 29  cmdID= 37238 "
		::= { iqdbd01CmdEntry 37238 }


	iqdbd01UtilsVBIBlankingBlank30 OBJECT-TYPE
		SYNTAX		INTEGER { disable(0), enable(1) }
		MAX-ACCESS		read-write
		STATUS			current
		DESCRIPTION
				"TYPE: - Checkbox
				 PAGE: - Utils
					Blank 30  cmdID= 37239 "
		::= { iqdbd01CmdEntry 37239 }


	iqdbd01UtilsVBIBlankingBlank31 OBJECT-TYPE
		SYNTAX		INTEGER { disable(0), enable(1) }
		MAX-ACCESS		read-write
		STATUS			current
		DESCRIPTION
				"TYPE: - Checkbox
				 PAGE: - Utils
					Blank 31  cmdID= 37240 "
		::= { iqdbd01CmdEntry 37240 }


	iqdbd01UtilsVBIBlankingBlank32 OBJECT-TYPE
		SYNTAX		INTEGER { disable(0), enable(1) }
		MAX-ACCESS		read-write
		STATUS			current
		DESCRIPTION
				"TYPE: - Checkbox
				 PAGE: - Utils
					Blank 32  cmdID= 37241 "
		::= { iqdbd01CmdEntry 37241 }


	iqdbd01UtilsVBIBlankingBlank33 OBJECT-TYPE
		SYNTAX		INTEGER { disable(0), enable(1) }
		MAX-ACCESS		read-write
		STATUS			current
		DESCRIPTION
				"TYPE: - Checkbox
				 PAGE: - Utils
					Blank 33  cmdID= 37242 "
		::= { iqdbd01CmdEntry 37242 }


	iqdbd01UtilsVBIBlankingBlank34 OBJECT-TYPE
		SYNTAX		INTEGER { disable(0), enable(1) }
		MAX-ACCESS		read-write
		STATUS			current
		DESCRIPTION
				"TYPE: - Checkbox
				 PAGE: - Utils
					Blank 34  cmdID= 37243 "
		::= { iqdbd01CmdEntry 37243 }


	iqdbd01RecallMemory OBJECT-TYPE
		SYNTAX		INTEGER {
							val_None_Selected(0),
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Recall Memory  cmdID= 37100
					None Selected  value= 0
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqdbd01CmdEntry 37100 }


	iqdbd01SelMemory OBJECT-TYPE
		SYNTAX		INTEGER {
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Sel Memory  cmdID= 37101
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqdbd01CmdEntry 37101 }


	iqdbd01SaveMemory OBJECT-TYPE
		SYNTAX		INTEGER { noAction(0),val_Save_Memory(1) }
		MAX-ACCESS		read-write
		STATUS			current
		DESCRIPTION
				"TYPE: - Button
				 PAGE: - Memories
					Save Memory  cmdID= 37102  value= 1  "
		::= { iqdbd01CmdEntry 37102 }


	iqdbd01ClearMemory OBJECT-TYPE
		SYNTAX		INTEGER { noAction(0),val_Clear_Memory(1) }
		MAX-ACCESS		read-write
		STATUS			current
		DESCRIPTION
				"TYPE: - Button
				 PAGE: - Memories
					Clear Memory  cmdID= 37105  value= 1  "
		::= { iqdbd01CmdEntry 37105 }


	iqdbd01MemoryNameChangeName OBJECT-TYPE
		SYNTAX		RollCallString
		MAX-ACCESS		read-write
		STATUS			current
		DESCRIPTION
				"TYPE: - Editstring
				 PAGE: - Memories
					Change Name  cmdID= 37103  "
		::= { iqdbd01CmdEntry 37103 }


	iqdbd01MemoryNameLastUserMemory OBJECT-TYPE
		SYNTAX		RollCallString
		MAX-ACCESS		read-only
		STATUS			current
		DESCRIPTION
				"TYPE: - Display
				 PAGE: - Memories
					Last User Memory  cmdID= 37104  format=   "
		::= { iqdbd01CmdEntry 37104 }


	iqdbd01MemoryName1 OBJECT-TYPE
		SYNTAX		RollCallString
		MAX-ACCESS		read-only
		STATUS			current
		DESCRIPTION
				"TYPE: - Display
				 PAGE: - Memories
					Memory Name1  cmdID= 37106  format=   "
		::= { iqdbd01CmdEntry 37106 }


	iqdbd01MemoryName2 OBJECT-TYPE
		SYNTAX		RollCallString
		MAX-ACCESS		read-only
		STATUS			current
		DESCRIPTION
				"TYPE: - Display
				 PAGE: - Memories
					Memory Name2  cmdID= 37107  format=   "
		::= { iqdbd01CmdEntry 37107 }


	iqdbd01MemoryName3 OBJECT-TYPE
		SYNTAX		RollCallString
		MAX-ACCESS		read-only
		STATUS			current
		DESCRIPTION
				"TYPE: - Display
				 PAGE: - Memories
					Memory Name3  cmdID= 37108  format=   "
		::= { iqdbd01CmdEntry 37108 }


	iqdbd01MemoryName4 OBJECT-TYPE
		SYNTAX		RollCallString
		MAX-ACCESS		read-only
		STATUS			current
		DESCRIPTION
				"TYPE: - Display
				 PAGE: - Memories
					Memory Name4  cmdID= 37109  format=   "
		::= { iqdbd01CmdEntry 37109 }


	iqdbd01MemoryName5 OBJECT-TYPE
		SYNTAX		RollCallString
		MAX-ACCESS		read-only
		STATUS			current
		DESCRIPTION
				"TYPE: - Display
				 PAGE: - Memories
					Memory Name5  cmdID= 37110  format=   "
		::= { iqdbd01CmdEntry 37110 }


	iqdbd01MemoryName6 OBJECT-TYPE
		SYNTAX		RollCallString
		MAX-ACCESS		read-only
		STATUS			current
		DESCRIPTION
				"TYPE: - Display
				 PAGE: - Memories
					Memory Name6  cmdID= 37111  format=   "
		::= { iqdbd01CmdEntry 37111 }


	iqdbd01MemoryName7 OBJECT-TYPE
		SYNTAX		RollCallString
		MAX-ACCESS		read-only
		STATUS			current
		DESCRIPTION
				"TYPE: - Display
				 PAGE: - Memories
					Memory Name7  cmdID= 37112  format=   "
		::= { iqdbd01CmdEntry 37112 }


	iqdbd01MemoryName8 OBJECT-TYPE
		SYNTAX		RollCallString
		MAX-ACCESS		read-only
		STATUS			current
		DESCRIPTION
				"TYPE: - Display
				 PAGE: - Memories
					Memory Name8  cmdID= 37113  format=   "
		::= { iqdbd01CmdEntry 37113 }


	iqdbd01MemoryName9 OBJECT-TYPE
		SYNTAX		RollCallString
		MAX-ACCESS		read-only
		STATUS			current
		DESCRIPTION
				"TYPE: - Display
				 PAGE: - Memories
					Memory Name9  cmdID= 37114  format=   "
		::= { iqdbd01CmdEntry 37114 }


	iqdbd01MemoryName10 OBJECT-TYPE
		SYNTAX		RollCallString
		MAX-ACCESS		read-only
		STATUS			current
		DESCRIPTION
				"TYPE: - Display
				 PAGE: - Memories
					Memory Name10  cmdID= 37115  format=   "
		::= { iqdbd01CmdEntry 37115 }


	iqdbd01MemoryName11 OBJECT-TYPE
		SYNTAX		RollCallString
		MAX-ACCESS		read-only
		STATUS			current
		DESCRIPTION
				"TYPE: - Display
				 PAGE: - Memories
					Memory Name11  cmdID= 37116  format=   "
		::= { iqdbd01CmdEntry 37116 }


	iqdbd01MemoryName12 OBJECT-TYPE
		SYNTAX		RollCallString
		MAX-ACCESS		read-only
		STATUS			current
		DESCRIPTION
				"TYPE: - Display
				 PAGE: - Memories
					Memory Name12  cmdID= 37117  format=   "
		::= { iqdbd01CmdEntry 37117 }


	iqdbd01MemoryName13 OBJECT-TYPE
		SYNTAX		RollCallString
		MAX-ACCESS		read-only
		STATUS			current
		DESCRIPTION
				"TYPE: - Display
				 PAGE: - Memories
					Memory Name13  cmdID= 37118  format=   "
		::= { iqdbd01CmdEntry 37118 }


	iqdbd01MemoryName14 OBJECT-TYPE
		SYNTAX		RollCallString
		MAX-ACCESS		read-only
		STATUS			current
		DESCRIPTION
				"TYPE: - Display
				 PAGE: - Memories
					Memory Name14  cmdID= 37119  format=   "
		::= { iqdbd01CmdEntry 37119 }


	iqdbd01MemoryName15 OBJECT-TYPE
		SYNTAX		RollCallString
		MAX-ACCESS		read-only
		STATUS			current
		DESCRIPTION
				"TYPE: - Display
				 PAGE: - Memories
					Memory Name15  cmdID= 37120  format=   "
		::= { iqdbd01CmdEntry 37120 }


	iqdbd01MemoryName16 OBJECT-TYPE
		SYNTAX		RollCallString
		MAX-ACCESS		read-only
		STATUS			current
		DESCRIPTION
				"TYPE: - Display
				 PAGE: - Memories
					Memory Name16  cmdID= 37121  format=   "
		::= { iqdbd01CmdEntry 37121 }


	iqdbd01LoggingVideoLoggingLogInput1Type OBJECT-TYPE
		SYNTAX		INTEGER { disable(0), enable(1) }
		MAX-ACCESS		read-write
		STATUS			current
		DESCRIPTION
				"TYPE: - Checkbox
				 PAGE: - RollCall- Logging
					Log Input 1 Type  cmdID= 35017 "
		::= { iqdbd01CmdEntry 35017 }


	iqdbd01LoggingVideoLoggingInput1Type OBJECT-TYPE
		SYNTAX		RollCallString
		MAX-ACCESS		read-only
		STATUS			current
		DESCRIPTION
				"TYPE: - Display
				 PAGE: - RollCall- Logging
					Input 1 Type=  cmdID= 36017  format=   "
		::= { iqdbd01CmdEntry 36017 }


	iqdbd01LoggingVideoLoggingLogInput1Status OBJECT-TYPE
		SYNTAX		INTEGER { disable(0), enable(1) }
		MAX-ACCESS		read-write
		STATUS			current
		DESCRIPTION
				"TYPE: - Checkbox
				 PAGE: - RollCall- Logging
					Log Input 1 Status  cmdID= 35005 "
		::= { iqdbd01CmdEntry 35005 }


	iqdbd01LoggingVideoLoggingInput1Status OBJECT-TYPE
		SYNTAX		RollCallString
		MAX-ACCESS		read-only
		STATUS			current
		DESCRIPTION
				"TYPE: - Display
				 PAGE: - RollCall- Logging
					Input 1 Status=  cmdID= 36005  format=   "
		::= { iqdbd01CmdEntry 36005 }


	iqdbd01LoggingVideoLoggingLogInput1Std OBJECT-TYPE
		SYNTAX		INTEGER { disable(0), enable(1) }
		MAX-ACCESS		read-write
		STATUS			current
		DESCRIPTION
				"TYPE: - Checkbox
				 PAGE: - RollCall- Logging
					Log Input 1 Std.  cmdID= 35016 "
		::= { iqdbd01CmdEntry 35016 }


	iqdbd01LoggingVideoLoggingInput1Std OBJECT-TYPE
		SYNTAX		RollCallString
		MAX-ACCESS		read-only
		STATUS			current
		DESCRIPTION
				"TYPE: - Display
				 PAGE: - RollCall- Logging
					Input 1 Std.=  cmdID= 36016  format=   "
		::= { iqdbd01CmdEntry 36016 }


	iqdbd01LoggingVideoLoggingLogInput1Errors OBJECT-TYPE
		SYNTAX		INTEGER { disable(0), enable(1) }
		MAX-ACCESS		read-write
		STATUS			current
		DESCRIPTION
				"TYPE: - Checkbox
				 PAGE: - RollCall- Logging
					Log Input 1 Errors  cmdID= 35002 "
		::= { iqdbd01CmdEntry 35002 }


	iqdbd01LoggingVideoLoggingInput1Errors OBJECT-TYPE
		SYNTAX		RollCallString
		MAX-ACCESS		read-only
		STATUS			current
		DESCRIPTION
				"TYPE: - Display
				 PAGE: - RollCall- Logging
					Input 1 Errors=  cmdID= 36002  format=   "
		::= { iqdbd01CmdEntry 36002 }


	iqdbd01LoggingVideoLoggingLogInput1ErrSecs OBJECT-TYPE
		SYNTAX		INTEGER { disable(0), enable(1) }
		MAX-ACCESS		read-write
		STATUS			current
		DESCRIPTION
				"TYPE: - Checkbox
				 PAGE: - RollCall- Logging
					Log Input 1 ErrSecs  cmdID= 35003 "
		::= { iqdbd01CmdEntry 35003 }


	iqdbd01LoggingVideoLoggingInput1ErrSecs OBJECT-TYPE
		SYNTAX		RollCallString
		MAX-ACCESS		read-only
		STATUS			current
		DESCRIPTION
				"TYPE: - Display
				 PAGE: - RollCall- Logging
					Input 1 ErrSecs=  cmdID= 36003  format=   "
		::= { iqdbd01CmdEntry 36003 }


	iqdbd01LoggingVideoLoggingLogInput1ANCErr OBJECT-TYPE
		SYNTAX		INTEGER { disable(0), enable(1) }
		MAX-ACCESS		read-write
		STATUS			current
		DESCRIPTION
				"TYPE: - Checkbox
				 PAGE: - RollCall- Logging
					Log Input 1 ANC Err  cmdID= 35000 "
		::= { iqdbd01CmdEntry 35000 }


	iqdbd01LoggingVideoLoggingInput1ANCErrors OBJECT-TYPE
		SYNTAX		RollCallString
		MAX-ACCESS		read-only
		STATUS			current
		DESCRIPTION
				"TYPE: - Display
				 PAGE: - RollCall- Logging
					Input 1 ANC Errors=  cmdID= 36000  format=   "
		::= { iqdbd01CmdEntry 36000 }


	iqdbd01LoggingVideoLoggingLogInput1ANCErrSec OBJECT-TYPE
		SYNTAX		INTEGER { disable(0), enable(1) }
		MAX-ACCESS		read-write
		STATUS			current
		DESCRIPTION
				"TYPE: - Checkbox
				 PAGE: - RollCall- Logging
					Log Input 1 ANC Err  cmdID= 35001 "
		::= { iqdbd01CmdEntry 35001 }


	iqdbd01LoggingVideoLoggingInput1ANCErrSecs OBJECT-TYPE
		SYNTAX		RollCallString
		MAX-ACCESS		read-only
		STATUS			current
		DESCRIPTION
				"TYPE: - Display
				 PAGE: - RollCall- Logging
					Input 1 ANC ErrSecs  cmdID= 36001  format=   "
		::= { iqdbd01CmdEntry 36001 }


	iqdbd01LoggingVideoLoggingLogOutputState OBJECT-TYPE
		SYNTAX		INTEGER { disable(0), enable(1) }
		MAX-ACCESS		read-write
		STATUS			current
		DESCRIPTION
				"TYPE: - Checkbox
				 PAGE: - RollCall- Logging
					Log Output State  cmdID= 35941 "
		::= { iqdbd01CmdEntry 35941 }


	iqdbd01LoggingVideoLoggingOutputState OBJECT-TYPE
		SYNTAX		RollCallString
		MAX-ACCESS		read-only
		STATUS			current
		DESCRIPTION
				"TYPE: - Display
				 PAGE: - RollCall- Logging
					Output State=  cmdID= 36941  format=   "
		::= { iqdbd01CmdEntry 36941 }


	iqdbd01LoggingVideoLoggingLogOutputType OBJECT-TYPE
		SYNTAX		INTEGER { disable(0), enable(1) }
		MAX-ACCESS		read-write
		STATUS			current
		DESCRIPTION
				"TYPE: - Checkbox
				 PAGE: - RollCall- Logging
					Log Output Type  cmdID= 35942 "
		::= { iqdbd01CmdEntry 35942 }


	iqdbd01LoggingVideoLoggingOutputType OBJECT-TYPE
		SYNTAX		RollCallString
		MAX-ACCESS		read-only
		STATUS			current
		DESCRIPTION
				"TYPE: - Display
				 PAGE: - RollCall- Logging
					Output Type=  cmdID= 36942  format=   "
		::= { iqdbd01CmdEntry 36942 }


	iqdbd01LoggingVideoLoggingLogOutputStandard OBJECT-TYPE
		SYNTAX		INTEGER { disable(0), enable(1) }
		MAX-ACCESS		read-write
		STATUS			current
		DESCRIPTION
				"TYPE: - Checkbox
				 PAGE: - RollCall- Logging
					Log Output Standard  cmdID= 35940 "
		::= { iqdbd01CmdEntry 35940 }


	iqdbd01LoggingVideoLoggingOutputStandard OBJECT-TYPE
		SYNTAX		RollCallString
		MAX-ACCESS		read-only
		STATUS			current
		DESCRIPTION
				"TYPE: - Display
				 PAGE: - RollCall- Logging
					Output Standard=  cmdID= 36940  format=   "
		::= { iqdbd01CmdEntry 36940 }


	iqdbd01LoggingVideoLoggingLogoutputANCstat OBJECT-TYPE
		SYNTAX		INTEGER { disable(0), enable(1) }
		MAX-ACCESS		read-write
		STATUS			current
		DESCRIPTION
				"TYPE: - Checkbox
				 PAGE: - RollCall- Logging
					Log output ANC stat  cmdID= 35946 "
		::= { iqdbd01CmdEntry 35946 }


	iqdbd01LoggingVideoLoggingOutputANCstate OBJECT-TYPE
		SYNTAX		RollCallString
		MAX-ACCESS		read-only
		STATUS			current
		DESCRIPTION
				"TYPE: - Display
				 PAGE: - RollCall- Logging
					Output ANC state=  cmdID= 36946  format=   "
		::= { iqdbd01CmdEntry 36946 }


	iqdbd01LoggingEmbAudLoggingLogInp1Emb1stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 stat  cmdID= 35006 "
		::= { iqdbd01CmdEntry 35006 }


	iqdbd01LoggingEmbAudLoggingInp1Emb1state OBJECT-TYPE
		SYNTAX		RollCallString
		MAX-ACCESS		read-only
		STATUS			current
		DESCRIPTION
				"TYPE: - Display
				 PAGE: - RollCall- Logging- Emb.Aud Logging
					Inp1 Emb.1 state=  cmdID= 36006  format=   "
		::= { iqdbd01CmdEntry 36006 }


	iqdbd01LoggingEmbAudLoggingLogInp1Emb2stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 stat  cmdID= 35007 "
		::= { iqdbd01CmdEntry 35007 }


	iqdbd01LoggingEmbAudLoggingInp1Emb2state OBJECT-TYPE
		SYNTAX		RollCallString
		MAX-ACCESS		read-only
		STATUS			current
		DESCRIPTION
				"TYPE: - Display
				 PAGE: - RollCall- Logging- Emb.Aud Logging
					Inp1 Emb.2 state=  cmdID= 36007  format=   "
		::= { iqdbd01CmdEntry 36007 }


	iqdbd01LoggingEmbAudLoggingLogInp1Emb3stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 stat  cmdID= 35008 "
		::= { iqdbd01CmdEntry 35008 }


	iqdbd01LoggingEmbAudLoggingInp1Emb3state OBJECT-TYPE
		SYNTAX		RollCallString
		MAX-ACCESS		read-only
		STATUS			current
		DESCRIPTION
				"TYPE: - Display
				 PAGE: - RollCall- Logging- Emb.Aud Logging
					Inp1 Emb.3 state=  cmdID= 36008  format=   "
		::= { iqdbd01CmdEntry 36008 }


	iqdbd01LoggingEmbAudLoggingLogInp1Emb4stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 stat  cmdID= 35009 "
		::= { iqdbd01CmdEntry 35009 }


	iqdbd01LoggingEmbAudLoggingInp1Emb4state OBJECT-TYPE
		SYNTAX		RollCallString
		MAX-ACCESS		read-only
		STATUS			current
		DESCRIPTION
				"TYPE: - Display
				 PAGE: - RollCall- Logging- Emb.Aud Logging
					Inp1 Emb.4 state=  cmdID= 36009  format=   "
		::= { iqdbd01CmdEntry 36009 }


	iqdbd01LoggingEmbAudLoggingLogInp1Emb5stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 stat  cmdID= 35010 "
		::= { iqdbd01CmdEntry 35010 }


	iqdbd01LoggingEmbAudLoggingInp1Emb5state OBJECT-TYPE
		SYNTAX		RollCallString
		MAX-ACCESS		read-only
		STATUS			current
		DESCRIPTION
				"TYPE: - Display
				 PAGE: - RollCall- Logging- Emb.Aud Logging
					Inp1 Emb.5 state=  cmdID= 36010  format=   "
		::= { iqdbd01CmdEntry 36010 }


	iqdbd01LoggingEmbAudLoggingLogInp1Emb6stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 stat  cmdID= 35011 "
		::= { iqdbd01CmdEntry 35011 }


	iqdbd01LoggingEmbAudLoggingInp1Emb6state OBJECT-TYPE
		SYNTAX		RollCallString
		MAX-ACCESS		read-only
		STATUS			current
		DESCRIPTION
				"TYPE: - Display
				 PAGE: - RollCall- Logging- Emb.Aud Logging
					Inp1 Emb.6 state=  cmdID= 36011  format=   "
		::= { iqdbd01CmdEntry 36011 }


	iqdbd01LoggingEmbAudLoggingLogInp1Emb7stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 stat  cmdID= 35012 "
		::= { iqdbd01CmdEntry 35012 }


	iqdbd01LoggingEmbAudLoggingInp1Emb7state OBJECT-TYPE
		SYNTAX		RollCallString
		MAX-ACCESS		read-only
		STATUS			current
		DESCRIPTION
				"TYPE: - Display
				 PAGE: - RollCall- Logging- Emb.Aud Logging
					Inp1 Emb.7 state=  cmdID= 36012  format=   "
		::= { iqdbd01CmdEntry 36012 }


	iqdbd01LoggingEmbAudLoggingLogInp1Emb8stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 stat  cmdID= 35013 "
		::= { iqdbd01CmdEntry 35013 }


	iqdbd01LoggingEmbAudLoggingInp1Emb8state OBJECT-TYPE
		SYNTAX		RollCallString
		MAX-ACCESS		read-only
		STATUS			current
		DESCRIPTION
				"TYPE: - Display
				 PAGE: - RollCall- Logging- Emb.Aud Logging
					Inp1 Emb.8 state=  cmdID= 36013  format=   "
		::= { iqdbd01CmdEntry 36013 }


	iqdbd01LoggingEmbAudLoggingLogInp1Emb1type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 type  cmdID= 35018 "
		::= { iqdbd01CmdEntry 35018 }


	iqdbd01LoggingEmbAudLoggingInp1Emb1type OBJECT-TYPE
		SYNTAX		RollCallString
		MAX-ACCESS		read-only
		STATUS			current
		DESCRIPTION
				"TYPE: - Display
				 PAGE: - RollCall- Logging- Emb.Aud Logging
					Inp1 Emb.1 type=  cmdID= 36018  format=   "
		::= { iqdbd01CmdEntry 36018 }


	iqdbd01LoggingEmbAudLoggingLogInp1Emb2type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 type  cmdID= 35019 "
		::= { iqdbd01CmdEntry 35019 }


	iqdbd01LoggingEmbAudLoggingInp1Emb2type OBJECT-TYPE
		SYNTAX		RollCallString
		MAX-ACCESS		read-only
		STATUS			current
		DESCRIPTION
				"TYPE: - Display
				 PAGE: - RollCall- Logging- Emb.Aud Logging
					Inp1 Emb.2 type=  cmdID= 36019  format=   "
		::= { iqdbd01CmdEntry 36019 }


	iqdbd01LoggingEmbAudLoggingLogInp1Emb3type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 type  cmdID= 35020 "
		::= { iqdbd01CmdEntry 35020 }


	iqdbd01LoggingEmbAudLoggingInp1Emb3type OBJECT-TYPE
		SYNTAX		RollCallString
		MAX-ACCESS		read-only
		STATUS			current
		DESCRIPTION
				"TYPE: - Display
				 PAGE: - RollCall- Logging- Emb.Aud Logging
					Inp1 Emb.3 type=  cmdID= 36020  format=   "
		::= { iqdbd01CmdEntry 36020 }


	iqdbd01LoggingEmbAudLoggingLogInp1Emb4type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 type  cmdID= 35021 "
		::= { iqdbd01CmdEntry 35021 }


	iqdbd01LoggingEmbAudLoggingInp1Emb4type OBJECT-TYPE
		SYNTAX		RollCallString
		MAX-ACCESS		read-only
		STATUS			current
		DESCRIPTION
				"TYPE: - Display
				 PAGE: - RollCall- Logging- Emb.Aud Logging
					Inp1 Emb.4 type=  cmdID= 36021  format=   "
		::= { iqdbd01CmdEntry 36021 }


	iqdbd01LoggingEmbAudLoggingLogInp1Emb5type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 type  cmdID= 35022 "
		::= { iqdbd01CmdEntry 35022 }


	iqdbd01LoggingEmbAudLoggingInp1Emb5type OBJECT-TYPE
		SYNTAX		RollCallString
		MAX-ACCESS		read-only
		STATUS			current
		DESCRIPTION
				"TYPE: - Display
				 PAGE: - RollCall- Logging- Emb.Aud Logging
					Inp1 Emb.5 type=  cmdID= 36022  format=   "
		::= { iqdbd01CmdEntry 36022 }


	iqdbd01LoggingEmbAudLoggingLogInp1Emb6type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 type  cmdID= 35023 "
		::= { iqdbd01CmdEntry 35023 }


	iqdbd01LoggingEmbAudLoggingInp1Emb6type OBJECT-TYPE
		SYNTAX		RollCallString
		MAX-ACCESS		read-only
		STATUS			current
		DESCRIPTION
				"TYPE: - Display
				 PAGE: - RollCall- Logging- Emb.Aud Logging
					Inp1 Emb.6 type=  cmdID= 36023  format=   "
		::= { iqdbd01CmdEntry 36023 }


	iqdbd01LoggingEmbAudLoggingLogInp1Emb7type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 type  cmdID= 35024 "
		::= { iqdbd01CmdEntry 35024 }


	iqdbd01LoggingEmbAudLoggingInp1Emb7type OBJECT-TYPE
		SYNTAX		RollCallString
		MAX-ACCESS		read-only
		STATUS			current
		DESCRIPTION
				"TYPE: - Display
				 PAGE: - RollCall- Logging- Emb.Aud Logging
					Inp1 Emb.7 type=  cmdID= 36024  format=   "
		::= { iqdbd01CmdEntry 36024 }


	iqdbd01LoggingEmbAudLoggingLogInp1Emb8type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 type  cmdID= 35025 "
		::= { iqdbd01CmdEntry 35025 }


	iqdbd01LoggingEmbAudLoggingInp1Emb8type OBJECT-TYPE
		SYNTAX		RollCallString
		MAX-ACCESS		read-only
		STATUS			current
		DESCRIPTION
				"TYPE: - Display
				 PAGE: - RollCall- Logging- Emb.Aud Logging
					Inp1 Emb.8 type=  cmdID= 36025  format=   "
		::= { iqdbd01CmdEntry 36025 }


	iqdbd01LoggingOPAudLoggingLogOutEmb1state OBJECT-TYPE
		SYNTAX		INTEGER { disable(0), enable(1) }
		MAX-ACCESS		read-write
		STATUS			current
		DESCRIPTION
				"TYPE: - Checkbox
				 PAGE: - RollCall- Logging
					Log Out Emb.1 state  cmdID= 35920 "
		::= { iqdbd01CmdEntry 35920 }


	iqdbd01LoggingOPAudLoggingOutEmb1state OBJECT-TYPE
		SYNTAX		RollCallString
		MAX-ACCESS		read-only
		STATUS			current
		DESCRIPTION
				"TYPE: - Display
				 PAGE: - RollCall- Logging
					Out Emb.1 state=  cmdID= 36920  format=   "
		::= { iqdbd01CmdEntry 36920 }


	iqdbd01LoggingOPAudLoggingLogOutEmb2state OBJECT-TYPE
		SYNTAX		INTEGER { disable(0), enable(1) }
		MAX-ACCESS		read-write
		STATUS			current
		DESCRIPTION
				"TYPE: - Checkbox
				 PAGE: - RollCall- Logging
					Log Out Emb.2 state  cmdID= 35921 "
		::= { iqdbd01CmdEntry 35921 }


	iqdbd01LoggingOPAudLoggingOutEmb2state OBJECT-TYPE
		SYNTAX		RollCallString
		MAX-ACCESS		read-only
		STATUS			current
		DESCRIPTION
				"TYPE: - Display
				 PAGE: - RollCall- Logging
					Out Emb.2 state=  cmdID= 36921  format=   "
		::= { iqdbd01CmdEntry 36921 }


	iqdbd01LoggingOPAudLoggingLogOutEmb3state OBJECT-TYPE
		SYNTAX		INTEGER { disable(0), enable(1) }
		MAX-ACCESS		read-write
		STATUS			current
		DESCRIPTION
				"TYPE: - Checkbox
				 PAGE: - RollCall- Logging
					Log Out Emb.3 state  cmdID= 35922 "
		::= { iqdbd01CmdEntry 35922 }


	iqdbd01LoggingOPAudLoggingOutEmb3state OBJECT-TYPE
		SYNTAX		RollCallString
		MAX-ACCESS		read-only
		STATUS			current
		DESCRIPTION
				"TYPE: - Display
				 PAGE: - RollCall- Logging
					Out Emb.3 state=  cmdID= 36922  format=   "
		::= { iqdbd01CmdEntry 36922 }


	iqdbd01LoggingOPAudLoggingLogOutEmb4state OBJECT-TYPE
		SYNTAX		INTEGER { disable(0), enable(1) }
		MAX-ACCESS		read-write
		STATUS			current
		DESCRIPTION
				"TYPE: - Checkbox
				 PAGE: - RollCall- Logging
					Log Out Emb.4 state  cmdID= 35923 "
		::= { iqdbd01CmdEntry 35923 }


	iqdbd01LoggingOPAudLoggingOutEmb4state OBJECT-TYPE
		SYNTAX		RollCallString
		MAX-ACCESS		read-only
		STATUS			current
		DESCRIPTION
				"TYPE: - Display
				 PAGE: - RollCall- Logging
					Out Emb.4 state=  cmdID= 36923  format=   "
		::= { iqdbd01CmdEntry 36923 }


	iqdbd01LoggingOPAudLoggingLogOutEmb5state OBJECT-TYPE
		SYNTAX		INTEGER { disable(0), enable(1) }
		MAX-ACCESS		read-write
		STATUS			current
		DESCRIPTION
				"TYPE: - Checkbox
				 PAGE: - RollCall- Logging
					Log Out Emb.5 state  cmdID= 35924 "
		::= { iqdbd01CmdEntry 35924 }


	iqdbd01LoggingOPAudLoggingOutEmb5state OBJECT-TYPE
		SYNTAX		RollCallString
		MAX-ACCESS		read-only
		STATUS			current
		DESCRIPTION
				"TYPE: - Display
				 PAGE: - RollCall- Logging
					Out Emb.5 state=  cmdID= 36924  format=   "
		::= { iqdbd01CmdEntry 36924 }


	iqdbd01LoggingOPAudLoggingLogOutEmb6state OBJECT-TYPE
		SYNTAX		INTEGER { disable(0), enable(1) }
		MAX-ACCESS		read-write
		STATUS			current
		DESCRIPTION
				"TYPE: - Checkbox
				 PAGE: - RollCall- Logging
					Log Out Emb.6 state  cmdID= 35925 "
		::= { iqdbd01CmdEntry 35925 }


	iqdbd01LoggingOPAudLoggingOutEmb6state OBJECT-TYPE
		SYNTAX		RollCallString
		MAX-ACCESS		read-only
		STATUS			current
		DESCRIPTION
				"TYPE: - Display
				 PAGE: - RollCall- Logging
					Out Emb.6 state=  cmdID= 36925  format=   "
		::= { iqdbd01CmdEntry 36925 }


	iqdbd01LoggingOPAudLoggingLogOutEmb7state OBJECT-TYPE
		SYNTAX		INTEGER { disable(0), enable(1) }
		MAX-ACCESS		read-write
		STATUS			current
		DESCRIPTION
				"TYPE: - Checkbox
				 PAGE: - RollCall- Logging
					Log Out Emb.7 state  cmdID= 35926 "
		::= { iqdbd01CmdEntry 35926 }


	iqdbd01LoggingOPAudLoggingOutEmb7state OBJECT-TYPE
		SYNTAX		RollCallString
		MAX-ACCESS		read-only
		STATUS			current
		DESCRIPTION
				"TYPE: - Display
				 PAGE: - RollCall- Logging
					Out Emb.7 state=  cmdID= 36926  format=   "
		::= { iqdbd01CmdEntry 36926 }


	iqdbd01LoggingOPAudLoggingLogOutEmb8state OBJECT-TYPE
		SYNTAX		INTEGER { disable(0), enable(1) }
		MAX-ACCESS		read-write
		STATUS			current
		DESCRIPTION
				"TYPE: - Checkbox
				 PAGE: - RollCall- Logging
					Log Out Emb.8 state  cmdID= 35927 "
		::= { iqdbd01CmdEntry 35927 }


	iqdbd01LoggingOPAudLoggingOutEmb8state OBJECT-TYPE
		SYNTAX		RollCallString
		MAX-ACCESS		read-only
		STATUS			current
		DESCRIPTION
				"TYPE: - Display
				 PAGE: - RollCall- Logging
					Out Emb.8 state=  cmdID= 36927  format=   "
		::= { iqdbd01CmdEntry 36927 }


	iqdbd01LoggingOPAudLoggingLogOutEmb1type OBJECT-TYPE
		SYNTAX		INTEGER { disable(0), enable(1) }
		MAX-ACCESS		read-write
		STATUS			current
		DESCRIPTION
				"TYPE: - Checkbox
				 PAGE: - RollCall- Logging
					Log Out Emb.1 type  cmdID= 35930 "
		::= { iqdbd01CmdEntry 35930 }


	iqdbd01LoggingOPAudLoggingOutEmb1type OBJECT-TYPE
		SYNTAX		RollCallString
		MAX-ACCESS		read-only
		STATUS			current
		DESCRIPTION
				"TYPE: - Display
				 PAGE: - RollCall- Logging
					Out Emb.1 type=  cmdID= 36930  format=   "
		::= { iqdbd01CmdEntry 36930 }


	iqdbd01LoggingOPAudLoggingLogOutEmb2type OBJECT-TYPE
		SYNTAX		INTEGER { disable(0), enable(1) }
		MAX-ACCESS		read-write
		STATUS			current
		DESCRIPTION
				"TYPE: - Checkbox
				 PAGE: - RollCall- Logging
					Log Out Emb.2 type  cmdID= 35931 "
		::= { iqdbd01CmdEntry 35931 }


	iqdbd01LoggingOPAudLoggingOutEmb2type OBJECT-TYPE
		SYNTAX		RollCallString
		MAX-ACCESS		read-only
		STATUS			current
		DESCRIPTION
				"TYPE: - Display
				 PAGE: - RollCall- Logging
					Out Emb.2 type=  cmdID= 36931  format=   "
		::= { iqdbd01CmdEntry 36931 }


	iqdbd01LoggingOPAudLoggingLogOutEmb3type OBJECT-TYPE
		SYNTAX		INTEGER { disable(0), enable(1) }
		MAX-ACCESS		read-write
		STATUS			current
		DESCRIPTION
				"TYPE: - Checkbox
				 PAGE: - RollCall- Logging
					Log Out Emb.3 type  cmdID= 35932 "
		::= { iqdbd01CmdEntry 35932 }


	iqdbd01LoggingOPAudLoggingOutEmb3type OBJECT-TYPE
		SYNTAX		RollCallString
		MAX-ACCESS		read-only
		STATUS			current
		DESCRIPTION
				"TYPE: - Display
				 PAGE: - RollCall- Logging
					Out Emb.3 type=  cmdID= 36932  format=   "
		::= { iqdbd01CmdEntry 36932 }


	iqdbd01LoggingOPAudLoggingLogOutEmb4type OBJECT-TYPE
		SYNTAX		INTEGER { disable(0), enable(1) }
		MAX-ACCESS		read-write
		STATUS			current
		DESCRIPTION
				"TYPE: - Checkbox
				 PAGE: - RollCall- Logging
					Log Out Emb.4 type  cmdID= 35933 "
		::= { iqdbd01CmdEntry 35933 }


	iqdbd01LoggingOPAudLoggingOutEmb4type OBJECT-TYPE
		SYNTAX		RollCallString
		MAX-ACCESS		read-only
		STATUS			current
		DESCRIPTION
				"TYPE: - Display
				 PAGE: - RollCall- Logging
					Out Emb.4 type=  cmdID= 36933  format=   "
		::= { iqdbd01CmdEntry 36933 }


	iqdbd01LoggingOPAudLoggingLogOutEmb5type OBJECT-TYPE
		SYNTAX		INTEGER { disable(0), enable(1) }
		MAX-ACCESS		read-write
		STATUS			current
		DESCRIPTION
				"TYPE: - Checkbox
				 PAGE: - RollCall- Logging
					Log Out Emb.5 type  cmdID= 35934 "
		::= { iqdbd01CmdEntry 35934 }


	iqdbd01LoggingOPAudLoggingOutEmb5type OBJECT-TYPE
		SYNTAX		RollCallString
		MAX-ACCESS		read-only
		STATUS			current
		DESCRIPTION
				"TYPE: - Display
				 PAGE: - RollCall- Logging
					Out Emb.5 type=  cmdID= 36934  format=   "
		::= { iqdbd01CmdEntry 36934 }


	iqdbd01LoggingOPAudLoggingLogOutEmb6type OBJECT-TYPE
		SYNTAX		INTEGER { disable(0), enable(1) }
		MAX-ACCESS		read-write
		STATUS			current
		DESCRIPTION
				"TYPE: - Checkbox
				 PAGE: - RollCall- Logging
					Log Out Emb.6 type  cmdID= 35935 "
		::= { iqdbd01CmdEntry 35935 }


	iqdbd01LoggingOPAudLoggingOutEmb6type OBJECT-TYPE
		SYNTAX		RollCallString
		MAX-ACCESS		read-only
		STATUS			current
		DESCRIPTION
				"TYPE: - Display
				 PAGE: - RollCall- Logging
					Out Emb.6 type=  cmdID= 36935  format=   "
		::= { iqdbd01CmdEntry 36935 }


	iqdbd01LoggingOPAudLoggingLogOutEmb7type OBJECT-TYPE
		SYNTAX		INTEGER { disable(0), enable(1) }
		MAX-ACCESS		read-write
		STATUS			current
		DESCRIPTION
				"TYPE: - Checkbox
				 PAGE: - RollCall- Logging
					Log Out Emb.7 type  cmdID= 35936 "
		::= { iqdbd01CmdEntry 35936 }


	iqdbd01LoggingOPAudLoggingOutEmb7type OBJECT-TYPE
		SYNTAX		RollCallString
		MAX-ACCESS		read-only
		STATUS			current
		DESCRIPTION
				"TYPE: - Display
				 PAGE: - RollCall- Logging
					Out Emb.7 type=  cmdID= 36936  format=   "
		::= { iqdbd01CmdEntry 36936 }


	iqdbd01LoggingOPAudLoggingLogOutEmb8type OBJECT-TYPE
		SYNTAX		INTEGER { disable(0), enable(1) }
		MAX-ACCESS		read-write
		STATUS			current
		DESCRIPTION
				"TYPE: - Checkbox
				 PAGE: - RollCall- Logging
					Log Out Emb.8 type  cmdID= 35937 "
		::= { iqdbd01CmdEntry 35937 }


	iqdbd01LoggingOPAudLoggingOutEmb8type OBJECT-TYPE
		SYNTAX		RollCallString
		MAX-ACCESS		read-only
		STATUS			current
		DESCRIPTION
				"TYPE: - Display
				 PAGE: - RollCall- Logging
					Out Emb.8 type=  cmdID= 36937  format=   "
		::= { iqdbd01CmdEntry 36937 }


	iqdbd01LoggingOPAudLevelLoggiLogOutEmb1LLev OBJECT-TYPE
		SYNTAX		INTEGER { disable(0), enable(1) }
		MAX-ACCESS		read-write
		STATUS			current
		DESCRIPTION
				"TYPE: - Checkbox
				 PAGE: - RollCall- Logging
					Log Out Emb.1-L Lev  cmdID= 35900 "
		::= { iqdbd01CmdEntry 35900 }


	iqdbd01LoggingOPAudLevelLoggiOutEmb1LLevel OBJECT-TYPE
		SYNTAX		RollCallString
		MAX-ACCESS		read-only
		STATUS			current
		DESCRIPTION
				"TYPE: - Display
				 PAGE: - RollCall- Logging
					Out Emb.1-L Level=  cmdID= 36900  format=   "
		::= { iqdbd01CmdEntry 36900 }


	iqdbd01LoggingOPAudLevelLoggiLogOutEmb1RLev OBJECT-TYPE
		SYNTAX		INTEGER { disable(0), enable(1) }
		MAX-ACCESS		read-write
		STATUS			current
		DESCRIPTION
				"TYPE: - Checkbox
				 PAGE: - RollCall- Logging
					Log Out Emb.1-R Lev  cmdID= 35901 "
		::= { iqdbd01CmdEntry 35901 }


	iqdbd01LoggingOPAudLevelLoggiOutEmb1RLevel OBJECT-TYPE
		SYNTAX		RollCallString
		MAX-ACCESS		read-only
		STATUS			current
		DESCRIPTION
				"TYPE: - Display
				 PAGE: - RollCall- Logging
					Out Emb.1-R Level=  cmdID= 36901  format=   "
		::= { iqdbd01CmdEntry 36901 }


	iqdbd01LoggingOPAudLevelLoggiLogOutEmb2LLev OBJECT-TYPE
		SYNTAX		INTEGER { disable(0), enable(1) }
		MAX-ACCESS		read-write
		STATUS			current
		DESCRIPTION
				"TYPE: - Checkbox
				 PAGE: - RollCall- Logging
					Log Out Emb.2-L Lev  cmdID= 35902 "
		::= { iqdbd01CmdEntry 35902 }


	iqdbd01LoggingOPAudLevelLoggiOutEmb2LLevel OBJECT-TYPE
		SYNTAX		RollCallString
		MAX-ACCESS		read-only
		STATUS			current
		DESCRIPTION
				"TYPE: - Display
				 PAGE: - RollCall- Logging
					Out Emb.2-L Level=  cmdID= 36902  format=   "
		::= { iqdbd01CmdEntry 36902 }


	iqdbd01LoggingOPAudLevelLoggiLogOutEmb2RLev OBJECT-TYPE
		SYNTAX		INTEGER { disable(0), enable(1) }
		MAX-ACCESS		read-write
		STATUS			current
		DESCRIPTION
				"TYPE: - Checkbox
				 PAGE: - RollCall- Logging
					Log Out Emb.2-R Lev  cmdID= 35903 "
		::= { iqdbd01CmdEntry 35903 }


	iqdbd01LoggingOPAudLevelLoggiOutEmb2RLevel OBJECT-TYPE
		SYNTAX		RollCallString
		MAX-ACCESS		read-only
		STATUS			current
		DESCRIPTION
				"TYPE: - Display
				 PAGE: - RollCall- Logging
					Out Emb.2-R Level=  cmdID= 36903  format=   "
		::= { iqdbd01CmdEntry 36903 }


	iqdbd01LoggingOPAudLevelLoggiLogOutEmb3LLev OBJECT-TYPE
		SYNTAX		INTEGER { disable(0), enable(1) }
		MAX-ACCESS		read-write
		STATUS			current
		DESCRIPTION
				"TYPE: - Checkbox
				 PAGE: - RollCall- Logging
					Log Out Emb.3-L Lev  cmdID= 35904 "
		::= { iqdbd01CmdEntry 35904 }


	iqdbd01LoggingOPAudLevelLoggiOutEmb3LLevel OBJECT-TYPE
		SYNTAX		RollCallString
		MAX-ACCESS		read-only
		STATUS			current
		DESCRIPTION
				"TYPE: - Display
				 PAGE: - RollCall- Logging
					Out Emb.3-L Level=  cmdID= 36904  format=   "
		::= { iqdbd01CmdEntry 36904 }


	iqdbd01LoggingOPAudLevelLoggiLogOutEmb3RLev OBJECT-TYPE
		SYNTAX		INTEGER { disable(0), enable(1) }
		MAX-ACCESS		read-write
		STATUS			current
		DESCRIPTION
				"TYPE: - Checkbox
				 PAGE: - RollCall- Logging
					Log Out Emb.3-R Lev  cmdID= 35905 "
		::= { iqdbd01CmdEntry 35905 }


	iqdbd01LoggingOPAudLevelLoggiOutEmb3RLevel OBJECT-TYPE
		SYNTAX		RollCallString
		MAX-ACCESS		read-only
		STATUS			current
		DESCRIPTION
				"TYPE: - Display
				 PAGE: - RollCall- Logging
					Out Emb.3-R Level=  cmdID= 36905  format=   "
		::= { iqdbd01CmdEntry 36905 }


	iqdbd01LoggingOPAudLevelLoggiLogOutEmb4LLev OBJECT-TYPE
		SYNTAX		INTEGER { disable(0), enable(1) }
		MAX-ACCESS		read-write
		STATUS			current
		DESCRIPTION
				"TYPE: - Checkbox
				 PAGE: - RollCall- Logging
					Log Out Emb.4-L Lev  cmdID= 35906 "
		::= { iqdbd01CmdEntry 35906 }


	iqdbd01LoggingOPAudLevelLoggiOutEmb4LLevel OBJECT-TYPE
		SYNTAX		RollCallString
		MAX-ACCESS		read-only
		STATUS			current
		DESCRIPTION
				"TYPE: - Display
				 PAGE: - RollCall- Logging
					Out Emb.4-L Level=  cmdID= 36906  format=   "
		::= { iqdbd01CmdEntry 36906 }


	iqdbd01LoggingOPAudLevelLoggiLogOutEmb4RLev OBJECT-TYPE
		SYNTAX		INTEGER { disable(0), enable(1) }
		MAX-ACCESS		read-write
		STATUS			current
		DESCRIPTION
				"TYPE: - Checkbox
				 PAGE: - RollCall- Logging
					Log Out Emb.4-R Lev  cmdID= 35907 "
		::= { iqdbd01CmdEntry 35907 }


	iqdbd01LoggingOPAudLevelLoggiOutEmb4RLevel OBJECT-TYPE
		SYNTAX		RollCallString
		MAX-ACCESS		read-only
		STATUS			current
		DESCRIPTION
				"TYPE: - Display
				 PAGE: - RollCall- Logging
					Out Emb.4-R Level=  cmdID= 36907  format=   "
		::= { iqdbd01CmdEntry 36907 }


	iqdbd01LoggingOPAudLevelLoggiLogOutEmb5LLev OBJECT-TYPE
		SYNTAX		INTEGER { disable(0), enable(1) }
		MAX-ACCESS		read-write
		STATUS			current
		DESCRIPTION
				"TYPE: - Checkbox
				 PAGE: - RollCall- Logging
					Log Out Emb.5-L Lev  cmdID= 35908 "
		::= { iqdbd01CmdEntry 35908 }


	iqdbd01LoggingOPAudLevelLoggiOutEmb5LLevel OBJECT-TYPE
		SYNTAX		RollCallString
		MAX-ACCESS		read-only
		STATUS			current
		DESCRIPTION
				"TYPE: - Display
				 PAGE: - RollCall- Logging
					Out Emb.5-L Level=  cmdID= 36908  format=   "
		::= { iqdbd01CmdEntry 36908 }


	iqdbd01LoggingOPAudLevelLoggiLogOutEmb5RLev OBJECT-TYPE
		SYNTAX		INTEGER { disable(0), enable(1) }
		MAX-ACCESS		read-write
		STATUS			current
		DESCRIPTION
				"TYPE: - Checkbox
				 PAGE: - RollCall- Logging
					Log Out Emb.5-R Lev  cmdID= 35909 "
		::= { iqdbd01CmdEntry 35909 }


	iqdbd01LoggingOPAudLevelLoggiOutEmb5RLevel OBJECT-TYPE
		SYNTAX		RollCallString
		MAX-ACCESS		read-only
		STATUS			current
		DESCRIPTION
				"TYPE: - Display
				 PAGE: - RollCall- Logging
					Out Emb.5-R Level=  cmdID= 36909  format=   "
		::= { iqdbd01CmdEntry 36909 }


	iqdbd01LoggingOPAudLevelLoggiLogOutEmb6LLev OBJECT-TYPE
		SYNTAX		INTEGER { disable(0), enable(1) }
		MAX-ACCESS		read-write
		STATUS			current
		DESCRIPTION
				"TYPE: - Checkbox
				 PAGE: - RollCall- Logging
					Log Out Emb.6-L Lev  cmdID= 35910 "
		::= { iqdbd01CmdEntry 35910 }


	iqdbd01LoggingOPAudLevelLoggiOutEmb6LLevel OBJECT-TYPE
		SYNTAX		RollCallString
		MAX-ACCESS		read-only
		STATUS			current
		DESCRIPTION
				"TYPE: - Display
				 PAGE: - RollCall- Logging
					Out Emb.6-L Level=  cmdID= 36910  format=   "
		::= { iqdbd01CmdEntry 36910 }


	iqdbd01LoggingOPAudLevelLoggiLogOutEmb6RLev OBJECT-TYPE
		SYNTAX		INTEGER { disable(0), enable(1) }
		MAX-ACCESS		read-write
		STATUS			current
		DESCRIPTION
				"TYPE: - Checkbox
				 PAGE: - RollCall- Logging
					Log Out Emb.6-R Lev  cmdID= 35911 "
		::= { iqdbd01CmdEntry 35911 }


	iqdbd01LoggingOPAudLevelLoggiOutEmb6RLevel OBJECT-TYPE
		SYNTAX		RollCallString
		MAX-ACCESS		read-only
		STATUS			current
		DESCRIPTION
				"TYPE: - Display
				 PAGE: - RollCall- Logging
					Out Emb.6-R Level=  cmdID= 36911  format=   "
		::= { iqdbd01CmdEntry 36911 }


	iqdbd01LoggingOPAudLevelLoggiLogOutEmb7LLev OBJECT-TYPE
		SYNTAX		INTEGER { disable(0), enable(1) }
		MAX-ACCESS		read-write
		STATUS			current
		DESCRIPTION
				"TYPE: - Checkbox
				 PAGE: - RollCall- Logging
					Log Out Emb.7-L Lev  cmdID= 35912 "
		::= { iqdbd01CmdEntry 35912 }


	iqdbd01LoggingOPAudLevelLoggiOutEmb7LLevel OBJECT-TYPE
		SYNTAX		RollCallString
		MAX-ACCESS		read-only
		STATUS			current
		DESCRIPTION
				"TYPE: - Display
				 PAGE: - RollCall- Logging
					Out Emb.7-L Level=  cmdID= 36912  format=   "
		::= { iqdbd01CmdEntry 36912 }


	iqdbd01LoggingOPAudLevelLoggiLogOutEmb7RLev OBJECT-TYPE
		SYNTAX		INTEGER { disable(0), enable(1) }
		MAX-ACCESS		read-write
		STATUS			current
		DESCRIPTION
				"TYPE: - Checkbox
				 PAGE: - RollCall- Logging
					Log Out Emb.7-R Lev  cmdID= 35913 "
		::= { iqdbd01CmdEntry 35913 }


	iqdbd01LoggingOPAudLevelLoggiOutEmb7RLevel OBJECT-TYPE
		SYNTAX		RollCallString
		MAX-ACCESS		read-only
		STATUS			current
		DESCRIPTION
				"TYPE: - Display
				 PAGE: - RollCall- Logging
					Out Emb.7-R Level=  cmdID= 36913  format=   "
		::= { iqdbd01CmdEntry 36913 }


	iqdbd01LoggingOPAudLevelLoggiLogOutEmb8LLev OBJECT-TYPE
		SYNTAX		INTEGER { disable(0), enable(1) }
		MAX-ACCESS		read-write
		STATUS			current
		DESCRIPTION
				"TYPE: - Checkbox
				 PAGE: - RollCall- Logging
					Log Out Emb.8-L Lev  cmdID= 35914 "
		::= { iqdbd01CmdEntry 35914 }


	iqdbd01LoggingOPAudLevelLoggiOutEmb8LLevel OBJECT-TYPE
		SYNTAX		RollCallString
		MAX-ACCESS		read-only
		STATUS			current
		DESCRIPTION
				"TYPE: - Display
				 PAGE: - RollCall- Logging
					Out Emb.8-L Level=  cmdID= 36914  format=   "
		::= { iqdbd01CmdEntry 36914 }


	iqdbd01LoggingOPAudLevelLoggiLogOutEmb8RLev OBJECT-TYPE
		SYNTAX		INTEGER { disable(0), enable(1) }
		MAX-ACCESS		read-write
		STATUS			current
		DESCRIPTION
				"TYPE: - Checkbox
				 PAGE: - RollCall- Logging
					Log Out Emb.8-R Lev  cmdID= 35915 "
		::= { iqdbd01CmdEntry 35915 }


	iqdbd01LoggingOPAudLevelLoggiOutEmb8RLevel OBJECT-TYPE
		SYNTAX		RollCallString
		MAX-ACCESS		read-only
		STATUS			current
		DESCRIPTION
				"TYPE: - Display
				 PAGE: - RollCall- Logging
					Out Emb.8-R Level=  cmdID= 36915  format=   "
		::= { iqdbd01CmdEntry 36915 }


	iqdbd01LoggingOPDolbyELoggingLogEmbDolbyE1 OBJECT-TYPE
		SYNTAX		INTEGER { disable(0), enable(1) }
		MAX-ACCESS		read-write
		STATUS			current
		DESCRIPTION
				"TYPE: - Checkbox
				 PAGE: - RollCall- Logging
					Log Emb DolbyE 1  cmdID= 35950 "
		::= { iqdbd01CmdEntry 35950 }


	iqdbd01LoggingOPDolbyELoggingEmbDolbyE1 OBJECT-TYPE
		SYNTAX		RollCallString
		MAX-ACCESS		read-only
		STATUS			current
		DESCRIPTION
				"TYPE: - Display
				 PAGE: - RollCall- Logging
					Emb DolbyE 1=  cmdID= 36950  format=   "
		::= { iqdbd01CmdEntry 36950 }


	iqdbd01LoggingOPDolbyELoggingLogEmbDolbyE2 OBJECT-TYPE
		SYNTAX		INTEGER { disable(0), enable(1) }
		MAX-ACCESS		read-write
		STATUS			current
		DESCRIPTION
				"TYPE: - Checkbox
				 PAGE: - RollCall- Logging
					Log Emb DolbyE 2  cmdID= 35951 "
		::= { iqdbd01CmdEntry 35951 }


	iqdbd01LoggingOPDolbyELoggingEmbDolbyE2 OBJECT-TYPE
		SYNTAX		RollCallString
		MAX-ACCESS		read-only
		STATUS			current
		DESCRIPTION
				"TYPE: - Display
				 PAGE: - RollCall- Logging
					Emb DolbyE 2=  cmdID= 36951  format=   "
		::= { iqdbd01CmdEntry 36951 }


	iqdbd01LoggingOPDolbyELoggingLogEmbDolbyE3 OBJECT-TYPE
		SYNTAX		INTEGER { disable(0), enable(1) }
		MAX-ACCESS		read-write
		STATUS			current
		DESCRIPTION
				"TYPE: - Checkbox
				 PAGE: - RollCall- Logging
					Log Emb DolbyE 3  cmdID= 35952 "
		::= { iqdbd01CmdEntry 35952 }


	iqdbd01LoggingOPDolbyELoggingEmbDolbyE3 OBJECT-TYPE
		SYNTAX		RollCallString
		MAX-ACCESS		read-only
		STATUS			current
		DESCRIPTION
				"TYPE: - Display
				 PAGE: - RollCall- Logging
					Emb DolbyE 3=  cmdID= 36952  format=   "
		::= { iqdbd01CmdEntry 36952 }


	iqdbd01LoggingOPDolbyELoggingLogEmbDolbyE4 OBJECT-TYPE
		SYNTAX		INTEGER { disable(0), enable(1) }
		MAX-ACCESS		read-write
		STATUS			current
		DESCRIPTION
				"TYPE: - Checkbox
				 PAGE: - RollCall- Logging
					Log Emb DolbyE 4  cmdID= 35953 "
		::= { iqdbd01CmdEntry 35953 }


	iqdbd01LoggingOPDolbyELoggingEmbDolbyE4 OBJECT-TYPE
		SYNTAX		RollCallString
		MAX-ACCESS		read-only
		STATUS			current
		DESCRIPTION
				"TYPE: - Display
				 PAGE: - RollCall- Logging
					Emb DolbyE 4=  cmdID= 36953  format=   "
		::= { iqdbd01CmdEntry 36953 }


	iqdbd01LoggingOPDolbyELoggingLogEmbDolbyE5 OBJECT-TYPE
		SYNTAX		INTEGER { disable(0), enable(1) }
		MAX-ACCESS		read-write
		STATUS			current
		DESCRIPTION
				"TYPE: - Checkbox
				 PAGE: - RollCall- Logging
					Log Emb DolbyE 5  cmdID= 35954 "
		::= { iqdbd01CmdEntry 35954 }


	iqdbd01LoggingOPDolbyELoggingEmbDolbyE5 OBJECT-TYPE
		SYNTAX		RollCallString
		MAX-ACCESS		read-only
		STATUS			current
		DESCRIPTION
				"TYPE: - Display
				 PAGE: - RollCall- Logging
					Emb DolbyE 5=  cmdID= 36954  format=   "
		::= { iqdbd01CmdEntry 36954 }


	iqdbd01LoggingOPDolbyELoggingLogEmbDolbyE6 OBJECT-TYPE
		SYNTAX		INTEGER { disable(0), enable(1) }
		MAX-ACCESS		read-write
		STATUS			current
		DESCRIPTION
				"TYPE: - Checkbox
				 PAGE: - RollCall- Logging
					Log Emb DolbyE 6  cmdID= 35955 "
		::= { iqdbd01CmdEntry 35955 }


	iqdbd01LoggingOPDolbyELoggingEmbDolbyE6 OBJECT-TYPE
		SYNTAX		RollCallString
		MAX-ACCESS		read-only
		STATUS			current
		DESCRIPTION
				"TYPE: - Display
				 PAGE: - RollCall- Logging
					Emb DolbyE 6=  cmdID= 36955  format=   "
		::= { iqdbd01CmdEntry 36955 }


	iqdbd01LoggingOPDolbyELoggingLogEmbDolbyE7 OBJECT-TYPE
		SYNTAX		INTEGER { disable(0), enable(1) }
		MAX-ACCESS		read-write
		STATUS			current
		DESCRIPTION
				"TYPE: - Checkbox
				 PAGE: - RollCall- Logging
					Log Emb DolbyE 7  cmdID= 35956 "
		::= { iqdbd01CmdEntry 35956 }


	iqdbd01LoggingOPDolbyELoggingEmbDolbyE7 OBJECT-TYPE
		SYNTAX		RollCallString
		MAX-ACCESS		read-only
		STATUS			current
		DESCRIPTION
				"TYPE: - Display
				 PAGE: - RollCall- Logging
					Emb DolbyE 7=  cmdID= 36956  format=   "
		::= { iqdbd01CmdEntry 36956 }


	iqdbd01LoggingOPDolbyELoggingLogEmbDolbyE8 OBJECT-TYPE
		SYNTAX		INTEGER { disable(0), enable(1) }
		MAX-ACCESS		read-write
		STATUS			current
		DESCRIPTION
				"TYPE: - Checkbox
				 PAGE: - RollCall- Logging
					Log Emb DolbyE 8  cmdID= 35957 "
		::= { iqdbd01CmdEntry 35957 }


	iqdbd01LoggingOPDolbyELoggingEmbDolbyE8 OBJECT-TYPE
		SYNTAX		RollCallString
		MAX-ACCESS		read-only
		STATUS			current
		DESCRIPTION
				"TYPE: - Display
				 PAGE: - RollCall- Logging
					Emb DolbyE 8=  cmdID= 36957  format=   "
		::= { iqdbd01CmdEntry 36957 }


	iqdbd01LoggingAESInputLoggingLogAESInput1sta OBJECT-TYPE
		SYNTAX		INTEGER { disable(0), enable(1) }
		MAX-ACCESS		read-write
		STATUS			current
		DESCRIPTION
				"TYPE: - Checkbox
				 PAGE: - RollCall- Logging
					Log AES Input 1 sta  cmdID= 35600 "
		::= { iqdbd01CmdEntry 35600 }


	iqdbd01LoggingAESInputLoggingAESInput1state OBJECT-TYPE
		SYNTAX		RollCallString
		MAX-ACCESS		read-only
		STATUS			current
		DESCRIPTION
				"TYPE: - Display
				 PAGE: - RollCall- Logging
					AES Input 1 state=  cmdID= 36600  format=   "
		::= { iqdbd01CmdEntry 36600 }


	iqdbd01LoggingAESInputLoggingLogAESInput2sta OBJECT-TYPE
		SYNTAX		INTEGER { disable(0), enable(1) }
		MAX-ACCESS		read-write
		STATUS			current
		DESCRIPTION
				"TYPE: - Checkbox
				 PAGE: - RollCall- Logging
					Log AES Input 2 sta  cmdID= 35601 "
		::= { iqdbd01CmdEntry 35601 }


	iqdbd01LoggingAESInputLoggingAESInput2state OBJECT-TYPE
		SYNTAX		RollCallString
		MAX-ACCESS		read-only
		STATUS			current
		DESCRIPTION
				"TYPE: - Display
				 PAGE: - RollCall- Logging
					AES Input 2 state=  cmdID= 36601  format=   "
		::= { iqdbd01CmdEntry 36601 }


	iqdbd01LoggingAESInputLoggingLogAESInput3sta OBJECT-TYPE
		SYNTAX		INTEGER { disable(0), enable(1) }
		MAX-ACCESS		read-write
		STATUS			current
		DESCRIPTION
				"TYPE: - Checkbox
				 PAGE: - RollCall- Logging
					Log AES Input 3 sta  cmdID= 35602 "
		::= { iqdbd01CmdEntry 35602 }


	iqdbd01LoggingAESInputLoggingAESInput3state OBJECT-TYPE
		SYNTAX		RollCallString
		MAX-ACCESS		read-only
		STATUS			current
		DESCRIPTION
				"TYPE: - Display
				 PAGE: - RollCall- Logging
					AES Input 3 state=  cmdID= 36602  format=   "
		::= { iqdbd01CmdEntry 36602 }


	iqdbd01LoggingAESInputLoggingLogAESInput4sta OBJECT-TYPE
		SYNTAX		INTEGER { disable(0), enable(1) }
		MAX-ACCESS		read-write
		STATUS			current
		DESCRIPTION
				"TYPE: - Checkbox
				 PAGE: - RollCall- Logging
					Log AES Input 4 sta  cmdID= 35603 "
		::= { iqdbd01CmdEntry 35603 }


	iqdbd01LoggingAESInputLoggingAESInput4state OBJECT-TYPE
		SYNTAX		RollCallString
		MAX-ACCESS		read-only
		STATUS			current
		DESCRIPTION
				"TYPE: - Display
				 PAGE: - RollCall- Logging
					AES Input 4 state=  cmdID= 36603  format=   "
		::= { iqdbd01CmdEntry 36603 }


	iqdbd01LoggingAESInputLoggingLogAESInput5sta OBJECT-TYPE
		SYNTAX		INTEGER { disable(0), enable(1) }
		MAX-ACCESS		read-write
		STATUS			current
		DESCRIPTION
				"TYPE: - Checkbox
				 PAGE: - RollCall- Logging
					Log AES Input 5 sta  cmdID= 35604 "
		::= { iqdbd01CmdEntry 35604 }


	iqdbd01LoggingAESInputLoggingAESInput5state OBJECT-TYPE
		SYNTAX		RollCallString
		MAX-ACCESS		read-only
		STATUS			current
		DESCRIPTION
				"TYPE: - Display
				 PAGE: - RollCall- Logging
					AES Input 5 state=  cmdID= 36604  format=   "
		::= { iqdbd01CmdEntry 36604 }


	iqdbd01LoggingAESInputLoggingLogAESInput6sta OBJECT-TYPE
		SYNTAX		INTEGER { disable(0), enable(1) }
		MAX-ACCESS		read-write
		STATUS			current
		DESCRIPTION
				"TYPE: - Checkbox
				 PAGE: - RollCall- Logging
					Log AES Input 6 sta  cmdID= 35605 "
		::= { iqdbd01CmdEntry 35605 }


	iqdbd01LoggingAESInputLoggingAESInput6state OBJECT-TYPE
		SYNTAX		RollCallString
		MAX-ACCESS		read-only
		STATUS			current
		DESCRIPTION
				"TYPE: - Display
				 PAGE: - RollCall- Logging
					AES Input 6 state=  cmdID= 36605  format=   "
		::= { iqdbd01CmdEntry 36605 }


	iqdbd01LoggingAESInputLoggingLogAESInput7sta OBJECT-TYPE
		SYNTAX		INTEGER { disable(0), enable(1) }
		MAX-ACCESS		read-write
		STATUS			current
		DESCRIPTION
				"TYPE: - Checkbox
				 PAGE: - RollCall- Logging
					Log AES Input 7 sta  cmdID= 35606 "
		::= { iqdbd01CmdEntry 35606 }


	iqdbd01LoggingAESInputLoggingAESInput7state OBJECT-TYPE
		SYNTAX		RollCallString
		MAX-ACCESS		read-only
		STATUS			current
		DESCRIPTION
				"TYPE: - Display
				 PAGE: - RollCall- Logging
					AES Input 7 state=  cmdID= 36606  format=   "
		::= { iqdbd01CmdEntry 36606 }


	iqdbd01LoggingAESInputLoggingLogAESInput8sta OBJECT-TYPE
		SYNTAX		INTEGER { disable(0), enable(1) }
		MAX-ACCESS		read-write
		STATUS			current
		DESCRIPTION
				"TYPE: - Checkbox
				 PAGE: - RollCall- Logging
					Log AES Input 8 sta  cmdID= 35607 "
		::= { iqdbd01CmdEntry 35607 }


	iqdbd01LoggingAESInputLoggingAESInput8state OBJECT-TYPE
		SYNTAX		RollCallString
		MAX-ACCESS		read-only
		STATUS			current
		DESCRIPTION
				"TYPE: - Display
				 PAGE: - RollCall- Logging
					AES Input 8 state=  cmdID= 36607  format=   "
		::= { iqdbd01CmdEntry 36607 }


	iqdbd01LoggingAESInputLoggingLogAESInput1typ OBJECT-TYPE
		SYNTAX		INTEGER { disable(0), enable(1) }
		MAX-ACCESS		read-write
		STATUS			current
		DESCRIPTION
				"TYPE: - Checkbox
				 PAGE: - RollCall- Logging
					Log AES Input 1 typ  cmdID= 35640 "
		::= { iqdbd01CmdEntry 35640 }


	iqdbd01LoggingAESInputLoggingAESInput1type OBJECT-TYPE
		SYNTAX		RollCallString
		MAX-ACCESS		read-only
		STATUS			current
		DESCRIPTION
				"TYPE: - Display
				 PAGE: - RollCall- Logging
					AES Input 1 type=  cmdID= 36640  format=   "
		::= { iqdbd01CmdEntry 36640 }


	iqdbd01LoggingAESInputLoggingLogAESInput2typ OBJECT-TYPE
		SYNTAX		INTEGER { disable(0), enable(1) }
		MAX-ACCESS		read-write
		STATUS			current
		DESCRIPTION
				"TYPE: - Checkbox
				 PAGE: - RollCall- Logging
					Log AES Input 2 typ  cmdID= 35641 "
		::= { iqdbd01CmdEntry 35641 }


	iqdbd01LoggingAESInputLoggingAESInput2type OBJECT-TYPE
		SYNTAX		RollCallString
		MAX-ACCESS		read-only
		STATUS			current
		DESCRIPTION
				"TYPE: - Display
				 PAGE: - RollCall- Logging
					AES Input 2 type=  cmdID= 36641  format=   "
		::= { iqdbd01CmdEntry 36641 }


	iqdbd01LoggingAESInputLoggingLogAESInput3typ OBJECT-TYPE
		SYNTAX		INTEGER { disable(0), enable(1) }
		MAX-ACCESS		read-write
		STATUS			current
		DESCRIPTION
				"TYPE: - Checkbox
				 PAGE: - RollCall- Logging
					Log AES Input 3 typ  cmdID= 35642 "
		::= { iqdbd01CmdEntry 35642 }


	iqdbd01LoggingAESInputLoggingAESInput3type OBJECT-TYPE
		SYNTAX		RollCallString
		MAX-ACCESS		read-only
		STATUS			current
		DESCRIPTION
				"TYPE: - Display
				 PAGE: - RollCall- Logging
					AES Input 3 type=  cmdID= 36642  format=   "
		::= { iqdbd01CmdEntry 36642 }


	iqdbd01LoggingAESInputLoggingLogAESInput4typ OBJECT-TYPE
		SYNTAX		INTEGER { disable(0), enable(1) }
		MAX-ACCESS		read-write
		STATUS			current
		DESCRIPTION
				"TYPE: - Checkbox
				 PAGE: - RollCall- Logging
					Log AES Input 4 typ  cmdID= 35643 "
		::= { iqdbd01CmdEntry 35643 }


	iqdbd01LoggingAESInputLoggingAESInput4type OBJECT-TYPE
		SYNTAX		RollCallString
		MAX-ACCESS		read-only
		STATUS			current
		DESCRIPTION
				"TYPE: - Display
				 PAGE: - RollCall- Logging
					AES Input 4 type=  cmdID= 36643  format=   "
		::= { iqdbd01CmdEntry 36643 }


	iqdbd01LoggingAESInputLoggingLogAESInput5typ OBJECT-TYPE
		SYNTAX		INTEGER { disable(0), enable(1) }
		MAX-ACCESS		read-write
		STATUS			current
		DESCRIPTION
				"TYPE: - Checkbox
				 PAGE: - RollCall- Logging
					Log AES Input 5 typ  cmdID= 35644 "
		::= { iqdbd01CmdEntry 35644 }


	iqdbd01LoggingAESInputLoggingAESInput5type OBJECT-TYPE
		SYNTAX		RollCallString
		MAX-ACCESS		read-only
		STATUS			current
		DESCRIPTION
				"TYPE: - Display
				 PAGE: - RollCall- Logging
					AES Input 5 type=  cmdID= 36644  format=   "
		::= { iqdbd01CmdEntry 36644 }


	iqdbd01LoggingAESInputLoggingLogAESInput6typ OBJECT-TYPE
		SYNTAX		INTEGER { disable(0), enable(1) }
		MAX-ACCESS		read-write
		STATUS			current
		DESCRIPTION
				"TYPE: - Checkbox
				 PAGE: - RollCall- Logging
					Log AES Input 6 typ  cmdID= 35645 "
		::= { iqdbd01CmdEntry 35645 }


	iqdbd01LoggingAESInputLoggingAESInput6type OBJECT-TYPE
		SYNTAX		RollCallString
		MAX-ACCESS		read-only
		STATUS			current
		DESCRIPTION
				"TYPE: - Display
				 PAGE: - RollCall- Logging
					AES Input 6 type=  cmdID= 36645  format=   "
		::= { iqdbd01CmdEntry 36645 }


	iqdbd01LoggingAESInputLoggingLogAESInput7typ OBJECT-TYPE
		SYNTAX		INTEGER { disable(0), enable(1) }
		MAX-ACCESS		read-write
		STATUS			current
		DESCRIPTION
				"TYPE: - Checkbox
				 PAGE: - RollCall- Logging
					Log AES Input 7 typ  cmdID= 35646 "
		::= { iqdbd01CmdEntry 35646 }


	iqdbd01LoggingAESInputLoggingAESInput7type OBJECT-TYPE
		SYNTAX		RollCallString
		MAX-ACCESS		read-only
		STATUS			current
		DESCRIPTION
				"TYPE: - Display
				 PAGE: - RollCall- Logging
					AES Input 7 type=  cmdID= 36646  format=   "
		::= { iqdbd01CmdEntry 36646 }


	iqdbd01LoggingAESInputLoggingLogAESInput8typ OBJECT-TYPE
		SYNTAX		INTEGER { disable(0), enable(1) }
		MAX-ACCESS		read-write
		STATUS			current
		DESCRIPTION
				"TYPE: - Checkbox
				 PAGE: - RollCall- Logging
					Log AES Input 8 typ  cmdID= 35647 "
		::= { iqdbd01CmdEntry 35647 }


	iqdbd01LoggingAESInputLoggingAESInput8type OBJECT-TYPE
		SYNTAX		RollCallString
		MAX-ACCESS		read-only
		STATUS			current
		DESCRIPTION
				"TYPE: - Display
				 PAGE: - RollCall- Logging
					AES Input 8 type=  cmdID= 36647  format=   "
		::= { iqdbd01CmdEntry 36647 }


	iqdbd01LoggingAESOutputLoggingLogAESOutput1st OBJECT-TYPE
		SYNTAX		INTEGER { disable(0), enable(1) }
		MAX-ACCESS		read-write
		STATUS			current
		DESCRIPTION
				"TYPE: - Checkbox
				 PAGE: - RollCall- Logging
					Log AES Output 1 st  cmdID= 35620 "
		::= { iqdbd01CmdEntry 35620 }


	iqdbd01LoggingAESOutputLoggingAESOutput1state OBJECT-TYPE
		SYNTAX		RollCallString
		MAX-ACCESS		read-only
		STATUS			current
		DESCRIPTION
				"TYPE: - Display
				 PAGE: - RollCall- Logging
					AES Output 1 state=  cmdID= 36620  format=   "
		::= { iqdbd01CmdEntry 36620 }


	iqdbd01LoggingAESOutputLoggingLogAESOutput2st OBJECT-TYPE
		SYNTAX		INTEGER { disable(0), enable(1) }
		MAX-ACCESS		read-write
		STATUS			current
		DESCRIPTION
				"TYPE: - Checkbox
				 PAGE: - RollCall- Logging
					Log AES Output 2 st  cmdID= 35621 "
		::= { iqdbd01CmdEntry 35621 }


	iqdbd01LoggingAESOutputLoggingAESOutput2state OBJECT-TYPE
		SYNTAX		RollCallString
		MAX-ACCESS		read-only
		STATUS			current
		DESCRIPTION
				"TYPE: - Display
				 PAGE: - RollCall- Logging
					AES Output 2 state=  cmdID= 36621  format=   "
		::= { iqdbd01CmdEntry 36621 }


	iqdbd01LoggingAESOutputLoggingLogAESOutput3st OBJECT-TYPE
		SYNTAX		INTEGER { disable(0), enable(1) }
		MAX-ACCESS		read-write
		STATUS			current
		DESCRIPTION
				"TYPE: - Checkbox
				 PAGE: - RollCall- Logging
					Log AES Output 3 st  cmdID= 35622 "
		::= { iqdbd01CmdEntry 35622 }


	iqdbd01LoggingAESOutputLoggingAESOutput3state OBJECT-TYPE
		SYNTAX		RollCallString
		MAX-ACCESS		read-only
		STATUS			current
		DESCRIPTION
				"TYPE: - Display
				 PAGE: - RollCall- Logging
					AES Output 3 state=  cmdID= 36622  format=   "
		::= { iqdbd01CmdEntry 36622 }


	iqdbd01LoggingAESOutputLoggingLogAESOutput4st OBJECT-TYPE
		SYNTAX		INTEGER { disable(0), enable(1) }
		MAX-ACCESS		read-write
		STATUS			current
		DESCRIPTION
				"TYPE: - Checkbox
				 PAGE: - RollCall- Logging
					Log AES Output 4 st  cmdID= 35623 "
		::= { iqdbd01CmdEntry 35623 }


	iqdbd01LoggingAESOutputLoggingAESOutput4state OBJECT-TYPE
		SYNTAX		RollCallString
		MAX-ACCESS		read-only
		STATUS			current
		DESCRIPTION
				"TYPE: - Display
				 PAGE: - RollCall- Logging
					AES Output 4 state=  cmdID= 36623  format=   "
		::= { iqdbd01CmdEntry 36623 }


	iqdbd01LoggingAESOutputLoggingLogAESOutput5st OBJECT-TYPE
		SYNTAX		INTEGER { disable(0), enable(1) }
		MAX-ACCESS		read-write
		STATUS			current
		DESCRIPTION
				"TYPE: - Checkbox
				 PAGE: - RollCall- Logging
					Log AES Output 5 st  cmdID= 35624 "
		::= { iqdbd01CmdEntry 35624 }


	iqdbd01LoggingAESOutputLoggingAESOutput5state OBJECT-TYPE
		SYNTAX		RollCallString
		MAX-ACCESS		read-only
		STATUS			current
		DESCRIPTION
				"TYPE: - Display
				 PAGE: - RollCall- Logging
					AES Output 5 state=  cmdID= 36624  format=   "
		::= { iqdbd01CmdEntry 36624 }


	iqdbd01LoggingAESOutputLoggingLogAESOutput6st OBJECT-TYPE
		SYNTAX		INTEGER { disable(0), enable(1) }
		MAX-ACCESS		read-write
		STATUS			current
		DESCRIPTION
				"TYPE: - Checkbox
				 PAGE: - RollCall- Logging
					Log AES Output 6 st  cmdID= 35625 "
		::= { iqdbd01CmdEntry 35625 }


	iqdbd01LoggingAESOutputLoggingAESOutput6state OBJECT-TYPE
		SYNTAX		RollCallString
		MAX-ACCESS		read-only
		STATUS			current
		DESCRIPTION
				"TYPE: - Display
				 PAGE: - RollCall- Logging
					AES Output 6 state=  cmdID= 36625  format=   "
		::= { iqdbd01CmdEntry 36625 }


	iqdbd01LoggingAESOutputLoggingLogAESOutput7st OBJECT-TYPE
		SYNTAX		INTEGER { disable(0), enable(1) }
		MAX-ACCESS		read-write
		STATUS			current
		DESCRIPTION
				"TYPE: - Checkbox
				 PAGE: - RollCall- Logging
					Log AES Output 7 st  cmdID= 35626 "
		::= { iqdbd01CmdEntry 35626 }


	iqdbd01LoggingAESOutputLoggingAESOutput7state OBJECT-TYPE
		SYNTAX		RollCallString
		MAX-ACCESS		read-only
		STATUS			current
		DESCRIPTION
				"TYPE: - Display
				 PAGE: - RollCall- Logging
					AES Output 7 state=  cmdID= 36626  format=   "
		::= { iqdbd01CmdEntry 36626 }


	iqdbd01LoggingAESOutputLoggingLogAESOutput8st OBJECT-TYPE
		SYNTAX		INTEGER { disable(0), enable(1) }
		MAX-ACCESS		read-write
		STATUS			current
		DESCRIPTION
				"TYPE: - Checkbox
				 PAGE: - RollCall- Logging
					Log AES Output 8 st  cmdID= 35627 "
		::= { iqdbd01CmdEntry 35627 }


	iqdbd01LoggingAESOutputLoggingAESOutput8state OBJECT-TYPE
		SYNTAX		RollCallString
		MAX-ACCESS		read-only
		STATUS			current
		DESCRIPTION
				"TYPE: - Display
				 PAGE: - RollCall- Logging
					AES Output 8 state=  cmdID= 36627  format=   "
		::= { iqdbd01CmdEntry 36627 }


	iqdbd01LoggingAESOutputLoggingLogAESOutput1ty OBJECT-TYPE
		SYNTAX		INTEGER { disable(0), enable(1) }
		MAX-ACCESS		read-write
		STATUS			current
		DESCRIPTION
				"TYPE: - Checkbox
				 PAGE: - RollCall- Logging
					Log AES Output 1 ty  cmdID= 35660 "
		::= { iqdbd01CmdEntry 35660 }


	iqdbd01LoggingAESOutputLoggingAESOutput1type OBJECT-TYPE
		SYNTAX		RollCallString
		MAX-ACCESS		read-only
		STATUS			current
		DESCRIPTION
				"TYPE: - Display
				 PAGE: - RollCall- Logging
					AES Output 1 type=  cmdID= 36660  format=   "
		::= { iqdbd01CmdEntry 36660 }


	iqdbd01LoggingAESOutputLoggingLogAESOutput2ty OBJECT-TYPE
		SYNTAX		INTEGER { disable(0), enable(1) }
		MAX-ACCESS		read-write
		STATUS			current
		DESCRIPTION
				"TYPE: - Checkbox
				 PAGE: - RollCall- Logging
					Log AES Output 2 ty  cmdID= 35661 "
		::= { iqdbd01CmdEntry 35661 }


	iqdbd01LoggingAESOutputLoggingAESOutput2type OBJECT-TYPE
		SYNTAX		RollCallString
		MAX-ACCESS		read-only
		STATUS			current
		DESCRIPTION
				"TYPE: - Display
				 PAGE: - RollCall- Logging
					AES Output 2 type=  cmdID= 36661  format=   "
		::= { iqdbd01CmdEntry 36661 }


	iqdbd01LoggingAESOutputLoggingLogAESOutput3ty OBJECT-TYPE
		SYNTAX		INTEGER { disable(0), enable(1) }
		MAX-ACCESS		read-write
		STATUS			current
		DESCRIPTION
				"TYPE: - Checkbox
				 PAGE: - RollCall- Logging
					Log AES Output 3 ty  cmdID= 35662 "
		::= { iqdbd01CmdEntry 35662 }


	iqdbd01LoggingAESOutputLoggingAESOutput3type OBJECT-TYPE
		SYNTAX		RollCallString
		MAX-ACCESS		read-only
		STATUS			current
		DESCRIPTION
				"TYPE: - Display
				 PAGE: - RollCall- Logging
					AES Output 3 type=  cmdID= 36662  format=   "
		::= { iqdbd01CmdEntry 36662 }


	iqdbd01LoggingAESOutputLoggingLogAESOutput4ty OBJECT-TYPE
		SYNTAX		INTEGER { disable(0), enable(1) }
		MAX-ACCESS		read-write
		STATUS			current
		DESCRIPTION
				"TYPE: - Checkbox
				 PAGE: - RollCall- Logging
					Log AES Output 4 ty  cmdID= 35663 "
		::= { iqdbd01CmdEntry 35663 }


	iqdbd01LoggingAESOutputLoggingAESOutput4type OBJECT-TYPE
		SYNTAX		RollCallString
		MAX-ACCESS		read-only
		STATUS			current
		DESCRIPTION
				"TYPE: - Display
				 PAGE: - RollCall- Logging
					AES Output 4 type=  cmdID= 36663  format=   "
		::= { iqdbd01CmdEntry 36663 }


	iqdbd01LoggingAESOutputLoggingLogAESOutput5ty OBJECT-TYPE
		SYNTAX		INTEGER { disable(0), enable(1) }
		MAX-ACCESS		read-write
		STATUS			current
		DESCRIPTION
				"TYPE: - Checkbox
				 PAGE: - RollCall- Logging
					Log AES Output 5 ty  cmdID= 35664 "
		::= { iqdbd01CmdEntry 35664 }


	iqdbd01LoggingAESOutputLoggingAESOutput5type OBJECT-TYPE
		SYNTAX		RollCallString
		MAX-ACCESS		read-only
		STATUS			current
		DESCRIPTION
				"TYPE: - Display
				 PAGE: - RollCall- Logging
					AES Output 5 type=  cmdID= 36664  format=   "
		::= { iqdbd01CmdEntry 36664 }


	iqdbd01LoggingAESOutputLoggingLogAESOutput6ty OBJECT-TYPE
		SYNTAX		INTEGER { disable(0), enable(1) }
		MAX-ACCESS		read-write
		STATUS			current
		DESCRIPTION
				"TYPE: - Checkbox
				 PAGE: - RollCall- Logging
					Log AES Output 6 ty  cmdID= 35665 "
		::= { iqdbd01CmdEntry 35665 }


	iqdbd01LoggingAESOutputLoggingAESOutput6type OBJECT-TYPE
		SYNTAX		RollCallString
		MAX-ACCESS		read-only
		STATUS			current
		DESCRIPTION
				"TYPE: - Display
				 PAGE: - RollCall- Logging
					AES Output 6 type=  cmdID= 36665  format=   "
		::= { iqdbd01CmdEntry 36665 }


	iqdbd01LoggingAESOutputLoggingLogAESOutput7ty OBJECT-TYPE
		SYNTAX		INTEGER { disable(0), enable(1) }
		MAX-ACCESS		read-write
		STATUS			current
		DESCRIPTION
				"TYPE: - Checkbox
				 PAGE: - RollCall- Logging
					Log AES Output 7 ty  cmdID= 35666 "
		::= { iqdbd01CmdEntry 35666 }


	iqdbd01LoggingAESOutputLoggingAESOutput7type OBJECT-TYPE
		SYNTAX		RollCallString
		MAX-ACCESS		read-only
		STATUS			current
		DESCRIPTION
				"TYPE: - Display
				 PAGE: - RollCall- Logging
					AES Output 7 type=  cmdID= 36666  format=   "
		::= { iqdbd01CmdEntry 36666 }


	iqdbd01LoggingAESOutputLoggingLogAESOutput8ty OBJECT-TYPE
		SYNTAX		INTEGER { disable(0), enable(1) }
		MAX-ACCESS		read-write
		STATUS			current
		DESCRIPTION
				"TYPE: - Checkbox
				 PAGE: - RollCall- Logging
					Log AES Output 8 ty  cmdID= 35667 "
		::= { iqdbd01CmdEntry 35667 }


	iqdbd01LoggingAESOutputLoggingAESOutput8type OBJECT-TYPE
		SYNTAX		RollCallString
		MAX-ACCESS		read-only
		STATUS			current
		DESCRIPTION
				"TYPE: - Display
				 PAGE: - RollCall- Logging
					AES Output 8 type=  cmdID= 36667  format=   "
		::= { iqdbd01CmdEntry 36667 }


	iqdbd01LoggingMiscLoggingLogSerialNo OBJECT-TYPE
		SYNTAX		INTEGER { disable(0), enable(1) }
		MAX-ACCESS		read-write
		STATUS			current
		DESCRIPTION
				"TYPE: - Checkbox
				 PAGE: - RollCall- Logging
					Log Serial No.  cmdID= 35015 "
		::= { iqdbd01CmdEntry 35015 }


	iqdbd01LoggingMiscLoggingSerialNo OBJECT-TYPE
		SYNTAX		RollCallString
		MAX-ACCESS		read-only
		STATUS			current
		DESCRIPTION
				"TYPE: - Display
				 PAGE: - RollCall- Logging
					Serial No.=  cmdID= 36015  format=   "
		::= { iqdbd01CmdEntry 36015 }


	iqdbd01LoggingMiscLoggingLogOSVersion OBJECT-TYPE
		SYNTAX		INTEGER { disable(0), enable(1) }
		MAX-ACCESS		read-write
		STATUS			current
		DESCRIPTION
				"TYPE: - Checkbox
				 PAGE: - RollCall- Logging
					Log OS Version  cmdID= 35993 "
		::= { iqdbd01CmdEntry 35993 }


	iqdbd01LoggingMiscLoggingOSVersion OBJECT-TYPE
		SYNTAX		RollCallString
		MAX-ACCESS		read-only
		STATUS			current
		DESCRIPTION
				"TYPE: - Display
				 PAGE: - RollCall- Logging
					OS Version=  cmdID= 36993  format=   "
		::= { iqdbd01CmdEntry 36993 }


	iqdbd01LoggingMiscLoggingLogBuildNo OBJECT-TYPE
		SYNTAX		INTEGER { disable(0), enable(1) }
		MAX-ACCESS		read-write
		STATUS			current
		DESCRIPTION
				"TYPE: - Checkbox
				 PAGE: - RollCall- Logging
					Log Build No.  cmdID= 35990 "
		::= { iqdbd01CmdEntry 35990 }


	iqdbd01LoggingMiscLoggingBuildNo OBJECT-TYPE
		SYNTAX		RollCallString
		MAX-ACCESS		read-only
		STATUS			current
		DESCRIPTION
				"TYPE: - Display
				 PAGE: - RollCall- Logging
					Build No.=  cmdID= 36990  format=   "
		::= { iqdbd01CmdEntry 36990 }


	iqdbd01LoggingMiscLoggingLogHardwareVer OBJECT-TYPE
		SYNTAX		INTEGER { disable(0), enable(1) }
		MAX-ACCESS		read-write
		STATUS			current
		DESCRIPTION
				"TYPE: - Checkbox
				 PAGE: - RollCall- Logging
					Log Hardware Ver.  cmdID= 35992 "
		::= { iqdbd01CmdEntry 35992 }


	iqdbd01LoggingMiscLoggingHardwareVer OBJECT-TYPE
		SYNTAX		RollCallString
		MAX-ACCESS		read-only
		STATUS			current
		DESCRIPTION
				"TYPE: - Display
				 PAGE: - RollCall- Logging
					Hardware Ver.=  cmdID= 36992  format=   "
		::= { iqdbd01CmdEntry 36992 }


	iqdbd01LoggingMiscLoggingLogFirmwareVer OBJECT-TYPE
		SYNTAX		INTEGER { disable(0), enable(1) }
		MAX-ACCESS		read-write
		STATUS			current
		DESCRIPTION
				"TYPE: - Checkbox
				 PAGE: - RollCall- Logging
					Log Firmware Ver.  cmdID= 35991 "
		::= { iqdbd01CmdEntry 35991 }


	iqdbd01LoggingMiscLoggingFirmwareVer OBJECT-TYPE
		SYNTAX		RollCallString
		MAX-ACCESS		read-only
		STATUS			current
		DESCRIPTION
				"TYPE: - Display
				 PAGE: - RollCall- Logging
					Firmware Ver.=  cmdID= 36991  format=   "
		::= { iqdbd01CmdEntry 36991 }


	iqdbd01LoggingMiscLoggingLogUpTime OBJECT-TYPE
		SYNTAX		INTEGER { disable(0), enable(1) }
		MAX-ACCESS		read-write
		STATUS			current
		DESCRIPTION
				"TYPE: - Checkbox
				 PAGE: - RollCall- Logging
					Log Up Time  cmdID= 35994 "
		::= { iqdbd01CmdEntry 35994 }


	iqdbd01LoggingMiscLoggingUpTime OBJECT-TYPE
		SYNTAX		RollCallString
		MAX-ACCESS		read-only
		STATUS			current
		DESCRIPTION
				"TYPE: - Display
				 PAGE: - RollCall- Logging
					Up Time=  cmdID= 36994  format=   "
		::= { iqdbd01CmdEntry 36994 }


	iqdbd01LoggingDolbyDecMetadataLogInputFormat OBJECT-TYPE
		SYNTAX		INTEGER { disable(0), enable(1) }
		MAX-ACCESS		read-write
		STATUS			current
		DESCRIPTION
				"TYPE: - Checkbox
				 PAGE: - RollCall- Logging- Dolby Dec Metadata
					Log Input Format   cmdID= 35800 "
		::= { iqdbd01CmdEntry 35800 }


	iqdbd01LoggingDolbyDecMetadataInputFormat OBJECT-TYPE
		SYNTAX		RollCallString
		MAX-ACCESS		read-only
		STATUS			current
		DESCRIPTION
				"TYPE: - Display
				 PAGE: - RollCall- Logging- Dolby Dec Metadata
					Input Format=  cmdID= 36800  format=   "
		::= { iqdbd01CmdEntry 36800 }


	iqdbd01LoggingDolbyDecMetadataLogInputBitDepth OBJECT-TYPE
		SYNTAX		INTEGER { disable(0), enable(1) }
		MAX-ACCESS		read-write
		STATUS			current
		DESCRIPTION
				"TYPE: - Checkbox
				 PAGE: - RollCall- Logging- Dolby Dec Metadata
					Log Input Bit Depth  cmdID= 35801 "
		::= { iqdbd01CmdEntry 35801 }


	iqdbd01LoggingDolbyDecMetadataInputBitDepth OBJECT-TYPE
		SYNTAX		RollCallString
		MAX-ACCESS		read-only
		STATUS			current
		DESCRIPTION
				"TYPE: - Display
				 PAGE: - RollCall- Logging- Dolby Dec Metadata
					Input Bit Depth=  cmdID= 36801  format=   "
		::= { iqdbd01CmdEntry 36801 }


	iqdbd01LoggingDolbyDecMetadataLogInpFrameRate OBJECT-TYPE
		SYNTAX		INTEGER { disable(0), enable(1) }
		MAX-ACCESS		read-write
		STATUS			current
		DESCRIPTION
				"TYPE: - Checkbox
				 PAGE: - RollCall- Logging- Dolby Dec Metadata
					Log Inp Frame Rate  cmdID= 35802 "
		::= { iqdbd01CmdEntry 35802 }


	iqdbd01LoggingDolbyDecMetadataInputFrameRate OBJECT-TYPE
		SYNTAX		RollCallString
		MAX-ACCESS		read-only
		STATUS			current
		DESCRIPTION
				"TYPE: - Display
				 PAGE: - RollCall- Logging- Dolby Dec Metadata
					Input Frame Rate=  cmdID= 36802  format=   "
		::= { iqdbd01CmdEntry 36802 }


	iqdbd01LoggingDolbyDecMetadataLogInpProgConfig OBJECT-TYPE
		SYNTAX		INTEGER { disable(0), enable(1) }
		MAX-ACCESS		read-write
		STATUS			current
		DESCRIPTION
				"TYPE: - Checkbox
				 PAGE: - RollCall- Logging- Dolby Dec Metadata
					Log Inp Prog Config  cmdID= 35803 "
		::= { iqdbd01CmdEntry 35803 }


	iqdbd01LoggingDolbyDecMetadataInputProgConfig OBJECT-TYPE
		SYNTAX		RollCallString
		MAX-ACCESS		read-only
		STATUS			current
		DESCRIPTION
				"TYPE: - Display
				 PAGE: - RollCall- Logging- Dolby Dec Metadata
					Input Prog Config=  cmdID= 36803  format=   "
		::= { iqdbd01CmdEntry 36803 }


	iqdbd01LoggingDolbyDecMetadataLogDolbyEErrCnt OBJECT-TYPE
		SYNTAX		INTEGER { disable(0), enable(1) }
		MAX-ACCESS		read-write
		STATUS			current
		DESCRIPTION
				"TYPE: - Checkbox
				 PAGE: - RollCall- Logging- Dolby Dec Metadata
					Log Dolby E Err Cnt  cmdID= 35804 "
		::= { iqdbd01CmdEntry 35804 }


	iqdbd01LoggingDolbyDecMetadataDolbyEErrCnt OBJECT-TYPE
		SYNTAX		RollCallString
		MAX-ACCESS		read-only
		STATUS			current
		DESCRIPTION
				"TYPE: - Display
				 PAGE: - RollCall- Logging- Dolby Dec Metadata
					Dolby E Err Cnt=  cmdID= 36804  format=   "
		::= { iqdbd01CmdEntry 36804 }


	iqdbd01LoggingDolbyDecMetadataLogDolbyDErrCnt OBJECT-TYPE
		SYNTAX		INTEGER { disable(0), enable(1) }
		MAX-ACCESS		read-write
		STATUS			current
		DESCRIPTION
				"TYPE: - Checkbox
				 PAGE: - RollCall- Logging- Dolby Dec Metadata
					Log Dolby D Err Cnt  cmdID= 35805 "
		::= { iqdbd01CmdEntry 35805 }


	iqdbd01LoggingDolbyDecMetadataDolbyDErrCnt OBJECT-TYPE
		SYNTAX		RollCallString
		MAX-ACCESS		read-only
		STATUS			current
		DESCRIPTION
				"TYPE: - Display
				 PAGE: - RollCall- Logging- Dolby Dec Metadata
					Dolby D Err Cnt=  cmdID= 36805  format=   "
		::= { iqdbd01CmdEntry 36805 }


	iqdbd01LoggingDolbyDecMetadataLogInpState OBJECT-TYPE
		SYNTAX		INTEGER { disable(0), enable(1) }
		MAX-ACCESS		read-write
		STATUS			current
		DESCRIPTION
				"TYPE: - Checkbox
				 PAGE: - RollCall- Logging- Dolby Dec Metadata
					Log Inp State  cmdID= 35806 "
		::= { iqdbd01CmdEntry 35806 }


	iqdbd01LoggingDolbyDecMetadataInputState OBJECT-TYPE
		SYNTAX		RollCallString
		MAX-ACCESS		read-only
		STATUS			current
		DESCRIPTION
				"TYPE: - Display
				 PAGE: - RollCall- Logging- Dolby Dec Metadata
					Input State=  cmdID= 36806  format=   "
		::= { iqdbd01CmdEntry 36806 }


	iqdbd01LoggingDolbyDecMetadataLogInpFrmSync OBJECT-TYPE
		SYNTAX		INTEGER { disable(0), enable(1) }
		MAX-ACCESS		read-write
		STATUS			current
		DESCRIPTION
				"TYPE: - Checkbox
				 PAGE: - RollCall- Logging- Dolby Dec Metadata
					Log Inp Frm Sync  cmdID= 35807 "
		::= { iqdbd01CmdEntry 35807 }


	iqdbd01LoggingDolbyDecMetadataInputFrameSync OBJECT-TYPE
		SYNTAX		RollCallString
		MAX-ACCESS		read-only
		STATUS			current
		DESCRIPTION
				"TYPE: - Display
				 PAGE: - RollCall- Logging- Dolby Dec Metadata
					Input Frame Sync=  cmdID= 36807  format=   "
		::= { iqdbd01CmdEntry 36807 }


	iqdbd01LoggingDolbyDecMetadataLogDolbyDListnM OBJECT-TYPE
		SYNTAX		INTEGER { disable(0), enable(1) }
		MAX-ACCESS		read-write
		STATUS			current
		DESCRIPTION
				"TYPE: - Checkbox
				 PAGE: - RollCall- Logging- Dolby Dec Metadata
					Log Dolby D Listn M  cmdID= 35808 "
		::= { iqdbd01CmdEntry 35808 }


	iqdbd01LoggingDolbyDecMetadataDolbyDListeningM OBJECT-TYPE
		SYNTAX		RollCallString
		MAX-ACCESS		read-only
		STATUS			current
		DESCRIPTION
				"TYPE: - Display
				 PAGE: - RollCall- Logging- Dolby Dec Metadata
					Dolby D Listening M  cmdID= 36808  format=   "
		::= { iqdbd01CmdEntry 36808 }


	iqdbd01LoggingDolbyDecMetadataLogDolbyDRngM OBJECT-TYPE
		SYNTAX		INTEGER { disable(0), enable(1) }
		MAX-ACCESS		read-write
		STATUS			current
		DESCRIPTION
				"TYPE: - Checkbox
				 PAGE: - RollCall- Logging- Dolby Dec Metadata
					Log Dolby D Rng M  cmdID= 35809 "
		::= { iqdbd01CmdEntry 35809 }


	iqdbd01LoggingDolbyDecMetadataDolbyDDynRngM OBJECT-TYPE
		SYNTAX		RollCallString
		MAX-ACCESS		read-only
		STATUS			current
		DESCRIPTION
				"TYPE: - Display
				 PAGE: - RollCall- Logging- Dolby Dec Metadata
					Dolby D Dyn Rng M=  cmdID= 36809  format=   "
		::= { iqdbd01CmdEntry 36809 }


	iqdbd01LoggingDolbyDecMetadataLogAuxRngMode OBJECT-TYPE
		SYNTAX		INTEGER { disable(0), enable(1) }
		MAX-ACCESS		read-write
		STATUS			current
		DESCRIPTION
				"TYPE: - Checkbox
				 PAGE: - RollCall- Logging- Dolby Dec Metadata
					Log Aux Rng Mode  cmdID= 35810 "
		::= { iqdbd01CmdEntry 35810 }


	iqdbd01LoggingDolbyDecMetadataAuxDynRngMode OBJECT-TYPE
		SYNTAX		RollCallString
		MAX-ACCESS		read-only
		STATUS			current
		DESCRIPTION
				"TYPE: - Display
				 PAGE: - RollCall- Logging- Dolby Dec Metadata
					Aux Dyn Rng Mode=  cmdID= 36810  format=   "
		::= { iqdbd01CmdEntry 36810 }


	iqdbd01DolbyDecMetadataDescTextLoggingLogProg1DescTXT OBJECT-TYPE
		SYNTAX		INTEGER { disable(0), enable(1) }
		MAX-ACCESS		read-write
		STATUS			current
		DESCRIPTION
				"TYPE: - Checkbox
				 PAGE: - RollCall- Logging- Dolby Dec Metadata
					Log Prog 1 Desc TXT  cmdID= 35820 "
		::= { iqdbd01CmdEntry 35820 }


	iqdbd01DolbyDecMetadataDescTextLoggingProg1DescText OBJECT-TYPE
		SYNTAX		RollCallString
		MAX-ACCESS		read-only
		STATUS			current
		DESCRIPTION
				"TYPE: - Display
				 PAGE: - RollCall- Logging- Dolby Dec Metadata
					Prog 1 Desc Text=  cmdID= 36820  format=   "
		::= { iqdbd01CmdEntry 36820 }


	iqdbd01DolbyDecMetadataDescTextLoggingProg1DescTextPt2 OBJECT-TYPE
		SYNTAX		RollCallString
		MAX-ACCESS		read-only
		STATUS			current
		DESCRIPTION
				"TYPE: - Display
				 PAGE: - RollCall- Logging- Dolby Dec Metadata
					Prog 1 Desc Text=  cmdID= 38800  format=   "
		::= { iqdbd01CmdEntry 38800 }


	iqdbd01DolbyDecMetadataDescTextLoggingLogProg2DescTXT OBJECT-TYPE
		SYNTAX		INTEGER { disable(0), enable(1) }
		MAX-ACCESS		read-write
		STATUS			current
		DESCRIPTION
				"TYPE: - Checkbox
				 PAGE: - RollCall- Logging- Dolby Dec Metadata
					Log Prog 2 Desc TXT  cmdID= 35821 "
		::= { iqdbd01CmdEntry 35821 }


	iqdbd01DolbyDecMetadataDescTextLoggingProg2DescText OBJECT-TYPE
		SYNTAX		RollCallString
		MAX-ACCESS		read-only
		STATUS			current
		DESCRIPTION
				"TYPE: - Display
				 PAGE: - RollCall- Logging- Dolby Dec Metadata
					Prog 2 Desc Text=  cmdID= 36821  format=   "
		::= { iqdbd01CmdEntry 36821 }


	iqdbd01DolbyDecMetadataDescTextLoggingProg2DescTextPt2 OBJECT-TYPE
		SYNTAX		RollCallString
		MAX-ACCESS		read-only
		STATUS			current
		DESCRIPTION
				"TYPE: - Display
				 PAGE: - RollCall- Logging- Dolby Dec Metadata
					Prog 2 Desc Text=  cmdID= 38801  format=   "
		::= { iqdbd01CmdEntry 38801 }


	iqdbd01DolbyDecMetadataDescTextLoggingLogProg3DescTXT OBJECT-TYPE
		SYNTAX		INTEGER { disable(0), enable(1) }
		MAX-ACCESS		read-write
		STATUS			current
		DESCRIPTION
				"TYPE: - Checkbox
				 PAGE: - RollCall- Logging- Dolby Dec Metadata
					Log Prog 3 Desc TXT  cmdID= 35822 "
		::= { iqdbd01CmdEntry 35822 }


	iqdbd01DolbyDecMetadataDescTextLoggingProg3DescText OBJECT-TYPE
		SYNTAX		RollCallString
		MAX-ACCESS		read-only
		STATUS			current
		DESCRIPTION
				"TYPE: - Display
				 PAGE: - RollCall- Logging- Dolby Dec Metadata
					Prog 3 Desc Text=  cmdID= 36822  format=   "
		::= { iqdbd01CmdEntry 36822 }


	iqdbd01DolbyDecMetadataDescTextLoggingProg3DescTextPt2 OBJECT-TYPE
		SYNTAX		RollCallString
		MAX-ACCESS		read-only
		STATUS			current
		DESCRIPTION
				"TYPE: - Display
				 PAGE: - RollCall- Logging- Dolby Dec Metadata
					Prog 3 Desc Text=  cmdID= 38802  format=   "
		::= { iqdbd01CmdEntry 38802 }


	iqdbd01DolbyDecMetadataDescTextLoggingLogProg4DescTXT OBJECT-TYPE
		SYNTAX		INTEGER { disable(0), enable(1) }
		MAX-ACCESS		read-write
		STATUS			current
		DESCRIPTION
				"TYPE: - Checkbox
				 PAGE: - RollCall- Logging- Dolby Dec Metadata
					Log Prog 4 Desc TXT  cmdID= 35823 "
		::= { iqdbd01CmdEntry 35823 }


	iqdbd01DolbyDecMetadataDescTextLoggingProg4DescTextPt2 OBJECT-TYPE
		SYNTAX		RollCallString
		MAX-ACCESS		read-only
		STATUS			current
		DESCRIPTION
				"TYPE: - Display
				 PAGE: - RollCall- Logging- Dolby Dec Metadata
					Prog 4 Desc Text=  cmdID= 38803  format=   "
		::= { iqdbd01CmdEntry 38803 }


	iqdbd01DolbyDecMetadataDescTextLoggingProg4DescText OBJECT-TYPE
		SYNTAX		RollCallString
		MAX-ACCESS		read-only
		STATUS			current
		DESCRIPTION
				"TYPE: - Display
				 PAGE: - RollCall- Logging- Dolby Dec Metadata
					Prog 4 Desc Text=  cmdID= 36823  format=   "
		::= { iqdbd01CmdEntry 36823 }


	iqdbd01DolbyDecMetadataDescTextLoggingLogProg5DescTXT OBJECT-TYPE
		SYNTAX		INTEGER { disable(0), enable(1) }
		MAX-ACCESS		read-write
		STATUS			current
		DESCRIPTION
				"TYPE: - Checkbox
				 PAGE: - RollCall- Logging- Dolby Dec Metadata
					Log Prog 5 Desc TXT  cmdID= 35824 "
		::= { iqdbd01CmdEntry 35824 }


	iqdbd01DolbyDecMetadataDescTextLoggingProg5DescText OBJECT-TYPE
		SYNTAX		RollCallString
		MAX-ACCESS		read-only
		STATUS			current
		DESCRIPTION
				"TYPE: - Display
				 PAGE: - RollCall- Logging- Dolby Dec Metadata
					Prog 5 Desc Text=  cmdID= 36824  format=   "
		::= { iqdbd01CmdEntry 36824 }


	iqdbd01DolbyDecMetadataDescTextLoggingProg5DescTextPt2 OBJECT-TYPE
		SYNTAX		RollCallString
		MAX-ACCESS		read-only
		STATUS			current
		DESCRIPTION
				"TYPE: - Display
				 PAGE: - RollCall- Logging- Dolby Dec Metadata
					Prog 5 Desc Text=  cmdID= 38804  format=   "
		::= { iqdbd01CmdEntry 38804 }


	iqdbd01DolbyDecMetadataDescTextLoggingLogProg6DescTXT OBJECT-TYPE
		SYNTAX		INTEGER { disable(0), enable(1) }
		MAX-ACCESS		read-write
		STATUS			current
		DESCRIPTION
				"TYPE: - Checkbox
				 PAGE: - RollCall- Logging- Dolby Dec Metadata
					Log Prog 6 Desc TXT  cmdID= 35825 "
		::= { iqdbd01CmdEntry 35825 }


	iqdbd01DolbyDecMetadataDescTextLoggingProg6DescText OBJECT-TYPE
		SYNTAX		RollCallString
		MAX-ACCESS		read-only
		STATUS			current
		DESCRIPTION
				"TYPE: - Display
				 PAGE: - RollCall- Logging- Dolby Dec Metadata
					Prog 6 Desc Text=  cmdID= 36825  format=   "
		::= { iqdbd01CmdEntry 36825 }


	iqdbd01DolbyDecMetadataDescTextLoggingProg6DescTextPt2 OBJECT-TYPE
		SYNTAX		RollCallString
		MAX-ACCESS		read-only
		STATUS			current
		DESCRIPTION
				"TYPE: - Display
				 PAGE: - RollCall- Logging- Dolby Dec Metadata
					Prog 6 Desc Text=  cmdID= 38805  format=   "
		::= { iqdbd01CmdEntry 38805 }


	iqdbd01DolbyDecMetadataDescTextLoggingLogProg7DescTXT OBJECT-TYPE
		SYNTAX		INTEGER { disable(0), enable(1) }
		MAX-ACCESS		read-write
		STATUS			current
		DESCRIPTION
				"TYPE: - Checkbox
				 PAGE: - RollCall- Logging- Dolby Dec Metadata
					Log Prog 7 Desc TXT  cmdID= 35826 "
		::= { iqdbd01CmdEntry 35826 }


	iqdbd01DolbyDecMetadataDescTextLoggingProg7DescText OBJECT-TYPE
		SYNTAX		RollCallString
		MAX-ACCESS		read-only
		STATUS			current
		DESCRIPTION
				"TYPE: - Display
				 PAGE: - RollCall- Logging- Dolby Dec Metadata
					Prog 7 Desc Text=  cmdID= 36826  format=   "
		::= { iqdbd01CmdEntry 36826 }


	iqdbd01DolbyDecMetadataDescTextLoggingProg7DescTextPt2 OBJECT-TYPE
		SYNTAX		RollCallString
		MAX-ACCESS		read-only
		STATUS			current
		DESCRIPTION
				"TYPE: - Display
				 PAGE: - RollCall- Logging- Dolby Dec Metadata
					Prog 7 Desc Text=  cmdID= 38806  format=   "
		::= { iqdbd01CmdEntry 38806 }


	iqdbd01DolbyDecMetadataDescTextLoggingLogProg8DescTXT OBJECT-TYPE
		SYNTAX		INTEGER { disable(0), enable(1) }
		MAX-ACCESS		read-write
		STATUS			current
		DESCRIPTION
				"TYPE: - Checkbox
				 PAGE: - RollCall- Logging- Dolby Dec Metadata
					Log Prog 8 Desc TXT  cmdID= 35827 "
		::= { iqdbd01CmdEntry 35827 }


	iqdbd01DolbyDecMetadataDescTextLoggingProg8DescText OBJECT-TYPE
		SYNTAX		RollCallString
		MAX-ACCESS		read-only
		STATUS			current
		DESCRIPTION
				"TYPE: - Display
				 PAGE: - RollCall- Logging- Dolby Dec Metadata
					Prog 8 Desc Text=  cmdID= 36827  format=   "
		::= { iqdbd01CmdEntry 36827 }


	iqdbd01DolbyDecMetadataDescTextLoggingProg8DescTextPt2 OBJECT-TYPE
		SYNTAX		RollCallString
		MAX-ACCESS		read-only
		STATUS			current
		DESCRIPTION
				"TYPE: - Display
				 PAGE: - RollCall- Logging- Dolby Dec Metadata
					Prog 8 Desc Text=  cmdID= 38807  format=   "
		::= { iqdbd01CmdEntry 38807 }


	iqdbd01DolbyDecMetadataLFEChanLoggingLogProg1LFEChan OBJECT-TYPE
		SYNTAX		INTEGER { disable(0), enable(1) }
		MAX-ACCESS		read-write
		STATUS			current
		DESCRIPTION
				"TYPE: - Checkbox
				 PAGE: - RollCall- Logging- Dolby Dec Metadata
					Log Prog 1 LFE Chan  cmdID= 35828 "
		::= { iqdbd01CmdEntry 35828 }


	iqdbd01DolbyDecMetadataLFEChanLoggingProg1LFEChan OBJECT-TYPE
		SYNTAX		RollCallString
		MAX-ACCESS		read-only
		STATUS			current
		DESCRIPTION
				"TYPE: - Display
				 PAGE: - RollCall- Logging- Dolby Dec Metadata
					Prog 1 LFE Chan=  cmdID= 36828  format=   "
		::= { iqdbd01CmdEntry 36828 }


	iqdbd01DolbyDecMetadataLFEChanLoggingLogProg2LFEChan OBJECT-TYPE
		SYNTAX		INTEGER { disable(0), enable(1) }
		MAX-ACCESS		read-write
		STATUS			current
		DESCRIPTION
				"TYPE: - Checkbox
				 PAGE: - RollCall- Logging- Dolby Dec Metadata
					Log Prog 2 LFE Chan  cmdID= 35829 "
		::= { iqdbd01CmdEntry 35829 }


	iqdbd01DolbyDecMetadataLFEChanLoggingProg2LFEChan OBJECT-TYPE
		SYNTAX		RollCallString
		MAX-ACCESS		read-only
		STATUS			current
		DESCRIPTION
				"TYPE: - Display
				 PAGE: - RollCall- Logging- Dolby Dec Metadata
					Prog 2 LFE Chan=  cmdID= 36829  format=   "
		::= { iqdbd01CmdEntry 36829 }


	iqdbd01DolbyDecMetadataLFEChanLoggingLogProg3LFEChan OBJECT-TYPE
		SYNTAX		INTEGER { disable(0), enable(1) }
		MAX-ACCESS		read-write
		STATUS			current
		DESCRIPTION
				"TYPE: - Checkbox
				 PAGE: - RollCall- Logging- Dolby Dec Metadata
					Log Prog 3 LFE Chan  cmdID= 35830 "
		::= { iqdbd01CmdEntry 35830 }


	iqdbd01DolbyDecMetadataLFEChanLoggingProg3LFEChan OBJECT-TYPE
		SYNTAX		RollCallString
		MAX-ACCESS		read-only
		STATUS			current
		DESCRIPTION
				"TYPE: - Display
				 PAGE: - RollCall- Logging- Dolby Dec Metadata
					Prog 3 LFE Chan=  cmdID= 36830  format=   "
		::= { iqdbd01CmdEntry 36830 }


	iqdbd01DolbyDecMetadataLFEChanLoggingLogProg4LFEChan OBJECT-TYPE
		SYNTAX		INTEGER { disable(0), enable(1) }
		MAX-ACCESS		read-write
		STATUS			current
		DESCRIPTION
				"TYPE: - Checkbox
				 PAGE: - RollCall- Logging- Dolby Dec Metadata
					Log Prog 4 LFE Chan  cmdID= 35831 "
		::= { iqdbd01CmdEntry 35831 }


	iqdbd01DolbyDecMetadataLFEChanLoggingProg4LFEChan OBJECT-TYPE
		SYNTAX		RollCallString
		MAX-ACCESS		read-only
		STATUS			current
		DESCRIPTION
				"TYPE: - Display
				 PAGE: - RollCall- Logging- Dolby Dec Metadata
					Prog 4 LFE Chan=  cmdID= 36831  format=   "
		::= { iqdbd01CmdEntry 36831 }


	iqdbd01DolbyDecMetadataLFEChanLoggingLogProg5LFEChan OBJECT-TYPE
		SYNTAX		INTEGER { disable(0), enable(1) }
		MAX-ACCESS		read-write
		STATUS			current
		DESCRIPTION
				"TYPE: - Checkbox
				 PAGE: - RollCall- Logging- Dolby Dec Metadata
					Log Prog 5 LFE Chan  cmdID= 35832 "
		::= { iqdbd01CmdEntry 35832 }


	iqdbd01DolbyDecMetadataLFEChanLoggingProg5LFEChan OBJECT-TYPE
		SYNTAX		RollCallString
		MAX-ACCESS		read-only
		STATUS			current
		DESCRIPTION
				"TYPE: - Display
				 PAGE: - RollCall- Logging- Dolby Dec Metadata
					Prog 5 LFE Chan=  cmdID= 36832  format=   "
		::= { iqdbd01CmdEntry 36832 }


	iqdbd01DolbyDecMetadataLFEChanLoggingLogProg6LFEChan OBJECT-TYPE
		SYNTAX		INTEGER { disable(0), enable(1) }
		MAX-ACCESS		read-write
		STATUS			current
		DESCRIPTION
				"TYPE: - Checkbox
				 PAGE: - RollCall- Logging- Dolby Dec Metadata
					Log Prog 6 LFE Chan  cmdID= 35833 "
		::= { iqdbd01CmdEntry 35833 }


	iqdbd01DolbyDecMetadataLFEChanLoggingProg6LFEChan OBJECT-TYPE
		SYNTAX		RollCallString
		MAX-ACCESS		read-only
		STATUS			current
		DESCRIPTION
				"TYPE: - Display
				 PAGE: - RollCall- Logging- Dolby Dec Metadata
					Prog 6 LFE Chan=  cmdID= 36833  format=   "
		::= { iqdbd01CmdEntry 36833 }


	iqdbd01DolbyDecMetadataLFEChanLoggingLogProg7LFEChan OBJECT-TYPE
		SYNTAX		INTEGER { disable(0), enable(1) }
		MAX-ACCESS		read-write
		STATUS			current
		DESCRIPTION
				"TYPE: - Checkbox
				 PAGE: - RollCall- Logging- Dolby Dec Metadata
					Log Prog 7 LFE Chan  cmdID= 35834 "
		::= { iqdbd01CmdEntry 35834 }


	iqdbd01DolbyDecMetadataLFEChanLoggingProg7LFEChan OBJECT-TYPE
		SYNTAX		RollCallString
		MAX-ACCESS		read-only
		STATUS			current
		DESCRIPTION
				"TYPE: - Display
				 PAGE: - RollCall- Logging- Dolby Dec Metadata
					Prog 7 LFE Chan=  cmdID= 36834  format=   "
		::= { iqdbd01CmdEntry 36834 }


	iqdbd01DolbyDecMetadataLFEChanLoggingLogProg8LFEChan OBJECT-TYPE
		SYNTAX		INTEGER { disable(0), enable(1) }
		MAX-ACCESS		read-write
		STATUS			current
		DESCRIPTION
				"TYPE: - Checkbox
				 PAGE: - RollCall- Logging- Dolby Dec Metadata
					Log Prog 8 LFE Chan  cmdID= 35835 "
		::= { iqdbd01CmdEntry 35835 }


	iqdbd01DolbyDecMetadataLFEChanLoggingProg8LFEChan OBJECT-TYPE
		SYNTAX		RollCallString
		MAX-ACCESS		read-only
		STATUS			current
		DESCRIPTION
				"TYPE: - Display
				 PAGE: - RollCall- Logging- Dolby Dec Metadata
					Prog 8 LFE Chan=  cmdID= 36835  format=   "
		::= { iqdbd01CmdEntry 36835 }


	iqdbd01DolbyDecMetadataChanModeLoggingLogProg1ChanMod OBJECT-TYPE
		SYNTAX		INTEGER { disable(0), enable(1) }
		MAX-ACCESS		read-write
		STATUS			current
		DESCRIPTION
				"TYPE: - Checkbox
				 PAGE: - RollCall- Logging- Dolby Dec Metadata
					Log Prog 1 Chan Mod  cmdID= 35836 "
		::= { iqdbd01CmdEntry 35836 }


	iqdbd01DolbyDecMetadataChanModeLoggingProg1ChanMode OBJECT-TYPE
		SYNTAX		RollCallString
		MAX-ACCESS		read-only
		STATUS			current
		DESCRIPTION
				"TYPE: - Display
				 PAGE: - RollCall- Logging- Dolby Dec Metadata
					Prog 1 Chan Mode=  cmdID= 36836  format=   "
		::= { iqdbd01CmdEntry 36836 }


	iqdbd01DolbyDecMetadataChanModeLoggingLogProg2ChanMod OBJECT-TYPE
		SYNTAX		INTEGER { disable(0), enable(1) }
		MAX-ACCESS		read-write
		STATUS			current
		DESCRIPTION
				"TYPE: - Checkbox
				 PAGE: - RollCall- Logging- Dolby Dec Metadata
					Log Prog 2 Chan Mod  cmdID= 35837 "
		::= { iqdbd01CmdEntry 35837 }


	iqdbd01DolbyDecMetadataChanModeLoggingProg2ChanMode OBJECT-TYPE
		SYNTAX		RollCallString
		MAX-ACCESS		read-only
		STATUS			current
		DESCRIPTION
				"TYPE: - Display
				 PAGE: - RollCall- Logging- Dolby Dec Metadata
					Prog 2 Chan Mode=  cmdID= 36837  format=   "
		::= { iqdbd01CmdEntry 36837 }


	iqdbd01DolbyDecMetadataChanModeLoggingLogProg3ChanMod OBJECT-TYPE
		SYNTAX		INTEGER { disable(0), enable(1) }
		MAX-ACCESS		read-write
		STATUS			current
		DESCRIPTION
				"TYPE: - Checkbox
				 PAGE: - RollCall- Logging- Dolby Dec Metadata
					Log Prog 3 Chan Mod  cmdID= 35838 "
		::= { iqdbd01CmdEntry 35838 }


	iqdbd01DolbyDecMetadataChanModeLoggingProg3ChanMode OBJECT-TYPE
		SYNTAX		RollCallString
		MAX-ACCESS		read-only
		STATUS			current
		DESCRIPTION
				"TYPE: - Display
				 PAGE: - RollCall- Logging- Dolby Dec Metadata
					Prog 3 Chan Mode=  cmdID= 36838  format=   "
		::= { iqdbd01CmdEntry 36838 }


	iqdbd01DolbyDecMetadataChanModeLoggingLogProg4ChanMod OBJECT-TYPE
		SYNTAX		INTEGER { disable(0), enable(1) }
		MAX-ACCESS		read-write
		STATUS			current
		DESCRIPTION
				"TYPE: - Checkbox
				 PAGE: - RollCall- Logging- Dolby Dec Metadata
					Log Prog 4 Chan Mod  cmdID= 35839 "
		::= { iqdbd01CmdEntry 35839 }


	iqdbd01DolbyDecMetadataChanModeLoggingProg4ChanMode OBJECT-TYPE
		SYNTAX		RollCallString
		MAX-ACCESS		read-only
		STATUS			current
		DESCRIPTION
				"TYPE: - Display
				 PAGE: - RollCall- Logging- Dolby Dec Metadata
					Prog 4 Chan Mode=  cmdID= 36839  format=   "
		::= { iqdbd01CmdEntry 36839 }


	iqdbd01DolbyDecMetadataChanModeLoggingLogProg5ChanMod OBJECT-TYPE
		SYNTAX		INTEGER { disable(0), enable(1) }
		MAX-ACCESS		read-write
		STATUS			current
		DESCRIPTION
				"TYPE: - Checkbox
				 PAGE: - RollCall- Logging- Dolby Dec Metadata
					Log Prog 5 Chan Mod  cmdID= 35840 "
		::= { iqdbd01CmdEntry 35840 }


	iqdbd01DolbyDecMetadataChanModeLoggingProg5ChanMode OBJECT-TYPE
		SYNTAX		RollCallString
		MAX-ACCESS		read-only
		STATUS			current
		DESCRIPTION
				"TYPE: - Display
				 PAGE: - RollCall- Logging- Dolby Dec Metadata
					Prog 5 Chan Mode=  cmdID= 36840  format=   "
		::= { iqdbd01CmdEntry 36840 }


	iqdbd01DolbyDecMetadataChanModeLoggingLogProg6ChanMod OBJECT-TYPE
		SYNTAX		INTEGER { disable(0), enable(1) }
		MAX-ACCESS		read-write
		STATUS			current
		DESCRIPTION
				"TYPE: - Checkbox
				 PAGE: - RollCall- Logging- Dolby Dec Metadata
					Log Prog 6 Chan Mod  cmdID= 35841 "
		::= { iqdbd01CmdEntry 35841 }


	iqdbd01DolbyDecMetadataChanModeLoggingProg6ChanMode OBJECT-TYPE
		SYNTAX		RollCallString
		MAX-ACCESS		read-only
		STATUS			current
		DESCRIPTION
				"TYPE: - Display
				 PAGE: - RollCall- Logging- Dolby Dec Metadata
					Prog 6 Chan Mode=  cmdID= 36841  format=   "
		::= { iqdbd01CmdEntry 36841 }


	iqdbd01DolbyDecMetadataChanModeLoggingLogProg7ChanMod OBJECT-TYPE
		SYNTAX		INTEGER { disable(0), enable(1) }
		MAX-ACCESS		read-write
		STATUS			current
		DESCRIPTION
				"TYPE: - Checkbox
				 PAGE: - RollCall- Logging- Dolby Dec Metadata
					Log Prog 7 Chan Mod  cmdID= 35842 "
		::= { iqdbd01CmdEntry 35842 }


	iqdbd01DolbyDecMetadataChanModeLoggingProg7ChanMode OBJECT-TYPE
		SYNTAX		RollCallString
		MAX-ACCESS		read-only
		STATUS			current
		DESCRIPTION
				"TYPE: - Display
				 PAGE: - RollCall- Logging- Dolby Dec Metadata
					Prog 7 Chan Mode=  cmdID= 36842  format=   "
		::= { iqdbd01CmdEntry 36842 }


	iqdbd01DolbyDecMetadataChanModeLoggingLogProg8ChanMod OBJECT-TYPE
		SYNTAX		INTEGER { disable(0), enable(1) }
		MAX-ACCESS		read-write
		STATUS			current
		DESCRIPTION
				"TYPE: - Checkbox
				 PAGE: - RollCall- Logging- Dolby Dec Metadata
					Log Prog 8 Chan Mod  cmdID= 35843 "
		::= { iqdbd01CmdEntry 35843 }


	iqdbd01DolbyDecMetadataChanModeLoggingProg8ChanMode OBJECT-TYPE
		SYNTAX		RollCallString
		MAX-ACCESS		read-only
		STATUS			current
		DESCRIPTION
				"TYPE: - Display
				 PAGE: - RollCall- Logging- Dolby Dec Metadata
					Prog 8 Chan Mode=  cmdID= 36843  format=   "
		::= { iqdbd01CmdEntry 36843 }


	iqdbd01DolbyDecMetadataStereoDOWNMIXLoggLogPgm1StDNMIX OBJECT-TYPE
		SYNTAX		INTEGER { disable(0), enable(1) }
		MAX-ACCESS		read-write
		STATUS			current
		DESCRIPTION
				"TYPE: - Checkbox
				 PAGE: - RollCall- Logging- Dolby Dec Metadata
					Log Pgm 1 St DNMIX  cmdID= 35844 "
		::= { iqdbd01CmdEntry 35844 }


	iqdbd01DolbyDecMetadataStereoDOWNMIXLoggPgm1StereoDNMIX OBJECT-TYPE
		SYNTAX		RollCallString
		MAX-ACCESS		read-only
		STATUS			current
		DESCRIPTION
				"TYPE: - Display
				 PAGE: - RollCall- Logging- Dolby Dec Metadata
					Pgm 1 Stereo DNMIX=  cmdID= 36844  format=   "
		::= { iqdbd01CmdEntry 36844 }


	iqdbd01DolbyDecMetadataStereoDOWNMIXLoggLogPgm2StDNMIX OBJECT-TYPE
		SYNTAX		INTEGER { disable(0), enable(1) }
		MAX-ACCESS		read-write
		STATUS			current
		DESCRIPTION
				"TYPE: - Checkbox
				 PAGE: - RollCall- Logging- Dolby Dec Metadata
					Log Pgm 2 St DNMIX  cmdID= 35845 "
		::= { iqdbd01CmdEntry 35845 }


	iqdbd01DolbyDecMetadataStereoDOWNMIXLoggPgm2StereoDNMIX OBJECT-TYPE
		SYNTAX		RollCallString
		MAX-ACCESS		read-only
		STATUS			current
		DESCRIPTION
				"TYPE: - Display
				 PAGE: - RollCall- Logging- Dolby Dec Metadata
					Pgm 2 Stereo DNMIX=  cmdID= 36845  format=   "
		::= { iqdbd01CmdEntry 36845 }


	iqdbd01DolbyDecMetadataStereoDOWNMIXLoggLogPgm3StDNMIX OBJECT-TYPE
		SYNTAX		INTEGER { disable(0), enable(1) }
		MAX-ACCESS		read-write
		STATUS			current
		DESCRIPTION
				"TYPE: - Checkbox
				 PAGE: - RollCall- Logging- Dolby Dec Metadata
					Log Pgm 3 St DNMIX  cmdID= 35846 "
		::= { iqdbd01CmdEntry 35846 }


	iqdbd01DolbyDecMetadataStereoDOWNMIXLoggPgm3StereoDNMIX OBJECT-TYPE
		SYNTAX		RollCallString
		MAX-ACCESS		read-only
		STATUS			current
		DESCRIPTION
				"TYPE: - Display
				 PAGE: - RollCall- Logging- Dolby Dec Metadata
					Pgm 3 Stereo DNMIX=  cmdID= 36846  format=   "
		::= { iqdbd01CmdEntry 36846 }


	iqdbd01DolbyDecMetadataStereoDOWNMIXLoggLogPgm4StDNMIX OBJECT-TYPE
		SYNTAX		INTEGER { disable(0), enable(1) }
		MAX-ACCESS		read-write
		STATUS			current
		DESCRIPTION
				"TYPE: - Checkbox
				 PAGE: - RollCall- Logging- Dolby Dec Metadata
					Log Pgm 4 St DNMIX  cmdID= 35847 "
		::= { iqdbd01CmdEntry 35847 }


	iqdbd01DolbyDecMetadataStereoDOWNMIXLoggPgm4StereoDNMIX OBJECT-TYPE
		SYNTAX		RollCallString
		MAX-ACCESS		read-only
		STATUS			current
		DESCRIPTION
				"TYPE: - Display
				 PAGE: - RollCall- Logging- Dolby Dec Metadata
					Pgm 4 Stereo DNMIX=  cmdID= 36847  format=   "
		::= { iqdbd01CmdEntry 36847 }


	iqdbd01DolbyDecMetadataStereoDOWNMIXLoggLogPgm5StDNMIX OBJECT-TYPE
		SYNTAX		INTEGER { disable(0), enable(1) }
		MAX-ACCESS		read-write
		STATUS			current
		DESCRIPTION
				"TYPE: - Checkbox
				 PAGE: - RollCall- Logging- Dolby Dec Metadata
					Log Pgm 5 St DNMIX  cmdID= 35848 "
		::= { iqdbd01CmdEntry 35848 }


	iqdbd01DolbyDecMetadataStereoDOWNMIXLoggPgm5StereoDNMIX OBJECT-TYPE
		SYNTAX		RollCallString
		MAX-ACCESS		read-only
		STATUS			current
		DESCRIPTION
				"TYPE: - Display
				 PAGE: - RollCall- Logging- Dolby Dec Metadata
					Pgm 5 Stereo DNMIX=  cmdID= 36848  format=   "
		::= { iqdbd01CmdEntry 36848 }


	iqdbd01DolbyDecMetadataStereoDOWNMIXLoggLogPgm6StDNMIX OBJECT-TYPE
		SYNTAX		INTEGER { disable(0), enable(1) }
		MAX-ACCESS		read-write
		STATUS			current
		DESCRIPTION
				"TYPE: - Checkbox
				 PAGE: - RollCall- Logging- Dolby Dec Metadata
					Log Pgm 6 St DNMIX  cmdID= 35849 "
		::= { iqdbd01CmdEntry 35849 }


	iqdbd01DolbyDecMetadataStereoDOWNMIXLoggPgm6StereoDNMIX OBJECT-TYPE
		SYNTAX		RollCallString
		MAX-ACCESS		read-only
		STATUS			current
		DESCRIPTION
				"TYPE: - Display
				 PAGE: - RollCall- Logging- Dolby Dec Metadata
					Pgm 6 Stereo DNMIX=  cmdID= 36849  format=   "
		::= { iqdbd01CmdEntry 36849 }


	iqdbd01DolbyDecMetadataStereoDOWNMIXLoggLogPgm7StDNMIX OBJECT-TYPE
		SYNTAX		INTEGER { disable(0), enable(1) }
		MAX-ACCESS		read-write
		STATUS			current
		DESCRIPTION
				"TYPE: - Checkbox
				 PAGE: - RollCall- Logging- Dolby Dec Metadata
					Log Pgm 7 St DNMIX  cmdID= 35850 "
		::= { iqdbd01CmdEntry 35850 }


	iqdbd01DolbyDecMetadataStereoDOWNMIXLoggPgm7StereoDNMIX OBJECT-TYPE
		SYNTAX		RollCallString
		MAX-ACCESS		read-only
		STATUS			current
		DESCRIPTION
				"TYPE: - Display
				 PAGE: - RollCall- Logging- Dolby Dec Metadata
					Pgm 7 Stereo DNMIX=  cmdID= 36850  format=   "
		::= { iqdbd01CmdEntry 36850 }


	iqdbd01DolbyDecMetadataStereoDOWNMIXLoggLogPgm8StDNMIX OBJECT-TYPE
		SYNTAX		INTEGER { disable(0), enable(1) }
		MAX-ACCESS		read-write
		STATUS			current
		DESCRIPTION
				"TYPE: - Checkbox
				 PAGE: - RollCall- Logging- Dolby Dec Metadata
					Log Pgm 8 St DNMIX  cmdID= 35851 "
		::= { iqdbd01CmdEntry 35851 }


	iqdbd01DolbyDecMetadataStereoDOWNMIXLoggPgm8StereoDNMIX OBJECT-TYPE
		SYNTAX		RollCallString
		MAX-ACCESS		read-only
		STATUS			current
		DESCRIPTION
				"TYPE: - Display
				 PAGE: - RollCall- Logging- Dolby Dec Metadata
					Pgm 8 Stereo DNMIX=  cmdID= 36851  format=   "
		::= { iqdbd01CmdEntry 36851 }


	iqdbd01DolbyDecMetadataDialnormLoggingLogProg1Dialnorm OBJECT-TYPE
		SYNTAX		INTEGER { disable(0), enable(1) }
		MAX-ACCESS		read-write
		STATUS			current
		DESCRIPTION
				"TYPE: - Checkbox
				 PAGE: - RollCall- Logging- Dolby Dec Metadata
					Log Prog 1 Dialnorm  cmdID= 35852 "
		::= { iqdbd01CmdEntry 35852 }


	iqdbd01DolbyDecMetadataDialnormLoggingProg1Dialnorm OBJECT-TYPE
		SYNTAX		RollCallString
		MAX-ACCESS		read-only
		STATUS			current
		DESCRIPTION
				"TYPE: - Display
				 PAGE: - RollCall- Logging- Dolby Dec Metadata
					Prog 1 Dialnorm=  cmdID= 36852  format=   "
		::= { iqdbd01CmdEntry 36852 }


	iqdbd01DolbyDecMetadataDialnormLoggingLogProg2Dialnorm OBJECT-TYPE
		SYNTAX		INTEGER { disable(0), enable(1) }
		MAX-ACCESS		read-write
		STATUS			current
		DESCRIPTION
				"TYPE: - Checkbox
				 PAGE: - RollCall- Logging- Dolby Dec Metadata
					Log Prog 2 Dialnorm  cmdID= 35853 "
		::= { iqdbd01CmdEntry 35853 }


	iqdbd01DolbyDecMetadataDialnormLoggingProg2Dialnorm OBJECT-TYPE
		SYNTAX		RollCallString
		MAX-ACCESS		read-only
		STATUS			current
		DESCRIPTION
				"TYPE: - Display
				 PAGE: - RollCall- Logging- Dolby Dec Metadata
					Prog 2 Dialnorm=  cmdID= 36853  format=   "
		::= { iqdbd01CmdEntry 36853 }


	iqdbd01DolbyDecMetadataDialnormLoggingLogProg3Dialnorm OBJECT-TYPE
		SYNTAX		INTEGER { disable(0), enable(1) }
		MAX-ACCESS		read-write
		STATUS			current
		DESCRIPTION
				"TYPE: - Checkbox
				 PAGE: - RollCall- Logging- Dolby Dec Metadata
					Log Prog 3 Dialnorm  cmdID= 35854 "
		::= { iqdbd01CmdEntry 35854 }


	iqdbd01DolbyDecMetadataDialnormLoggingProg3Dialnorm OBJECT-TYPE
		SYNTAX		RollCallString
		MAX-ACCESS		read-only
		STATUS			current
		DESCRIPTION
				"TYPE: - Display
				 PAGE: - RollCall- Logging- Dolby Dec Metadata
					Prog 3 Dialnorm=  cmdID= 36854  format=   "
		::= { iqdbd01CmdEntry 36854 }


	iqdbd01DolbyDecMetadataDialnormLoggingLogProg4Dialnorm OBJECT-TYPE
		SYNTAX		INTEGER { disable(0), enable(1) }
		MAX-ACCESS		read-write
		STATUS			current
		DESCRIPTION
				"TYPE: - Checkbox
				 PAGE: - RollCall- Logging- Dolby Dec Metadata
					Log Prog 4 Dialnorm  cmdID= 35855 "
		::= { iqdbd01CmdEntry 35855 }


	iqdbd01DolbyDecMetadataDialnormLoggingProg4Dialnorm OBJECT-TYPE
		SYNTAX		RollCallString
		MAX-ACCESS		read-only
		STATUS			current
		DESCRIPTION
				"TYPE: - Display
				 PAGE: - RollCall- Logging- Dolby Dec Metadata
					Prog 4 Dialnorm=  cmdID= 36855  format=   "
		::= { iqdbd01CmdEntry 36855 }


	iqdbd01DolbyDecMetadataDialnormLoggingLogProg5Dialnorm OBJECT-TYPE
		SYNTAX		INTEGER { disable(0), enable(1) }
		MAX-ACCESS		read-write
		STATUS			current
		DESCRIPTION
				"TYPE: - Checkbox
				 PAGE: - RollCall- Logging- Dolby Dec Metadata
					Log Prog 5 Dialnorm  cmdID= 35856 "
		::= { iqdbd01CmdEntry 35856 }


	iqdbd01DolbyDecMetadataDialnormLoggingProg5Dialnorm OBJECT-TYPE
		SYNTAX		RollCallString
		MAX-ACCESS		read-only
		STATUS			current
		DESCRIPTION
				"TYPE: - Display
				 PAGE: - RollCall- Logging- Dolby Dec Metadata
					Prog 5 Dialnorm=  cmdID= 36856  format=   "
		::= { iqdbd01CmdEntry 36856 }


	iqdbd01DolbyDecMetadataDialnormLoggingLogProg6Dialnorm OBJECT-TYPE
		SYNTAX		INTEGER { disable(0), enable(1) }
		MAX-ACCESS		read-write
		STATUS			current
		DESCRIPTION
				"TYPE: - Checkbox
				 PAGE: - RollCall- Logging- Dolby Dec Metadata
					Log Prog 6 Dialnorm  cmdID= 35857 "
		::= { iqdbd01CmdEntry 35857 }


	iqdbd01DolbyDecMetadataDialnormLoggingProg6Dialnorm OBJECT-TYPE
		SYNTAX		RollCallString
		MAX-ACCESS		read-only
		STATUS			current
		DESCRIPTION
				"TYPE: - Display
				 PAGE: - RollCall- Logging- Dolby Dec Metadata
					Prog 6 Dialnorm=  cmdID= 36857  format=   "
		::= { iqdbd01CmdEntry 36857 }


	iqdbd01DolbyDecMetadataDialnormLoggingLogProg7Dialnorm OBJECT-TYPE
		SYNTAX		INTEGER { disable(0), enable(1) }
		MAX-ACCESS		read-write
		STATUS			current
		DESCRIPTION
				"TYPE: - Checkbox
				 PAGE: - RollCall- Logging- Dolby Dec Metadata
					Log Prog 7 Dialnorm  cmdID= 35858 "
		::= { iqdbd01CmdEntry 35858 }


	iqdbd01DolbyDecMetadataDialnormLoggingProg7Dialnorm OBJECT-TYPE
		SYNTAX		RollCallString
		MAX-ACCESS		read-only
		STATUS			current
		DESCRIPTION
				"TYPE: - Display
				 PAGE: - RollCall- Logging- Dolby Dec Metadata
					Prog 7 Dialnorm=  cmdID= 36858  format=   "
		::= { iqdbd01CmdEntry 36858 }


	iqdbd01DolbyDecMetadataDialnormLoggingLogProg8Dialnorm OBJECT-TYPE
		SYNTAX		INTEGER { disable(0), enable(1) }
		MAX-ACCESS		read-write
		STATUS			current
		DESCRIPTION
				"TYPE: - Checkbox
				 PAGE: - RollCall- Logging- Dolby Dec Metadata
					Log Prog 8 Dialnorm  cmdID= 35859 "
		::= { iqdbd01CmdEntry 35859 }


	iqdbd01DolbyDecMetadataDialnormLoggingProg8Dialnorm OBJECT-TYPE
		SYNTAX		RollCallString
		MAX-ACCESS		read-only
		STATUS			current
		DESCRIPTION
				"TYPE: - Display
				 PAGE: - RollCall- Logging- Dolby Dec Metadata
					Prog 8 Dialnorm=  cmdID= 36859  format=   "
		::= { iqdbd01CmdEntry 36859 }


	iqdbd01DolbyDecMetadataCompGainLoggingLogPgm1CompGain OBJECT-TYPE
		SYNTAX		INTEGER { disable(0), enable(1) }
		MAX-ACCESS		read-write
		STATUS			current
		DESCRIPTION
				"TYPE: - Checkbox
				 PAGE: - RollCall- Logging- Dolby Dec Metadata
					Log Pgm 1 Comp Gain  cmdID= 35860 "
		::= { iqdbd01CmdEntry 35860 }


	iqdbd01DolbyDecMetadataCompGainLoggingPgm1CompGain OBJECT-TYPE
		SYNTAX		RollCallString
		MAX-ACCESS		read-only
		STATUS			current
		DESCRIPTION
				"TYPE: - Display
				 PAGE: - RollCall- Logging- Dolby Dec Metadata
					Pgm 1 Comp Gain=  cmdID= 36860  format=   "
		::= { iqdbd01CmdEntry 36860 }


	iqdbd01DolbyDecMetadataCompGainLoggingLogPgm2CompGain OBJECT-TYPE
		SYNTAX		INTEGER { disable(0), enable(1) }
		MAX-ACCESS		read-write
		STATUS			current
		DESCRIPTION
				"TYPE: - Checkbox
				 PAGE: - RollCall- Logging- Dolby Dec Metadata
					Log Pgm 2 Comp Gain  cmdID= 35861 "
		::= { iqdbd01CmdEntry 35861 }


	iqdbd01DolbyDecMetadataCompGainLoggingPgm2CompGain OBJECT-TYPE
		SYNTAX		RollCallString
		MAX-ACCESS		read-only
		STATUS			current
		DESCRIPTION
				"TYPE: - Display
				 PAGE: - RollCall- Logging- Dolby Dec Metadata
					Pgm 2 Comp Gain=  cmdID= 36861  format=   "
		::= { iqdbd01CmdEntry 36861 }


	iqdbd01DolbyDecMetadataCompGainLoggingLogPgm3CompGain OBJECT-TYPE
		SYNTAX		INTEGER { disable(0), enable(1) }
		MAX-ACCESS		read-write
		STATUS			current
		DESCRIPTION
				"TYPE: - Checkbox
				 PAGE: - RollCall- Logging- Dolby Dec Metadata
					Log Pgm 3 Comp Gain  cmdID= 35862 "
		::= { iqdbd01CmdEntry 35862 }


	iqdbd01DolbyDecMetadataCompGainLoggingPgm3CompGain OBJECT-TYPE
		SYNTAX		RollCallString
		MAX-ACCESS		read-only
		STATUS			current
		DESCRIPTION
				"TYPE: - Display
				 PAGE: - RollCall- Logging- Dolby Dec Metadata
					Pgm 3 Comp Gain=  cmdID= 36862  format=   "
		::= { iqdbd01CmdEntry 36862 }


	iqdbd01DolbyDecMetadataCompGainLoggingLogPgm4CompGain OBJECT-TYPE
		SYNTAX		INTEGER { disable(0), enable(1) }
		MAX-ACCESS		read-write
		STATUS			current
		DESCRIPTION
				"TYPE: - Checkbox
				 PAGE: - RollCall- Logging- Dolby Dec Metadata
					Log Pgm 4 Comp Gain  cmdID= 35863 "
		::= { iqdbd01CmdEntry 35863 }


	iqdbd01DolbyDecMetadataCompGainLoggingPgm4CompGain OBJECT-TYPE
		SYNTAX		RollCallString
		MAX-ACCESS		read-only
		STATUS			current
		DESCRIPTION
				"TYPE: - Display
				 PAGE: - RollCall- Logging- Dolby Dec Metadata
					Pgm 4 Comp Gain=  cmdID= 36863  format=   "
		::= { iqdbd01CmdEntry 36863 }


	iqdbd01DolbyDecMetadataCompGainLoggingLogPgm5CompGain OBJECT-TYPE
		SYNTAX		INTEGER { disable(0), enable(1) }
		MAX-ACCESS		read-write
		STATUS			current
		DESCRIPTION
				"TYPE: - Checkbox
				 PAGE: - RollCall- Logging- Dolby Dec Metadata
					Log Pgm 5 Comp Gain  cmdID= 35864 "
		::= { iqdbd01CmdEntry 35864 }


	iqdbd01DolbyDecMetadataCompGainLoggingPgm5CompGain OBJECT-TYPE
		SYNTAX		RollCallString
		MAX-ACCESS		read-only
		STATUS			current
		DESCRIPTION
				"TYPE: - Display
				 PAGE: - RollCall- Logging- Dolby Dec Metadata
					Pgm 5 Comp Gain=  cmdID= 36864  format=   "
		::= { iqdbd01CmdEntry 36864 }


	iqdbd01DolbyDecMetadataCompGainLoggingLogPgm6CompGain OBJECT-TYPE
		SYNTAX		INTEGER { disable(0), enable(1) }
		MAX-ACCESS		read-write
		STATUS			current
		DESCRIPTION
				"TYPE: - Checkbox
				 PAGE: - RollCall- Logging- Dolby Dec Metadata
					Log Pgm 6 Comp Gain  cmdID= 35865 "
		::= { iqdbd01CmdEntry 35865 }


	iqdbd01DolbyDecMetadataCompGainLoggingPgm6CompGain OBJECT-TYPE
		SYNTAX		RollCallString
		MAX-ACCESS		read-only
		STATUS			current
		DESCRIPTION
				"TYPE: - Display
				 PAGE: - RollCall- Logging- Dolby Dec Metadata
					Pgm 6 Comp Gain=  cmdID= 36865  format=   "
		::= { iqdbd01CmdEntry 36865 }


	iqdbd01DolbyDecMetadataCompGainLoggingLogPgm7CompGain OBJECT-TYPE
		SYNTAX		INTEGER { disable(0), enable(1) }
		MAX-ACCESS		read-write
		STATUS			current
		DESCRIPTION
				"TYPE: - Checkbox
				 PAGE: - RollCall- Logging- Dolby Dec Metadata
					Log Pgm 7 Comp Gain  cmdID= 35866 "
		::= { iqdbd01CmdEntry 35866 }


	iqdbd01DolbyDecMetadataCompGainLoggingPgm7CompGain OBJECT-TYPE
		SYNTAX		RollCallString
		MAX-ACCESS		read-only
		STATUS			current
		DESCRIPTION
				"TYPE: - Display
				 PAGE: - RollCall- Logging- Dolby Dec Metadata
					Pgm 7 Comp Gain=  cmdID= 36866  format=   "
		::= { iqdbd01CmdEntry 36866 }


	iqdbd01DolbyDecMetadataCompGainLoggingLogPgm8CompGain OBJECT-TYPE
		SYNTAX		INTEGER { disable(0), enable(1) }
		MAX-ACCESS		read-write
		STATUS			current
		DESCRIPTION
				"TYPE: - Checkbox
				 PAGE: - RollCall- Logging- Dolby Dec Metadata
					Log Pgm 8 Comp Gain  cmdID= 35867 "
		::= { iqdbd01CmdEntry 35867 }


	iqdbd01DolbyDecMetadataCompGainLoggingPgm8CompGain OBJECT-TYPE
		SYNTAX		RollCallString
		MAX-ACCESS		read-only
		STATUS			current
		DESCRIPTION
				"TYPE: - Display
				 PAGE: - RollCall- Logging- Dolby Dec Metadata
					Pgm 8 Comp Gain=  cmdID= 36867  format=   "
		::= { iqdbd01CmdEntry 36867 }


	iqdbd01DolbyDecMetadataDynamicGainLogginLogProg1DynGain OBJECT-TYPE
		SYNTAX		INTEGER { disable(0), enable(1) }
		MAX-ACCESS		read-write
		STATUS			current
		DESCRIPTION
				"TYPE: - Checkbox
				 PAGE: - RollCall- Logging- Dolby Dec Metadata
					Log Prog 1 Dyn Gain  cmdID= 35868 "
		::= { iqdbd01CmdEntry 35868 }


	iqdbd01DolbyDecMetadataDynamicGainLogginProg1DynGain OBJECT-TYPE
		SYNTAX		RollCallString
		MAX-ACCESS		read-only
		STATUS			current
		DESCRIPTION
				"TYPE: - Display
				 PAGE: - RollCall- Logging- Dolby Dec Metadata
					Prog 1 Dyn Gain=  cmdID= 36868  format=   "
		::= { iqdbd01CmdEntry 36868 }


	iqdbd01DolbyDecMetadataDynamicGainLogginLogProg2DynGain OBJECT-TYPE
		SYNTAX		INTEGER { disable(0), enable(1) }
		MAX-ACCESS		read-write
		STATUS			current
		DESCRIPTION
				"TYPE: - Checkbox
				 PAGE: - RollCall- Logging- Dolby Dec Metadata
					Log Prog 2 Dyn Gain  cmdID= 35869 "
		::= { iqdbd01CmdEntry 35869 }


	iqdbd01DolbyDecMetadataDynamicGainLogginProg2DynGain OBJECT-TYPE
		SYNTAX		RollCallString
		MAX-ACCESS		read-only
		STATUS			current
		DESCRIPTION
				"TYPE: - Display
				 PAGE: - RollCall- Logging- Dolby Dec Metadata
					Prog 2 Dyn Gain=  cmdID= 36869  format=   "
		::= { iqdbd01CmdEntry 36869 }


	iqdbd01DolbyDecMetadataDynamicGainLogginLogProg3DynGain OBJECT-TYPE
		SYNTAX		INTEGER { disable(0), enable(1) }
		MAX-ACCESS		read-write
		STATUS			current
		DESCRIPTION
				"TYPE: - Checkbox
				 PAGE: - RollCall- Logging- Dolby Dec Metadata
					Log Prog 3 Dyn Gain  cmdID= 35870 "
		::= { iqdbd01CmdEntry 35870 }


	iqdbd01DolbyDecMetadataDynamicGainLogginProg3DynGain OBJECT-TYPE
		SYNTAX		RollCallString
		MAX-ACCESS		read-only
		STATUS			current
		DESCRIPTION
				"TYPE: - Display
				 PAGE: - RollCall- Logging- Dolby Dec Metadata
					Prog 3 Dyn Gain=  cmdID= 36870  format=   "
		::= { iqdbd01CmdEntry 36870 }


	iqdbd01DolbyDecMetadataDynamicGainLogginLogProg4DynGain OBJECT-TYPE
		SYNTAX		INTEGER { disable(0), enable(1) }
		MAX-ACCESS		read-write
		STATUS			current
		DESCRIPTION
				"TYPE: - Checkbox
				 PAGE: - RollCall- Logging- Dolby Dec Metadata
					Log Prog 4 Dyn Gain  cmdID= 35871 "
		::= { iqdbd01CmdEntry 35871 }


	iqdbd01DolbyDecMetadataDynamicGainLogginProg4DynGain OBJECT-TYPE
		SYNTAX		RollCallString
		MAX-ACCESS		read-only
		STATUS			current
		DESCRIPTION
				"TYPE: - Display
				 PAGE: - RollCall- Logging- Dolby Dec Metadata
					Prog 4 Dyn Gain=  cmdID= 36871  format=   "
		::= { iqdbd01CmdEntry 36871 }


	iqdbd01DolbyDecMetadataDynamicGainLogginLogProg5DynGain OBJECT-TYPE
		SYNTAX		INTEGER { disable(0), enable(1) }
		MAX-ACCESS		read-write
		STATUS			current
		DESCRIPTION
				"TYPE: - Checkbox
				 PAGE: - RollCall- Logging- Dolby Dec Metadata
					Log Prog 5 Dyn Gain  cmdID= 35872 "
		::= { iqdbd01CmdEntry 35872 }


	iqdbd01DolbyDecMetadataDynamicGainLogginProg5DynGain OBJECT-TYPE
		SYNTAX		RollCallString
		MAX-ACCESS		read-only
		STATUS			current
		DESCRIPTION
				"TYPE: - Display
				 PAGE: - RollCall- Logging- Dolby Dec Metadata
					Prog 5 Dyn Gain=  cmdID= 36872  format=   "
		::= { iqdbd01CmdEntry 36872 }


	iqdbd01DolbyDecMetadataDynamicGainLogginLogProg6DynGain OBJECT-TYPE
		SYNTAX		INTEGER { disable(0), enable(1) }
		MAX-ACCESS		read-write
		STATUS			current
		DESCRIPTION
				"TYPE: - Checkbox
				 PAGE: - RollCall- Logging- Dolby Dec Metadata
					Log Prog 6 Dyn Gain  cmdID= 35873 "
		::= { iqdbd01CmdEntry 35873 }


	iqdbd01DolbyDecMetadataDynamicGainLogginProg6DynGain OBJECT-TYPE
		SYNTAX		RollCallString
		MAX-ACCESS		read-only
		STATUS			current
		DESCRIPTION
				"TYPE: - Display
				 PAGE: - RollCall- Logging- Dolby Dec Metadata
					Prog 6 Dyn Gain=  cmdID= 36873  format=   "
		::= { iqdbd01CmdEntry 36873 }


	iqdbd01DolbyDecMetadataDynamicGainLogginLogProg7DynGain OBJECT-TYPE
		SYNTAX		INTEGER { disable(0), enable(1) }
		MAX-ACCESS		read-write
		STATUS			current
		DESCRIPTION
				"TYPE: - Checkbox
				 PAGE: - RollCall- Logging- Dolby Dec Metadata
					Log Prog 7 Dyn Gain  cmdID= 35874 "
		::= { iqdbd01CmdEntry 35874 }


	iqdbd01DolbyDecMetadataDynamicGainLogginProg7DynGain OBJECT-TYPE
		SYNTAX		RollCallString
		MAX-ACCESS		read-only
		STATUS			current
		DESCRIPTION
				"TYPE: - Display
				 PAGE: - RollCall- Logging- Dolby Dec Metadata
					Prog 7 Dyn Gain=  cmdID= 36874  format=   "
		::= { iqdbd01CmdEntry 36874 }


	iqdbd01DolbyDecMetadataDynamicGainLogginLogProg8DynGain OBJECT-TYPE
		SYNTAX		INTEGER { disable(0), enable(1) }
		MAX-ACCESS		read-write
		STATUS			current
		DESCRIPTION
				"TYPE: - Checkbox
				 PAGE: - RollCall- Logging- Dolby Dec Metadata
					Log Prog 8 Dyn Gain  cmdID= 35875 "
		::= { iqdbd01CmdEntry 35875 }


	iqdbd01DolbyDecMetadataDynamicGainLogginProg8DynGain OBJECT-TYPE
		SYNTAX		RollCallString
		MAX-ACCESS		read-only
		STATUS			current
		DESCRIPTION
				"TYPE: - Display
				 PAGE: - RollCall- Logging- Dolby Dec Metadata
					Prog 8 Dyn Gain=  cmdID= 36875  format=   "
		::= { iqdbd01CmdEntry 36875 }


	iqdbd01RollCallRollTrackDisableAll OBJECT-TYPE
		SYNTAX		INTEGER { disable(0), enable(1) }
		MAX-ACCESS		read-write
		STATUS			current
		DESCRIPTION
				"TYPE: - Checkbox
				 PAGE: - RollCall
					Disable All  cmdID= 36104 "
		::= { iqdbd01CmdEntry 36104 }


	iqdbd01RollCallRollTrackIndex OBJECT-TYPE
		SYNTAX		INTEGER
		MAX-ACCESS		read-write
		STATUS			current
		DESCRIPTION
				"TYPE: - BarGraph
				 PAGE: - RollCall
					Index  cmdID= 36100  min= 1  max= 16   step= 1  format= %0.0f  div_scale= 1
					Min = 1  Max = 16  Step = 1 "
		::= { iqdbd01CmdEntry 36100 }


	iqdbd01RollCallRollTrackSource OBJECT-TYPE
		SYNTAX		INTEGER {
							val_Unused(-1),
							val_Video_Delay(0),
							val_Input_Present(1),
							val_Input_Loss(2),
							val_O_p_Freeze(3),
							val_O_p_UnFreeze(4),
							val_De_embed_1_Data(5),
							val_De_embed_1_Pcm(6),
							val_De_embed_1_Lost(7),
							val_De_embed_2_Data(8),
							val_De_embed_2_Pcm(9),
							val_De_embed_2_Lost(10),
							val_De_embed_3_Data(11),
							val_De_embed_3_Pcm(12),
							val_De_embed_3_Lost(13),
							val_De_embed_4_Data(14),
							val_De_embed_4_Pcm(15),
							val_De_embed_4_Lost(16),
							val_De_embed_5_Data(17),
							val_De_embed_5_Pcm(18),
							val_De_embed_5_Lost(19),
							val_De_embed_6_Data(20),
							val_De_embed_6_Pcm(21),
							val_De_embed_6_Lost(22),
							val_De_embed_7_Data(23),
							val_De_embed_7_Pcm(24),
							val_De_embed_7_Lost(25),
							val_De_embed_8_Data(26),
							val_De_embed_8_Pcm(27),
							val_De_embed_8_Lost(28),
							val_DD_Ch_1_Pcm(29),
							val_DD_Ch_1_Lost(30),
							val_DD_Ch_2_Pcm(31),
							val_DD_Ch_2_Lost(32),
							val_DD_Ch_3_Pcm(33),
							val_DD_Ch_3_Lost(34),
							val_DD_Ch_4_Pcm(35),
							val_DD_Ch_4_Lost(36),
							val_AES_5_Data(37),
							val_AES_5_Pcm(38),
							val_AES_5_Lost(39),
							val_AES_6_Data(40),
							val_AES_6_Pcm(41),
							val_AES_6_Lost(42),
							val_AES_7_Data(43),
							val_AES_7_Pcm(44),
							val_AES_7_Lost(45),
							val_AES_8_Data(46),
							val_AES_8_Pcm(47),
							val_AES_8_Lost(48),
							val_DD_Input_Lost(49),
							val_DD_PCM_Input(50),
							val_DD_Dolby_D_Input(51),
							val_DD_Dolby_E_Input(52)
							}
		MAX-ACCESS		read-write
		STATUS			current
		DESCRIPTION
				"TYPE: - RadiobuttonList
				 PAGE: - RollCall
					Source  cmdID= 36101
					Unused  value= -1
					Video Delay  value= 0
					Input Present  value= 1
					Input Loss  value= 2
					O/p Freeze  value= 3
					O/p UnFreeze  value= 4
					De-embed 1 Data  value= 5
					De-embed 1 Pcm  value= 6
					De-embed 1 Lost  value= 7
					De-embed 2 Data  value= 8
					De-embed 2 Pcm  value= 9
					De-embed 2 Lost  value= 10
					De-embed 3 Data  value= 11
					De-embed 3 Pcm  value= 12
					De-embed 3 Lost  value= 13
					De-embed 4 Data  value= 14
					De-embed 4 Pcm  value= 15
					De-embed 4 Lost  value= 16
					De-embed 5 Data  value= 17
					De-embed 5 Pcm  value= 18
					De-embed 5 Lost  value= 19
					De-embed 6 Data  value= 20
					De-embed 6 Pcm  value= 21
					De-embed 6 Lost  value= 22
					De-embed 7 Data  value= 23
					De-embed 7 Pcm  value= 24
					De-embed 7 Lost  value= 25
					De-embed 8 Data  value= 26
					De-embed 8 Pcm  value= 27
					De-embed 8 Lost  value= 28
					DD Ch 1 Pcm  value= 29
					DD Ch 1 Lost  value= 30
					DD Ch 2 Pcm  value= 31
					DD Ch 2 Lost  value= 32
					DD Ch 3 Pcm  value= 33
					DD Ch 3 Lost  value= 34
					DD Ch 4 Pcm  value= 35
					DD Ch 4 Lost  value= 36
					AES 5 Data  value= 37
					AES 5 Pcm  value= 38
					AES 5 Lost  value= 39
					AES 6 Data  value= 40
					AES 6 Pcm  value= 41
					AES 6 Lost  value= 42
					AES 7 Data  value= 43
					AES 7 Pcm  value= 44
					AES 7 Lost  value= 45
					AES 8 Data  value= 46
					AES 8 Pcm  value= 47
					AES 8 Lost  value= 48
					DD Input Lost  value= 49
					DD PCM Input  value= 50
					DD Dolby D Input   value= 51
					DD Dolby E Input   value= 52  "
		::= { iqdbd01CmdEntry 36101 }


	iqdbd01RollCallRollTrackAddress OBJECT-TYPE
		SYNTAX		RollCallString
		MAX-ACCESS		read-write
		STATUS			current
		DESCRIPTION
				"TYPE: - Editstring
				 PAGE: - RollCall
					Address  cmdID= 36102  "
		::= { iqdbd01CmdEntry 36102 }


	iqdbd01RollCallRollTrackCommand OBJECT-TYPE
		SYNTAX		RollCallString
		MAX-ACCESS		read-write
		STATUS			current
		DESCRIPTION
				"TYPE: - Editstring
				 PAGE: - RollCall
					Command  cmdID= 36103  "
		::= { iqdbd01CmdEntry 36103 }


	iqdbd01RollCallRollTrackStatus OBJECT-TYPE
		SYNTAX		RollCallString
		MAX-ACCESS		read-only
		STATUS			current
		DESCRIPTION
				"TYPE: - Display
				 PAGE: - RollCall
					Status  cmdID= 36105  format=   "
		::= { iqdbd01CmdEntry 36105 }


	iqdbd01RollCallRollTrackSending OBJECT-TYPE
		SYNTAX		RollCallString
		MAX-ACCESS		read-only
		STATUS			current
		DESCRIPTION
				"TYPE: - Display
				 PAGE: - RollCall
					Sending  cmdID= 36106  format=   "
		::= { iqdbd01CmdEntry 36106 }


	iqdbd01SetupProduct OBJECT-TYPE
		SYNTAX		RollCallString
		MAX-ACCESS		read-only
		STATUS			current
		DESCRIPTION
				"TYPE: - Display
					Product  cmdID= 32771  format=   "
		::= { iqdbd01CmdEntry 32771 }


	iqdbd01SetupRelease OBJECT-TYPE
		SYNTAX		RollCallString
		MAX-ACCESS		read-only
		STATUS			current
		DESCRIPTION
				"TYPE: - Display
					Release  cmdID= 2  format=   "
		::= { iqdbd01CmdEntry 2 }


	iqdbd01SetupBuild OBJECT-TYPE
		SYNTAX		RollCallString
		MAX-ACCESS		read-only
		STATUS			current
		DESCRIPTION
				"TYPE: - Display
					Build  cmdID= 5  format=   "
		::= { iqdbd01CmdEntry 5 }


	iqdbd01SetupKOS OBJECT-TYPE
		SYNTAX		RollCallString
		MAX-ACCESS		read-only
		STATUS			current
		DESCRIPTION
				"TYPE: - Display
					KOS  cmdID= 32772  format=   "
		::= { iqdbd01CmdEntry 32772 }


	iqdbd01SetupSerialNo OBJECT-TYPE
		SYNTAX		RollCallString
		MAX-ACCESS		read-only
		STATUS			current
		DESCRIPTION
				"TYPE: - Display
					Serial No.  cmdID= 1  format=   "
		::= { iqdbd01CmdEntry 1 }


	iqdbd01SetupFirmware OBJECT-TYPE
		SYNTAX		RollCallString
		MAX-ACCESS		read-only
		STATUS			current
		DESCRIPTION
				"TYPE: - Display
					Firmware  cmdID= 32769  format=   "
		::= { iqdbd01CmdEntry 32769 }


	iqdbd01SetupPCB OBJECT-TYPE
		SYNTAX		RollCallString
		MAX-ACCESS		read-only
		STATUS			current
		DESCRIPTION
				"TYPE: - Display
					PCB  cmdID= 32770  format=   "
		::= { iqdbd01CmdEntry 32770 }


	iqdbd01SetupFactoryDefault OBJECT-TYPE
		SYNTAX		INTEGER { noAction(0),val_Factory_Default(1) }
		MAX-ACCESS		read-write
		STATUS			current
		DESCRIPTION
				"TYPE: - Button
					Factory Default  cmdID= 37002  value= 1  "
		::= { iqdbd01CmdEntry 37002 }


	iqdbd01SetupRestart OBJECT-TYPE
		SYNTAX		INTEGER { noAction(0),val_Restart(1) }
		MAX-ACCESS		read-write
		STATUS			current
		DESCRIPTION
				"TYPE: - Button
					Restart  cmdID= 4  value= 1  "
		::= { iqdbd01CmdEntry 4 }


	iqdbd01SetupDefaultsSettings OBJECT-TYPE
		SYNTAX		INTEGER { noAction(0),val_Defaults_Settings(1) }
		MAX-ACCESS		read-write
		STATUS			current
		DESCRIPTION
				"TYPE: - Button
					Defaults Settings  cmdID= 37001  value= 1  "
		::= { iqdbd01CmdEntry 37001 }


	iqdbd01SetupDisplay OBJECT-TYPE
		SYNTAX		INTEGER {
							val_Video_Status(0),
							val_Audio_Status(1),
							val_Dolby_Dec_Status(2)
							}
		MAX-ACCESS		read-write
		STATUS			current
		DESCRIPTION
				"TYPE: - RadiobuttonList
					Display  cmdID= 32773
					Video Status  value= 0
					Audio Status  value= 1
					Dolby Dec Status  value= 2  "
		::= { iqdbd01CmdEntry 32773 }


	iqdbd01SetupSerialNumber OBJECT-TYPE
		SYNTAX		RollCallString
		MAX-ACCESS		read-write
		STATUS			current
		DESCRIPTION
				"TYPE: - Editstring
					Serial Number  cmdID= 32774  "
		::= { iqdbd01CmdEntry 32774 }


	iqdbd01SetupBoardID OBJECT-TYPE
		SYNTAX		INTEGER {
							val_IQDBD00(498),
							val_IQDBD01(499)
							}
		MAX-ACCESS		read-write
		STATUS			current
		DESCRIPTION
				"TYPE: - RadiobuttonList
					BoardID  cmdID= 32776
					IQDBD00  value= 498
					IQDBD01  value= 499  "
		::= { iqdbd01CmdEntry 32776 }


	iqdbd01SetupSaveID OBJECT-TYPE
		SYNTAX		INTEGER { noAction(0),val_Save_ID(1) }
		MAX-ACCESS		read-write
		STATUS			current
		DESCRIPTION
				"TYPE: - Button
					Save ID  cmdID= 32775  value= 1  "
		::= { iqdbd01CmdEntry 32775 }


	iqdbd01EngineerEngineerPassword OBJECT-TYPE
		SYNTAX		RollCallString
		MAX-ACCESS		read-write
		STATUS			current
		DESCRIPTION
				"TYPE: - Editstring
				 PAGE: - Engineer
					Engineer Password  cmdID= 34011  "
		::= { iqdbd01CmdEntry 34011 }


	iqdbd01EngineerShowEngineer OBJECT-TYPE
		SYNTAX		INTEGER { disable(0), enable(1) }
		MAX-ACCESS		read-write
		STATUS			current
		DESCRIPTION
				"TYPE: - Checkbox
				 PAGE: - Engineer
					Show Engineer  cmdID= 34012 "
		::= { iqdbd01CmdEntry 34012 }


	iqdbd01EngineerPageOptions1 OBJECT-TYPE
		SYNTAX		INTEGER { disable(0), enable(1) }
		MAX-ACCESS		read-write
		STATUS			current
		DESCRIPTION
				"TYPE: - Checkbox
				 PAGE: - Engineer
					$S1  cmdID= 34014 "
		::= { iqdbd01CmdEntry 34014 }


	iqdbd01EngineerPageOptions2 OBJECT-TYPE
		SYNTAX		INTEGER { disable(0), enable(1) }
		MAX-ACCESS		read-write
		STATUS			current
		DESCRIPTION
				"TYPE: - Checkbox
				 PAGE: - Engineer
					$S1  cmdID= 34015 "
		::= { iqdbd01CmdEntry 34015 }


	iqdbd01EngineerPageOptions3 OBJECT-TYPE
		SYNTAX		INTEGER { disable(0), enable(1) }
		MAX-ACCESS		read-write
		STATUS			current
		DESCRIPTION
				"TYPE: - Checkbox
				 PAGE: - Engineer
					$S1  cmdID= 34016 "
		::= { iqdbd01CmdEntry 34016 }


	iqdbd01OptionsDolbyModuleS1 OBJECT-TYPE
		SYNTAX		INTEGER { disable(0), enable(1) }
		MAX-ACCESS		read-write
		STATUS			current
		DESCRIPTION
				"TYPE: - Checkbox
				 PAGE: - Engineer
					$S1  cmdID= 34017 "
		::= { iqdbd01CmdEntry 34017 }


	iqdbd01EngineerPageOptionsUndoChanges OBJECT-TYPE
		SYNTAX		INTEGER { noAction(0),val_Undo_Changes(1) }
		MAX-ACCESS		read-write
		STATUS			current
		DESCRIPTION
				"TYPE: - Button
				 PAGE: - Engineer
					Undo Changes  cmdID= 34013  value= 1  "
		::= { iqdbd01CmdEntry 34013 }


	iqdbd01EngineerPageDolbyETimingLineNumber OBJECT-TYPE
		SYNTAX		RollCallString
		MAX-ACCESS		read-only
		STATUS			current
		DESCRIPTION
				"TYPE: - Display
				 PAGE: - Engineer
					Line Number  cmdID= 38651  format=   "
		::= { iqdbd01CmdEntry 38651 }


	iqdbd01EngineerPageDolbyETimingSampleNumber OBJECT-TYPE
		SYNTAX		RollCallString
		MAX-ACCESS		read-only
		STATUS			current
		DESCRIPTION
				"TYPE: - Display
				 PAGE: - Engineer
					Sample Number  cmdID= 38657  format=   "
		::= { iqdbd01CmdEntry 38657 }


	iqdbd01EngineerPagePaAutoalignEmbeddedInputs OBJECT-TYPE
		SYNTAX		INTEGER { disable(0), enable(1) }
		MAX-ACCESS		read-write
		STATUS			current
		DESCRIPTION
				"TYPE: - Checkbox
				 PAGE: - Engineer
					Embedded Inputs  cmdID= 34060 "
		::= { iqdbd01CmdEntry 34060 }


	iqdbd01EngineerPagePaAutoalignAESInputs OBJECT-TYPE
		SYNTAX		INTEGER { disable(0), enable(1) }
		MAX-ACCESS		read-write
		STATUS			current
		DESCRIPTION
				"TYPE: - Checkbox
				 PAGE: - Engineer
					AES Inputs  cmdID= 34061 "
		::= { iqdbd01CmdEntry 34061 }


	iqdbd01EngineerShowEngineer2 OBJECT-TYPE
		SYNTAX		INTEGER { disable(0), enable(1) }
		MAX-ACCESS		read-write
		STATUS			current
		DESCRIPTION
				"TYPE: - Checkbox
				 PAGE: - Engineer
					Show Engineer2  cmdID= 34050 "
		::= { iqdbd01CmdEntry 34050 }


	iqdbd01EngineerUseEmbDelayFbac OBJECT-TYPE
		SYNTAX		INTEGER { disable(0), enable(1) }
		MAX-ACCESS		read-write
		STATUS			current
		DESCRIPTION
				"TYPE: - Checkbox
				 PAGE: - Engineer
					Use Emb Delay F/bac  cmdID= 34049 "
		::= { iqdbd01CmdEntry 34049 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S35034500
--				:
-- Comments		: Serial Number or module
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:12:00
--				:
-- Comments		: Uptime in formated date-time string
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 1
--				:
-- Comments		: Number or current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				:
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 0000100251
--				:
-- Comments		: String of current Software build number
--
---------------------------------------------------------------------------------------------------
-- Header		: INFORMATION1
--
-- MIB ref		: swCardEventLogSlotXX       .12.73.78.70.79.82.77.65.84.73.79.78.49
-- absolute OID	: 1.3.6.1.4.1.7995.2.6.1.1.XX.12.73.78.70.79.82.77.65.84.73.79.78.49
-- Vary			: YES
--
-- Value(s)		: D/E Decode Text A
--				:
-- Comments		: User configurable text string
--
---------------------------------------------------------------------------------------------------
-- Header		: INFORMATION2
--
-- MIB ref		: swCardEventLogSlotXX       .12.73.78.70.79.82.77.65.84.73.79.78.50
-- absolute OID	: 1.3.6.1.4.1.7995.2.6.1.1.XX.12.73.78.70.79.82.77.65.84.73.79.78.50
-- Vary			: YES
--
-- Value(s)		: D/E Decode Text B
--				:
-- Comments		: User configurable text string
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD / SD SDI
--				:
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2010-04-22T15:42:54Z
--				:
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: OK
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2010-04-22T15:53:03Z
--				:
-- Comments		: Time String of last control modification
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: HD / SD SDI
--				:
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: BLACK
--				: PATTERN
--				: MONO
--				: FROZEN
--				: OK
--				: FAIL
-- Comments		:
--
---------------------------------------------------------------------------------------------------
-- Header		: AES_INPUT_1_TYPE
--
-- MIB ref		: swCardEventLogSlotXX       .16.65.69.83.95.73.78.80.85.84.95.49.95.84.89.80.69
-- absolute OID	: 1.3.6.1.4.1.7995.2.6.1.1.XX.16.65.69.83.95.73.78.80.85.84.95.49.95.84.89.80.69
-- Vary			: YES
--
-- Value(s)		: Unknown
--				: NONPCM
--              : PCM
--              : WARN: No Input
-- Comments		:
--
---------------------------------------------------------------------------------------------------
-- Header		: AES_INPUT_2_TYPE
--
-- MIB ref		: swCardEventLogSlotXX       .16.65.69.83.95.73.78.80.85.84.95.50.95.84.89.80.69
-- absolute OID	: 1.3.6.1.4.1.7995.2.6.1.1.XX.16.65.69.83.95.73.78.80.85.84.95.50.95.84.89.80.69
-- Vary			: YES
--
-- Value(s)		: Unknown
--				: NONPCM
--              : PCM
--              : WARN: No Input
-- Comments		:
--
---------------------------------------------------------------------------------------------------
-- Header		: AES_INPUT_3_TYPE
--
-- MIB ref		: swCardEventLogSlotXX       .16.65.69.83.95.73.78.80.85.84.95.51.95.84.89.80.69
-- absolute OID	: 1.3.6.1.4.1.7995.2.6.1.1.XX.16.65.69.83.95.73.78.80.85.84.95.51.95.84.89.80.69
-- Vary			: YES
--
-- Value(s)		: Unknown
--				: NONPCM
--              : PCM
--              : WARN: No Input
-- Comments		:
--
---------------------------------------------------------------------------------------------------
-- Header		: AES_INPUT_4_TYPE
--
-- MIB ref		: swCardEventLogSlotXX       .16.65.69.83.95.73.78.80.85.84.95.52.95.84.89.80.69
-- absolute OID	: 1.3.6.1.4.1.7995.2.6.1.1.XX.16.65.69.83.95.73.78.80.85.84.95.52.95.84.89.80.69
-- Vary			: YES
--
-- Value(s)		: Unknown
--				: NONPCM
--              : PCM
--              : WARN: No Input
-- Comments		:
--
---------------------------------------------------------------------------------------------------
-- Header		: AES_INPUT_5_TYPE
--
-- MIB ref		: swCardEventLogSlotXX       .16.65.69.83.95.73.78.80.85.84.95.53.95.84.89.80.69
-- absolute OID	: 1.3.6.1.4.1.7995.2.6.1.1.XX.16.65.69.83.95.73.78.80.85.84.95.53.95.84.89.80.69
-- Vary			: YES
--
-- Value(s)		: Unknown
--				: NONPCM
--              : PCM
--              : WARN: No Input
-- Comments		:
--
---------------------------------------------------------------------------------------------------
-- Header		: AES_INPUT_6_TYPE
--
-- MIB ref		: swCardEventLogSlotXX       .16.65.69.83.95.73.78.80.85.84.95.54.95.84.89.80.69
-- absolute OID	: 1.3.6.1.4.1.7995.2.6.1.1.XX.16.65.69.83.95.73.78.80.85.84.95.54.95.84.89.80.69
-- Vary			: YES
--
-- Value(s)		: Unknown
--				: NONPCM
--              : PCM
--              : WARN: No Input
-- Comments		:
--
---------------------------------------------------------------------------------------------------
-- Header		: AES_INPUT_7_TYPE
--
-- MIB ref		: swCardEventLogSlotXX       .16.65.69.83.95.73.78.80.85.84.95.55.95.84.89.80.69
-- absolute OID	: 1.3.6.1.4.1.7995.2.6.1.1.XX.16.65.69.83.95.73.78.80.85.84.95.55.95.84.89.80.69
-- Vary			: YES
--
-- Value(s)		: Unknown
--				: NONPCM
--              : PCM
--              : WARN: No Input
-- Comments		:
--
---------------------------------------------------------------------------------------------------
-- Header		: AES_INPUT_8_TYPE
--
-- MIB ref		: swCardEventLogSlotXX       .16.65.69.83.95.73.78.80.85.84.95.56.95.84.89.80.69
-- absolute OID	: 1.3.6.1.4.1.7995.2.6.1.1.XX.16.65.69.83.95.73.78.80.85.84.95.56.95.84.89.80.69
-- Vary			: YES
--
-- Value(s)		: Unknown
--				: NONPCM
--              : PCM
--              : WARN: No Input
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 2.195
--				:
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: RDAUD1B.004
--				:
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: NONE
--              : WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_INPUT_1_STATE
--
-- MIB ref		: swCardEventLogSlotXX       .17.65.69.83.95.73.78.80.85.84.95.49.95.83.84.65.84.69
-- absolute OID	: 1.3.6.1.4.1.7995.2.6.1.1.XX.17.65.69.83.95.73.78.80.85.84.95.49.95.83.84.65.84.69
-- Vary			: YES
--
-- Value(s)		: LOST
--				: FAIL:Lost
--              : OK
--              : Unknown
-- Comments		:
--
---------------------------------------------------------------------------------------------------
-- Header		: AES_INPUT_2_STATE
--
-- MIB ref		: swCardEventLogSlotXX       .17.65.69.83.95.73.78.80.85.84.95.50.95.83.84.65.84.69
-- absolute OID	: 1.3.6.1.4.1.7995.2.6.1.1.XX.17.65.69.83.95.73.78.80.85.84.95.50.95.83.84.65.84.69
-- Vary			: YES
--
-- Value(s)		: LOST
--				: FAIL:Lost
--              : OK
--              : Unknown
-- Comments		:
--
---------------------------------------------------------------------------------------------------
-- Header		: AES_INPUT_3_STATE
--
-- MIB ref		: swCardEventLogSlotXX       .17.65.69.83.95.73.78.80.85.84.95.51.95.83.84.65.84.69
-- absolute OID	: 1.3.6.1.4.1.7995.2.6.1.1.XX.17.65.69.83.95.73.78.80.85.84.95.51.95.83.84.65.84.69
-- Vary			: YES
--
-- Value(s)		: LOST
--				: FAIL:Lost
--              : OK
--              : Unknown
-- Comments		:
--
---------------------------------------------------------------------------------------------------
-- Header		: AES_INPUT_4_STATE
--
-- MIB ref		: swCardEventLogSlotXX       .17.65.69.83.95.73.78.80.85.84.95.52.95.83.84.65.84.69
-- absolute OID	: 1.3.6.1.4.1.7995.2.6.1.1.XX.17.65.69.83.95.73.78.80.85.84.95.52.95.83.84.65.84.69
-- Vary			: YES
--
-- Value(s)		: LOST
--				: FAIL:Lost
--              : OK
--              : Unknown
-- Comments		:
--
---------------------------------------------------------------------------------------------------
-- Header		: AES_INPUT_5_STATE
--
-- MIB ref		: swCardEventLogSlotXX       .17.65.69.83.95.73.78.80.85.84.95.53.95.83.84.65.84.69
-- absolute OID	: 1.3.6.1.4.1.7995.2.6.1.1.XX.17.65.69.83.95.73.78.80.85.84.95.53.95.83.84.65.84.69
-- Vary			: YES
--
-- Value(s)		: LOST
--				: FAIL:Lost
--              : OK
--              : Unknown
-- Comments		:
--
---------------------------------------------------------------------------------------------------
-- Header		: AES_INPUT_6_STATE
--
-- MIB ref		: swCardEventLogSlotXX       .17.65.69.83.95.73.78.80.85.84.95.54.95.83.84.65.84.69
-- absolute OID	: 1.3.6.1.4.1.7995.2.6.1.1.XX.17.65.69.83.95.73.78.80.85.84.95.54.95.83.84.65.84.69
-- Vary			: YES
--
-- Value(s)		: LOST
--				: FAIL:Lost
--              : OK
--              : Unknown
-- Comments		:
--
---------------------------------------------------------------------------------------------------
-- Header		: AES_INPUT_7_STATE
--
-- MIB ref		: swCardEventLogSlotXX       .17.65.69.83.95.73.78.80.85.84.95.55.95.83.84.65.84.69
-- absolute OID	: 1.3.6.1.4.1.7995.2.6.1.1.XX.17.65.69.83.95.73.78.80.85.84.95.55.95.83.84.65.84.69
-- Vary			: YES
--
-- Value(s)		: LOST
--				: FAIL:Lost
--              : OK
--              : Unknown
-- Comments		:
--
---------------------------------------------------------------------------------------------------
-- Header		: AES_INPUT_8_STATE
--
-- MIB ref		: swCardEventLogSlotXX       .17.65.69.83.95.73.78.80.85.84.95.56.95.83.84.65.84.69
-- absolute OID	: 1.3.6.1.4.1.7995.2.6.1.1.XX.17.65.69.83.95.73.78.80.85.84.95.56.95.83.84.65.84.69
-- Vary			: YES
--
-- Value(s)		: LOST
--				: FAIL:Lost
--              : OK
--              : Unknown
-- Comments		:
--
---------------------------------------------------------------------------------------------------
-- Header		: AES_OUTPUT_1_TYPE
--
-- MIB ref		: swCardEventLogSlotXX       .17.65.69.83.95.79.85.84.80.85.84.95.49.95.84.89.80.69
-- absolute OID	: 1.3.6.1.4.1.7995.2.6.1.1.XX.17.65.69.83.95.79.85.84.80.85.84.95.49.95.84.89.80.69
-- Vary			: YES
--
-- Value(s)		: Unknown
--				: PCM
--              : NONPCM
--              : WARN: No Input
-- Comments		:
--
---------------------------------------------------------------------------------------------------
-- Header		: AES_OUTPUT_2_TYPE
--
-- MIB ref		: swCardEventLogSlotXX       .17.65.69.83.95.79.85.84.80.85.84.95.50.95.84.89.80.69
-- absolute OID	: 1.3.6.1.4.1.7995.2.6.1.1.XX.17.65.69.83.95.79.85.84.80.85.84.95.50.95.84.89.80.69
-- Vary			: YES
--
-- Value(s)		: Unknown
--				: PCM
--              : NONPCM
--              : WARN: No Input
-- Comments		:
--
---------------------------------------------------------------------------------------------------
-- Header		: AES_OUTPUT_3_TYPE
--
-- MIB ref		: swCardEventLogSlotXX       .17.65.69.83.95.79.85.84.80.85.84.95.51.95.84.89.80.69
-- absolute OID	: 1.3.6.1.4.1.7995.2.6.1.1.XX.17.65.69.83.95.79.85.84.80.85.84.95.51.95.84.89.80.69
-- Vary			: YES
--
-- Value(s)		: Unknown
--				: PCM
--              : NONPCM
--              : WARN: No Input
-- Comments		:
--
---------------------------------------------------------------------------------------------------
-- Header		: AES_OUTPUT_4_TYPE
--
-- MIB ref		: swCardEventLogSlotXX       .17.65.69.83.95.79.85.84.80.85.84.95.52.95.84.89.80.69
-- absolute OID	: 1.3.6.1.4.1.7995.2.6.1.1.XX.17.65.69.83.95.79.85.84.80.85.84.95.52.95.84.89.80.69
-- Vary			: YES
--
-- Value(s)		: Unknown
--				: PCM
--              : NONPCM
--              : WARN: No Input
-- Comments		:
--
---------------------------------------------------------------------------------------------------
-- Header		: AES_OUTPUT_5_TYPE
--
-- MIB ref		: swCardEventLogSlotXX       .17.65.69.83.95.79.85.84.80.85.84.95.53.95.84.89.80.69
-- absolute OID	: 1.3.6.1.4.1.7995.2.6.1.1.XX.17.65.69.83.95.79.85.84.80.85.84.95.53.95.84.89.80.69
-- Vary			: YES
--
-- Value(s)		: Unknown
--				: PCM
--              : NONPCM
--              : WARN: No Input
-- Comments		:
--
---------------------------------------------------------------------------------------------------
-- Header		: AES_OUTPUT_6_TYPE
--
-- MIB ref		: swCardEventLogSlotXX       .17.65.69.83.95.79.85.84.80.85.84.95.54.95.84.89.80.69
-- absolute OID	: 1.3.6.1.4.1.7995.2.6.1.1.XX.17.65.69.83.95.79.85.84.80.85.84.95.54.95.84.89.80.69
-- Vary			: YES
--
-- Value(s)		: Unknown
--				: PCM
--              : NONPCM
--              : WARN: No Input
-- Comments		:
--
---------------------------------------------------------------------------------------------------
-- Header		: AES_OUTPUT_7_TYPE
--
-- MIB ref		: swCardEventLogSlotXX       .17.65.69.83.95.79.85.84.80.85.84.95.55.95.84.89.80.69
-- absolute OID	: 1.3.6.1.4.1.7995.2.6.1.1.XX.17.65.69.83.95.79.85.84.80.85.84.95.55.95.84.89.80.69
-- Vary			: YES
--
-- Value(s)		: Unknown
--				: PCM
--              : NONPCM
--              : WARN: No Input
-- Comments		:
--
---------------------------------------------------------------------------------------------------
-- Header		: AES_OUTPUT_8_TYPE
--
-- MIB ref		: swCardEventLogSlotXX       .17.65.69.83.95.79.85.84.80.85.84.95.56.95.84.89.80.69
-- absolute OID	: 1.3.6.1.4.1.7995.2.6.1.1.XX.17.65.69.83.95.79.85.84.80.85.84.95.56.95.84.89.80.69
-- Vary			: YES
--
-- Value(s)		: Unknown
--				: PCM
--              : NONPCM
--              : WARN: No Input
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_OUTPUT_1_STATE
--
-- MIB ref		: swCardEventLogSlotXX       .18.65.69.83.95.79.85.84.80.85.84.95.49.95.83.84.65.84.69
-- absolute OID	: 1.3.6.1.4.1.7995.2.6.1.1.XX.18.65.69.83.95.79.85.84.80.85.84.95.49.95.83.84.65.84.69
-- Vary			: YES
--
-- Value(s)		: WARN:Off
-- Value(s)		: LOST
--				: FAIL:Lost
--              : OK
--              : Unknown
-- Comments		:
--
---------------------------------------------------------------------------------------------------
-- Header		: AES_OUTPUT_2_STATE
--
-- MIB ref		: swCardEventLogSlotXX       .18.65.69.83.95.79.85.84.80.85.84.95.50.95.83.84.65.84.69
-- absolute OID	: 1.3.6.1.4.1.7995.2.6.1.1.XX.18.65.69.83.95.79.85.84.80.85.84.95.50.95.83.84.65.84.69
-- Vary			: YES
--
-- Value(s)		: WARN:Off
-- Value(s)		: LOST
--				: FAIL:Lost
--              : OK
--              : Unknown
-- Comments		:
--
---------------------------------------------------------------------------------------------------
-- Header		: AES_OUTPUT_3_STATE
--
-- MIB ref		: swCardEventLogSlotXX       .18.65.69.83.95.79.85.84.80.85.84.95.51.95.83.84.65.84.69
-- absolute OID	: 1.3.6.1.4.1.7995.2.6.1.1.XX.18.65.69.83.95.79.85.84.80.85.84.95.51.95.83.84.65.84.69
-- Vary			: YES
--
-- Value(s)		: WARN:Off
-- Value(s)		: LOST
--				: FAIL:Lost
--              : OK
--              : Unknown
-- Comments		:
--
---------------------------------------------------------------------------------------------------
-- Header		: AES_OUTPUT_4_STATE
--
-- MIB ref		: swCardEventLogSlotXX       .18.65.69.83.95.79.85.84.80.85.84.95.52.95.83.84.65.84.69
-- absolute OID	: 1.3.6.1.4.1.7995.2.6.1.1.XX.18.65.69.83.95.79.85.84.80.85.84.95.52.95.83.84.65.84.69
-- Vary			: YES
--
-- Value(s)		: WARN:Off
-- Value(s)		: LOST
--				: FAIL:Lost
--              : OK
--              : Unknown
-- Comments		:
--
---------------------------------------------------------------------------------------------------
-- Header		: AES_OUTPUT_5_STATE
--
-- MIB ref		: swCardEventLogSlotXX       .18.65.69.83.95.79.85.84.80.85.84.95.53.95.83.84.65.84.69
-- absolute OID	: 1.3.6.1.4.1.7995.2.6.1.1.XX.18.65.69.83.95.79.85.84.80.85.84.95.53.95.83.84.65.84.69
-- Vary			: YES
--
-- Value(s)		: WARN:Off
-- Value(s)		: LOST
--				: FAIL:Lost
--              : OK
--              : Unknown
-- Comments		:
--
---------------------------------------------------------------------------------------------------
-- Header		: AES_OUTPUT_6_STATE
--
-- MIB ref		: swCardEventLogSlotXX       .18.65.69.83.95.79.85.84.80.85.84.95.54.95.83.84.65.84.69
-- absolute OID	: 1.3.6.1.4.1.7995.2.6.1.1.XX.18.65.69.83.95.79.85.84.80.85.84.95.54.95.83.84.65.84.69
-- Vary			: YES
--
-- Value(s)		: WARN:Off
-- Value(s)		: LOST
--				: FAIL:Lost
--              : OK
--              : Unknown
-- Comments		:
--
---------------------------------------------------------------------------------------------------
-- Header		: AES_OUTPUT_7_STATE
--
-- MIB ref		: swCardEventLogSlotXX       .18.65.69.83.95.79.85.84.80.85.84.95.55.95.83.84.65.84.69
-- absolute OID	: 1.3.6.1.4.1.7995.2.6.1.1.XX.18.65.69.83.95.79.85.84.80.85.84.95.55.95.83.84.65.84.69
-- Vary			: YES
--
-- Value(s)		: WARN:Off
-- Value(s)		: LOST
--				: FAIL:Lost
--              : OK
--              : Unknown
-- Comments		:
--
---------------------------------------------------------------------------------------------------
-- Header		: AES_OUTPUT_8_STATE
--
-- MIB ref		: swCardEventLogSlotXX       .18.65.69.83.95.79.85.84.80.85.84.95.56.95.83.84.65.84.69
-- absolute OID	: 1.3.6.1.4.1.7995.2.6.1.1.XX.18.65.69.83.95.79.85.84.80.85.84.95.56.95.83.84.65.84.69
-- Vary			: YES
--
-- Value(s)		: Warn:Off
-- Value(s)		: LOST
--				: FAIL:Lost
--              : OK
--              : Unknown
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
-- Vary			: YES
--
-- Value(s)		: 0
--				:
-- Comments		: Number of error seconds
--
---------------------------------------------------------------------------------------------------
-- Header		: OUTPUT_1_ANC_STATE
--
-- MIB ref		: swCardEventLogSlotXX       .18.79.85.84.80.85.84.95.49.95.65.78.67.95.83.84.65.84.69
-- absolute OID	: 1.3.6.1.4.1.7995.2.6.1.1.XX.18.79.85.84.80.85.84.95.49.95.65.78.67.95.83.84.65.84.69
-- Vary			: YES
--
-- Value(s)		: OK
--				: ANC FULL
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: NONE
--              : WARN
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
-- Vary			: YES
--
-- Value(s)		: 0
--				:
-- Comments		: Number of error seconds
--
---------------------------------------------------------------------------------------------------
-- Header		: DOLBY_DECODE_INPUT_STATE
--
-- MIB ref		: swCardEventLogSlotXX       .24.68.79.76.66.89.95.68.69.67.79.68.69.95.73.78.80.85.84.95.83.84.65.84.69
-- absolute OID	: 1.3.6.1.4.1.7995.2.6.1.1.XX.24.68.79.76.66.89.95.68.69.67.79.68.69.95.73.78.80.85.84.95.83.84.65.84.69
-- Vary			: YES
--
-- Value(s)     : FAIL
--              : OK
--              : FAIL:No Input
--              : WARN:Mute
--              : -
-- Comments		:
--
---------------------------------------------------------------------------------------------------
-- Header		: DOLBY_DECODE_D_DYNRNG_MODE
--
-- MIB ref		: swCardEventLogSlotXX       .26.68.79.76.66.89.95.68.69.67.79.68.69.95.68.95.68.89.78.82.78.71.95.77.79.68.69
-- absolute OID	: 1.3.6.1.4.1.7995.2.6.1.1.XX.26.68.79.76.66.89.95.68.69.67.79.68.69.95.68.95.68.89.78.82.78.71.95.77.79.68.69
-- Vary			: YES
--
-- Value(s)     : Bypass
--              : Custom
--              : RF
--              : Line
--              : -
-- Comments		:
--
---------------------------------------------------------------------------------------------------
-- Header		: DOLBY_DECODE_PROG_1_DIALNORM
--
-- MIB ref		: swCardEventLogSlotXX       .28.68.79.76.66.89.95.68.69.67.79.68.69.95.80.82.79.71.95.49.95.68.73.65.76.78.79.82.77
-- absolute OID	: 1.3.6.1.4.1.7995.2.6.1.1.XX.28.68.79.76.66.89.95.68.69.67.79.68.69.95.80.82.79.71.95.49.95.68.73.65.76.78.79.82.77
-- Vary			: YES
--
-- Value(s)     : -1 dB to -31 bB
--				:
-- Comments		:
--
---------------------------------------------------------------------------------------------------
-- Header		: DOLBY_DECODE_PROG_1_LFE_CHAN
--
-- MIB ref		: swCardEventLogSlotXX       .28.68.79.76.66.89.95.68.69.67.79.68.69.95.80.82.79.71.95.49.95.76.70.69.95.67.72.65.78
-- absolute OID	: 1.3.6.1.4.1.7995.2.6.1.1.XX.28.68.79.76.66.89.95.68.69.67.79.68.69.95.80.82.79.71.95.49.95.76.70.69.95.67.72.65.78
-- Vary			: YES
--
-- Value(s)     : OFF
--              : ON
--              : -
-- Comments		:
--
---------------------------------------------------------------------------------------------------
-- Header		: DOLBY_DECODE_PROG_2_DIALNORM
--
-- MIB ref		: swCardEventLogSlotXX       .28.68.79.76.66.89.95.68.69.67.79.68.69.95.80.82.79.71.95.50.95.68.73.65.76.78.79.82.77
-- absolute OID	: 1.3.6.1.4.1.7995.2.6.1.1.XX.28.68.79.76.66.89.95.68.69.67.79.68.69.95.80.82.79.71.95.50.95.68.73.65.76.78.79.82.77
-- Vary			: YES
--
-- Value(s)     : -1 dB to -31 bB
--				:
-- Comments		:
--
---------------------------------------------------------------------------------------------------
-- Header		: DOLBY_DECODE_PROG_2_LFE_CHAN
--
-- MIB ref		: swCardEventLogSlotXX       .28.68.79.76.66.89.95.68.69.67.79.68.69.95.80.82.79.71.95.50.95.76.70.69.95.67.72.65.78
-- absolute OID	: 1.3.6.1.4.1.7995.2.6.1.1.XX.28.68.79.76.66.89.95.68.69.67.79.68.69.95.80.82.79.71.95.50.95.76.70.69.95.67.72.65.78
-- Vary			: YES
--
-- Value(s)     : OFF
--              : ON
--              : -
-- Comments		:
--
---------------------------------------------------------------------------------------------------
-- Header		: DOLBY_DECODE_PROG_3_DIALNORM
--
-- MIB ref		: swCardEventLogSlotXX       .28.68.79.76.66.89.95.68.69.67.79.68.69.95.80.82.79.71.95.51.95.68.73.65.76.78.79.82.77
-- absolute OID	: 1.3.6.1.4.1.7995.2.6.1.1.XX.28.68.79.76.66.89.95.68.69.67.79.68.69.95.80.82.79.71.95.51.95.68.73.65.76.78.79.82.77
-- Vary			: YES
--
-- Value(s)     : -1 dB to -31 bB
--				:
-- Comments		:
--
---------------------------------------------------------------------------------------------------
-- Header		: DOLBY_DECODE_PROG_3_LFE_CHAN
--
-- MIB ref		: swCardEventLogSlotXX       .28.68.79.76.66.89.95.68.69.67.79.68.69.95.80.82.79.71.95.51.95.76.70.69.95.67.72.65.78
-- absolute OID	: 1.3.6.1.4.1.7995.2.6.1.1.XX.28.68.79.76.66.89.95.68.69.67.79.68.69.95.80.82.79.71.95.51.95.76.70.69.95.67.72.65.78
-- Vary			: YES
--
-- Value(s)     : OFF
--              : ON
--              : -
-- Comments		:
--
---------------------------------------------------------------------------------------------------
-- Header		: DOLBY_DECODE_PROG_4_DIALNORM
--
-- MIB ref		: swCardEventLogSlotXX       .28.68.79.76.66.89.95.68.69.67.79.68.69.95.80.82.79.71.95.52.95.68.73.65.76.78.79.82.77
-- absolute OID	: 1.3.6.1.4.1.7995.2.6.1.1.XX.28.68.79.76.66.89.95.68.69.67.79.68.69.95.80.82.79.71.95.52.95.68.73.65.76.78.79.82.77
-- Vary			: YES
--
-- Value(s)     : -1 dB to -31 bB
--				:
-- Comments		:
--
---------------------------------------------------------------------------------------------------
-- Header		: DOLBY_DECODE_PROG_4_LFE_CHAN
--
-- MIB ref		: swCardEventLogSlotXX       .28.68.79.76.66.89.95.68.69.67.79.68.69.95.80.82.79.71.95.52.95.76.70.69.95.67.72.65.78
-- absolute OID	: 1.3.6.1.4.1.7995.2.6.1.1.XX.28.68.79.76.66.89.95.68.69.67.79.68.69.95.80.82.79.71.95.52.95.76.70.69.95.67.72.65.78
-- Vary			: YES
--
-- Value(s)     : OFF
--              : ON
--              : -
-- Comments		:
--
---------------------------------------------------------------------------------------------------
-- Header		: DOLBY_DECODE_PROG_5_DIALNORM
--
-- MIB ref		: swCardEventLogSlotXX       .28.68.79.76.66.89.95.68.69.67.79.68.69.95.80.82.79.71.95.53.95.68.73.65.76.78.79.82.77
-- absolute OID	: 1.3.6.1.4.1.7995.2.6.1.1.XX.28.68.79.76.66.89.95.68.69.67.79.68.69.95.80.82.79.71.95.53.95.68.73.65.76.78.79.82.77
-- Vary			: YES
--
-- Value(s)     : -1 dB to -31 bB
--				:
-- Comments		:
--
---------------------------------------------------------------------------------------------------
-- Header		: DOLBY_DECODE_PROG_5_LFE_CHAN
--
-- MIB ref		: swCardEventLogSlotXX       .28.68.79.76.66.89.95.68.69.67.79.68.69.95.80.82.79.71.95.53.95.76.70.69.95.67.72.65.78
-- absolute OID	: 1.3.6.1.4.1.7995.2.6.1.1.XX.28.68.79.76.66.89.95.68.69.67.79.68.69.95.80.82.79.71.95.53.95.76.70.69.95.67.72.65.78
-- Vary			: YES
--
-- Value(s)     : OFF
--              : ON
--              : -
-- Comments		:
--
---------------------------------------------------------------------------------------------------
-- Header		: DOLBY_DECODE_PROG_6_DIALNORM
--
-- MIB ref		: swCardEventLogSlotXX       .28.68.79.76.66.89.95.68.69.67.79.68.69.95.80.82.79.71.95.54.95.68.73.65.76.78.79.82.77
-- absolute OID	: 1.3.6.1.4.1.7995.2.6.1.1.XX.28.68.79.76.66.89.95.68.69.67.79.68.69.95.80.82.79.71.95.54.95.68.73.65.76.78.79.82.77
-- Vary			: YES
--
-- Value(s)     : -1 dB to -31 bB
--				:
-- Comments		:
--
---------------------------------------------------------------------------------------------------
-- Header		: DOLBY_DECODE_PROG_6_LFE_CHAN
--
-- MIB ref		: swCardEventLogSlotXX       .28.68.79.76.66.89.95.68.69.67.79.68.69.95.80.82.79.71.95.54.95.76.70.69.95.67.72.65.78
-- absolute OID	: 1.3.6.1.4.1.7995.2.6.1.1.XX.28.68.79.76.66.89.95.68.69.67.79.68.69.95.80.82.79.71.95.54.95.76.70.69.95.67.72.65.78
-- Vary			: YES
--
-- Value(s)     : OFF
--              : ON
--              : -
-- Comments		:
--
---------------------------------------------------------------------------------------------------
-- Header		: DOLBY_DECODE_PROG_7_DIALNORM
--
-- MIB ref		: swCardEventLogSlotXX       .28.68.79.76.66.89.95.68.69.67.79.68.69.95.80.82.79.71.95.55.95.68.73.65.76.78.79.82.77
-- absolute OID	: 1.3.6.1.4.1.7995.2.6.1.1.XX.28.68.79.76.66.89.95.68.69.67.79.68.69.95.80.82.79.71.95.55.95.68.73.65.76.78.79.82.77
-- Vary			: YES
--
-- Value(s)     : -1 dB to -31 bB
--				:
-- Comments		:
--
---------------------------------------------------------------------------------------------------
-- Header		: DOLBY_DECODE_PROG_7_LFE_CHAN
--
-- MIB ref		: swCardEventLogSlotXX       .28.68.79.76.66.89.95.68.69.67.79.68.69.95.80.82.79.71.95.55.95.76.70.69.95.67.72.65.78
-- absolute OID	: 1.3.6.1.4.1.7995.2.6.1.1.XX.28.68.79.76.66.89.95.68.69.67.79.68.69.95.80.82.79.71.95.55.95.76.70.69.95.67.72.65.78
-- Vary			: YES
--
-- Value(s)     : OFF
--              : ON
--              : -
-- Comments		:
--
---------------------------------------------------------------------------------------------------
-- Header		: DOLBY_DECODE_PROG_8_DIALNORM
--
-- MIB ref		: swCardEventLogSlotXX       .28.68.79.76.66.89.95.68.69.67.79.68.69.95.80.82.79.71.95.56.95.68.73.65.76.78.79.82.77
-- absolute OID	: 1.3.6.1.4.1.7995.2.6.1.1.XX.28.68.79.76.66.89.95.68.69.67.79.68.69.95.80.82.79.71.95.56.95.68.73.65.76.78.79.82.77
-- Vary			: YES
--
-- Value(s)     : -1 dB to -31 bB
--				:
-- Comments		:
--
---------------------------------------------------------------------------------------------------
-- Header		: DOLBY_DECODE_PROG_8_LFE_CHAN
--
-- MIB ref		: swCardEventLogSlotXX       .28.68.79.76.66.89.95.68.69.67.79.68.69.95.80.82.79.71.95.56.95.76.70.69.95.67.72.65.78
-- absolute OID	: 1.3.6.1.4.1.7995.2.6.1.1.XX.28.68.79.76.66.89.95.68.69.67.79.68.69.95.80.82.79.71.95.56.95.76.70.69.95.67.72.65.78
-- Vary			: YES
--
-- Value(s)     : OFF
--              : ON
--              : -
-- Comments		:
--
---------------------------------------------------------------------------------------------------
-- Header		: DOLBY_DECODE_D_LISTENING_MODE
--
-- MIB ref		: swCardEventLogSlotXX       .29.68.79.76.66.89.95.68.69.67.79.68.69.95.68.95.76.73.83.84.69.78.73.78.71.95.77.79.68.69
-- absolute OID	: 1.3.6.1.4.1.7995.2.6.1.1.XX.29.68.79.76.66.89.95.68.69.67.79.68.69.95.68.95.76.73.83.84.69.78.73.78.71.95.77.79.68.69
-- Vary			: YES
--
-- Value(s)     : Full
--              : Mono
--              : Stereo
--              : Phantom
--              : 3 Stereo
--              : EX
--              : -
-- Comments		:
--
---------------------------------------------------------------------------------------------------
-- Header		: DOLBY_DECODE_INPUT_FRAME_SYNC
--
-- MIB ref		: swCardEventLogSlotXX       .29.68.79.76.66.89.95.68.69.67.79.68.69.95.73.78.80.85.84.95.70.82.65.77.69.95.83.89.78.67
-- absolute OID	: 1.3.6.1.4.1.7995.2.6.1.1.XX.29.68.79.76.66.89.95.68.69.67.79.68.69.95.73.78.80.85.84.95.70.82.65.77.69.95.83.89.78.67
-- Vary			: YES
--
-- Value(s)     : FAIL
--              : OK
--              : FAIL:No Input
--              : WARN:Mute
--              : -
-- Comments		:
--
---------------------------------------------------------------------------------------------------
-- Header		: DOLBY_DECODE_PROG_1_CHAN_MODE
--
-- MIB ref		: swCardEventLogSlotXX       .29.68.79.76.66.89.95.68.69.67.79.68.69.95.80.82.79.71.95.49.95.67.72.65.78.95.77.79.68.69
-- absolute OID	: 1.3.6.1.4.1.7995.2.6.1.1.XX.29.68.79.76.66.89.95.68.69.67.79.68.69.95.80.82.79.71.95.49.95.67.72.65.78.95.77.79.68.69
-- Vary			: YES
--
-- Value(s)     : 1+1
--              : 1/0
--              : 2/0
--              : 3/0
--              : 2/1
--              : 3/1
--              : 2/2
--              : 3/2
--              : -
-- Comments		:
--
---------------------------------------------------------------------------------------------------
-- Header		: DOLBY_DECODE_PROG_1_COMP_GAIN
--
-- MIB ref		: swCardEventLogSlotXX       .29.68.79.76.66.89.95.68.69.67.79.68.69.95.80.82.79.71.95.49.95.67.79.77.80.95.71.65.73.78
-- absolute OID	: 1.3.6.1.4.1.7995.2.6.1.1.XX.29.68.79.76.66.89.95.68.69.67.79.68.69.95.80.82.79.71.95.49.95.67.79.77.80.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_1_DESC_TEXT
--
-- MIB ref		: swCardEventLogSlotXX       .29.68.79.76.66.89.95.68.69.67.79.68.69.95.80.82.79.71.95.49.95.68.69.83.67.95.84.69.88.84
-- absolute OID	: 1.3.6.1.4.1.7995.2.6.1.1.XX.29.68.79.76.66.89.95.68.69.67.79.68.69.95.80.82.79.71.95.49.95.68.69.83.67.95.84.69.88.84
-- Vary			: YES
--
-- Value(s)     :  <32Character Program Description>
-- Comments		:
--
---------------------------------------------------------------------------------------------------
-- Header		: DOLBY_DECODE_PROG_2_CHAN_MODE
--
-- MIB ref		: swCardEventLogSlotXX       .29.68.79.76.66.89.95.68.69.67.79.68.69.95.80.82.79.71.95.50.95.67.72.65.78.95.77.79.68.69
-- absolute OID	: 1.3.6.1.4.1.7995.2.6.1.1.XX.29.68.79.76.66.89.95.68.69.67.79.68.69.95.80.82.79.71.95.50.95.67.72.65.78.95.77.79.68.69
-- Vary			: YES
--
-- Value(s)     : 1+1
--              : 1/0
--              : 2/0
--              : 3/0
--              : 2/1
--              : 3/1
--              : 2/2
--              : 3/2
--              : -
-- Comments		:
--
---------------------------------------------------------------------------------------------------
-- Header		: DOLBY_DECODE_PROG_2_COMP_GAIN
--
-- MIB ref		: swCardEventLogSlotXX       .29.68.79.76.66.89.95.68.69.67.79.68.69.95.80.82.79.71.95.50.95.67.79.77.80.95.71.65.73.78
-- absolute OID	: 1.3.6.1.4.1.7995.2.6.1.1.XX.29.68.79.76.66.89.95.68.69.67.79.68.69.95.80.82.79.71.95.50.95.67.79.77.80.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_2_DESC_TEXT
--
-- MIB ref		: swCardEventLogSlotXX       .29.68.79.76.66.89.95.68.69.67.79.68.69.95.80.82.79.71.95.50.95.68.69.83.67.95.84.69.88.84
-- absolute OID	: 1.3.6.1.4.1.7995.2.6.1.1.XX.29.68.79.76.66.89.95.68.69.67.79.68.69.95.80.82.79.71.95.50.95.68.69.83.67.95.84.69.88.84
-- Vary			: YES
--
-- Value(s)     :  <32Character Program Description>
--				:
-- Comments		:
--
---------------------------------------------------------------------------------------------------
-- Header		: DOLBY_DECODE_PROG_3_CHAN_MODE
--
-- MIB ref		: swCardEventLogSlotXX       .29.68.79.76.66.89.95.68.69.67.79.68.69.95.80.82.79.71.95.51.95.67.72.65.78.95.77.79.68.69
-- absolute OID	: 1.3.6.1.4.1.7995.2.6.1.1.XX.29.68.79.76.66.89.95.68.69.67.79.68.69.95.80.82.79.71.95.51.95.67.72.65.78.95.77.79.68.69
-- Vary			: YES
--
-- Value(s)     : 1+1
--              : 1/0
--              : 2/0
--              : 3/0
--              : 2/1
--              : 3/1
--              : 2/2
--              : 3/2
--              : -
-- Comments		:
--
---------------------------------------------------------------------------------------------------
-- Header		: DOLBY_DECODE_PROG_3_COMP_GAIN
--
-- MIB ref		: swCardEventLogSlotXX       .29.68.79.76.66.89.95.68.69.67.79.68.69.95.80.82.79.71.95.51.95.67.79.77.80.95.71.65.73.78
-- absolute OID	: 1.3.6.1.4.1.7995.2.6.1.1.XX.29.68.79.76.66.89.95.68.69.67.79.68.69.95.80.82.79.71.95.51.95.67.79.77.80.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_3_DESC_TEXT
--
-- MIB ref		: swCardEventLogSlotXX       .29.68.79.76.66.89.95.68.69.67.79.68.69.95.80.82.79.71.95.51.95.68.69.83.67.95.84.69.88.84
-- absolute OID	: 1.3.6.1.4.1.7995.2.6.1.1.XX.29.68.79.76.66.89.95.68.69.67.79.68.69.95.80.82.79.71.95.51.95.68.69.83.67.95.84.69.88.84
-- Vary			: YES
--
-- Value(s)     :  <32Character Program Description>

--				:
-- Comments		:
--
---------------------------------------------------------------------------------------------------
-- Header		: DOLBY_DECODE_PROG_4_CHAN_MODE
--
-- MIB ref		: swCardEventLogSlotXX       .29.68.79.76.66.89.95.68.69.67.79.68.69.95.80.82.79.71.95.52.95.67.72.65.78.95.77.79.68.69
-- absolute OID	: 1.3.6.1.4.1.7995.2.6.1.1.XX.29.68.79.76.66.89.95.68.69.67.79.68.69.95.80.82.79.71.95.52.95.67.72.65.78.95.77.79.68.69
-- Vary			: YES
--
-- Value(s)     : 1+1
--              : 1/0
--              : 2/0
--              : 3/0
--              : 2/1
--              : 3/1
--              : 2/2
--              : 3/2
--              : -
-- Comments		:
--
---------------------------------------------------------------------------------------------------
-- Header		: DOLBY_DECODE_PROG_4_COMP_GAIN
--
-- MIB ref		: swCardEventLogSlotXX       .29.68.79.76.66.89.95.68.69.67.79.68.69.95.80.82.79.71.95.52.95.67.79.77.80.95.71.65.73.78
-- absolute OID	: 1.3.6.1.4.1.7995.2.6.1.1.XX.29.68.79.76.66.89.95.68.69.67.79.68.69.95.80.82.79.71.95.52.95.67.79.77.80.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_4_DESC_TEXT
--
-- MIB ref		: swCardEventLogSlotXX       .29.68.79.76.66.89.95.68.69.67.79.68.69.95.80.82.79.71.95.52.95.68.69.83.67.95.84.69.88.84
-- absolute OID	: 1.3.6.1.4.1.7995.2.6.1.1.XX.29.68.79.76.66.89.95.68.69.67.79.68.69.95.80.82.79.71.95.52.95.68.69.83.67.95.84.69.88.84
-- Vary			: YES
--
-- Value(s)     :  <32Character Program Description>
--				:
-- Comments		:
--
---------------------------------------------------------------------------------------------------
-- Header		: DOLBY_DECODE_PROG_5_CHAN_MODE
--
-- MIB ref		: swCardEventLogSlotXX       .29.68.79.76.66.89.95.68.69.67.79.68.69.95.80.82.79.71.95.53.95.67.72.65.78.95.77.79.68.69
-- absolute OID	: 1.3.6.1.4.1.7995.2.6.1.1.XX.29.68.79.76.66.89.95.68.69.67.79.68.69.95.80.82.79.71.95.53.95.67.72.65.78.95.77.79.68.69
-- Vary			: YES
--
-- Value(s)     : 1+1
--              : 1/0
--              : 2/0
--              : 3/0
--              : 2/1
--              : 3/1
--              : 2/2
--              : 3/2
--              : -
-- Comments		:
--
---------------------------------------------------------------------------------------------------
-- Header		: DOLBY_DECODE_PROG_5_COMP_GAIN
--
-- MIB ref		: swCardEventLogSlotXX       .29.68.79.76.66.89.95.68.69.67.79.68.69.95.80.82.79.71.95.53.95.67.79.77.80.95.71.65.73.78
-- absolute OID	: 1.3.6.1.4.1.7995.2.6.1.1.XX.29.68.79.76.66.89.95.68.69.67.79.68.69.95.80.82.79.71.95.53.95.67.79.77.80.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_5_DESC_TEXT
--
-- MIB ref		: swCardEventLogSlotXX       .29.68.79.76.66.89.95.68.69.67.79.68.69.95.80.82.79.71.95.53.95.68.69.83.67.95.84.69.88.84
-- absolute OID	: 1.3.6.1.4.1.7995.2.6.1.1.XX.29.68.79.76.66.89.95.68.69.67.79.68.69.95.80.82.79.71.95.53.95.68.69.83.67.95.84.69.88.84
-- Vary			: YES
--
-- Value(s)     :  <32Character Program Description>
--				:
-- Comments		:
--
---------------------------------------------------------------------------------------------------
-- Header		: DOLBY_DECODE_PROG_6_CHAN_MODE
--
-- MIB ref		: swCardEventLogSlotXX       .29.68.79.76.66.89.95.68.69.67.79.68.69.95.80.82.79.71.95.54.95.67.72.65.78.95.77.79.68.69
-- absolute OID	: 1.3.6.1.4.1.7995.2.6.1.1.XX.29.68.79.76.66.89.95.68.69.67.79.68.69.95.80.82.79.71.95.54.95.67.72.65.78.95.77.79.68.69
-- Vary			: YES
--
-- Value(s)     : 1+1
--              : 1/0
--              : 2/0
--              : 3/0
--              : 2/1
--              : 3/1
--              : 2/2
--              : 3/2
--              : -
-- Comments		:
--
---------------------------------------------------------------------------------------------------
-- Header		: DOLBY_DECODE_PROG_6_COMP_GAIN
--
-- MIB ref		: swCardEventLogSlotXX       .29.68.79.76.66.89.95.68.69.67.79.68.69.95.80.82.79.71.95.54.95.67.79.77.80.95.71.65.73.78
-- absolute OID	: 1.3.6.1.4.1.7995.2.6.1.1.XX.29.68.79.76.66.89.95.68.69.67.79.68.69.95.80.82.79.71.95.54.95.67.79.77.80.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_6_DESC_TEXT
--
-- MIB ref		: swCardEventLogSlotXX       .29.68.79.76.66.89.95.68.69.67.79.68.69.95.80.82.79.71.95.54.95.68.69.83.67.95.84.69.88.84
-- absolute OID	: 1.3.6.1.4.1.7995.2.6.1.1.XX.29.68.79.76.66.89.95.68.69.67.79.68.69.95.80.82.79.71.95.54.95.68.69.83.67.95.84.69.88.84
-- Vary			: YES
--
-- Value(s)     :  <32Character Program Description>
--				:
-- Comments		:
--
---------------------------------------------------------------------------------------------------
-- Header		: DOLBY_DECODE_PROG_7_CHAN_MODE
--
-- MIB ref		: swCardEventLogSlotXX       .29.68.79.76.66.89.95.68.69.67.79.68.69.95.80.82.79.71.95.55.95.67.72.65.78.95.77.79.68.69
-- absolute OID	: 1.3.6.1.4.1.7995.2.6.1.1.XX.29.68.79.76.66.89.95.68.69.67.79.68.69.95.80.82.79.71.95.55.95.67.72.65.78.95.77.79.68.69
-- Vary			: YES
--
-- Value(s)     : 1+1
--              : 1/0
--              : 2/0
--              : 3/0
--              : 2/1
--              : 3/1
--              : 2/2
--              : 3/2
--              : -
-- Comments		:
--
---------------------------------------------------------------------------------------------------
-- Header		: DOLBY_DECODE_PROG_7_COMP_GAIN
--
-- MIB ref		: swCardEventLogSlotXX       .29.68.79.76.66.89.95.68.69.67.79.68.69.95.80.82.79.71.95.55.95.67.79.77.80.95.71.65.73.78
-- absolute OID	: 1.3.6.1.4.1.7995.2.6.1.1.XX.29.68.79.76.66.89.95.68.69.67.79.68.69.95.80.82.79.71.95.55.95.67.79.77.80.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_7_DESC_TEXT
--
-- MIB ref		: swCardEventLogSlotXX       .29.68.79.76.66.89.95.68.69.67.79.68.69.95.80.82.79.71.95.55.95.68.69.83.67.95.84.69.88.84
-- absolute OID	: 1.3.6.1.4.1.7995.2.6.1.1.XX.29.68.79.76.66.89.95.68.69.67.79.68.69.95.80.82.79.71.95.55.95.68.69.83.67.95.84.69.88.84
-- Vary			: YES
--
-- Value(s)     :  <32Character Program Description>
--				:
-- Comments		:
--
---------------------------------------------------------------------------------------------------
-- Header		: DOLBY_DECODE_PROG_8_CHAN_MODE
--
-- MIB ref		: swCardEventLogSlotXX       .29.68.79.76.66.89.95.68.69.67.79.68.69.95.80.82.79.71.95.56.95.67.72.65.78.95.77.79.68.69
-- absolute OID	: 1.3.6.1.4.1.7995.2.6.1.1.XX.29.68.79.76.66.89.95.68.69.67.79.68.69.95.80.82.79.71.95.56.95.67.72.65.78.95.77.79.68.69
-- Vary			: YES
--
-- Value(s)     : 1+1
--              : 1/0
--              : 2/0
--              : 3/0
--              : 2/1
--              : 3/1
--              : 2/2
--              : 3/2
--              : -
-- Comments		:
--
---------------------------------------------------------------------------------------------------
-- Header		: DOLBY_DECODE_PROG_8_COMP_GAIN
--
-- MIB ref		: swCardEventLogSlotXX       .29.68.79.76.66.89.95.68.69.67.79.68.69.95.80.82.79.71.95.56.95.67.79.77.80.95.71.65.73.78
-- absolute OID	: 1.3.6.1.4.1.7995.2.6.1.1.XX.29.68.79.76.66.89.95.68.69.67.79.68.69.95.80.82.79.71.95.56.95.67.79.77.80.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_8_DESC_TEXT
--
-- MIB ref		: swCardEventLogSlotXX       .29.68.79.76.66.89.95.68.69.67.79.68.69.95.80.82.79.71.95.56.95.68.69.83.67.95.84.69.88.84
-- absolute OID	: 1.3.6.1.4.1.7995.2.6.1.1.XX.29.68.79.76.66.89.95.68.69.67.79.68.69.95.80.82.79.71.95.56.95.68.69.83.67.95.84.69.88.84
-- Vary			: YES
--
-- Value(s)     :  <32Character Program Description>
--				:
-- Comments		:
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: DOLBY_DECODE_INPUT_PROG_CONFIG
--
-- MIB ref		: swCardEventLogSlotXX       .30.68.79.76.66.89.95.68.69.67.79.68.69.95.73.78.80.85.84.95.80.82.79.71.95.67.79.78.70.73.71
-- absolute OID	: 1.3.6.1.4.1.7995.2.6.1.1.XX.30.68.79.76.66.89.95.68.69.67.79.68.69.95.73.78.80.85.84.95.80.82.79.71.95.67.79.78.70.73.71
-- Vary			: YES
--
--              : 3/2L
--              : 3/2
--              : 3/1
--              : 2/0 (dsurmod:10)
--              : 2/0 (dsurmod:0X)
--              : 1+1
--              : 1/0
--              : 5.1+2
--              : 5.1+1+1
--              : 4+4
--              : 4+2+2
--              : 4+2+1+1
--              : 4+1+1+1+1
--              : 2+2+2+2
--              : 2+2+2+1+1
--              : 2+2+1+1+1+1
--              : 2+1+1+1+1+1+1
--              : 1+1+1+1+1+1+1+1
--              : 5.1
--              : 4+2
--              : 4+1+1
--              : 2+2+2
--              : 2+2+1+1
--              : 2+1+1+1+1
--              : 1+1+1+1+1+1
--              : 4
--              : 2+2
--              : 2+1+1
--              : 1+1+1+1
--              : -
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: LOST
--				: FAIL:Lost
--              : OK
--              : Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: LOST
--				: FAIL:Lost
--              : OK
--              : Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: LOST
--				: FAIL:Lost
--              : OK
--              : Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: DOLBY_DECODE_AUXOUT_DYNRNG_MODE
--
-- MIB ref		: swCardEventLogSlotXX       .31.68.79.76.66.89.95.68.69.67.79.68.69.95.65.85.88.79.85.84.95.68.89.78.82.78.71.95.77.79.68.69
-- absolute OID	: 1.3.6.1.4.1.7995.2.6.1.1.XX.31.68.79.76.66.89.95.68.69.67.79.68.69.95.65.85.88.79.85.84.95.68.89.78.82.78.71.95.77.79.68.69
-- Vary			: YES
--
-- Value(s)     : RF
--              : LINE
--              : -
-- Comments		:
--
---------------------------------------------------------------------------------------------------
-- Header		: DOLBY_DECODE_E_INPUT_FRAME_RATE
--
-- MIB ref		: swCardEventLogSlotXX       .31.68.79.76.66.89.95.68.69.67.79.68.69.95.69.95.73.78.80.85.84.95.70.82.65.77.69.95.82.65.84.69
-- absolute OID	: 1.3.6.1.4.1.7995.2.6.1.1.XX.31.68.79.76.66.89.95.68.69.67.79.68.69.95.69.95.73.78.80.85.84.95.70.82.65.77.69.95.82.65.84.69
-- Vary			: YES
--
-- Value(s)     : 23
--              : 24
--              : 25
--              : 29
--              : 30
--              : -
-- Comments		:
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_2_DOLBY
--
-- MIB ref		: swCardEventLogSlotXX       .31.79.85.84.80.85.84.95.49.95.69.77.66.69.68.68.69.68.95.65.85.68.73.79.95.50.95.68.79.76.66.89
-- absolute OID	: 1.3.6.1.4.1.7995.2.6.1.1.XX.31.79.85.84.80.85.84.95.49.95.69.77.66.69.68.68.69.68.95.65.85.68.73.79.95.50.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_3_DOLBY
--
-- MIB ref		: swCardEventLogSlotXX       .31.79.85.84.80.85.84.95.49.95.69.77.66.69.68.68.69.68.95.65.85.68.73.79.95.51.95.68.79.76.66.89
-- absolute OID	: 1.3.6.1.4.1.7995.2.6.1.1.XX.31.79.85.84.80.85.84.95.49.95.69.77.66.69.68.68.69.68.95.65.85.68.73.79.95.51.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_4_DOLBY
--
-- MIB ref		: swCardEventLogSlotXX       .31.79.85.84.80.85.84.95.49.95.69.77.66.69.68.68.69.68.95.65.85.68.73.79.95.52.95.68.79.76.66.89
-- absolute OID	: 1.3.6.1.4.1.7995.2.6.1.1.XX.31.79.85.84.80.85.84.95.49.95.69.77.66.69.68.68.69.68.95.65.85.68.73.79.95.52.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_5_DOLBY
--
-- MIB ref		: swCardEventLogSlotXX       .31.79.85.84.80.85.84.95.49.95.69.77.66.69.68.68.69.68.95.65.85.68.73.79.95.53.95.68.79.76.66.89
-- absolute OID	: 1.3.6.1.4.1.7995.2.6.1.1.XX.31.79.85.84.80.85.84.95.49.95.69.77.66.69.68.68.69.68.95.65.85.68.73.79.95.53.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_6_DOLBY
--
-- MIB ref		: swCardEventLogSlotXX       .31.79.85.84.80.85.84.95.49.95.69.77.66.69.68.68.69.68.95.65.85.68.73.79.95.54.95.68.79.76.66.89
-- absolute OID	: 1.3.6.1.4.1.7995.2.6.1.1.XX.31.79.85.84.80.85.84.95.49.95.69.77.66.69.68.68.69.68.95.65.85.68.73.79.95.54.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_7_DOLBY
--
-- MIB ref		: swCardEventLogSlotXX       .31.79.85.84.80.85.84.95.49.95.69.77.66.69.68.68.69.68.95.65.85.68.73.79.95.55.95.68.79.76.66.89
-- absolute OID	: 1.3.6.1.4.1.7995.2.6.1.1.XX.31.79.85.84.80.85.84.95.49.95.69.77.66.69.68.68.69.68.95.65.85.68.73.79.95.55.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_8_DOLBY
--
-- MIB ref		: swCardEventLogSlotXX       .31.79.85.84.80.85.84.95.49.95.69.77.66.69.68.68.69.68.95.65.85.68.73.79.95.56.95.68.79.76.66.89
-- absolute OID	: 1.3.6.1.4.1.7995.2.6.1.1.XX.31.79.85.84.80.85.84.95.49.95.69.77.66.69.68.68.69.68.95.65.85.68.73.79.95.56.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: WARN:No Input
--      		: LOST
--				: FAIL:Lost
--              : OK
--              : Unknown
-- Comments		:
--
---------------------------------------------------------------------------------------------------
-- Header		: DOLBY_DECODE_D_INPUT_ERROR_COUNT
--
-- MIB ref		: swCardEventLogSlotXX       .32.68.79.76.66.89.95.68.69.67.79.68.69.95.68.95.73.78.80.85.84.95.69.82.82.79.82.95.67.79.85.78.84
-- absolute OID	: 1.3.6.1.4.1.7995.2.6.1.1.XX.32.68.79.76.66.89.95.68.69.67.79.68.69.95.68.95.73.78.80.85.84.95.69.82.82.79.82.95.67.79.85.78.84
-- Vary			: YES
--
-- Value(s)     : 0 to 4294967295
--				:
-- Comments		:
--
---------------------------------------------------------------------------------------------------
-- Header		: DOLBY_DECODE_E_INPUT_ERROR_COUNT
--
-- MIB ref		: swCardEventLogSlotXX       .32.68.79.76.66.89.95.68.69.67.79.68.69.95.69.95.73.78.80.85.84.95.69.82.82.79.82.95.67.79.85.78.84
-- absolute OID	: 1.3.6.1.4.1.7995.2.6.1.1.XX.32.68.79.76.66.89.95.68.69.67.79.68.69.95.69.95.73.78.80.85.84.95.69.82.82.79.82.95.67.79.85.78.84
-- Vary			: YES
--
-- Value(s)     : 0 to 4294967295
--				:
-- Comments		:
--
---------------------------------------------------------------------------------------------------
-- Header		: OUTPUT_1_EMBEDDED_AUDIO_1_1_LEVEL
--
-- MIB ref		: swCardEventLogSlotXX       .33.79.85.84.80.85.84.95.49.95.69.77.66.69.68.68.69.68.95.65.85.68.73.79.95.49.95.49.95.76.69.86.69.76
-- absolute OID	: 1.3.6.1.4.1.7995.2.6.1.1.XX.33.79.85.84.80.85.84.95.49.95.69.77.66.69.68.68.69.68.95.65.85.68.73.79.95.49.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_1_2_LEVEL
--
-- MIB ref		: swCardEventLogSlotXX       .33.79.85.84.80.85.84.95.49.95.69.77.66.69.68.68.69.68.95.65.85.68.73.79.95.49.95.50.95.76.69.86.69.76
-- absolute OID	: 1.3.6.1.4.1.7995.2.6.1.1.XX.33.79.85.84.80.85.84.95.49.95.69.77.66.69.68.68.69.68.95.65.85.68.73.79.95.49.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_1_LEVEL
--
-- MIB ref		: swCardEventLogSlotXX       .33.79.85.84.80.85.84.95.49.95.69.77.66.69.68.68.69.68.95.65.85.68.73.79.95.50.95.49.95.76.69.86.69.76
-- absolute OID	: 1.3.6.1.4.1.7995.2.6.1.1.XX.33.79.85.84.80.85.84.95.49.95.69.77.66.69.68.68.69.68.95.65.85.68.73.79.95.50.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_2_LEVEL
--
-- MIB ref		: swCardEventLogSlotXX       .33.79.85.84.80.85.84.95.49.95.69.77.66.69.68.68.69.68.95.65.85.68.73.79.95.50.95.50.95.76.69.86.69.76
-- absolute OID	: 1.3.6.1.4.1.7995.2.6.1.1.XX.33.79.85.84.80.85.84.95.49.95.69.77.66.69.68.68.69.68.95.65.85.68.73.79.95.50.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_1_LEVEL
--
-- MIB ref		: swCardEventLogSlotXX       .33.79.85.84.80.85.84.95.49.95.69.77.66.69.68.68.69.68.95.65.85.68.73.79.95.51.95.49.95.76.69.86.69.76
-- absolute OID	: 1.3.6.1.4.1.7995.2.6.1.1.XX.33.79.85.84.80.85.84.95.49.95.69.77.66.69.68.68.69.68.95.65.85.68.73.79.95.51.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_2_LEVEL
--
-- MIB ref		: swCardEventLogSlotXX       .33.79.85.84.80.85.84.95.49.95.69.77.66.69.68.68.69.68.95.65.85.68.73.79.95.51.95.50.95.76.69.86.69.76
-- absolute OID	: 1.3.6.1.4.1.7995.2.6.1.1.XX.33.79.85.84.80.85.84.95.49.95.69.77.66.69.68.68.69.68.95.65.85.68.73.79.95.51.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_4_1_LEVEL
--
-- MIB ref		: swCardEventLogSlotXX       .33.79.85.84.80.85.84.95.49.95.69.77.66.69.68.68.69.68.95.65.85.68.73.79.95.52.95.49.95.76.69.86.69.76
-- absolute OID	: 1.3.6.1.4.1.7995.2.6.1.1.XX.33.79.85.84.80.85.84.95.49.95.69.77.66.69.68.68.69.68.95.65.85.68.73.79.95.52.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_4_2_LEVEL
--
-- MIB ref		: swCardEventLogSlotXX       .33.79.85.84.80.85.84.95.49.95.69.77.66.69.68.68.69.68.95.65.85.68.73.79.95.52.95.50.95.76.69.86.69.76
-- absolute OID	: 1.3.6.1.4.1.7995.2.6.1.1.XX.33.79.85.84.80.85.84.95.49.95.69.77.66.69.68.68.69.68.95.65.85.68.73.79.95.52.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_5_1_LEVEL
--
-- MIB ref		: swCardEventLogSlotXX       .33.79.85.84.80.85.84.95.49.95.69.77.66.69.68.68.69.68.95.65.85.68.73.79.95.53.95.49.95.76.69.86.69.76
-- absolute OID	: 1.3.6.1.4.1.7995.2.6.1.1.XX.33.79.85.84.80.85.84.95.49.95.69.77.66.69.68.68.69.68.95.65.85.68.73.79.95.53.95.49.95.76.69.86.69.76
-- Vary			: YES
--
-- Value(s)		: OK
--				: WARN:Silent
--              : WARN:Quiet
--              : WARN:Loud
--              : WARN:Overflow
--
---------------------------------------------------------------------------------------------------
-- Header		: OUTPUT_1_EMBEDDED_AUDIO_5_2_LEVEL
--
-- MIB ref		: swCardEventLogSlotXX       .33.79.85.84.80.85.84.95.49.95.69.77.66.69.68.68.69.68.95.65.85.68.73.79.95.53.95.50.95.76.69.86.69.76
-- absolute OID	: 1.3.6.1.4.1.7995.2.6.1.1.XX.33.79.85.84.80.85.84.95.49.95.69.77.66.69.68.68.69.68.95.65.85.68.73.79.95.53.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_1_LEVEL
--
-- MIB ref		: swCardEventLogSlotXX       .33.79.85.84.80.85.84.95.49.95.69.77.66.69.68.68.69.68.95.65.85.68.73.79.95.54.95.49.95.76.69.86.69.76
-- absolute OID	: 1.3.6.1.4.1.7995.2.6.1.1.XX.33.79.85.84.80.85.84.95.49.95.69.77.66.69.68.68.69.68.95.65.85.68.73.79.95.54.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_2_LEVEL
--
-- MIB ref		: swCardEventLogSlotXX       .33.79.85.84.80.85.84.95.49.95.69.77.66.69.68.68.69.68.95.65.85.68.73.79.95.54.95.50.95.76.69.86.69.76
-- absolute OID	: 1.3.6.1.4.1.7995.2.6.1.1.XX.33.79.85.84.80.85.84.95.49.95.69.77.66.69.68.68.69.68.95.65.85.68.73.79.95.54.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_7_1_LEVEL
--
-- MIB ref		: swCardEventLogSlotXX       .33.79.85.84.80.85.84.95.49.95.69.77.66.69.68.68.69.68.95.65.85.68.73.79.95.55.95.49.95.76.69.86.69.76
-- absolute OID	: 1.3.6.1.4.1.7995.2.6.1.1.XX.33.79.85.84.80.85.84.95.49.95.69.77.66.69.68.68.69.68.95.65.85.68.73.79.95.55.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_7_2_LEVEL
--
-- MIB ref		: swCardEventLogSlotXX       .33.79.85.84.80.85.84.95.49.95.69.77.66.69.68.68.69.68.95.65.85.68.73.79.95.55.95.50.95.76.69.86.69.76
-- absolute OID	: 1.3.6.1.4.1.7995.2.6.1.1.XX.33.79.85.84.80.85.84.95.49.95.69.77.66.69.68.68.69.68.95.65.85.68.73.79.95.55.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_1_LEVEL
--
-- MIB ref		: swCardEventLogSlotXX       .33.79.85.84.80.85.84.95.49.95.69.77.66.69.68.68.69.68.95.65.85.68.73.79.95.56.95.49.95.76.69.86.69.76
-- absolute OID	: 1.3.6.1.4.1.7995.2.6.1.1.XX.33.79.85.84.80.85.84.95.49.95.69.77.66.69.68.68.69.68.95.65.85.68.73.79.95.56.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_2_LEVEL
--
-- MIB ref		: swCardEventLogSlotXX       .33.79.85.84.80.85.84.95.49.95.69.77.66.69.68.68.69.68.95.65.85.68.73.79.95.56.95.50.95.76.69.86.69.76
-- absolute OID	: 1.3.6.1.4.1.7995.2.6.1.1.XX.33.79.85.84.80.85.84.95.49.95.69.77.66.69.68.68.69.68.95.65.85.68.73.79.95.56.95.50.95.76.69.86.69.76
-- Vary			: YES
--
-- Value(s)		: OK
--				: WARN:Silent
--              : WARN:Quiet
--              : WARN:Loud
--              : WARN:Overflow
-- Comments		:
--
---------------------------------------------------------------------------------------------------
-- Header		: DOLBY_DECODE_PROG_1_DYN_RANGE_GAIN
--
-- MIB ref		: swCardEventLogSlotXX       .34.68.79.76.66.89.95.68.69.67.79.68.69.95.80.82.79.71.95.49.95.68.89.78.95.82.65.78.71.69.95.71.65.73.78
-- absolute OID	: 1.3.6.1.4.1.7995.2.6.1.1.XX.34.68.79.76.66.89.95.68.69.67.79.68.69.95.80.82.79.71.95.49.95.68.89.78.95.82.65.78.71.69.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_1_STEREO_DOWNMIX
--
-- MIB ref		: swCardEventLogSlotXX       .34.68.79.76.66.89.95.68.69.67.79.68.69.95.80.82.79.71.95.49.95.83.84.69.82.69.79.95.68.79.87.78.77.73.88
-- absolute OID	: 1.3.6.1.4.1.7995.2.6.1.1.XX.34.68.79.76.66.89.95.68.69.67.79.68.69.95.80.82.79.71.95.49.95.83.84.69.82.69.79.95.68.79.87.78.77.73.88
-- Vary			: YES
--
-- Value(s)     : Not Indicated
--              : Lt/Rt
--              : Lo/Ro
--              : -
-- Comments		:
--
---------------------------------------------------------------------------------------------------
-- Header		: DOLBY_DECODE_PROG_2_DYN_RANGE_GAIN
--
-- MIB ref		: swCardEventLogSlotXX       .34.68.79.76.66.89.95.68.69.67.79.68.69.95.80.82.79.71.95.50.95.68.89.78.95.82.65.78.71.69.95.71.65.73.78
-- absolute OID	: 1.3.6.1.4.1.7995.2.6.1.1.XX.34.68.79.76.66.89.95.68.69.67.79.68.69.95.80.82.79.71.95.50.95.68.89.78.95.82.65.78.71.69.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_2_STEREO_DOWNMIX
--
-- MIB ref		: swCardEventLogSlotXX       .34.68.79.76.66.89.95.68.69.67.79.68.69.95.80.82.79.71.95.50.95.83.84.69.82.69.79.95.68.79.87.78.77.73.88
-- absolute OID	: 1.3.6.1.4.1.7995.2.6.1.1.XX.34.68.79.76.66.89.95.68.69.67.79.68.69.95.80.82.79.71.95.50.95.83.84.69.82.69.79.95.68.79.87.78.77.73.88
-- Vary			: YES
--
-- Value(s)     : Not Indicated
--              : Lt/Rt
--              : Lo/Ro
--              : -
-- Comments		:
--
---------------------------------------------------------------------------------------------------
-- Header		: DOLBY_DECODE_PROG_3_DYN_RANGE_GAIN
--
-- MIB ref		: swCardEventLogSlotXX       .34.68.79.76.66.89.95.68.69.67.79.68.69.95.80.82.79.71.95.51.95.68.89.78.95.82.65.78.71.69.95.71.65.73.78
-- absolute OID	: 1.3.6.1.4.1.7995.2.6.1.1.XX.34.68.79.76.66.89.95.68.69.67.79.68.69.95.80.82.79.71.95.51.95.68.89.78.95.82.65.78.71.69.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_3_STEREO_DOWNMIX
--
-- MIB ref		: swCardEventLogSlotXX       .34.68.79.76.66.89.95.68.69.67.79.68.69.95.80.82.79.71.95.51.95.83.84.69.82.69.79.95.68.79.87.78.77.73.88
-- absolute OID	: 1.3.6.1.4.1.7995.2.6.1.1.XX.34.68.79.76.66.89.95.68.69.67.79.68.69.95.80.82.79.71.95.51.95.83.84.69.82.69.79.95.68.79.87.78.77.73.88
-- Vary			: YES
--
-- Value(s)     : Not Indicated
--              : Lt/Rt
--              : Lo/Ro
--              : -
-- Comments		:
--
---------------------------------------------------------------------------------------------------
-- Header		: DOLBY_DECODE_PROG_4_DYN_RANGE_GAIN
--
-- MIB ref		: swCardEventLogSlotXX       .34.68.79.76.66.89.95.68.69.67.79.68.69.95.80.82.79.71.95.52.95.68.89.78.95.82.65.78.71.69.95.71.65.73.78
-- absolute OID	: 1.3.6.1.4.1.7995.2.6.1.1.XX.34.68.79.76.66.89.95.68.69.67.79.68.69.95.80.82.79.71.95.52.95.68.89.78.95.82.65.78.71.69.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_4_STEREO_DOWNMIX
--
-- MIB ref		: swCardEventLogSlotXX       .34.68.79.76.66.89.95.68.69.67.79.68.69.95.80.82.79.71.95.52.95.83.84.69.82.69.79.95.68.79.87.78.77.73.88
-- absolute OID	: 1.3.6.1.4.1.7995.2.6.1.1.XX.34.68.79.76.66.89.95.68.69.67.79.68.69.95.80.82.79.71.95.52.95.83.84.69.82.69.79.95.68.79.87.78.77.73.88
-- Vary			: YES
--
-- Value(s)     : Not Indicated
--              : Lt/Rt
--              : Lo/Ro
--              : -
-- Comments		:
--
---------------------------------------------------------------------------------------------------
-- Header		: DOLBY_DECODE_PROG_5_DYN_RANGE_GAIN
--
-- MIB ref		: swCardEventLogSlotXX       .34.68.79.76.66.89.95.68.69.67.79.68.69.95.80.82.79.71.95.53.95.68.89.78.95.82.65.78.71.69.95.71.65.73.78
-- absolute OID	: 1.3.6.1.4.1.7995.2.6.1.1.XX.34.68.79.76.66.89.95.68.69.67.79.68.69.95.80.82.79.71.95.53.95.68.89.78.95.82.65.78.71.69.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_5_STEREO_DOWNMIX
--
-- MIB ref		: swCardEventLogSlotXX       .34.68.79.76.66.89.95.68.69.67.79.68.69.95.80.82.79.71.95.53.95.83.84.69.82.69.79.95.68.79.87.78.77.73.88
-- absolute OID	: 1.3.6.1.4.1.7995.2.6.1.1.XX.34.68.79.76.66.89.95.68.69.67.79.68.69.95.80.82.79.71.95.53.95.83.84.69.82.69.79.95.68.79.87.78.77.73.88
-- Vary			: YES
--
-- Value(s)     : Not Indicated
--              : Lt/Rt
--              : Lo/Ro
--              : -
-- Comments		:
--
---------------------------------------------------------------------------------------------------
-- Header		: DOLBY_DECODE_PROG_6_DYN_RANGE_GAIN
--
-- MIB ref		: swCardEventLogSlotXX       .34.68.79.76.66.89.95.68.69.67.79.68.69.95.80.82.79.71.95.54.95.68.89.78.95.82.65.78.71.69.95.71.65.73.78
-- absolute OID	: 1.3.6.1.4.1.7995.2.6.1.1.XX.34.68.79.76.66.89.95.68.69.67.79.68.69.95.80.82.79.71.95.54.95.68.89.78.95.82.65.78.71.69.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_6_STEREO_DOWNMIX
--
-- MIB ref		: swCardEventLogSlotXX       .34.68.79.76.66.89.95.68.69.67.79.68.69.95.80.82.79.71.95.54.95.83.84.69.82.69.79.95.68.79.87.78.77.73.88
-- absolute OID	: 1.3.6.1.4.1.7995.2.6.1.1.XX.34.68.79.76.66.89.95.68.69.67.79.68.69.95.80.82.79.71.95.54.95.83.84.69.82.69.79.95.68.79.87.78.77.73.88
-- Vary			: YES
--
-- Value(s)     : Not Indicated
--              : Lt/Rt
--              : Lo/Ro
--              : -
-- Comments		:
--
---------------------------------------------------------------------------------------------------
-- Header		: DOLBY_DECODE_PROG_7_DYN_RANGE_GAIN
--
-- MIB ref		: swCardEventLogSlotXX       .34.68.79.76.66.89.95.68.69.67.79.68.69.95.80.82.79.71.95.55.95.68.89.78.95.82.65.78.71.69.95.71.65.73.78
-- absolute OID	: 1.3.6.1.4.1.7995.2.6.1.1.XX.34.68.79.76.66.89.95.68.69.67.79.68.69.95.80.82.79.71.95.55.95.68.89.78.95.82.65.78.71.69.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_7_STEREO_DOWNMIX
--
-- MIB ref		: swCardEventLogSlotXX       .34.68.79.76.66.89.95.68.69.67.79.68.69.95.80.82.79.71.95.55.95.83.84.69.82.69.79.95.68.79.87.78.77.73.88
-- absolute OID	: 1.3.6.1.4.1.7995.2.6.1.1.XX.34.68.79.76.66.89.95.68.69.67.79.68.69.95.80.82.79.71.95.55.95.83.84.69.82.69.79.95.68.79.87.78.77.73.88
-- Vary			: YES
--
-- Value(s)     : Not Indicated
--              : Lt/Rt
--              : Lo/Ro
--              : -
-- Comments		:
--
---------------------------------------------------------------------------------------------------
-- Header		: DOLBY_DECODE_PROG_8_DYN_RANGE_GAIN
--
-- MIB ref		: swCardEventLogSlotXX       .34.68.79.76.66.89.95.68.69.67.79.68.69.95.80.82.79.71.95.56.95.68.89.78.95.82.65.78.71.69.95.71.65.73.78
-- absolute OID	: 1.3.6.1.4.1.7995.2.6.1.1.XX.34.68.79.76.66.89.95.68.69.67.79.68.69.95.80.82.79.71.95.56.95.68.89.78.95.82.65.78.71.69.95.71.65.73.78
-- Vary			: YES
--
-- Value(s)     : NONE
--              : Film Standard
--              : Film Light
--              : Music Standard
--              : Music Light
--              : Speech
--              : -
-- Comments		:
--
---------------------------------------------------------------------------------------------------
-- Header		: DOLBY_DECODE_PROG_8_STEREO_DOWNMIX
--
-- MIB ref		: swCardEventLogSlotXX       .34.68.79.76.66.89.95.68.69.67.79.68.69.95.80.82.79.71.95.56.95.83.84.69.82.69.79.95.68.79.87.78.77.73.88
-- absolute OID	: 1.3.6.1.4.1.7995.2.6.1.1.XX.34.68.79.76.66.89.95.68.69.67.79.68.69.95.80.82.79.71.95.56.95.83.84.69.82.69.79.95.68.79.87.78.77.73.88
-- Vary			: YES
--
-- Value(s)     : Not Indicated
--              : Lt/Rt
--              : Lo/Ro
--              : -
-- Comments		:
--
---------------------------------------------------------------------------------------------------
-- Header		: DOLBY_DECODE_INPUT_BITSTREAM_FORMAT
--
-- MIB ref		: swCardEventLogSlotXX       .35.68.79.76.66.89.95.68.69.67.79.68.69.95.73.78.80.85.84.95.66.73.84.83.84.82.69.65.77.95.70.79.82.77.65.84
-- absolute OID	: 1.3.6.1.4.1.7995.2.6.1.1.XX.35.68.79.76.66.89.95.68.69.67.79.68.69.95.73.78.80.85.84.95.66.73.84.83.84.82.69.65.77.95.70.79.82.77.65.84
-- Vary			: YES
--
-- Value(s)     : PCM
--              : Dolby D
--              : Dolby E
--              : -
-- Comments		:
--
---------------------------------------------------------------------------------------------------
