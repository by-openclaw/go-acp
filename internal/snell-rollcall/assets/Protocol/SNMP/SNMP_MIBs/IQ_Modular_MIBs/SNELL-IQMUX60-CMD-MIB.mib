-- ************************************************************************************
-- Snell&Wilcox Card:IQMUX60
--        Module Id#:404
--       Command Set:5
--          Filename:SNELL-IQMUX60-CMD-MIB.mib
--            Author:Jonathan Riches
--              Date:13/07/2006
--              Time:16:25
--
-- Copyright (c) 2005 Snell & Wilcox Ltd
-- All rights reserved.
--
-- ************************************************************************************

SNELL-IQMUX60-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQMUX60,
    moduleIQMUX60MIB
        FROM SNELL-WILCOX-PRODUCT-REG;

 moduleIQMUX60CmdMi MODULE-IDENTITY
    LAST-UPDATED "0607131625Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQMUX60MIB 1 }




--********************************************************************************
--*
--*  Snell Wilcox Card:
--*  command set:
--*  list commands/menus:
--*
--******************************************************************************
	iqmux60CmdTable OBJECT-TYPE
		SYNTAX			SEQUENCE OF Iqmux60CmdEntry
		MAX-ACCESS		not-accessible
		STATUS			current
		DESCRIPTION
				"Note the instance of this table is relected in the command set Version"
		::= { moduleIQMUX60 1 }

	iqmux60CmdEntry OBJECT-TYPE
		SYNTAX		Iqmux60CmdEntry
		MAX-ACCESS		not-accessible
		STATUS			current
		DESCRIPTION
				"Entry in command table."
		INDEX	{ iqmux60SlotIndex }
		::= { iqmux60CmdTable 1 }

	Iqmux60CmdEntry ::=
		SEQUENCE {
			iqmux60SlotIndex
				Unsigned32,
			iqmux60VideoInput
				INTEGER,
			iqmux60VideoInput525
				INTEGER,
			iqmux60VideoInput625
				INTEGER,
			iqmux60VideoProcAmp1In1ProcAmpEnable
				INTEGER,
			iqmux60VideoProcAmp1LumaGain
				INTEGER,
			iqmux60VideoProcAmp1ChromaGain
				INTEGER,
			iqmux60VideoProcAmp1BlackLevel
				INTEGER,
			iqmux60VideoProcAmp1PicturePosition
				INTEGER,
			iqmux60VideoProcAmp1YCTiming
				INTEGER,
			iqmux60VideoProcAmp2In2ProcAmpEnable
				INTEGER,
			iqmux60VideoProcAmp2LumaGain
				INTEGER,
			iqmux60VideoProcAmp2ChromaGain
				INTEGER,
			iqmux60VideoProcAmp2BlackLevel
				INTEGER,
			iqmux60VideoProcAmp2PicturePosition
				INTEGER,
			iqmux60VideoProcAmp2YCTiming
				INTEGER,
			iqmux60AudioDeembed
				INTEGER,
			iqmux60AudioAESOutputAES1Source
				INTEGER,
			iqmux60AudioAESOutputAES2Source
				INTEGER,
			iqmux60AudioProcAmpDeembedStereo1
				INTEGER,
			iqmux60ProcAmpDeembed1LGainDeembed1L
				INTEGER,
			iqmux60ProcAmpDeembed1LInvert
				INTEGER,
			iqmux60ProcAmpDeembed1LMute
				INTEGER,
			iqmux60ProcAmpDeembed1RGainDeembed1R
				INTEGER,
			iqmux60ProcAmpDeembed1RInvert
				INTEGER,
			iqmux60ProcAmpDeembed1RMute
				INTEGER,
			iqmux60AudioProcAmpDeembedStereo2
				INTEGER,
			iqmux60ProcAmpDeembed2LGainDeembed2L
				INTEGER,
			iqmux60ProcAmpDeembed2LInvert
				INTEGER,
			iqmux60ProcAmpDeembed2LMute
				INTEGER,
			iqmux60ProcAmpDeembed2RGainDeembed2R
				INTEGER,
			iqmux60ProcAmpDeembed2RInvert
				INTEGER,
			iqmux60ProcAmpDeembed2RMute
				INTEGER,
			iqmux60AudioProcAmpDeembedStereo3
				INTEGER,
			iqmux60ProcAmpDeembed3LGainDeembed3L
				INTEGER,
			iqmux60ProcAmpDeembed3LInvert
				INTEGER,
			iqmux60ProcAmpDeembed3LMute
				INTEGER,
			iqmux60ProcAmpDeembed3RGainDeembed3R
				INTEGER,
			iqmux60ProcAmpDeembed3RInvert
				INTEGER,
			iqmux60ProcAmpDeembed3RMute
				INTEGER,
			iqmux60AudioProcAmpDeembedStereo4
				INTEGER,
			iqmux60ProcAmpDeembed4LGainDeembed4L
				INTEGER,
			iqmux60ProcAmpDeembed4LInvert
				INTEGER,
			iqmux60ProcAmpDeembed4LMute
				INTEGER,
			iqmux60ProcAmpDeembed4RGainDeembed4R
				INTEGER,
			iqmux60ProcAmpDeembed4RInvert
				INTEGER,
			iqmux60ProcAmpDeembed4RMute
				INTEGER,
			iqmux60AudioProcAmpDeembedStereo5
				INTEGER,
			iqmux60ProcAmpDeembed5LGainDeembed5L
				INTEGER,
			iqmux60ProcAmpDeembed5LInvert
				INTEGER,
			iqmux60ProcAmpDeembed5LMute
				INTEGER,
			iqmux60ProcAmpDeembed5RGainDeembed5R
				INTEGER,
			iqmux60ProcAmpDeembed5RInvert
				INTEGER,
			iqmux60ProcAmpDeembed5RMute
				INTEGER,
			iqmux60AudioProcAmpDeembedStereo6
				INTEGER,
			iqmux60ProcAmpDeembed6LGainDeembed6L
				INTEGER,
			iqmux60ProcAmpDeembed6LInvert
				INTEGER,
			iqmux60ProcAmpDeembed6LMute
				INTEGER,
			iqmux60ProcAmpDeembed6RGainDeembed6R
				INTEGER,
			iqmux60ProcAmpDeembed6RInvert
				INTEGER,
			iqmux60ProcAmpDeembed6RMute
				INTEGER,
			iqmux60AudioProcAmpDeembedStereo7
				INTEGER,
			iqmux60ProcAmpDeembed7LGainDeembed7L
				INTEGER,
			iqmux60ProcAmpDeembed7LInvert
				INTEGER,
			iqmux60ProcAmpDeembed7LMute
				INTEGER,
			iqmux60ProcAmpDeembed7RGainDeembed7R
				INTEGER,
			iqmux60ProcAmpDeembed7RInvert
				INTEGER,
			iqmux60ProcAmpDeembed7RMute
				INTEGER,
			iqmux60AudioProcAmpDeembedStereo8
				INTEGER,
			iqmux60ProcAmpDeembed8LGainDeembed8L
				INTEGER,
			iqmux60ProcAmpDeembed8LInvert
				INTEGER,
			iqmux60ProcAmpDeembed8LMute
				INTEGER,
			iqmux60ProcAmpDeembed8RGainDeembed8R
				INTEGER,
			iqmux60ProcAmpDeembed8RInvert
				INTEGER,
			iqmux60ProcAmpDeembed8RMute
				INTEGER,
			iqmux60AudioProcAmpAESStereo1
				INTEGER,
			iqmux60ProcAmpAES1LGainAES1L
				INTEGER,
			iqmux60ProcAmpAES1LInvert
				INTEGER,
			iqmux60ProcAmpAES1LMute
				INTEGER,
			iqmux60ProcAmpAES1RGainAES1R
				INTEGER,
			iqmux60ProcAmpAES1RInvert
				INTEGER,
			iqmux60ProcAmpAES1RMute
				INTEGER,
			iqmux60AudioProcAmpAESStereo2
				INTEGER,
			iqmux60ProcAmpAES2LGainAES2L
				INTEGER,
			iqmux60ProcAmpAES2LInvert
				INTEGER,
			iqmux60ProcAmpAES2LMute
				INTEGER,
			iqmux60ProcAmpAES2RGainAES2R
				INTEGER,
			iqmux60ProcAmpAES2RInvert
				INTEGER,
			iqmux60ProcAmpAES2RMute
				INTEGER,
			iqmux60AudioProcAmpStereo1
				INTEGER,
			iqmux60ProcAmpAnalog1LGainAnalog1L
				INTEGER,
			iqmux60ProcAmpAnalog1LInvert
				INTEGER,
			iqmux60ProcAmpAnalog1LMute
				INTEGER,
			iqmux60ProcAmpAnalog1RGainAnalog1R
				INTEGER,
			iqmux60ProcAmpAnalog1RInvert
				INTEGER,
			iqmux60ProcAmpAnalog1RMute
				INTEGER,
			iqmux60AudioProcAmpStereo2
				INTEGER,
			iqmux60ProcAmpAnalog2LGainAnalog2L
				INTEGER,
			iqmux60ProcAmpAnalog2LInvert
				INTEGER,
			iqmux60ProcAmpAnalog2LMute
				INTEGER,
			iqmux60ProcAmpAnalog2RGainAnalog2R
				INTEGER,
			iqmux60ProcAmpAnalog2RInvert
				INTEGER,
			iqmux60ProcAmpAnalog2RMute
				INTEGER,
			iqmux60EmbedEmbedder1Embed1Source
				INTEGER,
			iqmux60EmbedEmbedder1PairSelection
				INTEGER,
			iqmux60EmbedEmbedder1Disable
				INTEGER,
			iqmux60EmbedEmbedder2Embed2Source
				INTEGER,
			iqmux60EmbedEmbedder2PairSelection
				INTEGER,
			iqmux60EmbedEmbedder2Disable
				INTEGER,
			iqmux60EmbedEmbedder3Embed3Source
				INTEGER,
			iqmux60EmbedEmbedder3PairSelection
				INTEGER,
			iqmux60EmbedEmbedder3Disable
				INTEGER,
			iqmux60EmbedEmbedder4Embed4Source
				INTEGER,
			iqmux60EmbedEmbedder4PairSelection
				INTEGER,
			iqmux60EmbedEmbedder4Disable
				INTEGER,
			iqmux60Mixer1Mix1Source1
				INTEGER,
			iqmux60MixMixer1Gain1
				INTEGER,
			iqmux60Mixer1Mix1Source2
				INTEGER,
			iqmux60MixMixer1Gain2
				INTEGER,
			iqmux60Mixer1Mix1Source3
				INTEGER,
			iqmux60MixMixer1Gain3
				INTEGER,
			iqmux60Mixer1Mix1Source4
				INTEGER,
			iqmux60MixMixer1Gain4
				INTEGER,
			iqmux60Mixer2Mix2Source1
				INTEGER,
			iqmux60MixMixer2Gain1
				INTEGER,
			iqmux60Mixer2Mix2Source2
				INTEGER,
			iqmux60MixMixer2Gain2
				INTEGER,
			iqmux60Mixer2Mix2Source3
				INTEGER,
			iqmux60MixMixer2Gain3
				INTEGER,
			iqmux60Mixer2Mix2Source4
				INTEGER,
			iqmux60MixMixer2Gain4
				INTEGER,
			iqmux60Mixer3Mix3Source1
				INTEGER,
			iqmux60MixMixer3Gain1
				INTEGER,
			iqmux60Mixer3Mix3Source2
				INTEGER,
			iqmux60MixMixer3Gain2
				INTEGER,
			iqmux60Mixer3Mix3Source3
				INTEGER,
			iqmux60MixMixer3Gain3
				INTEGER,
			iqmux60Mixer3Mix3Source4
				INTEGER,
			iqmux60MixMixer3Gain4
				INTEGER,
			iqmux60Mixer4Mix4Source1
				INTEGER,
			iqmux60MixMixer4Gain1
				INTEGER,
			iqmux60Mixer4Mix4Source2
				INTEGER,
			iqmux60MixMixer4Gain2
				INTEGER,
			iqmux60Mixer4Mix4Source3
				INTEGER,
			iqmux60MixMixer4Gain3
				INTEGER,
			iqmux60Mixer4Mix4Source4
				INTEGER,
			iqmux60MixMixer4Gain4
				INTEGER,
			iqmux60BusSourceBusALSource
				INTEGER,
			iqmux60BusSourceBusARSource
				INTEGER,
			iqmux60BusSourceBusBLSource
				INTEGER,
			iqmux60BusSourceBusBRSource
				INTEGER,
			iqmux60BusSourceBusCLSource
				INTEGER,
			iqmux60BusSourceBusCRSource
				INTEGER,
			iqmux60BusSourceBusDLSource
				INTEGER,
			iqmux60BusSourceBusDRSource
				INTEGER,
			iqmux60BusesBusProcAmpStereoA
				INTEGER,
			iqmux60BusProcAmpBusALGainBusAL
				INTEGER,
			iqmux60BusProcAmpBusALInvert
				INTEGER,
			iqmux60BusProcAmpBusALMute
				INTEGER,
			iqmux60BusProcAmpBusARGainBusAR
				INTEGER,
			iqmux60BusProcAmpBusARInvert
				INTEGER,
			iqmux60BusProcAmpBusARMute
				INTEGER,
			iqmux60BusesBusProcAmpStereoB
				INTEGER,
			iqmux60BusProcAmpBusBLGainBusBL
				INTEGER,
			iqmux60BusProcAmpBusBLInvert
				INTEGER,
			iqmux60BusProcAmpBusBLMute
				INTEGER,
			iqmux60BusProcAmpBusBRGainBusBR
				INTEGER,
			iqmux60BusProcAmpBusBRInvert
				INTEGER,
			iqmux60BusProcAmpBusBRMute
				INTEGER,
			iqmux60BusesBusProcAmpStereoC
				INTEGER,
			iqmux60BusProcAmpBusCLGainBusCL
				INTEGER,
			iqmux60BusProcAmpBusCLInvert
				INTEGER,
			iqmux60BusProcAmpBusCLMute
				INTEGER,
			iqmux60BusProcAmpBusCRGainBusCR
				INTEGER,
			iqmux60BusProcAmpBusCRInvert
				INTEGER,
			iqmux60BusProcAmpBusCRMute
				INTEGER,
			iqmux60BusesBusProcAmpStereoD
				INTEGER,
			iqmux60BusProcAmpBusDLGainBusDL
				INTEGER,
			iqmux60BusProcAmpBusDLInvert
				INTEGER,
			iqmux60BusProcAmpBusDLMute
				INTEGER,
			iqmux60BusProcAmpBusDRGainBusDR
				INTEGER,
			iqmux60BusProcAmpBusDRInvert
				INTEGER,
			iqmux60BusProcAmpBusDRMute
				INTEGER,
			iqmux60AudioDelayAESInput1Delay
				INTEGER,
			iqmux60AudioDelayAESInput2Delay
				INTEGER,
			iqmux60AudioDelayAnalogIn1Delay
				INTEGER,
			iqmux60AudioDelayAnalogIn2Delay
				INTEGER,
			iqmux60DelayDelaySelectInternal
				INTEGER,
			iqmux60DelayDelaySelectManual
				INTEGER,
			iqmux60DelayDelaySelectRolltrack14
				INTEGER,
			iqmux60DelayDelaySelectRolltrack15
				INTEGER,
			iqmux60DelayDelaySelectRolltrack16
				INTEGER,
			iqmux60DelayDelaySelectRolltrack17
				INTEGER,
			iqmux60DelayDelaySelectGPIDelaySelect
				INTEGER,
			iqmux60DelayDelayStatusManual
				INTEGER,
			iqmux60DelayDelayStatusInternal
				RollCallString,
			iqmux60DelayDelayStatusRolltrack14
				RollCallString,
			iqmux60DelayDelayStatusRolltrack15
				RollCallString,
			iqmux60DelayDelayStatusRolltrack16
				RollCallString,
			iqmux60DelayDelayStatusRolltrack17
				RollCallString,
			iqmux60DelayDelayStatusGPIDelayDisplay
				RollCallString,
			iqmux60DelayDelayStatusTotalDelayDisplay
				RollCallString,
			iqmux60AudioMonitorSilenceLevel
				INTEGER,
			iqmux60AudioMonitorLowLevel
				INTEGER,
			iqmux60AudioMonitorHighLevel
				INTEGER,
			iqmux60AudioMonitorOverloadLevel
				INTEGER,
			iqmux60AudioMonitorWarningTimer
				INTEGER,
			iqmux60Freeze
				INTEGER,
			iqmux60VideoDelay
				INTEGER,
			iqmux60VideoDelayDelayPhase625HPhase
				INTEGER,
			iqmux60VideoDelayDelayPhase625VPhase
				INTEGER,
			iqmux60VideoDelayDelayPhase525HPhase
				INTEGER,
			iqmux60VideoDelayDelayPhase525VPhase
				INTEGER,
			iqmux60UserMemMemory1Save1
				INTEGER,
			iqmux60UserMemMemory1Recall1
				INTEGER,
			iqmux60UserMemMemory1Clear1
				INTEGER,
			iqmux60UserMemMemory1Name1
				RollCallString,
			iqmux60UserMemMemory2Save2
				INTEGER,
			iqmux60UserMemMemory2Recall2
				INTEGER,
			iqmux60UserMemMemory2Clear2
				INTEGER,
			iqmux60UserMemMemory2Name2
				RollCallString,
			iqmux60UserMemMemory3Save3
				INTEGER,
			iqmux60UserMemMemory3Recall3
				INTEGER,
			iqmux60UserMemMemory3Clear3
				INTEGER,
			iqmux60UserMemMemory3Name3
				RollCallString,
			iqmux60UserMemMemory4Save4
				INTEGER,
			iqmux60UserMemMemory4Recall4
				INTEGER,
			iqmux60UserMemMemory4Clear4
				INTEGER,
			iqmux60UserMemMemory4Name4
				RollCallString,
			iqmux60UserMemMemory5Save5
				INTEGER,
			iqmux60UserMemMemory5Recall5
				INTEGER,
			iqmux60UserMemMemory5Clear5
				INTEGER,
			iqmux60UserMemMemory5Name5
				RollCallString,
			iqmux60UserMemMemory6Save6
				INTEGER,
			iqmux60UserMemMemory6Recall6
				INTEGER,
			iqmux60UserMemMemory6Clear6
				INTEGER,
			iqmux60UserMemMemory6Name6
				RollCallString,
			iqmux60UserMemMemory7Save7
				INTEGER,
			iqmux60UserMemMemory7Recall7
				INTEGER,
			iqmux60UserMemMemory7Clear7
				INTEGER,
			iqmux60UserMemMemory7Name7
				RollCallString,
			iqmux60UserMemMemory8Save8
				INTEGER,
			iqmux60UserMemMemory8Recall8
				INTEGER,
			iqmux60UserMemMemory8Clear8
				INTEGER,
			iqmux60UserMemMemory8Name8
				RollCallString,
			iqmux60SetupPatternAnimatedPattern
				INTEGER,
			iqmux60SetupPatternEnablePattern
				INTEGER,
			iqmux60SetupPattern
				INTEGER,
			iqmux60SetupCaptionEditCaption
				RollCallString,
			iqmux60SetupCaption
				INTEGER,
			iqmux60BlankingVIPass525BlankAll
				INTEGER,
			iqmux60BlankingVIPass525PassAll
				INTEGER,
			iqmux60BlankingVIPass525Line11
				INTEGER,
			iqmux60BlankingVIPass525Line274
				INTEGER,
			iqmux60BlankingVIPass525Line12
				INTEGER,
			iqmux60BlankingVIPass525Line275
				INTEGER,
			iqmux60BlankingVIPass525Line13
				INTEGER,
			iqmux60BlankingVIPass525Line276
				INTEGER,
			iqmux60BlankingVIPass525Line14
				INTEGER,
			iqmux60BlankingVIPass525Line277
				INTEGER,
			iqmux60BlankingVIPass525Line15
				INTEGER,
			iqmux60BlankingVIPass525Line278
				INTEGER,
			iqmux60BlankingVIPass525Line16
				INTEGER,
			iqmux60BlankingVIPass525Line279
				INTEGER,
			iqmux60BlankingVIPass525Line17
				INTEGER,
			iqmux60BlankingVIPass525Line280
				INTEGER,
			iqmux60BlankingVIPass525Line18
				INTEGER,
			iqmux60BlankingVIPass525Line281
				INTEGER,
			iqmux60BlankingVIPass525Line19
				INTEGER,
			iqmux60BlankingVIPass525Line282
				INTEGER,
			iqmux60BlankingVIPass525Line20
				INTEGER,
			iqmux60BlankingVIPass525Line283
				INTEGER,
			iqmux60BlankingVIPass525Line21
				INTEGER,
			iqmux60BlankingVIPass625BlankAll
				INTEGER,
			iqmux60BlankingVIPass625PassAll
				INTEGER,
			iqmux60BlankingVIPass625Line7
				INTEGER,
			iqmux60BlankingVIPass625Line320
				INTEGER,
			iqmux60BlankingVIPass625Line8
				INTEGER,
			iqmux60BlankingVIPass625Line321
				INTEGER,
			iqmux60BlankingVIPass625Line9
				INTEGER,
			iqmux60BlankingVIPass625Line322
				INTEGER,
			iqmux60BlankingVIPass625Line10
				INTEGER,
			iqmux60BlankingVIPass625Line323
				INTEGER,
			iqmux60BlankingVIPass625Line11
				INTEGER,
			iqmux60BlankingVIPass625Line324
				INTEGER,
			iqmux60BlankingVIPass625Line12
				INTEGER,
			iqmux60BlankingVIPass625Line325
				INTEGER,
			iqmux60BlankingVIPass625Line13
				INTEGER,
			iqmux60BlankingVIPass625Line326
				INTEGER,
			iqmux60BlankingVIPass625Line14
				INTEGER,
			iqmux60BlankingVIPass625Line327
				INTEGER,
			iqmux60BlankingVIPass625Line15
				INTEGER,
			iqmux60BlankingVIPass625Line328
				INTEGER,
			iqmux60BlankingVIPass625Line16
				INTEGER,
			iqmux60BlankingVIPass625Line329
				INTEGER,
			iqmux60BlankingVIPass625Line17
				INTEGER,
			iqmux60BlankingVIPass625Line330
				INTEGER,
			iqmux60BlankingVIPass625Line18
				INTEGER,
			iqmux60BlankingVIPass625Line331
				INTEGER,
			iqmux60BlankingVIPass625Line19
				INTEGER,
			iqmux60BlankingVIPass625Line332
				INTEGER,
			iqmux60BlankingVIPass625Line20
				INTEGER,
			iqmux60BlankingVIPass625Line333
				INTEGER,
			iqmux60BlankingVIPass625Line21
				INTEGER,
			iqmux60BlankingVIPass625Line334
				INTEGER,
			iqmux60BlankingVIPass625Line22
				INTEGER,
			iqmux60BlankingVIPass625Line335
				INTEGER,
			iqmux60BlankingVIPass625Line23
				INTEGER,
			iqmux60SetupBlankingHancBlank
				INTEGER,
			iqmux60SetupAudioToneIdentEnable
				INTEGER,
			iqmux60SetupAudioToneFrequency
				INTEGER,
			iqmux60SetupAudioToneFrequencyR
				INTEGER,
			iqmux60SetupAudioToneHeadRoom
				INTEGER,
			iqmux60SetupAudioToneADCLineUp
				INTEGER,
			iqmux60SetupSlewRate
				INTEGER,
			iqmux60SetupChannelStatus
				RollCallString,
			iqmux60GPIIOGPIInputDisableInputs
				INTEGER,
			iqmux60GPIIOGPIInputInputTimerEnable
				INTEGER,
			iqmux60GPIIOGPIInputTimerActiveHigh
				INTEGER,
			iqmux60GPIIOGPIInputInputSelection
				INTEGER,
			iqmux60GPIIOGPIInputGPIInStatus
				RollCallString,
			iqmux60GPIIOGPIOutputOutActiveHigh
				INTEGER,
			iqmux60GPIIOGPIOutputOutputSelection
				INTEGER,
			iqmux60GPIIOGPIOutputGPIOutStatus
				RollCallString,
			iqmux60GPIIOGPIInputOutputGPIO1
				INTEGER,
			iqmux60SetupGPIIOInputSelection
				INTEGER,
			iqmux60SetupGPIIOOutputSelection
				INTEGER,
			iqmux60SetupRollTrackRollTrackIndex
				INTEGER,
			iqmux60SetupRollTrackRollTrackSource
				INTEGER,
			iqmux60SetupRollTrackRollTrackDisable
				INTEGER,
			iqmux60SetupRollTrackRollTrackAddress
				RollCallString,
			iqmux60SetupRollTrackRollTrackCommand
				RollCallString,
			iqmux60SetupRollTrackRollTrackSending
				RollCallString,
			iqmux60SetupRollTrackRollTrackStatus
				RollCallString,
			iqmux60SetupRollTrackRollTrackIndexExt
				INTEGER,
			iqmux60SetupRollTrackRollTrackSourceExt
				INTEGER,
			iqmux60SetupRollTrackRollTrackAddressExt
				RollCallString,
			iqmux60SetupRollTrackRollTrackCommandExt
				RollCallString,
			iqmux60SetupLoggingInput
				INTEGER,
			iqmux60SetupLoggingStd
				INTEGER,
			iqmux60SetupLoggingInput1
				INTEGER,
			iqmux60SetupLoggingStd1
				INTEGER,
			iqmux60SetupLoggingInput2
				INTEGER,
			iqmux60SetupLoggingStd2
				INTEGER,
			iqmux60SetupLoggingEDH
				INTEGER,
			iqmux60SetupLoggingEDHErrors
				INTEGER,
			iqmux60SetupLoggingRollTrack
				INTEGER,
			iqmux60SetupLoggingDeembed1
				INTEGER,
			iqmux60SetupLoggingDeembed2
				INTEGER,
			iqmux60SetupLoggingDeembed3
				INTEGER,
			iqmux60SetupLoggingDeembed4
				INTEGER,
			iqmux60SetupLoggingDeembed5
				INTEGER,
			iqmux60SetupLoggingDeembed6
				INTEGER,
			iqmux60SetupLoggingDeembed7
				INTEGER,
			iqmux60SetupLoggingDeembed8
				INTEGER,
			iqmux60SetupLoggingnPCM1
				INTEGER,
			iqmux60SetupLoggingnPCM2
				INTEGER,
			iqmux60SetupLoggingnPCM3
				INTEGER,
			iqmux60SetupLoggingnPCM4
				INTEGER,
			iqmux60SetupLoggingnPCM5
				INTEGER,
			iqmux60SetupLoggingnPCM6
				INTEGER,
			iqmux60SetupLoggingnPCM7
				INTEGER,
			iqmux60SetupLoggingnPCM8
				INTEGER,
			iqmux60SetupLoggingAES1
				INTEGER,
			iqmux60SetupLoggingAES2
				INTEGER,
			iqmux60SetupLoggingBusAL
				INTEGER,
			iqmux60SetupLoggingBusAR
				INTEGER,
			iqmux60SetupLoggingBusBL
				INTEGER,
			iqmux60SetupLoggingBusBR
				INTEGER,
			iqmux60SetupLoggingBusCL
				INTEGER,
			iqmux60SetupLoggingBusCR
				INTEGER,
			iqmux60SetupLoggingBusDL
				INTEGER,
			iqmux60SetupLoggingBusDR
				INTEGER,
			iqmux60SetupLoggingFault
				INTEGER,
			iqmux60SetupLoggingStatusINPUT
				RollCallString,
			iqmux60SetupLoggingStatusSTD
				RollCallString,
			iqmux60SetupLoggingStatusINPUT1
				RollCallString,
			iqmux60SetupLoggingStatusSTD1
				RollCallString,
			iqmux60SetupLoggingStatusINPUT2
				RollCallString,
			iqmux60SetupLoggingStatusSTD2
				RollCallString,
			iqmux60SetupLoggingStatusEDH
				RollCallString,
			iqmux60SetupLoggingStatusERRSEC
				RollCallString,
			iqmux60SetupLoggingStatusROLLTRACK
				RollCallString,
			iqmux60SetupLoggingStatusDEEMBED1
				RollCallString,
			iqmux60SetupLoggingStatusDEEMBED2
				RollCallString,
			iqmux60SetupLoggingStatusDEEMBED3
				RollCallString,
			iqmux60SetupLoggingStatusDEEMBED4
				RollCallString,
			iqmux60SetupLoggingStatusDEEMBED5
				RollCallString,
			iqmux60SetupLoggingStatusDEEMBED6
				RollCallString,
			iqmux60SetupLoggingStatusDEEMBED7
				RollCallString,
			iqmux60SetupLoggingStatusDEEMBED8
				RollCallString,
			iqmux60SetupLoggingStatusNPCM1
				RollCallString,
			iqmux60SetupLoggingStatusNPCM2
				RollCallString,
			iqmux60SetupLoggingStatusNPCM3
				RollCallString,
			iqmux60SetupLoggingStatusNPCM4
				RollCallString,
			iqmux60SetupLoggingStatusNPCM5
				RollCallString,
			iqmux60SetupLoggingStatusNPCM6
				RollCallString,
			iqmux60SetupLoggingStatusNPCM7
				RollCallString,
			iqmux60SetupLoggingStatusNPCM8
				RollCallString,
			iqmux60SetupLoggingStatusAES1
				RollCallString,
			iqmux60SetupLoggingStatusAES2
				RollCallString,
			iqmux60SetupLoggingStatusBUSAL
				RollCallString,
			iqmux60SetupLoggingStatusBUSAR
				RollCallString,
			iqmux60SetupLoggingStatusBUSBL
				RollCallString,
			iqmux60SetupLoggingStatusBUSBR
				RollCallString,
			iqmux60SetupLoggingStatusBUSCL
				RollCallString,
			iqmux60SetupLoggingStatusBUSCR
				RollCallString,
			iqmux60SetupLoggingStatusBUSDL
				RollCallString,
			iqmux60SetupLoggingStatusBUSDR
				RollCallString,
			iqmux60SetupLoggingStatusFAULT
				RollCallString,
			iqmux60SetupInformationWindow
				INTEGER,
			iqmux60SetupInformationWindowResetErrors
				INTEGER,
			iqmux60SetupDefaultOutput
				INTEGER,
			iqmux60SetupDefaultPattern
				INTEGER,
			iqmux60SetupUnitSoftwareVersion
				RollCallString,
			iqmux60SetupUnitSerialNo
				RollCallString,
			iqmux60SetupUnitPresetUnit
				INTEGER,
			iqmux60SetupUnitRestart
				INTEGER,
			iqmux60SetupUnitBuildNo
				RollCallString
		}

	iqmux60SlotIndex OBJECT-TYPE
		SYNTAX		Unsigned32
		MAX-ACCESS		not-accessible
		STATUS			current
		DESCRIPTION
				"The unique Index value for each slot.  Its value
					ranges between 1 and the value of slotNumber."
		::= { iqmux60CmdEntry 0 }


	iqmux60VideoInput OBJECT-TYPE
		SYNTAX		INTEGER {
							val_Input_1_SDI(0),
							val_Input_2_SDI(1)
							}
		MAX-ACCESS		read-write
		STATUS			current
		DESCRIPTION
				"TYPE: - Button
				 PAGE: - Video- Input
					input 1 SDI  cmdID= 2251  value= 0
					input 2 SDI  cmdID= 2251  value= 1  "
		::= { iqmux60CmdEntry 2251 }


	iqmux60VideoInput525 OBJECT-TYPE
		SYNTAX		INTEGER { disable(0), enable(1) }
		MAX-ACCESS		read-write
		STATUS			current
		DESCRIPTION
				"TYPE: - Checkbox
				 PAGE: - Video- Input
					525  cmdID= 1405 "
		::= { iqmux60CmdEntry 1405 }


	iqmux60VideoInput625 OBJECT-TYPE
		SYNTAX		INTEGER { disable(0), enable(1) }
		MAX-ACCESS		read-write
		STATUS			current
		DESCRIPTION
				"TYPE: - Checkbox
				 PAGE: - Video- Input
					625  cmdID= 1406 "
		::= { iqmux60CmdEntry 1406 }


	iqmux60VideoProcAmp1In1ProcAmpEnable OBJECT-TYPE
		SYNTAX		INTEGER { disable(0), enable(1) }
		MAX-ACCESS		read-write
		STATUS			current
		DESCRIPTION
				"TYPE: - Checkbox
				 PAGE: - Video- ProcAmp 1
					In1 ProcAmp Enable  cmdID= 2864 "
		::= { iqmux60CmdEntry 2864 }


	iqmux60VideoProcAmp1LumaGain OBJECT-TYPE
		SYNTAX		INTEGER
		MAX-ACCESS		read-write
		STATUS			current
		DESCRIPTION
				"TYPE: - Number
				 PAGE: - Video- ProcAmp 1
					Luma Gain  cmdID= 2707  min= -60  max= 60  step= 1  format= %1.1f dB  div_scale= 10
					Min = -6.0 dB  Max = 6.0 dB  Step = 0.1 dB "
		::= { iqmux60CmdEntry 2707 }


	iqmux60VideoProcAmp1ChromaGain OBJECT-TYPE
		SYNTAX		INTEGER
		MAX-ACCESS		read-write
		STATUS			current
		DESCRIPTION
				"TYPE: - Number
				 PAGE: - Video- ProcAmp 1
					Chroma Gain  cmdID= 2706  min= -60  max= 60  step= 1  format= %1.1f dB  div_scale= 10
					Min = -6.0 dB  Max = 6.0 dB  Step = 0.1 dB "
		::= { iqmux60CmdEntry 2706 }


	iqmux60VideoProcAmp1BlackLevel OBJECT-TYPE
		SYNTAX		INTEGER
		MAX-ACCESS		read-write
		STATUS			current
		DESCRIPTION
				"TYPE: - Number
				 PAGE: - Video- ProcAmp 1
					Black Level  cmdID= 2708  min= -1000  max= 1000  step= 8  format= %1.1f mV  div_scale= 10
					Min = -100.0 mV  Max = 100.0 mV  Step = 0.8 mV "
		::= { iqmux60CmdEntry 2708 }


	iqmux60VideoProcAmp1PicturePosition OBJECT-TYPE
		SYNTAX		INTEGER
		MAX-ACCESS		read-write
		STATUS			current
		DESCRIPTION
				"TYPE: - Number
				 PAGE: - Video- ProcAmp 1
					Picture Position  cmdID= 2709  min= -592  max= 592  step= 148  format= %3.0f ns  div_scale= 1
					Min = -592 ns  Max = 592 ns  Step = 148 ns "
		::= { iqmux60CmdEntry 2709 }


	iqmux60VideoProcAmp1YCTiming OBJECT-TYPE
		SYNTAX		INTEGER
		MAX-ACCESS		read-write
		STATUS			current
		DESCRIPTION
				"TYPE: - Number
				 PAGE: - Video- ProcAmp 1
					Y/C Timing  cmdID= 2924  min= -592  max= 592  step= 148  format= %3.0fns  div_scale= 1
					Min = -592ns  Max = 592ns  Step = 148ns "
		::= { iqmux60CmdEntry 2924 }


	iqmux60VideoProcAmp2In2ProcAmpEnable OBJECT-TYPE
		SYNTAX		INTEGER { disable(0), enable(1) }
		MAX-ACCESS		read-write
		STATUS			current
		DESCRIPTION
				"TYPE: - Checkbox
				 PAGE: - Video- ProcAmp 2
					In2 ProcAmp Enable  cmdID= 2865 "
		::= { iqmux60CmdEntry 2865 }


	iqmux60VideoProcAmp2LumaGain OBJECT-TYPE
		SYNTAX		INTEGER
		MAX-ACCESS		read-write
		STATUS			current
		DESCRIPTION
				"TYPE: - Number
				 PAGE: - Video- ProcAmp 2
					Luma Gain  cmdID= 2711  min= -60  max= 60  step= 1  format= %1.1f dB  div_scale= 10
					Min = -6.0 dB  Max = 6.0 dB  Step = 0.1 dB "
		::= { iqmux60CmdEntry 2711 }


	iqmux60VideoProcAmp2ChromaGain OBJECT-TYPE
		SYNTAX		INTEGER
		MAX-ACCESS		read-write
		STATUS			current
		DESCRIPTION
				"TYPE: - Number
				 PAGE: - Video- ProcAmp 2
					Chroma Gain  cmdID= 2710  min= -60  max= 60  step= 1  format= %1.1f dB  div_scale= 10
					Min = -6.0 dB  Max = 6.0 dB  Step = 0.1 dB "
		::= { iqmux60CmdEntry 2710 }


	iqmux60VideoProcAmp2BlackLevel OBJECT-TYPE
		SYNTAX		INTEGER
		MAX-ACCESS		read-write
		STATUS			current
		DESCRIPTION
				"TYPE: - Number
				 PAGE: - Video- ProcAmp 2
					Black Level  cmdID= 2712  min= -1000  max= 1000  step= 8  format= %1.1f mV  div_scale= 10
					Min = -100.0 mV  Max = 100.0 mV  Step = 0.8 mV "
		::= { iqmux60CmdEntry 2712 }


	iqmux60VideoProcAmp2PicturePosition OBJECT-TYPE
		SYNTAX		INTEGER
		MAX-ACCESS		read-write
		STATUS			current
		DESCRIPTION
				"TYPE: - Number
				 PAGE: - Video- ProcAmp 2
					Picture Position  cmdID= 2713  min= -592  max= 592  step= 148  format= %3.0f ns  div_scale= 1
					Min = -592 ns  Max = 592 ns  Step = 148 ns "
		::= { iqmux60CmdEntry 2713 }


	iqmux60VideoProcAmp2YCTiming OBJECT-TYPE
		SYNTAX		INTEGER
		MAX-ACCESS		read-write
		STATUS			current
		DESCRIPTION
				"TYPE: - Number
				 PAGE: - Video- ProcAmp 2
					Y/C Timing  cmdID= 2925  min= -592  max= 592  step= 148  format= %3.0fns  div_scale= 1
					Min = -592ns  Max = 592ns  Step = 148ns "
		::= { iqmux60CmdEntry 2925 }


	iqmux60AudioDeembed OBJECT-TYPE
		SYNTAX		INTEGER {
							val_Input_1_SDI(0),
							val_Input_2_SDI(1),
							val_Follow_Video(2)
							}
		MAX-ACCESS		read-write
		STATUS			current
		DESCRIPTION
				"TYPE: - Button
				 PAGE: - Audio- De-embed
					input 1 SDI  cmdID= 2923  value= 0
					input 2 SDI  cmdID= 2923  value= 1
					follow Video  cmdID= 2923  value= 2  "
		::= { iqmux60CmdEntry 2923 }


	iqmux60AudioAESOutputAES1Source OBJECT-TYPE
		SYNTAX		INTEGER {
							val_BUS_A(0),
							val_BUS_B(1),
							val_BUS_C(2),
							val_BUS_D(3),
							val_AES_1_Direct(4),
							val_AES_2_Direct(5),
							val_DeEmbed_1(6),
							val_DeEmbed_2(7),
							val_DeEmbed_3(8),
							val_DeEmbed_4(9),
							val_DeEmbed_5(10),
							val_DeEmbed_6(11),
							val_DeEmbed_7(12),
							val_DeEmbed_8(13),
							val_Test_tone(14),
							val_Silence(15)
							}
		MAX-ACCESS		read-write
		STATUS			current
		DESCRIPTION
				"TYPE: - RadiobuttonList
				 PAGE: - Audio- AES Output
					AES 1 Source  cmdID= 2951
					bUS A  value= 0
					bUS B  value= 1
					bUS C  value= 2
					bUS D  value= 3
					aES 1 Direct  value= 4
					aES 2 Direct  value= 5
					deEmbed 1  value= 6
					deEmbed 2  value= 7
					deEmbed 3  value= 8
					deEmbed 4  value= 9
					deEmbed 5  value= 10
					deEmbed 6  value= 11
					deEmbed 7  value= 12
					deEmbed 8  value= 13
					test tone  value= 14
					silence  value= 15  "
		::= { iqmux60CmdEntry 2951 }


	iqmux60AudioAESOutputAES2Source OBJECT-TYPE
		SYNTAX		INTEGER {
							val_BUS_A(0),
							val_BUS_B(1),
							val_BUS_C(2),
							val_BUS_D(3),
							val_AES_1_Direct(4),
							val_AES_2_Direct(5),
							val_DeEmbed_1(6),
							val_DeEmbed_2(7),
							val_DeEmbed_3(8),
							val_DeEmbed_4(9),
							val_DeEmbed_5(10),
							val_DeEmbed_6(11),
							val_DeEmbed_7(12),
							val_DeEmbed_8(13),
							val_Test_tone(14),
							val_Silence(15)
							}
		MAX-ACCESS		read-write
		STATUS			current
		DESCRIPTION
				"TYPE: - RadiobuttonList
				 PAGE: - Audio- AES Output
					AES 2 Source  cmdID= 2952
					bUS A  value= 0
					bUS B  value= 1
					bUS C  value= 2
					bUS D  value= 3
					aES 1 Direct  value= 4
					aES 2 Direct  value= 5
					deEmbed 1  value= 6
					deEmbed 2  value= 7
					deEmbed 3  value= 8
					deEmbed 4  value= 9
					deEmbed 5  value= 10
					deEmbed 6  value= 11
					deEmbed 7  value= 12
					deEmbed 8  value= 13
					test tone  value= 14
					silence  value= 15  "
		::= { iqmux60CmdEntry 2952 }


	iqmux60AudioProcAmpDeembedStereo1 OBJECT-TYPE
		SYNTAX		INTEGER { disable(0), enable(1) }
		MAX-ACCESS		read-write
		STATUS			current
		DESCRIPTION
				"TYPE: - Checkbox
				 PAGE: - Audio- ProcAmp
					Stereo 1  cmdID= 3324 "
		::= { iqmux60CmdEntry 3324 }


	iqmux60ProcAmpDeembed1LGainDeembed1L OBJECT-TYPE
		SYNTAX		INTEGER
		MAX-ACCESS		read-write
		STATUS			current
		DESCRIPTION
				"TYPE: - Number
				 PAGE: - Audio- ProcAmp
					Gain De-embed 1L  cmdID= 3088  min= -180  max= 180  step= 1  format= %0.1fdB  div_scale= 10
					Min = -18.0dB  Max = 18.0dB  Step = 0.1dB "
		::= { iqmux60CmdEntry 3088 }


	iqmux60ProcAmpDeembed1LInvert OBJECT-TYPE
		SYNTAX		INTEGER { disable(0), enable(1) }
		MAX-ACCESS		read-write
		STATUS			current
		DESCRIPTION
				"TYPE: - Checkbox
				 PAGE: - Audio- ProcAmp
					Invert  cmdID= 3168 "
		::= { iqmux60CmdEntry 3168 }


	iqmux60ProcAmpDeembed1LMute OBJECT-TYPE
		SYNTAX		INTEGER { disable(0), enable(1) }
		MAX-ACCESS		read-write
		STATUS			current
		DESCRIPTION
				"TYPE: - Checkbox
				 PAGE: - Audio- ProcAmp
					Mute  cmdID= 3248 "
		::= { iqmux60CmdEntry 3248 }


	iqmux60ProcAmpDeembed1RGainDeembed1R OBJECT-TYPE
		SYNTAX		INTEGER
		MAX-ACCESS		read-write
		STATUS			current
		DESCRIPTION
				"TYPE: - Number
				 PAGE: - Audio- ProcAmp
					Gain De-embed 1R  cmdID= 3089  min= -180  max= 180  step= 1  format= %0.1fdB  div_scale= 10
					Min = -18.0dB  Max = 18.0dB  Step = 0.1dB "
		::= { iqmux60CmdEntry 3089 }


	iqmux60ProcAmpDeembed1RInvert OBJECT-TYPE
		SYNTAX		INTEGER { disable(0), enable(1) }
		MAX-ACCESS		read-write
		STATUS			current
		DESCRIPTION
				"TYPE: - Checkbox
				 PAGE: - Audio- ProcAmp
					Invert  cmdID= 3169 "
		::= { iqmux60CmdEntry 3169 }


	iqmux60ProcAmpDeembed1RMute OBJECT-TYPE
		SYNTAX		INTEGER { disable(0), enable(1) }
		MAX-ACCESS		read-write
		STATUS			current
		DESCRIPTION
				"TYPE: - Checkbox
				 PAGE: - Audio- ProcAmp
					Mute  cmdID= 3249 "
		::= { iqmux60CmdEntry 3249 }


	iqmux60AudioProcAmpDeembedStereo2 OBJECT-TYPE
		SYNTAX		INTEGER { disable(0), enable(1) }
		MAX-ACCESS		read-write
		STATUS			current
		DESCRIPTION
				"TYPE: - Checkbox
				 PAGE: - Audio- ProcAmp
					Stereo 2  cmdID= 3325 "
		::= { iqmux60CmdEntry 3325 }


	iqmux60ProcAmpDeembed2LGainDeembed2L OBJECT-TYPE
		SYNTAX		INTEGER
		MAX-ACCESS		read-write
		STATUS			current
		DESCRIPTION
				"TYPE: - Number
				 PAGE: - Audio- ProcAmp
					Gain De-embed 2L  cmdID= 3090  min= -180  max= 180  step= 1  format= %0.1fdB  div_scale= 10
					Min = -18.0dB  Max = 18.0dB  Step = 0.1dB "
		::= { iqmux60CmdEntry 3090 }


	iqmux60ProcAmpDeembed2LInvert OBJECT-TYPE
		SYNTAX		INTEGER { disable(0), enable(1) }
		MAX-ACCESS		read-write
		STATUS			current
		DESCRIPTION
				"TYPE: - Checkbox
				 PAGE: - Audio- ProcAmp
					Invert  cmdID= 3170 "
		::= { iqmux60CmdEntry 3170 }


	iqmux60ProcAmpDeembed2LMute OBJECT-TYPE
		SYNTAX		INTEGER { disable(0), enable(1) }
		MAX-ACCESS		read-write
		STATUS			current
		DESCRIPTION
				"TYPE: - Checkbox
				 PAGE: - Audio- ProcAmp
					Mute  cmdID= 3250 "
		::= { iqmux60CmdEntry 3250 }


	iqmux60ProcAmpDeembed2RGainDeembed2R OBJECT-TYPE
		SYNTAX		INTEGER
		MAX-ACCESS		read-write
		STATUS			current
		DESCRIPTION
				"TYPE: - Number
				 PAGE: - Audio- ProcAmp
					Gain De-embed 2R  cmdID= 3091  min= -180  max= 180  step= 1  format= %0.1fdB  div_scale= 10
					Min = -18.0dB  Max = 18.0dB  Step = 0.1dB "
		::= { iqmux60CmdEntry 3091 }


	iqmux60ProcAmpDeembed2RInvert OBJECT-TYPE
		SYNTAX		INTEGER { disable(0), enable(1) }
		MAX-ACCESS		read-write
		STATUS			current
		DESCRIPTION
				"TYPE: - Checkbox
				 PAGE: - Audio- ProcAmp
					Invert  cmdID= 3171 "
		::= { iqmux60CmdEntry 3171 }


	iqmux60ProcAmpDeembed2RMute OBJECT-TYPE
		SYNTAX		INTEGER { disable(0), enable(1) }
		MAX-ACCESS		read-write
		STATUS			current
		DESCRIPTION
				"TYPE: - Checkbox
				 PAGE: - Audio- ProcAmp
					Mute  cmdID= 3251 "
		::= { iqmux60CmdEntry 3251 }


	iqmux60AudioProcAmpDeembedStereo3 OBJECT-TYPE
		SYNTAX		INTEGER { disable(0), enable(1) }
		MAX-ACCESS		read-write
		STATUS			current
		DESCRIPTION
				"TYPE: - Checkbox
				 PAGE: - Audio- ProcAmp
					Stereo 3  cmdID= 3326 "
		::= { iqmux60CmdEntry 3326 }


	iqmux60ProcAmpDeembed3LGainDeembed3L OBJECT-TYPE
		SYNTAX		INTEGER
		MAX-ACCESS		read-write
		STATUS			current
		DESCRIPTION
				"TYPE: - Number
				 PAGE: - Audio- ProcAmp
					Gain De-embed 3L  cmdID= 3092  min= -180  max= 180  step= 1  format= %0.1fdB  div_scale= 10
					Min = -18.0dB  Max = 18.0dB  Step = 0.1dB "
		::= { iqmux60CmdEntry 3092 }


	iqmux60ProcAmpDeembed3LInvert OBJECT-TYPE
		SYNTAX		INTEGER { disable(0), enable(1) }
		MAX-ACCESS		read-write
		STATUS			current
		DESCRIPTION
				"TYPE: - Checkbox
				 PAGE: - Audio- ProcAmp
					Invert  cmdID= 3172 "
		::= { iqmux60CmdEntry 3172 }


	iqmux60ProcAmpDeembed3LMute OBJECT-TYPE
		SYNTAX		INTEGER { disable(0), enable(1) }
		MAX-ACCESS		read-write
		STATUS			current
		DESCRIPTION
				"TYPE: - Checkbox
				 PAGE: - Audio- ProcAmp
					Mute  cmdID= 3252 "
		::= { iqmux60CmdEntry 3252 }


	iqmux60ProcAmpDeembed3RGainDeembed3R OBJECT-TYPE
		SYNTAX		INTEGER
		MAX-ACCESS		read-write
		STATUS			current
		DESCRIPTION
				"TYPE: - Number
				 PAGE: - Audio- ProcAmp
					Gain De-embed 3R  cmdID= 3093  min= -180  max= 180  step= 1  format= %0.1fdB  div_scale= 10
					Min = -18.0dB  Max = 18.0dB  Step = 0.1dB "
		::= { iqmux60CmdEntry 3093 }


	iqmux60ProcAmpDeembed3RInvert OBJECT-TYPE
		SYNTAX		INTEGER { disable(0), enable(1) }
		MAX-ACCESS		read-write
		STATUS			current
		DESCRIPTION
				"TYPE: - Checkbox
				 PAGE: - Audio- ProcAmp
					Invert  cmdID= 3173 "
		::= { iqmux60CmdEntry 3173 }


	iqmux60ProcAmpDeembed3RMute OBJECT-TYPE
		SYNTAX		INTEGER { disable(0), enable(1) }
		MAX-ACCESS		read-write
		STATUS			current
		DESCRIPTION
				"TYPE: - Checkbox
				 PAGE: - Audio- ProcAmp
					Mute  cmdID= 3253 "
		::= { iqmux60CmdEntry 3253 }


	iqmux60AudioProcAmpDeembedStereo4 OBJECT-TYPE
		SYNTAX		INTEGER { disable(0), enable(1) }
		MAX-ACCESS		read-write
		STATUS			current
		DESCRIPTION
				"TYPE: - Checkbox
				 PAGE: - Audio- ProcAmp
					Stereo 4  cmdID= 3327 "
		::= { iqmux60CmdEntry 3327 }


	iqmux60ProcAmpDeembed4LGainDeembed4L OBJECT-TYPE
		SYNTAX		INTEGER
		MAX-ACCESS		read-write
		STATUS			current
		DESCRIPTION
				"TYPE: - Number
				 PAGE: - Audio- ProcAmp
					Gain De-embed 4L  cmdID= 3094  min= -180  max= 180  step= 1  format= %0.1fdB  div_scale= 10
					Min = -18.0dB  Max = 18.0dB  Step = 0.1dB "
		::= { iqmux60CmdEntry 3094 }


	iqmux60ProcAmpDeembed4LInvert OBJECT-TYPE
		SYNTAX		INTEGER { disable(0), enable(1) }
		MAX-ACCESS		read-write
		STATUS			current
		DESCRIPTION
				"TYPE: - Checkbox
				 PAGE: - Audio- ProcAmp
					Invert  cmdID= 3174 "
		::= { iqmux60CmdEntry 3174 }


	iqmux60ProcAmpDeembed4LMute OBJECT-TYPE
		SYNTAX		INTEGER { disable(0), enable(1) }
		MAX-ACCESS		read-write
		STATUS			current
		DESCRIPTION
				"TYPE: - Checkbox
				 PAGE: - Audio- ProcAmp
					Mute  cmdID= 3254 "
		::= { iqmux60CmdEntry 3254 }


	iqmux60ProcAmpDeembed4RGainDeembed4R OBJECT-TYPE
		SYNTAX		INTEGER
		MAX-ACCESS		read-write
		STATUS			current
		DESCRIPTION
				"TYPE: - Number
				 PAGE: - Audio- ProcAmp
					Gain De-embed 4R  cmdID= 3095  min= -180  max= 180  step= 1  format= %0.1fdB  div_scale= 10
					Min = -18.0dB  Max = 18.0dB  Step = 0.1dB "
		::= { iqmux60CmdEntry 3095 }


	iqmux60ProcAmpDeembed4RInvert OBJECT-TYPE
		SYNTAX		INTEGER { disable(0), enable(1) }
		MAX-ACCESS		read-write
		STATUS			current
		DESCRIPTION
				"TYPE: - Checkbox
				 PAGE: - Audio- ProcAmp
					Invert  cmdID= 3175 "
		::= { iqmux60CmdEntry 3175 }


	iqmux60ProcAmpDeembed4RMute OBJECT-TYPE
		SYNTAX		INTEGER { disable(0), enable(1) }
		MAX-ACCESS		read-write
		STATUS			current
		DESCRIPTION
				"TYPE: - Checkbox
				 PAGE: - Audio- ProcAmp
					Mute  cmdID= 3255 "
		::= { iqmux60CmdEntry 3255 }


	iqmux60AudioProcAmpDeembedStereo5 OBJECT-TYPE
		SYNTAX		INTEGER { disable(0), enable(1) }
		MAX-ACCESS		read-write
		STATUS			current
		DESCRIPTION
				"TYPE: - Checkbox
				 PAGE: - Audio- ProcAmp
					Stereo 5  cmdID= 3328 "
		::= { iqmux60CmdEntry 3328 }


	iqmux60ProcAmpDeembed5LGainDeembed5L OBJECT-TYPE
		SYNTAX		INTEGER
		MAX-ACCESS		read-write
		STATUS			current
		DESCRIPTION
				"TYPE: - Number
				 PAGE: - Audio- ProcAmp
					Gain De-embed 5L  cmdID= 3096  min= -180  max= 180  step= 1  format= %0.1fdB  div_scale= 10
					Min = -18.0dB  Max = 18.0dB  Step = 0.1dB "
		::= { iqmux60CmdEntry 3096 }


	iqmux60ProcAmpDeembed5LInvert OBJECT-TYPE
		SYNTAX		INTEGER { disable(0), enable(1) }
		MAX-ACCESS		read-write
		STATUS			current
		DESCRIPTION
				"TYPE: - Checkbox
				 PAGE: - Audio- ProcAmp
					Invert  cmdID= 3176 "
		::= { iqmux60CmdEntry 3176 }


	iqmux60ProcAmpDeembed5LMute OBJECT-TYPE
		SYNTAX		INTEGER { disable(0), enable(1) }
		MAX-ACCESS		read-write
		STATUS			current
		DESCRIPTION
				"TYPE: - Checkbox
				 PAGE: - Audio- ProcAmp
					Mute  cmdID= 3256 "
		::= { iqmux60CmdEntry 3256 }


	iqmux60ProcAmpDeembed5RGainDeembed5R OBJECT-TYPE
		SYNTAX		INTEGER
		MAX-ACCESS		read-write
		STATUS			current
		DESCRIPTION
				"TYPE: - Number
				 PAGE: - Audio- ProcAmp
					Gain De-embed 5R  cmdID= 3097  min= -180  max= 180  step= 1  format= %0.1fdB  div_scale= 10
					Min = -18.0dB  Max = 18.0dB  Step = 0.1dB "
		::= { iqmux60CmdEntry 3097 }


	iqmux60ProcAmpDeembed5RInvert OBJECT-TYPE
		SYNTAX		INTEGER { disable(0), enable(1) }
		MAX-ACCESS		read-write
		STATUS			current
		DESCRIPTION
				"TYPE: - Checkbox
				 PAGE: - Audio- ProcAmp
					Invert  cmdID= 3177 "
		::= { iqmux60CmdEntry 3177 }


	iqmux60ProcAmpDeembed5RMute OBJECT-TYPE
		SYNTAX		INTEGER { disable(0), enable(1) }
		MAX-ACCESS		read-write
		STATUS			current
		DESCRIPTION
				"TYPE: - Checkbox
				 PAGE: - Audio- ProcAmp
					Mute  cmdID= 3257 "
		::= { iqmux60CmdEntry 3257 }


	iqmux60AudioProcAmpDeembedStereo6 OBJECT-TYPE
		SYNTAX		INTEGER { disable(0), enable(1) }
		MAX-ACCESS		read-write
		STATUS			current
		DESCRIPTION
				"TYPE: - Checkbox
				 PAGE: - Audio- ProcAmp
					Stereo 6  cmdID= 3329 "
		::= { iqmux60CmdEntry 3329 }


	iqmux60ProcAmpDeembed6LGainDeembed6L OBJECT-TYPE
		SYNTAX		INTEGER
		MAX-ACCESS		read-write
		STATUS			current
		DESCRIPTION
				"TYPE: - Number
				 PAGE: - Audio- ProcAmp
					Gain De-embed 6L  cmdID= 3098  min= -180  max= 180  step= 1  format= %0.1fdB  div_scale= 10
					Min = -18.0dB  Max = 18.0dB  Step = 0.1dB "
		::= { iqmux60CmdEntry 3098 }


	iqmux60ProcAmpDeembed6LInvert OBJECT-TYPE
		SYNTAX		INTEGER { disable(0), enable(1) }
		MAX-ACCESS		read-write
		STATUS			current
		DESCRIPTION
				"TYPE: - Checkbox
				 PAGE: - Audio- ProcAmp
					Invert  cmdID= 3178 "
		::= { iqmux60CmdEntry 3178 }


	iqmux60ProcAmpDeembed6LMute OBJECT-TYPE
		SYNTAX		INTEGER { disable(0), enable(1) }
		MAX-ACCESS		read-write
		STATUS			current
		DESCRIPTION
				"TYPE: - Checkbox
				 PAGE: - Audio- ProcAmp
					Mute  cmdID= 3258 "
		::= { iqmux60CmdEntry 3258 }


	iqmux60ProcAmpDeembed6RGainDeembed6R OBJECT-TYPE
		SYNTAX		INTEGER
		MAX-ACCESS		read-write
		STATUS			current
		DESCRIPTION
				"TYPE: - Number
				 PAGE: - Audio- ProcAmp
					Gain De-embed 6R  cmdID= 3099  min= -180  max= 180  step= 1  format= %0.1fdB  div_scale= 10
					Min = -18.0dB  Max = 18.0dB  Step = 0.1dB "
		::= { iqmux60CmdEntry 3099 }


	iqmux60ProcAmpDeembed6RInvert OBJECT-TYPE
		SYNTAX		INTEGER { disable(0), enable(1) }
		MAX-ACCESS		read-write
		STATUS			current
		DESCRIPTION
				"TYPE: - Checkbox
				 PAGE: - Audio- ProcAmp
					Invert  cmdID= 3179 "
		::= { iqmux60CmdEntry 3179 }


	iqmux60ProcAmpDeembed6RMute OBJECT-TYPE
		SYNTAX		INTEGER { disable(0), enable(1) }
		MAX-ACCESS		read-write
		STATUS			current
		DESCRIPTION
				"TYPE: - Checkbox
				 PAGE: - Audio- ProcAmp
					Mute  cmdID= 3259 "
		::= { iqmux60CmdEntry 3259 }


	iqmux60AudioProcAmpDeembedStereo7 OBJECT-TYPE
		SYNTAX		INTEGER { disable(0), enable(1) }
		MAX-ACCESS		read-write
		STATUS			current
		DESCRIPTION
				"TYPE: - Checkbox
				 PAGE: - Audio- ProcAmp
					Stereo 7  cmdID= 3330 "
		::= { iqmux60CmdEntry 3330 }


	iqmux60ProcAmpDeembed7LGainDeembed7L OBJECT-TYPE
		SYNTAX		INTEGER
		MAX-ACCESS		read-write
		STATUS			current
		DESCRIPTION
				"TYPE: - Number
				 PAGE: - Audio- ProcAmp
					Gain De-embed 7L  cmdID= 3100  min= -180  max= 180  step= 1  format= %0.1fdB  div_scale= 10
					Min = -18.0dB  Max = 18.0dB  Step = 0.1dB "
		::= { iqmux60CmdEntry 3100 }


	iqmux60ProcAmpDeembed7LInvert OBJECT-TYPE
		SYNTAX		INTEGER { disable(0), enable(1) }
		MAX-ACCESS		read-write
		STATUS			current
		DESCRIPTION
				"TYPE: - Checkbox
				 PAGE: - Audio- ProcAmp
					Invert  cmdID= 3180 "
		::= { iqmux60CmdEntry 3180 }


	iqmux60ProcAmpDeembed7LMute OBJECT-TYPE
		SYNTAX		INTEGER { disable(0), enable(1) }
		MAX-ACCESS		read-write
		STATUS			current
		DESCRIPTION
				"TYPE: - Checkbox
				 PAGE: - Audio- ProcAmp
					Mute  cmdID= 3260 "
		::= { iqmux60CmdEntry 3260 }


	iqmux60ProcAmpDeembed7RGainDeembed7R OBJECT-TYPE
		SYNTAX		INTEGER
		MAX-ACCESS		read-write
		STATUS			current
		DESCRIPTION
				"TYPE: - Number
				 PAGE: - Audio- ProcAmp
					Gain De-embed 7R  cmdID= 3101  min= -180  max= 180  step= 1  format= %0.1fdB  div_scale= 10
					Min = -18.0dB  Max = 18.0dB  Step = 0.1dB "
		::= { iqmux60CmdEntry 3101 }


	iqmux60ProcAmpDeembed7RInvert OBJECT-TYPE
		SYNTAX		INTEGER { disable(0), enable(1) }
		MAX-ACCESS		read-write
		STATUS			current
		DESCRIPTION
				"TYPE: - Checkbox
				 PAGE: - Audio- ProcAmp
					Invert  cmdID= 3181 "
		::= { iqmux60CmdEntry 3181 }


	iqmux60ProcAmpDeembed7RMute OBJECT-TYPE
		SYNTAX		INTEGER { disable(0), enable(1) }
		MAX-ACCESS		read-write
		STATUS			current
		DESCRIPTION
				"TYPE: - Checkbox
				 PAGE: - Audio- ProcAmp
					Mute  cmdID= 3261 "
		::= { iqmux60CmdEntry 3261 }


	iqmux60AudioProcAmpDeembedStereo8 OBJECT-TYPE
		SYNTAX		INTEGER { disable(0), enable(1) }
		MAX-ACCESS		read-write
		STATUS			current
		DESCRIPTION
				"TYPE: - Checkbox
				 PAGE: - Audio- ProcAmp
					Stereo 8  cmdID= 3331 "
		::= { iqmux60CmdEntry 3331 }


	iqmux60ProcAmpDeembed8LGainDeembed8L OBJECT-TYPE
		SYNTAX		INTEGER
		MAX-ACCESS		read-write
		STATUS			current
		DESCRIPTION
				"TYPE: - Number
				 PAGE: - Audio- ProcAmp
					Gain De-embed 8L  cmdID= 3102  min= -180  max= 180  step= 1  format= %0.1fdB  div_scale= 10
					Min = -18.0dB  Max = 18.0dB  Step = 0.1dB "
		::= { iqmux60CmdEntry 3102 }


	iqmux60ProcAmpDeembed8LInvert OBJECT-TYPE
		SYNTAX		INTEGER { disable(0), enable(1) }
		MAX-ACCESS		read-write
		STATUS			current
		DESCRIPTION
				"TYPE: - Checkbox
				 PAGE: - Audio- ProcAmp
					Invert  cmdID= 3182 "
		::= { iqmux60CmdEntry 3182 }


	iqmux60ProcAmpDeembed8LMute OBJECT-TYPE
		SYNTAX		INTEGER { disable(0), enable(1) }
		MAX-ACCESS		read-write
		STATUS			current
		DESCRIPTION
				"TYPE: - Checkbox
				 PAGE: - Audio- ProcAmp
					Mute  cmdID= 3262 "
		::= { iqmux60CmdEntry 3262 }


	iqmux60ProcAmpDeembed8RGainDeembed8R OBJECT-TYPE
		SYNTAX		INTEGER
		MAX-ACCESS		read-write
		STATUS			current
		DESCRIPTION
				"TYPE: - Number
				 PAGE: - Audio- ProcAmp
					Gain De-embed 8R  cmdID= 3103  min= -180  max= 180  step= 1  format= %0.1fdB  div_scale= 10
					Min = -18.0dB  Max = 18.0dB  Step = 0.1dB "
		::= { iqmux60CmdEntry 3103 }


	iqmux60ProcAmpDeembed8RInvert OBJECT-TYPE
		SYNTAX		INTEGER { disable(0), enable(1) }
		MAX-ACCESS		read-write
		STATUS			current
		DESCRIPTION
				"TYPE: - Checkbox
				 PAGE: - Audio- ProcAmp
					Invert  cmdID= 3183 "
		::= { iqmux60CmdEntry 3183 }


	iqmux60ProcAmpDeembed8RMute OBJECT-TYPE
		SYNTAX		INTEGER { disable(0), enable(1) }
		MAX-ACCESS		read-write
		STATUS			current
		DESCRIPTION
				"TYPE: - Checkbox
				 PAGE: - Audio- ProcAmp
					Mute  cmdID= 3263 "
		::= { iqmux60CmdEntry 3263 }


	iqmux60AudioProcAmpAESStereo1 OBJECT-TYPE
		SYNTAX		INTEGER { disable(0), enable(1) }
		MAX-ACCESS		read-write
		STATUS			current
		DESCRIPTION
				"TYPE: - Checkbox
				 PAGE: - Audio- ProcAmp
					Stereo 1  cmdID= 3332 "
		::= { iqmux60CmdEntry 3332 }


	iqmux60ProcAmpAES1LGainAES1L OBJECT-TYPE
		SYNTAX		INTEGER
		MAX-ACCESS		read-write
		STATUS			current
		DESCRIPTION
				"TYPE: - Number
				 PAGE: - Audio- ProcAmp
					Gain AES 1L  cmdID= 3104  min= -180  max= 180  step= 1  format= %0.1fdB  div_scale= 10
					Min = -18.0dB  Max = 18.0dB  Step = 0.1dB "
		::= { iqmux60CmdEntry 3104 }


	iqmux60ProcAmpAES1LInvert OBJECT-TYPE
		SYNTAX		INTEGER { disable(0), enable(1) }
		MAX-ACCESS		read-write
		STATUS			current
		DESCRIPTION
				"TYPE: - Checkbox
				 PAGE: - Audio- ProcAmp
					Invert  cmdID= 3184 "
		::= { iqmux60CmdEntry 3184 }


	iqmux60ProcAmpAES1LMute OBJECT-TYPE
		SYNTAX		INTEGER { disable(0), enable(1) }
		MAX-ACCESS		read-write
		STATUS			current
		DESCRIPTION
				"TYPE: - Checkbox
				 PAGE: - Audio- ProcAmp
					Mute  cmdID= 3264 "
		::= { iqmux60CmdEntry 3264 }


	iqmux60ProcAmpAES1RGainAES1R OBJECT-TYPE
		SYNTAX		INTEGER
		MAX-ACCESS		read-write
		STATUS			current
		DESCRIPTION
				"TYPE: - Number
				 PAGE: - Audio- ProcAmp
					Gain AES 1R  cmdID= 3105  min= -180  max= 180  step= 1  format= %0.1fdB  div_scale= 10
					Min = -18.0dB  Max = 18.0dB  Step = 0.1dB "
		::= { iqmux60CmdEntry 3105 }


	iqmux60ProcAmpAES1RInvert OBJECT-TYPE
		SYNTAX		INTEGER { disable(0), enable(1) }
		MAX-ACCESS		read-write
		STATUS			current
		DESCRIPTION
				"TYPE: - Checkbox
				 PAGE: - Audio- ProcAmp
					Invert  cmdID= 3185 "
		::= { iqmux60CmdEntry 3185 }


	iqmux60ProcAmpAES1RMute OBJECT-TYPE
		SYNTAX		INTEGER { disable(0), enable(1) }
		MAX-ACCESS		read-write
		STATUS			current
		DESCRIPTION
				"TYPE: - Checkbox
				 PAGE: - Audio- ProcAmp
					Mute  cmdID= 3265 "
		::= { iqmux60CmdEntry 3265 }


	iqmux60AudioProcAmpAESStereo2 OBJECT-TYPE
		SYNTAX		INTEGER { disable(0), enable(1) }
		MAX-ACCESS		read-write
		STATUS			current
		DESCRIPTION
				"TYPE: - Checkbox
				 PAGE: - Audio- ProcAmp
					Stereo 2  cmdID= 3333 "
		::= { iqmux60CmdEntry 3333 }


	iqmux60ProcAmpAES2LGainAES2L OBJECT-TYPE
		SYNTAX		INTEGER
		MAX-ACCESS		read-write
		STATUS			current
		DESCRIPTION
				"TYPE: - Number
				 PAGE: - Audio- ProcAmp
					Gain AES 2L  cmdID= 3106  min= -180  max= 180  step= 1  format= %0.1fdB  div_scale= 10
					Min = -18.0dB  Max = 18.0dB  Step = 0.1dB "
		::= { iqmux60CmdEntry 3106 }


	iqmux60ProcAmpAES2LInvert OBJECT-TYPE
		SYNTAX		INTEGER { disable(0), enable(1) }
		MAX-ACCESS		read-write
		STATUS			current
		DESCRIPTION
				"TYPE: - Checkbox
				 PAGE: - Audio- ProcAmp
					Invert  cmdID= 3186 "
		::= { iqmux60CmdEntry 3186 }


	iqmux60ProcAmpAES2LMute OBJECT-TYPE
		SYNTAX		INTEGER { disable(0), enable(1) }
		MAX-ACCESS		read-write
		STATUS			current
		DESCRIPTION
				"TYPE: - Checkbox
				 PAGE: - Audio- ProcAmp
					Mute  cmdID= 3266 "
		::= { iqmux60CmdEntry 3266 }


	iqmux60ProcAmpAES2RGainAES2R OBJECT-TYPE
		SYNTAX		INTEGER
		MAX-ACCESS		read-write
		STATUS			current
		DESCRIPTION
				"TYPE: - Number
				 PAGE: - Audio- ProcAmp
					Gain AES 2R  cmdID= 3107  min= -180  max= 180  step= 1  format= %0.1fdB  div_scale= 10
					Min = -18.0dB  Max = 18.0dB  Step = 0.1dB "
		::= { iqmux60CmdEntry 3107 }


	iqmux60ProcAmpAES2RInvert OBJECT-TYPE
		SYNTAX		INTEGER { disable(0), enable(1) }
		MAX-ACCESS		read-write
		STATUS			current
		DESCRIPTION
				"TYPE: - Checkbox
				 PAGE: - Audio- ProcAmp
					Invert  cmdID= 3187 "
		::= { iqmux60CmdEntry 3187 }


	iqmux60ProcAmpAES2RMute OBJECT-TYPE
		SYNTAX		INTEGER { disable(0), enable(1) }
		MAX-ACCESS		read-write
		STATUS			current
		DESCRIPTION
				"TYPE: - Checkbox
				 PAGE: - Audio- ProcAmp
					Mute  cmdID= 3267 "
		::= { iqmux60CmdEntry 3267 }


	iqmux60AudioProcAmpStereo1 OBJECT-TYPE
		SYNTAX		INTEGER { disable(0), enable(1) }
		MAX-ACCESS		read-write
		STATUS			current
		DESCRIPTION
				"TYPE: - Checkbox
				 PAGE: - Audio- ProcAmp
					Stereo 1  cmdID= 3334 "
		::= { iqmux60CmdEntry 3334 }


	iqmux60ProcAmpAnalog1LGainAnalog1L OBJECT-TYPE
		SYNTAX		INTEGER
		MAX-ACCESS		read-write
		STATUS			current
		DESCRIPTION
				"TYPE: - Number
				 PAGE: - Audio- ProcAmp
					Gain Analog 1L  cmdID= 3108  min= -180  max= 180  step= 1  format= %0.1fdB  div_scale= 10
					Min = -18.0dB  Max = 18.0dB  Step = 0.1dB "
		::= { iqmux60CmdEntry 3108 }


	iqmux60ProcAmpAnalog1LInvert OBJECT-TYPE
		SYNTAX		INTEGER { disable(0), enable(1) }
		MAX-ACCESS		read-write
		STATUS			current
		DESCRIPTION
				"TYPE: - Checkbox
				 PAGE: - Audio- ProcAmp
					Invert  cmdID= 3188 "
		::= { iqmux60CmdEntry 3188 }


	iqmux60ProcAmpAnalog1LMute OBJECT-TYPE
		SYNTAX		INTEGER { disable(0), enable(1) }
		MAX-ACCESS		read-write
		STATUS			current
		DESCRIPTION
				"TYPE: - Checkbox
				 PAGE: - Audio- ProcAmp
					Mute  cmdID= 3268 "
		::= { iqmux60CmdEntry 3268 }


	iqmux60ProcAmpAnalog1RGainAnalog1R OBJECT-TYPE
		SYNTAX		INTEGER
		MAX-ACCESS		read-write
		STATUS			current
		DESCRIPTION
				"TYPE: - Number
				 PAGE: - Audio- ProcAmp
					Gain Analog 1R  cmdID= 3109  min= -180  max= 180  step= 1  format= %0.1fdB  div_scale= 10
					Min = -18.0dB  Max = 18.0dB  Step = 0.1dB "
		::= { iqmux60CmdEntry 3109 }


	iqmux60ProcAmpAnalog1RInvert OBJECT-TYPE
		SYNTAX		INTEGER { disable(0), enable(1) }
		MAX-ACCESS		read-write
		STATUS			current
		DESCRIPTION
				"TYPE: - Checkbox
				 PAGE: - Audio- ProcAmp
					Invert  cmdID= 3189 "
		::= { iqmux60CmdEntry 3189 }


	iqmux60ProcAmpAnalog1RMute OBJECT-TYPE
		SYNTAX		INTEGER { disable(0), enable(1) }
		MAX-ACCESS		read-write
		STATUS			current
		DESCRIPTION
				"TYPE: - Checkbox
				 PAGE: - Audio- ProcAmp
					Mute  cmdID= 3269 "
		::= { iqmux60CmdEntry 3269 }


	iqmux60AudioProcAmpStereo2 OBJECT-TYPE
		SYNTAX		INTEGER { disable(0), enable(1) }
		MAX-ACCESS		read-write
		STATUS			current
		DESCRIPTION
				"TYPE: - Checkbox
				 PAGE: - Audio- ProcAmp
					Stereo 2  cmdID= 3335 "
		::= { iqmux60CmdEntry 3335 }


	iqmux60ProcAmpAnalog2LGainAnalog2L OBJECT-TYPE
		SYNTAX		INTEGER
		MAX-ACCESS		read-write
		STATUS			current
		DESCRIPTION
				"TYPE: - Number
				 PAGE: - Audio- ProcAmp
					Gain Analog 2L  cmdID= 3110  min= -180  max= 180  step= 1  format= %0.1fdB  div_scale= 10
					Min = -18.0dB  Max = 18.0dB  Step = 0.1dB "
		::= { iqmux60CmdEntry 3110 }


	iqmux60ProcAmpAnalog2LInvert OBJECT-TYPE
		SYNTAX		INTEGER { disable(0), enable(1) }
		MAX-ACCESS		read-write
		STATUS			current
		DESCRIPTION
				"TYPE: - Checkbox
				 PAGE: - Audio- ProcAmp
					Invert  cmdID= 3190 "
		::= { iqmux60CmdEntry 3190 }


	iqmux60ProcAmpAnalog2LMute OBJECT-TYPE
		SYNTAX		INTEGER { disable(0), enable(1) }
		MAX-ACCESS		read-write
		STATUS			current
		DESCRIPTION
				"TYPE: - Checkbox
				 PAGE: - Audio- ProcAmp
					Mute  cmdID= 3270 "
		::= { iqmux60CmdEntry 3270 }


	iqmux60ProcAmpAnalog2RGainAnalog2R OBJECT-TYPE
		SYNTAX		INTEGER
		MAX-ACCESS		read-write
		STATUS			current
		DESCRIPTION
				"TYPE: - Number
				 PAGE: - Audio- ProcAmp
					Gain Analog 2R  cmdID= 3111  min= -180  max= 180  step= 1  format= %0.1fdB  div_scale= 10
					Min = -18.0dB  Max = 18.0dB  Step = 0.1dB "
		::= { iqmux60CmdEntry 3111 }


	iqmux60ProcAmpAnalog2RInvert OBJECT-TYPE
		SYNTAX		INTEGER { disable(0), enable(1) }
		MAX-ACCESS		read-write
		STATUS			current
		DESCRIPTION
				"TYPE: - Checkbox
				 PAGE: - Audio- ProcAmp
					Invert  cmdID= 3191 "
		::= { iqmux60CmdEntry 3191 }


	iqmux60ProcAmpAnalog2RMute OBJECT-TYPE
		SYNTAX		INTEGER { disable(0), enable(1) }
		MAX-ACCESS		read-write
		STATUS			current
		DESCRIPTION
				"TYPE: - Checkbox
				 PAGE: - Audio- ProcAmp
					Mute  cmdID= 3271 "
		::= { iqmux60CmdEntry 3271 }


	iqmux60EmbedEmbedder1Embed1Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- Embed- Embedder 1
					Embed 1 Source  cmdID= 2941
					bUS A  value= 0
					bUS B  value= 1
					bUS C  value= 2
					bUS D  value= 3
					aES 1 Direct  value= 4
					aES 2 Direct  value= 5
					test tone  value= 6
					silence  value= 7  "
		::= { iqmux60CmdEntry 2941 }


	iqmux60EmbedEmbedder1PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 1
					Pair Selection  cmdID= 2531
					select Pair 1  value= 0
					select Pair 2  value= 1
					select Pair 3  value= 2
					select Pair 4  value= 3
					select Pair 5  value= 4
					select Pair 6  value= 5
					select Pair 7  value= 6
					select Pair 8  value= 7  "
		::= { iqmux60CmdEntry 2531 }


	iqmux60EmbedEmbedder1Disable OBJECT-TYPE
		SYNTAX		INTEGER { disable(0), enable(1) }
		MAX-ACCESS		read-write
		STATUS			current
		DESCRIPTION
				"TYPE: - Checkbox
				 PAGE: - Audio- Embed- Embedder 1
					Disable  cmdID= 2541 "
		::= { iqmux60CmdEntry 2541 }


	iqmux60EmbedEmbedder2Embed2Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- Embed- Embedder 2
					Embed 2 Source  cmdID= 2942
					bUS A  value= 0
					bUS B  value= 1
					bUS C  value= 2
					bUS D  value= 3
					aES 1 Direct  value= 4
					aES 2 Direct  value= 5
					test tone  value= 6
					silence  value= 7  "
		::= { iqmux60CmdEntry 2942 }


	iqmux60EmbedEmbedder2PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 2
					Pair Selection  cmdID= 2532
					select Pair 1  value= 0
					select Pair 2  value= 1
					select Pair 3  value= 2
					select Pair 4  value= 3
					select Pair 5  value= 4
					select Pair 6  value= 5
					select Pair 7  value= 6
					select Pair 8  value= 7  "
		::= { iqmux60CmdEntry 2532 }


	iqmux60EmbedEmbedder2Disable OBJECT-TYPE
		SYNTAX		INTEGER { disable(0), enable(1) }
		MAX-ACCESS		read-write
		STATUS			current
		DESCRIPTION
				"TYPE: - Checkbox
				 PAGE: - Audio- Embed- Embedder 2
					Disable  cmdID= 2542 "
		::= { iqmux60CmdEntry 2542 }


	iqmux60EmbedEmbedder3Embed3Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- Embed- Embedder 3
					Embed 3 Source  cmdID= 2943
					bUS A  value= 0
					bUS B  value= 1
					bUS C  value= 2
					bUS D  value= 3
					aES 1 Direct  value= 4
					aES 2 Direct  value= 5
					test tone  value= 6
					silence  value= 7  "
		::= { iqmux60CmdEntry 2943 }


	iqmux60EmbedEmbedder3PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 3
					Pair Selection  cmdID= 2533
					select Pair 1  value= 0
					select Pair 2  value= 1
					select Pair 3  value= 2
					select Pair 4  value= 3
					select Pair 5  value= 4
					select Pair 6  value= 5
					select Pair 7  value= 6
					select Pair 8  value= 7  "
		::= { iqmux60CmdEntry 2533 }


	iqmux60EmbedEmbedder3Disable OBJECT-TYPE
		SYNTAX		INTEGER { disable(0), enable(1) }
		MAX-ACCESS		read-write
		STATUS			current
		DESCRIPTION
				"TYPE: - Checkbox
				 PAGE: - Audio- Embed- Embedder 3
					Disable  cmdID= 2543 "
		::= { iqmux60CmdEntry 2543 }


	iqmux60EmbedEmbedder4Embed4Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- Embed- Embedder 4
					Embed 4 Source  cmdID= 2944
					bUS A  value= 0
					bUS B  value= 1
					bUS C  value= 2
					bUS D  value= 3
					aES 1 Direct  value= 4
					aES 2 Direct  value= 5
					test tone  value= 6
					silence  value= 7  "
		::= { iqmux60CmdEntry 2944 }


	iqmux60EmbedEmbedder4PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 4
					Pair Selection  cmdID= 2534
					select Pair 1  value= 0
					select Pair 2  value= 1
					select Pair 3  value= 2
					select Pair 4  value= 3
					select Pair 5  value= 4
					select Pair 6  value= 5
					select Pair 7  value= 6
					select Pair 8  value= 7  "
		::= { iqmux60CmdEntry 2534 }


	iqmux60EmbedEmbedder4Disable OBJECT-TYPE
		SYNTAX		INTEGER { disable(0), enable(1) }
		MAX-ACCESS		read-write
		STATUS			current
		DESCRIPTION
				"TYPE: - Checkbox
				 PAGE: - Audio- Embed- Embedder 4
					Disable  cmdID= 2544 "
		::= { iqmux60CmdEntry 2544 }


	iqmux60Mixer1Mix1Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 1- Mix1 Source1
					Mix1 Source1  cmdID= 3440
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3440 }


	iqmux60MixMixer1Gain1 OBJECT-TYPE
		SYNTAX		INTEGER
		MAX-ACCESS		read-write
		STATUS			current
		DESCRIPTION
				"TYPE: - Number
				 PAGE: - Audio- Mix- Mixer 1
					Gain1  cmdID= 3360  min= -71  max= 0  step= 1  format= %0.0fdB  div_scale= 1
					Min = -71dB  Max = 0dB  Step = 1dB "
		::= { iqmux60CmdEntry 3360 }


	iqmux60Mixer1Mix1Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 1- Mix1 Source2
					Mix1 Source2  cmdID= 3441
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3441 }


	iqmux60MixMixer1Gain2 OBJECT-TYPE
		SYNTAX		INTEGER
		MAX-ACCESS		read-write
		STATUS			current
		DESCRIPTION
				"TYPE: - Number
				 PAGE: - Audio- Mix- Mixer 1
					Gain2  cmdID= 3361  min= -71  max= 0  step= 1  format= %0.0fdB  div_scale= 1
					Min = -71dB  Max = 0dB  Step = 1dB "
		::= { iqmux60CmdEntry 3361 }


	iqmux60Mixer1Mix1Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 1- Mix1 Source3
					Mix1 Source3  cmdID= 3442
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3442 }


	iqmux60MixMixer1Gain3 OBJECT-TYPE
		SYNTAX		INTEGER
		MAX-ACCESS		read-write
		STATUS			current
		DESCRIPTION
				"TYPE: - Number
				 PAGE: - Audio- Mix- Mixer 1
					Gain3  cmdID= 3362  min= -71  max= 0  step= 1  format= %0.0fdB  div_scale= 1
					Min = -71dB  Max = 0dB  Step = 1dB "
		::= { iqmux60CmdEntry 3362 }


	iqmux60Mixer1Mix1Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 1- Mix1 Source4
					Mix1 Source4  cmdID= 3443
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3443 }


	iqmux60MixMixer1Gain4 OBJECT-TYPE
		SYNTAX		INTEGER
		MAX-ACCESS		read-write
		STATUS			current
		DESCRIPTION
				"TYPE: - Number
				 PAGE: - Audio- Mix- Mixer 1
					Gain4  cmdID= 3363  min= -71  max= 0  step= 1  format= %0.0fdB  div_scale= 1
					Min = -71dB  Max = 0dB  Step = 1dB "
		::= { iqmux60CmdEntry 3363 }


	iqmux60Mixer2Mix2Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 2- Mix2 Source1
					Mix2 Source1  cmdID= 3444
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3444 }


	iqmux60MixMixer2Gain1 OBJECT-TYPE
		SYNTAX		INTEGER
		MAX-ACCESS		read-write
		STATUS			current
		DESCRIPTION
				"TYPE: - Number
				 PAGE: - Audio- Mix- Mixer 2
					Gain1  cmdID= 3364  min= -71  max= 0  step= 1  format= %0.0fdB  div_scale= 1
					Min = -71dB  Max = 0dB  Step = 1dB "
		::= { iqmux60CmdEntry 3364 }


	iqmux60Mixer2Mix2Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 2- Mix2 Source2
					Mix2 Source2  cmdID= 3445
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3445 }


	iqmux60MixMixer2Gain2 OBJECT-TYPE
		SYNTAX		INTEGER
		MAX-ACCESS		read-write
		STATUS			current
		DESCRIPTION
				"TYPE: - Number
				 PAGE: - Audio- Mix- Mixer 2
					Gain2  cmdID= 3365  min= -71  max= 0  step= 1  format= %0.0fdB  div_scale= 1
					Min = -71dB  Max = 0dB  Step = 1dB "
		::= { iqmux60CmdEntry 3365 }


	iqmux60Mixer2Mix2Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 2- Mix2 Source3
					Mix2 Source3  cmdID= 3446
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3446 }


	iqmux60MixMixer2Gain3 OBJECT-TYPE
		SYNTAX		INTEGER
		MAX-ACCESS		read-write
		STATUS			current
		DESCRIPTION
				"TYPE: - Number
				 PAGE: - Audio- Mix- Mixer 2
					Gain3  cmdID= 3366  min= -71  max= 0  step= 1  format= %0.0fdB  div_scale= 1
					Min = -71dB  Max = 0dB  Step = 1dB "
		::= { iqmux60CmdEntry 3366 }


	iqmux60Mixer2Mix2Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 2- Mix2 Source4
					Mix2 Source4  cmdID= 3447
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3447 }


	iqmux60MixMixer2Gain4 OBJECT-TYPE
		SYNTAX		INTEGER
		MAX-ACCESS		read-write
		STATUS			current
		DESCRIPTION
				"TYPE: - Number
				 PAGE: - Audio- Mix- Mixer 2
					Gain4  cmdID= 3367  min= -71  max= 0  step= 1  format= %0.0fdB  div_scale= 1
					Min = -71dB  Max = 0dB  Step = 1dB "
		::= { iqmux60CmdEntry 3367 }


	iqmux60Mixer3Mix3Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 3- Mix3 Source1
					Mix3 Source1  cmdID= 3448
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3448 }


	iqmux60MixMixer3Gain1 OBJECT-TYPE
		SYNTAX		INTEGER
		MAX-ACCESS		read-write
		STATUS			current
		DESCRIPTION
				"TYPE: - Number
				 PAGE: - Audio- Mix- Mixer 3
					Gain1  cmdID= 3368  min= -71  max= 0  step= 1  format= %0.0fdB  div_scale= 1
					Min = -71dB  Max = 0dB  Step = 1dB "
		::= { iqmux60CmdEntry 3368 }


	iqmux60Mixer3Mix3Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 3- Mix3 Source2
					Mix3 Source2  cmdID= 3449
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3449 }


	iqmux60MixMixer3Gain2 OBJECT-TYPE
		SYNTAX		INTEGER
		MAX-ACCESS		read-write
		STATUS			current
		DESCRIPTION
				"TYPE: - Number
				 PAGE: - Audio- Mix- Mixer 3
					Gain2  cmdID= 3369  min= -71  max= 0  step= 1  format= %0.0fdB  div_scale= 1
					Min = -71dB  Max = 0dB  Step = 1dB "
		::= { iqmux60CmdEntry 3369 }


	iqmux60Mixer3Mix3Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 3- Mix3 Source3
					Mix3 Source3  cmdID= 3450
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3450 }


	iqmux60MixMixer3Gain3 OBJECT-TYPE
		SYNTAX		INTEGER
		MAX-ACCESS		read-write
		STATUS			current
		DESCRIPTION
				"TYPE: - Number
				 PAGE: - Audio- Mix- Mixer 3
					Gain3  cmdID= 3370  min= -71  max= 0  step= 1  format= %0.0fdB  div_scale= 1
					Min = -71dB  Max = 0dB  Step = 1dB "
		::= { iqmux60CmdEntry 3370 }


	iqmux60Mixer3Mix3Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 3- Mix3 Source4
					Mix3 Source4  cmdID= 3451
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3451 }


	iqmux60MixMixer3Gain4 OBJECT-TYPE
		SYNTAX		INTEGER
		MAX-ACCESS		read-write
		STATUS			current
		DESCRIPTION
				"TYPE: - Number
				 PAGE: - Audio- Mix- Mixer 3
					Gain4  cmdID= 3371  min= -71  max= 0  step= 1  format= %0.0fdB  div_scale= 1
					Min = -71dB  Max = 0dB  Step = 1dB "
		::= { iqmux60CmdEntry 3371 }


	iqmux60Mixer4Mix4Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 4- Mix4 Source1
					Mix4 Source1  cmdID= 3452
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3452 }


	iqmux60MixMixer4Gain1 OBJECT-TYPE
		SYNTAX		INTEGER
		MAX-ACCESS		read-write
		STATUS			current
		DESCRIPTION
				"TYPE: - Number
				 PAGE: - Audio- Mix- Mixer 4
					Gain1  cmdID= 3372  min= -71  max= 0  step= 1  format= %0.0fdB  div_scale= 1
					Min = -71dB  Max = 0dB  Step = 1dB "
		::= { iqmux60CmdEntry 3372 }


	iqmux60Mixer4Mix4Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 4- Mix4 Source2
					Mix4 Source2  cmdID= 3453
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3453 }


	iqmux60MixMixer4Gain2 OBJECT-TYPE
		SYNTAX		INTEGER
		MAX-ACCESS		read-write
		STATUS			current
		DESCRIPTION
				"TYPE: - Number
				 PAGE: - Audio- Mix- Mixer 4
					Gain2  cmdID= 3373  min= -71  max= 0  step= 1  format= %0.0fdB  div_scale= 1
					Min = -71dB  Max = 0dB  Step = 1dB "
		::= { iqmux60CmdEntry 3373 }


	iqmux60Mixer4Mix4Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 4- Mix4 Source3
					Mix4 Source3  cmdID= 3454
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3454 }


	iqmux60MixMixer4Gain3 OBJECT-TYPE
		SYNTAX		INTEGER
		MAX-ACCESS		read-write
		STATUS			current
		DESCRIPTION
				"TYPE: - Number
				 PAGE: - Audio- Mix- Mixer 4
					Gain3  cmdID= 3374  min= -71  max= 0  step= 1  format= %0.0fdB  div_scale= 1
					Min = -71dB  Max = 0dB  Step = 1dB "
		::= { iqmux60CmdEntry 3374 }


	iqmux60Mixer4Mix4Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 4- Mix4 Source4
					Mix4 Source4  cmdID= 3455
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux60CmdEntry 3455 }


	iqmux60MixMixer4Gain4 OBJECT-TYPE
		SYNTAX		INTEGER
		MAX-ACCESS		read-write
		STATUS			current
		DESCRIPTION
				"TYPE: - Number
				 PAGE: - Audio- Mix- Mixer 4
					Gain4  cmdID= 3375  min= -71  max= 0  step= 1  format= %0.0fdB  div_scale= 1
					Min = -71dB  Max = 0dB  Step = 1dB "
		::= { iqmux60CmdEntry 3375 }


	iqmux60BusSourceBusALSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusAL Source
					BusAL Source  cmdID= 3520
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux60CmdEntry 3520 }


	iqmux60BusSourceBusARSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusAR Source
					BusAR Source  cmdID= 3521
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux60CmdEntry 3521 }


	iqmux60BusSourceBusBLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusBL Source
					BusBL Source  cmdID= 3522
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux60CmdEntry 3522 }


	iqmux60BusSourceBusBRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusBR Source
					BusBR Source  cmdID= 3523
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux60CmdEntry 3523 }


	iqmux60BusSourceBusCLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusCL Source
					BusCL Source  cmdID= 3524
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux60CmdEntry 3524 }


	iqmux60BusSourceBusCRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusCR Source
					BusCR Source  cmdID= 3525
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux60CmdEntry 3525 }


	iqmux60BusSourceBusDLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusDL Source
					BusDL Source  cmdID= 3526
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux60CmdEntry 3526 }


	iqmux60BusSourceBusDRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusDR Source
					BusDR Source  cmdID= 3527
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux60CmdEntry 3527 }


	iqmux60BusesBusProcAmpStereoA OBJECT-TYPE
		SYNTAX		INTEGER { disable(0), enable(1) }
		MAX-ACCESS		read-write
		STATUS			current
		DESCRIPTION
				"TYPE: - Checkbox
				 PAGE: - Audio- Buses
					Stereo A  cmdID= 3320 "
		::= { iqmux60CmdEntry 3320 }


	iqmux60BusProcAmpBusALGainBusAL OBJECT-TYPE
		SYNTAX		INTEGER
		MAX-ACCESS		read-write
		STATUS			current
		DESCRIPTION
				"TYPE: - Number
				 PAGE: - Audio- Buses
					Gain Bus AL  cmdID= 3080  min= -180  max= 180  step= 1  format= %0.1fdB  div_scale= 10
					Min = -18.0dB  Max = 18.0dB  Step = 0.1dB "
		::= { iqmux60CmdEntry 3080 }


	iqmux60BusProcAmpBusALInvert OBJECT-TYPE
		SYNTAX		INTEGER { disable(0), enable(1) }
		MAX-ACCESS		read-write
		STATUS			current
		DESCRIPTION
				"TYPE: - Checkbox
				 PAGE: - Audio- Buses
					Invert  cmdID= 3160 "
		::= { iqmux60CmdEntry 3160 }


	iqmux60BusProcAmpBusALMute OBJECT-TYPE
		SYNTAX		INTEGER { disable(0), enable(1) }
		MAX-ACCESS		read-write
		STATUS			current
		DESCRIPTION
				"TYPE: - Checkbox
				 PAGE: - Audio- Buses
					Mute  cmdID= 3240 "
		::= { iqmux60CmdEntry 3240 }


	iqmux60BusProcAmpBusARGainBusAR OBJECT-TYPE
		SYNTAX		INTEGER
		MAX-ACCESS		read-write
		STATUS			current
		DESCRIPTION
				"TYPE: - Number
				 PAGE: - Audio- Buses
					Gain Bus AR  cmdID= 3081  min= -180  max= 180  step= 1  format= %0.1fdB  div_scale= 10
					Min = -18.0dB  Max = 18.0dB  Step = 0.1dB "
		::= { iqmux60CmdEntry 3081 }


	iqmux60BusProcAmpBusARInvert OBJECT-TYPE
		SYNTAX		INTEGER { disable(0), enable(1) }
		MAX-ACCESS		read-write
		STATUS			current
		DESCRIPTION
				"TYPE: - Checkbox
				 PAGE: - Audio- Buses
					Invert  cmdID= 3161 "
		::= { iqmux60CmdEntry 3161 }


	iqmux60BusProcAmpBusARMute OBJECT-TYPE
		SYNTAX		INTEGER { disable(0), enable(1) }
		MAX-ACCESS		read-write
		STATUS			current
		DESCRIPTION
				"TYPE: - Checkbox
				 PAGE: - Audio- Buses
					Mute  cmdID= 3241 "
		::= { iqmux60CmdEntry 3241 }


	iqmux60BusesBusProcAmpStereoB OBJECT-TYPE
		SYNTAX		INTEGER { disable(0), enable(1) }
		MAX-ACCESS		read-write
		STATUS			current
		DESCRIPTION
				"TYPE: - Checkbox
				 PAGE: - Audio- Buses
					Stereo B  cmdID= 3321 "
		::= { iqmux60CmdEntry 3321 }


	iqmux60BusProcAmpBusBLGainBusBL OBJECT-TYPE
		SYNTAX		INTEGER
		MAX-ACCESS		read-write
		STATUS			current
		DESCRIPTION
				"TYPE: - Number
				 PAGE: - Audio- Buses
					Gain Bus BL  cmdID= 3082  min= -180  max= 180  step= 1  format= %0.1fdB  div_scale= 10
					Min = -18.0dB  Max = 18.0dB  Step = 0.1dB "
		::= { iqmux60CmdEntry 3082 }


	iqmux60BusProcAmpBusBLInvert OBJECT-TYPE
		SYNTAX		INTEGER { disable(0), enable(1) }
		MAX-ACCESS		read-write
		STATUS			current
		DESCRIPTION
				"TYPE: - Checkbox
				 PAGE: - Audio- Buses
					Invert  cmdID= 3162 "
		::= { iqmux60CmdEntry 3162 }


	iqmux60BusProcAmpBusBLMute OBJECT-TYPE
		SYNTAX		INTEGER { disable(0), enable(1) }
		MAX-ACCESS		read-write
		STATUS			current
		DESCRIPTION
				"TYPE: - Checkbox
				 PAGE: - Audio- Buses
					Mute  cmdID= 3242 "
		::= { iqmux60CmdEntry 3242 }


	iqmux60BusProcAmpBusBRGainBusBR OBJECT-TYPE
		SYNTAX		INTEGER
		MAX-ACCESS		read-write
		STATUS			current
		DESCRIPTION
				"TYPE: - Number
				 PAGE: - Audio- Buses
					Gain Bus BR  cmdID= 3083  min= -180  max= 180  step= 1  format= %0.1fdB  div_scale= 10
					Min = -18.0dB  Max = 18.0dB  Step = 0.1dB "
		::= { iqmux60CmdEntry 3083 }


	iqmux60BusProcAmpBusBRInvert OBJECT-TYPE
		SYNTAX		INTEGER { disable(0), enable(1) }
		MAX-ACCESS		read-write
		STATUS			current
		DESCRIPTION
				"TYPE: - Checkbox
				 PAGE: - Audio- Buses
					Invert  cmdID= 3163 "
		::= { iqmux60CmdEntry 3163 }


	iqmux60BusProcAmpBusBRMute OBJECT-TYPE
		SYNTAX		INTEGER { disable(0), enable(1) }
		MAX-ACCESS		read-write
		STATUS			current
		DESCRIPTION
				"TYPE: - Checkbox
				 PAGE: - Audio- Buses
					Mute  cmdID= 3243 "
		::= { iqmux60CmdEntry 3243 }


	iqmux60BusesBusProcAmpStereoC OBJECT-TYPE
		SYNTAX		INTEGER { disable(0), enable(1) }
		MAX-ACCESS		read-write
		STATUS			current
		DESCRIPTION
				"TYPE: - Checkbox
				 PAGE: - Audio- Buses
					Stereo C  cmdID= 3322 "
		::= { iqmux60CmdEntry 3322 }


	iqmux60BusProcAmpBusCLGainBusCL OBJECT-TYPE
		SYNTAX		INTEGER
		MAX-ACCESS		read-write
		STATUS			current
		DESCRIPTION
				"TYPE: - Number
				 PAGE: - Audio- Buses
					Gain Bus CL  cmdID= 3084  min= -180  max= 180  step= 1  format= %0.1fdB  div_scale= 10
					Min = -18.0dB  Max = 18.0dB  Step = 0.1dB "
		::= { iqmux60CmdEntry 3084 }


	iqmux60BusProcAmpBusCLInvert OBJECT-TYPE
		SYNTAX		INTEGER { disable(0), enable(1) }
		MAX-ACCESS		read-write
		STATUS			current
		DESCRIPTION
				"TYPE: - Checkbox
				 PAGE: - Audio- Buses
					Invert  cmdID= 3164 "
		::= { iqmux60CmdEntry 3164 }


	iqmux60BusProcAmpBusCLMute OBJECT-TYPE
		SYNTAX		INTEGER { disable(0), enable(1) }
		MAX-ACCESS		read-write
		STATUS			current
		DESCRIPTION
				"TYPE: - Checkbox
				 PAGE: - Audio- Buses
					Mute  cmdID= 3244 "
		::= { iqmux60CmdEntry 3244 }


	iqmux60BusProcAmpBusCRGainBusCR OBJECT-TYPE
		SYNTAX		INTEGER
		MAX-ACCESS		read-write
		STATUS			current
		DESCRIPTION
				"TYPE: - Number
				 PAGE: - Audio- Buses
					Gain Bus CR  cmdID= 3085  min= -180  max= 180  step= 1  format= %0.1fdB  div_scale= 10
					Min = -18.0dB  Max = 18.0dB  Step = 0.1dB "
		::= { iqmux60CmdEntry 3085 }


	iqmux60BusProcAmpBusCRInvert OBJECT-TYPE
		SYNTAX		INTEGER { disable(0), enable(1) }
		MAX-ACCESS		read-write
		STATUS			current
		DESCRIPTION
				"TYPE: - Checkbox
				 PAGE: - Audio- Buses
					Invert  cmdID= 3165 "
		::= { iqmux60CmdEntry 3165 }


	iqmux60BusProcAmpBusCRMute OBJECT-TYPE
		SYNTAX		INTEGER { disable(0), enable(1) }
		MAX-ACCESS		read-write
		STATUS			current
		DESCRIPTION
				"TYPE: - Checkbox
				 PAGE: - Audio- Buses
					Mute  cmdID= 3245 "
		::= { iqmux60CmdEntry 3245 }


	iqmux60BusesBusProcAmpStereoD OBJECT-TYPE
		SYNTAX		INTEGER { disable(0), enable(1) }
		MAX-ACCESS		read-write
		STATUS			current
		DESCRIPTION
				"TYPE: - Checkbox
				 PAGE: - Audio- Buses
					Stereo D  cmdID= 3323 "
		::= { iqmux60CmdEntry 3323 }


	iqmux60BusProcAmpBusDLGainBusDL OBJECT-TYPE
		SYNTAX		INTEGER
		MAX-ACCESS		read-write
		STATUS			current
		DESCRIPTION
				"TYPE: - Number
				 PAGE: - Audio- Buses
					Gain Bus DL  cmdID= 3086  min= -180  max= 180  step= 1  format= %0.1fdB  div_scale= 10
					Min = -18.0dB  Max = 18.0dB  Step = 0.1dB "
		::= { iqmux60CmdEntry 3086 }


	iqmux60BusProcAmpBusDLInvert OBJECT-TYPE
		SYNTAX		INTEGER { disable(0), enable(1) }
		MAX-ACCESS		read-write
		STATUS			current
		DESCRIPTION
				"TYPE: - Checkbox
				 PAGE: - Audio- Buses
					Invert  cmdID= 3166 "
		::= { iqmux60CmdEntry 3166 }


	iqmux60BusProcAmpBusDLMute OBJECT-TYPE
		SYNTAX		INTEGER { disable(0), enable(1) }
		MAX-ACCESS		read-write
		STATUS			current
		DESCRIPTION
				"TYPE: - Checkbox
				 PAGE: - Audio- Buses
					Mute  cmdID= 3246 "
		::= { iqmux60CmdEntry 3246 }


	iqmux60BusProcAmpBusDRGainBusDR OBJECT-TYPE
		SYNTAX		INTEGER
		MAX-ACCESS		read-write
		STATUS			current
		DESCRIPTION
				"TYPE: - Number
				 PAGE: - Audio- Buses
					Gain Bus DR  cmdID= 3087  min= -180  max= 180  step= 1  format= %0.1fdB  div_scale= 10
					Min = -18.0dB  Max = 18.0dB  Step = 0.1dB "
		::= { iqmux60CmdEntry 3087 }


	iqmux60BusProcAmpBusDRInvert OBJECT-TYPE
		SYNTAX		INTEGER { disable(0), enable(1) }
		MAX-ACCESS		read-write
		STATUS			current
		DESCRIPTION
				"TYPE: - Checkbox
				 PAGE: - Audio- Buses
					Invert  cmdID= 3167 "
		::= { iqmux60CmdEntry 3167 }


	iqmux60BusProcAmpBusDRMute OBJECT-TYPE
		SYNTAX		INTEGER { disable(0), enable(1) }
		MAX-ACCESS		read-write
		STATUS			current
		DESCRIPTION
				"TYPE: - Checkbox
				 PAGE: - Audio- Buses
					Mute  cmdID= 3247 "
		::= { iqmux60CmdEntry 3247 }


	iqmux60AudioDelayAESInput1Delay OBJECT-TYPE
		SYNTAX		INTEGER
		MAX-ACCESS		read-write
		STATUS			current
		DESCRIPTION
				"TYPE: - Number
				 PAGE: - Audio- Delay
					AES Input 1 Delay  cmdID= 2928  min= 0  max= 1500  step= 1  format= %0.0f ms  div_scale= 1
					Min = 0 ms  Max = 1500 ms  Step = 1 ms "
		::= { iqmux60CmdEntry 2928 }


	iqmux60AudioDelayAESInput2Delay OBJECT-TYPE
		SYNTAX		INTEGER
		MAX-ACCESS		read-write
		STATUS			current
		DESCRIPTION
				"TYPE: - Number
				 PAGE: - Audio- Delay
					AES Input 2 Delay  cmdID= 2929  min= 0  max= 1500  step= 1  format= %0.0f ms  div_scale= 1
					Min = 0 ms  Max = 1500 ms  Step = 1 ms "
		::= { iqmux60CmdEntry 2929 }


	iqmux60AudioDelayAnalogIn1Delay OBJECT-TYPE
		SYNTAX		INTEGER
		MAX-ACCESS		read-write
		STATUS			current
		DESCRIPTION
				"TYPE: - Number
				 PAGE: - Audio- Delay
					Analog In 1 Delay  cmdID= 2930  min= 0  max= 1500  step= 1  format= %0.0f ms  div_scale= 1
					Min = 0 ms  Max = 1500 ms  Step = 1 ms "
		::= { iqmux60CmdEntry 2930 }


	iqmux60AudioDelayAnalogIn2Delay OBJECT-TYPE
		SYNTAX		INTEGER
		MAX-ACCESS		read-write
		STATUS			current
		DESCRIPTION
				"TYPE: - Number
				 PAGE: - Audio- Delay
					Analog In 2 Delay  cmdID= 2931  min= 0  max= 1500  step= 1  format= %0.0f ms  div_scale= 1
					Min = 0 ms  Max = 1500 ms  Step = 1 ms "
		::= { iqmux60CmdEntry 2931 }


	iqmux60DelayDelaySelectInternal OBJECT-TYPE
		SYNTAX		INTEGER { disable(0), enable(1) }
		MAX-ACCESS		read-write
		STATUS			current
		DESCRIPTION
				"TYPE: - Checkbox
				 PAGE: - Audio- Delay
					Internal  cmdID= 2567 "
		::= { iqmux60CmdEntry 2567 }


	iqmux60DelayDelaySelectManual OBJECT-TYPE
		SYNTAX		INTEGER { disable(0), enable(1) }
		MAX-ACCESS		read-write
		STATUS			current
		DESCRIPTION
				"TYPE: - Checkbox
				 PAGE: - Audio- Delay
					Manual  cmdID= 2568 "
		::= { iqmux60CmdEntry 2568 }


	iqmux60DelayDelaySelectRolltrack14 OBJECT-TYPE
		SYNTAX		INTEGER { disable(0), enable(1) }
		MAX-ACCESS		read-write
		STATUS			current
		DESCRIPTION
				"TYPE: - Checkbox
				 PAGE: - Audio- Delay
					Rolltrack 14  cmdID= 2569 "
		::= { iqmux60CmdEntry 2569 }


	iqmux60DelayDelaySelectRolltrack15 OBJECT-TYPE
		SYNTAX		INTEGER { disable(0), enable(1) }
		MAX-ACCESS		read-write
		STATUS			current
		DESCRIPTION
				"TYPE: - Checkbox
				 PAGE: - Audio- Delay
					Rolltrack 15  cmdID= 2570 "
		::= { iqmux60CmdEntry 2570 }


	iqmux60DelayDelaySelectRolltrack16 OBJECT-TYPE
		SYNTAX		INTEGER { disable(0), enable(1) }
		MAX-ACCESS		read-write
		STATUS			current
		DESCRIPTION
				"TYPE: - Checkbox
				 PAGE: - Audio- Delay
					Rolltrack 16  cmdID= 2571 "
		::= { iqmux60CmdEntry 2571 }


	iqmux60DelayDelaySelectRolltrack17 OBJECT-TYPE
		SYNTAX		INTEGER { disable(0), enable(1) }
		MAX-ACCESS		read-write
		STATUS			current
		DESCRIPTION
				"TYPE: - Checkbox
				 PAGE: - Audio- Delay
					Rolltrack 17  cmdID= 2572 "
		::= { iqmux60CmdEntry 2572 }


	iqmux60DelayDelaySelectGPIDelaySelect OBJECT-TYPE
		SYNTAX		INTEGER { disable(0), enable(1) }
		MAX-ACCESS		read-write
		STATUS			current
		DESCRIPTION
				"TYPE: - Checkbox
				 PAGE: - Audio- Delay
					GPI Delay Select  cmdID= 3051 "
		::= { iqmux60CmdEntry 3051 }


	iqmux60DelayDelayStatusManual OBJECT-TYPE
		SYNTAX		INTEGER
		MAX-ACCESS		read-write
		STATUS			current
		DESCRIPTION
				"TYPE: - Number
				 PAGE: - Audio- Delay
					Manual Delay  cmdID= 2573  min= -40  max= 1500  step= 1  format= %3.0f ms  div_scale= 1
					Manual  cmdID= 2573  format=
					Min = -40 ms  Max = 1500 ms  Step =   1 ms "
		::= { iqmux60CmdEntry 2573 }


	iqmux60DelayDelayStatusInternal OBJECT-TYPE
		SYNTAX		RollCallString
		MAX-ACCESS		read-only
		STATUS			current
		DESCRIPTION
				"TYPE: - Display
				 PAGE: - Audio- Delay
					Internal  cmdID= 2574  format=   "
		::= { iqmux60CmdEntry 2574 }


	iqmux60DelayDelayStatusRolltrack14 OBJECT-TYPE
		SYNTAX		RollCallString
		MAX-ACCESS		read-only
		STATUS			current
		DESCRIPTION
				"TYPE: - Display
				 PAGE: - Audio- Delay
					Rolltrack 14  cmdID= 14  format=   "
		::= { iqmux60CmdEntry 14 }


	iqmux60DelayDelayStatusRolltrack15 OBJECT-TYPE
		SYNTAX		RollCallString
		MAX-ACCESS		read-only
		STATUS			current
		DESCRIPTION
				"TYPE: - Display
				 PAGE: - Audio- Delay
					Rolltrack 15  cmdID= 15  format=   "
		::= { iqmux60CmdEntry 15 }


	iqmux60DelayDelayStatusRolltrack16 OBJECT-TYPE
		SYNTAX		RollCallString
		MAX-ACCESS		read-only
		STATUS			current
		DESCRIPTION
				"TYPE: - Display
				 PAGE: - Audio- Delay
					Rolltrack 16  cmdID= 16  format=   "
		::= { iqmux60CmdEntry 16 }


	iqmux60DelayDelayStatusRolltrack17 OBJECT-TYPE
		SYNTAX		RollCallString
		MAX-ACCESS		read-only
		STATUS			current
		DESCRIPTION
				"TYPE: - Display
				 PAGE: - Audio- Delay
					Rolltrack 17  cmdID= 17  format=   "
		::= { iqmux60CmdEntry 17 }


	iqmux60DelayDelayStatusGPIDelayDisplay OBJECT-TYPE
		SYNTAX		RollCallString
		MAX-ACCESS		read-only
		STATUS			current
		DESCRIPTION
				"TYPE: - Display
				 PAGE: - Audio- Delay
					GPI Delay Display  cmdID= 3052  format=   "
		::= { iqmux60CmdEntry 3052 }


	iqmux60DelayDelayStatusTotalDelayDisplay OBJECT-TYPE
		SYNTAX		RollCallString
		MAX-ACCESS		read-only
		STATUS			current
		DESCRIPTION
				"TYPE: - Display
				 PAGE: - Audio- Delay
					Total Delay Display  cmdID= 2979  format=   "
		::= { iqmux60CmdEntry 2979 }


	iqmux60AudioMonitorSilenceLevel OBJECT-TYPE
		SYNTAX		INTEGER
		MAX-ACCESS		read-write
		STATUS			current
		DESCRIPTION
				"TYPE: - Number
				 PAGE: - Audio- Monitor
					Silence Level  cmdID= 3056  min= -80  max= 0  step= 1  format= %1.1f dB  div_scale= 1
					Min = -80.0 dB  Max = 0.0 dB  Step = 1.0 dB "
		::= { iqmux60CmdEntry 3056 }


	iqmux60AudioMonitorLowLevel OBJECT-TYPE
		SYNTAX		INTEGER
		MAX-ACCESS		read-write
		STATUS			current
		DESCRIPTION
				"TYPE: - Number
				 PAGE: - Audio- Monitor
					Low Level  cmdID= 2517  min= -80  max= 0  step= 1  format= %1.1f dB  div_scale= 1
					Min = -80.0 dB  Max = 0.0 dB  Step = 1.0 dB "
		::= { iqmux60CmdEntry 2517 }


	iqmux60AudioMonitorHighLevel OBJECT-TYPE
		SYNTAX		INTEGER
		MAX-ACCESS		read-write
		STATUS			current
		DESCRIPTION
				"TYPE: - Number
				 PAGE: - Audio- Monitor
					High Level  cmdID= 3057  min= -80  max= 0  step= 1  format= %1.1f dB  div_scale= 1
					Min = -80.0 dB  Max = 0.0 dB  Step = 1.0 dB "
		::= { iqmux60CmdEntry 3057 }


	iqmux60AudioMonitorOverloadLevel OBJECT-TYPE
		SYNTAX		INTEGER
		MAX-ACCESS		read-write
		STATUS			current
		DESCRIPTION
				"TYPE: - Number
				 PAGE: - Audio- Monitor
					Overload Level  cmdID= 3058  min= -80  max= 0  step= 1  format= %1.1f dB  div_scale= 1
					Min = -80.0 dB  Max = 0.0 dB  Step = 1.0 dB "
		::= { iqmux60CmdEntry 3058 }


	iqmux60AudioMonitorWarningTimer OBJECT-TYPE
		SYNTAX		INTEGER
		MAX-ACCESS		read-write
		STATUS			current
		DESCRIPTION
				"TYPE: - Number
				 PAGE: - Audio- Monitor
					Warning Timer  cmdID= 2518  min= 1  max= 20  step= 1  format= %1.0f sec  div_scale= 1
					Min = 1 sec  Max = 20 sec  Step = 1 sec "
		::= { iqmux60CmdEntry 2518 }


	iqmux60Freeze OBJECT-TYPE
		SYNTAX		INTEGER { disable(0), enable(1) }
		MAX-ACCESS		read-write
		STATUS			current
		DESCRIPTION
				"TYPE: - Checkbox
					Freeze  cmdID= 1208 "
		::= { iqmux60CmdEntry 1208 }


	iqmux60VideoDelay OBJECT-TYPE
		SYNTAX		INTEGER {
							val_0_Frame_Delay(0),
							val_1_Frame_Delay(1),
							val_2_Frame_Delay(2)
							}
		MAX-ACCESS		read-write
		STATUS			current
		DESCRIPTION
				"TYPE: - Button
				 PAGE: - Video Delay
					0 Frame Delay  cmdID= 2973  value= 0
					1 Frame Delay  cmdID= 2973  value= 1
					2 Frame Delay  cmdID= 2973  value= 2  "
		::= { iqmux60CmdEntry 2973 }


	iqmux60VideoDelayDelayPhase625HPhase OBJECT-TYPE
		SYNTAX		INTEGER
		MAX-ACCESS		read-write
		STATUS			current
		DESCRIPTION
				"TYPE: - Number
				 PAGE: - Video Delay
					625 H Phase  cmdID= 2974  min= 0  max= 63962899  step= -28499  format=  %.0fns  div_scale= 1000
					Min =  0ns  Max =  63963ns  Step =  -28ns "
		::= { iqmux60CmdEntry 2974 }


	iqmux60VideoDelayDelayPhase625VPhase OBJECT-TYPE
		SYNTAX		INTEGER
		MAX-ACCESS		read-write
		STATUS			current
		DESCRIPTION
				"TYPE: - Number
				 PAGE: - Video Delay
					625 V Phase  cmdID= 2975  min= 0  max= 624  step= 1  format=  %.0flines  div_scale= 1
					Min =  0lines  Max =  624lines  Step =  1lines "
		::= { iqmux60CmdEntry 2975 }


	iqmux60VideoDelayDelayPhase525HPhase OBJECT-TYPE
		SYNTAX		INTEGER
		MAX-ACCESS		read-write
		STATUS			current
		DESCRIPTION
				"TYPE: - Number
				 PAGE: - Video Delay
					525 H Phase  cmdID= 2976  min= 0  max= 63518455  step= -28499  format=  %.0fns  div_scale= 1000
					Min =  0ns  Max =  63518ns  Step =  -28ns "
		::= { iqmux60CmdEntry 2976 }


	iqmux60VideoDelayDelayPhase525VPhase OBJECT-TYPE
		SYNTAX		INTEGER
		MAX-ACCESS		read-write
		STATUS			current
		DESCRIPTION
				"TYPE: - Number
				 PAGE: - Video Delay
					525 V Phase  cmdID= 2977  min= 0  max= 524  step= 1  format=  %.0flines  div_scale= 1
					Min =  0lines  Max =  524lines  Step =  1lines "
		::= { iqmux60CmdEntry 2977 }


	iqmux60UserMemMemory1Save1 OBJECT-TYPE
		SYNTAX		INTEGER { noAction(0),save_1(1) }
		MAX-ACCESS		read-write
		STATUS			current
		DESCRIPTION
				"TYPE: - Button
				 PAGE: - User Mem
					save 1  cmdID= 1600  value= 1  "
		::= { iqmux60CmdEntry 1600 }


	iqmux60UserMemMemory1Recall1 OBJECT-TYPE
		SYNTAX		INTEGER { noAction(0),recall_1(1) }
		MAX-ACCESS		read-write
		STATUS			current
		DESCRIPTION
				"TYPE: - Button
				 PAGE: - User Mem
					recall 1  cmdID= 1601  value= 1  "
		::= { iqmux60CmdEntry 1601 }


	iqmux60UserMemMemory1Clear1 OBJECT-TYPE
		SYNTAX		INTEGER { noAction(0),clear_1(1) }
		MAX-ACCESS		read-write
		STATUS			current
		DESCRIPTION
				"TYPE: - Button
				 PAGE: - User Mem
					clear 1  cmdID= 1602  value= 1  "
		::= { iqmux60CmdEntry 1602 }


	iqmux60UserMemMemory1Name1 OBJECT-TYPE
		SYNTAX		RollCallString
		MAX-ACCESS		read-write
		STATUS			current
		DESCRIPTION
				"TYPE: - Editstring
				 PAGE: - User Mem
					Name 1  cmdID= 1603  "
		::= { iqmux60CmdEntry 1603 }


	iqmux60UserMemMemory2Save2 OBJECT-TYPE
		SYNTAX		INTEGER { noAction(0),save_2(1) }
		MAX-ACCESS		read-write
		STATUS			current
		DESCRIPTION
				"TYPE: - Button
				 PAGE: - User Mem
					save 2  cmdID= 1604  value= 1  "
		::= { iqmux60CmdEntry 1604 }


	iqmux60UserMemMemory2Recall2 OBJECT-TYPE
		SYNTAX		INTEGER { noAction(0),recall_2(1) }
		MAX-ACCESS		read-write
		STATUS			current
		DESCRIPTION
				"TYPE: - Button
				 PAGE: - User Mem
					recall 2  cmdID= 1605  value= 1  "
		::= { iqmux60CmdEntry 1605 }


	iqmux60UserMemMemory2Clear2 OBJECT-TYPE
		SYNTAX		INTEGER { noAction(0),clear_2(1) }
		MAX-ACCESS		read-write
		STATUS			current
		DESCRIPTION
				"TYPE: - Button
				 PAGE: - User Mem
					clear 2  cmdID= 1606  value= 1  "
		::= { iqmux60CmdEntry 1606 }


	iqmux60UserMemMemory2Name2 OBJECT-TYPE
		SYNTAX		RollCallString
		MAX-ACCESS		read-write
		STATUS			current
		DESCRIPTION
				"TYPE: - Editstring
				 PAGE: - User Mem
					Name 2  cmdID= 1607  "
		::= { iqmux60CmdEntry 1607 }


	iqmux60UserMemMemory3Save3 OBJECT-TYPE
		SYNTAX		INTEGER { noAction(0),save_3(1) }
		MAX-ACCESS		read-write
		STATUS			current
		DESCRIPTION
				"TYPE: - Button
				 PAGE: - User Mem
					save 3  cmdID= 1608  value= 1  "
		::= { iqmux60CmdEntry 1608 }


	iqmux60UserMemMemory3Recall3 OBJECT-TYPE
		SYNTAX		INTEGER { noAction(0),recall_3(1) }
		MAX-ACCESS		read-write
		STATUS			current
		DESCRIPTION
				"TYPE: - Button
				 PAGE: - User Mem
					recall 3  cmdID= 1609  value= 1  "
		::= { iqmux60CmdEntry 1609 }


	iqmux60UserMemMemory3Clear3 OBJECT-TYPE
		SYNTAX		INTEGER { noAction(0),clear_3(1) }
		MAX-ACCESS		read-write
		STATUS			current
		DESCRIPTION
				"TYPE: - Button
				 PAGE: - User Mem
					clear 3  cmdID= 1610  value= 1  "
		::= { iqmux60CmdEntry 1610 }


	iqmux60UserMemMemory3Name3 OBJECT-TYPE
		SYNTAX		RollCallString
		MAX-ACCESS		read-write
		STATUS			current
		DESCRIPTION
				"TYPE: - Editstring
				 PAGE: - User Mem
					Name 3  cmdID= 1611  "
		::= { iqmux60CmdEntry 1611 }


	iqmux60UserMemMemory4Save4 OBJECT-TYPE
		SYNTAX		INTEGER { noAction(0),save_4(1) }
		MAX-ACCESS		read-write
		STATUS			current
		DESCRIPTION
				"TYPE: - Button
				 PAGE: - User Mem
					save 4  cmdID= 1612  value= 1  "
		::= { iqmux60CmdEntry 1612 }


	iqmux60UserMemMemory4Recall4 OBJECT-TYPE
		SYNTAX		INTEGER { noAction(0),recall_4(1) }
		MAX-ACCESS		read-write
		STATUS			current
		DESCRIPTION
				"TYPE: - Button
				 PAGE: - User Mem
					recall 4  cmdID= 1613  value= 1  "
		::= { iqmux60CmdEntry 1613 }


	iqmux60UserMemMemory4Clear4 OBJECT-TYPE
		SYNTAX		INTEGER { noAction(0),clear_4(1) }
		MAX-ACCESS		read-write
		STATUS			current
		DESCRIPTION
				"TYPE: - Button
				 PAGE: - User Mem
					clear 4  cmdID= 1614  value= 1  "
		::= { iqmux60CmdEntry 1614 }


	iqmux60UserMemMemory4Name4 OBJECT-TYPE
		SYNTAX		RollCallString
		MAX-ACCESS		read-write
		STATUS			current
		DESCRIPTION
				"TYPE: - Editstring
				 PAGE: - User Mem
					Name 4  cmdID= 1615  "
		::= { iqmux60CmdEntry 1615 }


	iqmux60UserMemMemory5Save5 OBJECT-TYPE
		SYNTAX		INTEGER { noAction(0),save_5(1) }
		MAX-ACCESS		read-write
		STATUS			current
		DESCRIPTION
				"TYPE: - Button
				 PAGE: - User Mem
					save 5  cmdID= 1616  value= 1  "
		::= { iqmux60CmdEntry 1616 }


	iqmux60UserMemMemory5Recall5 OBJECT-TYPE
		SYNTAX		INTEGER { noAction(0),recall_5(1) }
		MAX-ACCESS		read-write
		STATUS			current
		DESCRIPTION
				"TYPE: - Button
				 PAGE: - User Mem
					recall 5  cmdID= 1617  value= 1  "
		::= { iqmux60CmdEntry 1617 }


	iqmux60UserMemMemory5Clear5 OBJECT-TYPE
		SYNTAX		INTEGER { noAction(0),clear_5(1) }
		MAX-ACCESS		read-write
		STATUS			current
		DESCRIPTION
				"TYPE: - Button
				 PAGE: - User Mem
					clear 5  cmdID= 1618  value= 1  "
		::= { iqmux60CmdEntry 1618 }


	iqmux60UserMemMemory5Name5 OBJECT-TYPE
		SYNTAX		RollCallString
		MAX-ACCESS		read-write
		STATUS			current
		DESCRIPTION
				"TYPE: - Editstring
				 PAGE: - User Mem
					Name 5  cmdID= 1619  "
		::= { iqmux60CmdEntry 1619 }


	iqmux60UserMemMemory6Save6 OBJECT-TYPE
		SYNTAX		INTEGER { noAction(0),save_6(1) }
		MAX-ACCESS		read-write
		STATUS			current
		DESCRIPTION
				"TYPE: - Button
				 PAGE: - User Mem
					save 6  cmdID= 1620  value= 1  "
		::= { iqmux60CmdEntry 1620 }


	iqmux60UserMemMemory6Recall6 OBJECT-TYPE
		SYNTAX		INTEGER { noAction(0),recall_6(1) }
		MAX-ACCESS		read-write
		STATUS			current
		DESCRIPTION
				"TYPE: - Button
				 PAGE: - User Mem
					recall 6  cmdID= 1621  value= 1  "
		::= { iqmux60CmdEntry 1621 }


	iqmux60UserMemMemory6Clear6 OBJECT-TYPE
		SYNTAX		INTEGER { noAction(0),clear_6(1) }
		MAX-ACCESS		read-write
		STATUS			current
		DESCRIPTION
				"TYPE: - Button
				 PAGE: - User Mem
					clear 6  cmdID= 1622  value= 1  "
		::= { iqmux60CmdEntry 1622 }


	iqmux60UserMemMemory6Name6 OBJECT-TYPE
		SYNTAX		RollCallString
		MAX-ACCESS		read-write
		STATUS			current
		DESCRIPTION
				"TYPE: - Editstring
				 PAGE: - User Mem
					Name 6  cmdID= 1623  "
		::= { iqmux60CmdEntry 1623 }


	iqmux60UserMemMemory7Save7 OBJECT-TYPE
		SYNTAX		INTEGER { noAction(0),save_7(1) }
		MAX-ACCESS		read-write
		STATUS			current
		DESCRIPTION
				"TYPE: - Button
				 PAGE: - User Mem
					save 7  cmdID= 1624  value= 1  "
		::= { iqmux60CmdEntry 1624 }


	iqmux60UserMemMemory7Recall7 OBJECT-TYPE
		SYNTAX		INTEGER { noAction(0),recall_7(1) }
		MAX-ACCESS		read-write
		STATUS			current
		DESCRIPTION
				"TYPE: - Button
				 PAGE: - User Mem
					recall 7  cmdID= 1625  value= 1  "
		::= { iqmux60CmdEntry 1625 }


	iqmux60UserMemMemory7Clear7 OBJECT-TYPE
		SYNTAX		INTEGER { noAction(0),clear_7(1) }
		MAX-ACCESS		read-write
		STATUS			current
		DESCRIPTION
				"TYPE: - Button
				 PAGE: - User Mem
					clear 7  cmdID= 1626  value= 1  "
		::= { iqmux60CmdEntry 1626 }


	iqmux60UserMemMemory7Name7 OBJECT-TYPE
		SYNTAX		RollCallString
		MAX-ACCESS		read-write
		STATUS			current
		DESCRIPTION
				"TYPE: - Editstring
				 PAGE: - User Mem
					Name 7  cmdID= 1627  "
		::= { iqmux60CmdEntry 1627 }


	iqmux60UserMemMemory8Save8 OBJECT-TYPE
		SYNTAX		INTEGER { noAction(0),save_8(1) }
		MAX-ACCESS		read-write
		STATUS			current
		DESCRIPTION
				"TYPE: - Button
				 PAGE: - User Mem
					save 8  cmdID= 1628  value= 1  "
		::= { iqmux60CmdEntry 1628 }


	iqmux60UserMemMemory8Recall8 OBJECT-TYPE
		SYNTAX		INTEGER { noAction(0),recall_8(1) }
		MAX-ACCESS		read-write
		STATUS			current
		DESCRIPTION
				"TYPE: - Button
				 PAGE: - User Mem
					recall 8  cmdID= 1629  value= 1  "
		::= { iqmux60CmdEntry 1629 }


	iqmux60UserMemMemory8Clear8 OBJECT-TYPE
		SYNTAX		INTEGER { noAction(0),clear_8(1) }
		MAX-ACCESS		read-write
		STATUS			current
		DESCRIPTION
				"TYPE: - Button
				 PAGE: - User Mem
					clear 8  cmdID= 1630  value= 1  "
		::= { iqmux60CmdEntry 1630 }


	iqmux60UserMemMemory8Name8 OBJECT-TYPE
		SYNTAX		RollCallString
		MAX-ACCESS		read-write
		STATUS			current
		DESCRIPTION
				"TYPE: - Editstring
				 PAGE: - User Mem
					Name 8  cmdID= 1631  "
		::= { iqmux60CmdEntry 1631 }


	iqmux60SetupPatternAnimatedPattern OBJECT-TYPE
		SYNTAX		INTEGER { disable(0), enable(1) }
		MAX-ACCESS		read-write
		STATUS			current
		DESCRIPTION
				"TYPE: - Checkbox
				 PAGE: - Setup- Pattern
					Animated Pattern  cmdID= 2940 "
		::= { iqmux60CmdEntry 2940 }


	iqmux60SetupPatternEnablePattern OBJECT-TYPE
		SYNTAX		INTEGER { disable(0), enable(1) }
		MAX-ACCESS		read-write
		STATUS			current
		DESCRIPTION
				"TYPE: - Checkbox
				 PAGE: - Setup- Pattern
					Enable Pattern  cmdID= 1035 "
		::= { iqmux60CmdEntry 1035 }


	iqmux60SetupPattern OBJECT-TYPE
		SYNTAX		INTEGER {
							val_Black(0),
							val_EBU_Colour_Bars(1),
							val_Val_100_Colour_Bars(2),
							val_Ramp(3),
							val_Multiburst(4),
							val_Pulse_Bar(5)
							}
		MAX-ACCESS		read-write
		STATUS			current
		DESCRIPTION
				"TYPE: - Button
				 PAGE: - Setup- Pattern
					black  cmdID= 1036  value= 0
					eBU Colour Bars  cmdID= 1036  value= 1
					100% Colour Bars  cmdID= 1036  value= 2
					ramp  cmdID= 1036  value= 3
					multiburst  cmdID= 1036  value= 4
					pulse & Bar  cmdID= 1036  value= 5  "
		::= { iqmux60CmdEntry 1036 }


	iqmux60SetupCaptionEditCaption OBJECT-TYPE
		SYNTAX		RollCallString
		MAX-ACCESS		read-write
		STATUS			current
		DESCRIPTION
				"TYPE: - Editstring
				 PAGE: - Setup- Caption
					Edit Caption  cmdID= 1041  "
		::= { iqmux60CmdEntry 1041 }


	iqmux60SetupCaption OBJECT-TYPE
		SYNTAX		INTEGER {
							val_Caption_Off(0),
							val_Caption_On(1)
							}
		MAX-ACCESS		read-write
		STATUS			current
		DESCRIPTION
				"TYPE: - Button
				 PAGE: - Setup- Caption
					caption Off  cmdID= 1037  value= 0
					caption On  cmdID= 1037  value= 1  "
		::= { iqmux60CmdEntry 1037 }


	iqmux60BlankingVIPass525BlankAll OBJECT-TYPE
		SYNTAX		INTEGER { noAction(0),blank_All(1) }
		MAX-ACCESS		read-write
		STATUS			current
		DESCRIPTION
				"TYPE: - Button
				 PAGE: - Setup- Blanking
					blank All  cmdID= 1298  value= 1  "
		::= { iqmux60CmdEntry 1298 }


	iqmux60BlankingVIPass525PassAll OBJECT-TYPE
		SYNTAX		INTEGER { noAction(0),pass_All(1) }
		MAX-ACCESS		read-write
		STATUS			current
		DESCRIPTION
				"TYPE: - Button
				 PAGE: - Setup- Blanking
					pass All  cmdID= 1297  value= 1  "
		::= { iqmux60CmdEntry 1297 }


	iqmux60BlankingVIPass525Line11 OBJECT-TYPE
		SYNTAX		INTEGER { disable(0), enable(1) }
		MAX-ACCESS		read-write
		STATUS			current
		DESCRIPTION
				"TYPE: - Checkbox
				 PAGE: - Setup- Blanking
					Line 11  cmdID= 1211 "
		::= { iqmux60CmdEntry 1211 }


	iqmux60BlankingVIPass525Line274 OBJECT-TYPE
		SYNTAX		INTEGER { disable(0), enable(1) }
		MAX-ACCESS		read-write
		STATUS			current
		DESCRIPTION
				"TYPE: - Checkbox
				 PAGE: - Setup- Blanking
					Line 274  cmdID= 1231 "
		::= { iqmux60CmdEntry 1231 }


	iqmux60BlankingVIPass525Line12 OBJECT-TYPE
		SYNTAX		INTEGER { disable(0), enable(1) }
		MAX-ACCESS		read-write
		STATUS			current
		DESCRIPTION
				"TYPE: - Checkbox
				 PAGE: - Setup- Blanking
					Line 12  cmdID= 1212 "
		::= { iqmux60CmdEntry 1212 }


	iqmux60BlankingVIPass525Line275 OBJECT-TYPE
		SYNTAX		INTEGER { disable(0), enable(1) }
		MAX-ACCESS		read-write
		STATUS			current
		DESCRIPTION
				"TYPE: - Checkbox
				 PAGE: - Setup- Blanking
					Line 275  cmdID= 1232 "
		::= { iqmux60CmdEntry 1232 }


	iqmux60BlankingVIPass525Line13 OBJECT-TYPE
		SYNTAX		INTEGER { disable(0), enable(1) }
		MAX-ACCESS		read-write
		STATUS			current
		DESCRIPTION
				"TYPE: - Checkbox
				 PAGE: - Setup- Blanking
					Line 13  cmdID= 1213 "
		::= { iqmux60CmdEntry 1213 }


	iqmux60BlankingVIPass525Line276 OBJECT-TYPE
		SYNTAX		INTEGER { disable(0), enable(1) }
		MAX-ACCESS		read-write
		STATUS			current
		DESCRIPTION
				"TYPE: - Checkbox
				 PAGE: - Setup- Blanking
					Line 276  cmdID= 1233 "
		::= { iqmux60CmdEntry 1233 }


	iqmux60BlankingVIPass525Line14 OBJECT-TYPE
		SYNTAX		INTEGER { disable(0), enable(1) }
		MAX-ACCESS		read-write
		STATUS			current
		DESCRIPTION
				"TYPE: - Checkbox
				 PAGE: - Setup- Blanking
					Line 14  cmdID= 1214 "
		::= { iqmux60CmdEntry 1214 }


	iqmux60BlankingVIPass525Line277 OBJECT-TYPE
		SYNTAX		INTEGER { disable(0), enable(1) }
		MAX-ACCESS		read-write
		STATUS			current
		DESCRIPTION
				"TYPE: - Checkbox
				 PAGE: - Setup- Blanking
					Line 277  cmdID= 1234 "
		::= { iqmux60CmdEntry 1234 }


	iqmux60BlankingVIPass525Line15 OBJECT-TYPE
		SYNTAX		INTEGER { disable(0), enable(1) }
		MAX-ACCESS		read-write
		STATUS			current
		DESCRIPTION
				"TYPE: - Checkbox
				 PAGE: - Setup- Blanking
					Line 15  cmdID= 1215 "
		::= { iqmux60CmdEntry 1215 }


	iqmux60BlankingVIPass525Line278 OBJECT-TYPE
		SYNTAX		INTEGER { disable(0), enable(1) }
		MAX-ACCESS		read-write
		STATUS			current
		DESCRIPTION
				"TYPE: - Checkbox
				 PAGE: - Setup- Blanking
					Line 278  cmdID= 1235 "
		::= { iqmux60CmdEntry 1235 }


	iqmux60BlankingVIPass525Line16 OBJECT-TYPE
		SYNTAX		INTEGER { disable(0), enable(1) }
		MAX-ACCESS		read-write
		STATUS			current
		DESCRIPTION
				"TYPE: - Checkbox
				 PAGE: - Setup- Blanking
					Line 16  cmdID= 1216 "
		::= { iqmux60CmdEntry 1216 }


	iqmux60BlankingVIPass525Line279 OBJECT-TYPE
		SYNTAX		INTEGER { disable(0), enable(1) }
		MAX-ACCESS		read-write
		STATUS			current
		DESCRIPTION
				"TYPE: - Checkbox
				 PAGE: - Setup- Blanking
					Line 279  cmdID= 1236 "
		::= { iqmux60CmdEntry 1236 }


	iqmux60BlankingVIPass525Line17 OBJECT-TYPE
		SYNTAX		INTEGER { disable(0), enable(1) }
		MAX-ACCESS		read-write
		STATUS			current
		DESCRIPTION
				"TYPE: - Checkbox
				 PAGE: - Setup- Blanking
					Line 17  cmdID= 1217 "
		::= { iqmux60CmdEntry 1217 }


	iqmux60BlankingVIPass525Line280 OBJECT-TYPE
		SYNTAX		INTEGER { disable(0), enable(1) }
		MAX-ACCESS		read-write
		STATUS			current
		DESCRIPTION
				"TYPE: - Checkbox
				 PAGE: - Setup- Blanking
					Line 280  cmdID= 1237 "
		::= { iqmux60CmdEntry 1237 }


	iqmux60BlankingVIPass525Line18 OBJECT-TYPE
		SYNTAX		INTEGER { disable(0), enable(1) }
		MAX-ACCESS		read-write
		STATUS			current
		DESCRIPTION
				"TYPE: - Checkbox
				 PAGE: - Setup- Blanking
					Line 18  cmdID= 1218 "
		::= { iqmux60CmdEntry 1218 }


	iqmux60BlankingVIPass525Line281 OBJECT-TYPE
		SYNTAX		INTEGER { disable(0), enable(1) }
		MAX-ACCESS		read-write
		STATUS			current
		DESCRIPTION
				"TYPE: - Checkbox
				 PAGE: - Setup- Blanking
					Line 281  cmdID= 1238 "
		::= { iqmux60CmdEntry 1238 }


	iqmux60BlankingVIPass525Line19 OBJECT-TYPE
		SYNTAX		INTEGER { disable(0), enable(1) }
		MAX-ACCESS		read-write
		STATUS			current
		DESCRIPTION
				"TYPE: - Checkbox
				 PAGE: - Setup- Blanking
					Line 19  cmdID= 1219 "
		::= { iqmux60CmdEntry 1219 }


	iqmux60BlankingVIPass525Line282 OBJECT-TYPE
		SYNTAX		INTEGER { disable(0), enable(1) }
		MAX-ACCESS		read-write
		STATUS			current
		DESCRIPTION
				"TYPE: - Checkbox
				 PAGE: - Setup- Blanking
					Line 282  cmdID= 1239 "
		::= { iqmux60CmdEntry 1239 }


	iqmux60BlankingVIPass525Line20 OBJECT-TYPE
		SYNTAX		INTEGER { disable(0), enable(1) }
		MAX-ACCESS		read-write
		STATUS			current
		DESCRIPTION
				"TYPE: - Checkbox
				 PAGE: - Setup- Blanking
					Line 20  cmdID= 1220 "
		::= { iqmux60CmdEntry 1220 }


	iqmux60BlankingVIPass525Line283 OBJECT-TYPE
		SYNTAX		INTEGER { disable(0), enable(1) }
		MAX-ACCESS		read-write
		STATUS			current
		DESCRIPTION
				"TYPE: - Checkbox
				 PAGE: - Setup- Blanking
					Line 283  cmdID= 1240 "
		::= { iqmux60CmdEntry 1240 }


	iqmux60BlankingVIPass525Line21 OBJECT-TYPE
		SYNTAX		INTEGER { disable(0), enable(1) }
		MAX-ACCESS		read-write
		STATUS			current
		DESCRIPTION
				"TYPE: - Checkbox
				 PAGE: - Setup- Blanking
					Line 21  cmdID= 1221 "
		::= { iqmux60CmdEntry 1221 }


	iqmux60BlankingVIPass625BlankAll OBJECT-TYPE
		SYNTAX		INTEGER { noAction(0),blank_All(1) }
		MAX-ACCESS		read-write
		STATUS			current
		DESCRIPTION
				"TYPE: - Button
				 PAGE: - Setup- Blanking
					blank All  cmdID= 1296  value= 1  "
		::= { iqmux60CmdEntry 1296 }


	iqmux60BlankingVIPass625PassAll OBJECT-TYPE
		SYNTAX		INTEGER { noAction(0),pass_All(1) }
		MAX-ACCESS		read-write
		STATUS			current
		DESCRIPTION
				"TYPE: - Button
				 PAGE: - Setup- Blanking
					pass All  cmdID= 1295  value= 1  "
		::= { iqmux60CmdEntry 1295 }


	iqmux60BlankingVIPass625Line7 OBJECT-TYPE
		SYNTAX		INTEGER { disable(0), enable(1) }
		MAX-ACCESS		read-write
		STATUS			current
		DESCRIPTION
				"TYPE: - Checkbox
				 PAGE: - Setup- Blanking
					Line 7  cmdID= 1251 "
		::= { iqmux60CmdEntry 1251 }


	iqmux60BlankingVIPass625Line320 OBJECT-TYPE
		SYNTAX		INTEGER { disable(0), enable(1) }
		MAX-ACCESS		read-write
		STATUS			current
		DESCRIPTION
				"TYPE: - Checkbox
				 PAGE: - Setup- Blanking
					Line 320  cmdID= 1272 "
		::= { iqmux60CmdEntry 1272 }


	iqmux60BlankingVIPass625Line8 OBJECT-TYPE
		SYNTAX		INTEGER { disable(0), enable(1) }
		MAX-ACCESS		read-write
		STATUS			current
		DESCRIPTION
				"TYPE: - Checkbox
				 PAGE: - Setup- Blanking
					Line 8  cmdID= 1252 "
		::= { iqmux60CmdEntry 1252 }


	iqmux60BlankingVIPass625Line321 OBJECT-TYPE
		SYNTAX		INTEGER { disable(0), enable(1) }
		MAX-ACCESS		read-write
		STATUS			current
		DESCRIPTION
				"TYPE: - Checkbox
				 PAGE: - Setup- Blanking
					Line 321  cmdID= 1273 "
		::= { iqmux60CmdEntry 1273 }


	iqmux60BlankingVIPass625Line9 OBJECT-TYPE
		SYNTAX		INTEGER { disable(0), enable(1) }
		MAX-ACCESS		read-write
		STATUS			current
		DESCRIPTION
				"TYPE: - Checkbox
				 PAGE: - Setup- Blanking
					Line 9  cmdID= 1253 "
		::= { iqmux60CmdEntry 1253 }


	iqmux60BlankingVIPass625Line322 OBJECT-TYPE
		SYNTAX		INTEGER { disable(0), enable(1) }
		MAX-ACCESS		read-write
		STATUS			current
		DESCRIPTION
				"TYPE: - Checkbox
				 PAGE: - Setup- Blanking
					Line 322  cmdID= 1274 "
		::= { iqmux60CmdEntry 1274 }


	iqmux60BlankingVIPass625Line10 OBJECT-TYPE
		SYNTAX		INTEGER { disable(0), enable(1) }
		MAX-ACCESS		read-write
		STATUS			current
		DESCRIPTION
				"TYPE: - Checkbox
				 PAGE: - Setup- Blanking
					Line 10  cmdID= 1254 "
		::= { iqmux60CmdEntry 1254 }


	iqmux60BlankingVIPass625Line323 OBJECT-TYPE
		SYNTAX		INTEGER { disable(0), enable(1) }
		MAX-ACCESS		read-write
		STATUS			current
		DESCRIPTION
				"TYPE: - Checkbox
				 PAGE: - Setup- Blanking
					Line 323  cmdID= 1275 "
		::= { iqmux60CmdEntry 1275 }


	iqmux60BlankingVIPass625Line11 OBJECT-TYPE
		SYNTAX		INTEGER { disable(0), enable(1) }
		MAX-ACCESS		read-write
		STATUS			current
		DESCRIPTION
				"TYPE: - Checkbox
				 PAGE: - Setup- Blanking
					Line 11  cmdID= 1255 "
		::= { iqmux60CmdEntry 1255 }


	iqmux60BlankingVIPass625Line324 OBJECT-TYPE
		SYNTAX		INTEGER { disable(0), enable(1) }
		MAX-ACCESS		read-write
		STATUS			current
		DESCRIPTION
				"TYPE: - Checkbox
				 PAGE: - Setup- Blanking
					Line 324  cmdID= 1276 "
		::= { iqmux60CmdEntry 1276 }


	iqmux60BlankingVIPass625Line12 OBJECT-TYPE
		SYNTAX		INTEGER { disable(0), enable(1) }
		MAX-ACCESS		read-write
		STATUS			current
		DESCRIPTION
				"TYPE: - Checkbox
				 PAGE: - Setup- Blanking
					Line 12  cmdID= 1256 "
		::= { iqmux60CmdEntry 1256 }


	iqmux60BlankingVIPass625Line325 OBJECT-TYPE
		SYNTAX		INTEGER { disable(0), enable(1) }
		MAX-ACCESS		read-write
		STATUS			current
		DESCRIPTION
				"TYPE: - Checkbox
				 PAGE: - Setup- Blanking
					Line 325  cmdID= 1277 "
		::= { iqmux60CmdEntry 1277 }


	iqmux60BlankingVIPass625Line13 OBJECT-TYPE
		SYNTAX		INTEGER { disable(0), enable(1) }
		MAX-ACCESS		read-write
		STATUS			current
		DESCRIPTION
				"TYPE: - Checkbox
				 PAGE: - Setup- Blanking
					Line 13  cmdID= 1257 "
		::= { iqmux60CmdEntry 1257 }


	iqmux60BlankingVIPass625Line326 OBJECT-TYPE
		SYNTAX		INTEGER { disable(0), enable(1) }
		MAX-ACCESS		read-write
		STATUS			current
		DESCRIPTION
				"TYPE: - Checkbox
				 PAGE: - Setup- Blanking
					Line 326  cmdID= 1278 "
		::= { iqmux60CmdEntry 1278 }


	iqmux60BlankingVIPass625Line14 OBJECT-TYPE
		SYNTAX		INTEGER { disable(0), enable(1) }
		MAX-ACCESS		read-write
		STATUS			current
		DESCRIPTION
				"TYPE: - Checkbox
				 PAGE: - Setup- Blanking
					Line 14  cmdID= 1258 "
		::= { iqmux60CmdEntry 1258 }


	iqmux60BlankingVIPass625Line327 OBJECT-TYPE
		SYNTAX		INTEGER { disable(0), enable(1) }
		MAX-ACCESS		read-write
		STATUS			current
		DESCRIPTION
				"TYPE: - Checkbox
				 PAGE: - Setup- Blanking
					Line 327  cmdID= 1279 "
		::= { iqmux60CmdEntry 1279 }


	iqmux60BlankingVIPass625Line15 OBJECT-TYPE
		SYNTAX		INTEGER { disable(0), enable(1) }
		MAX-ACCESS		read-write
		STATUS			current
		DESCRIPTION
				"TYPE: - Checkbox
				 PAGE: - Setup- Blanking
					Line 15  cmdID= 1259 "
		::= { iqmux60CmdEntry 1259 }


	iqmux60BlankingVIPass625Line328 OBJECT-TYPE
		SYNTAX		INTEGER { disable(0), enable(1) }
		MAX-ACCESS		read-write
		STATUS			current
		DESCRIPTION
				"TYPE: - Checkbox
				 PAGE: - Setup- Blanking
					Line 328  cmdID= 1280 "
		::= { iqmux60CmdEntry 1280 }


	iqmux60BlankingVIPass625Line16 OBJECT-TYPE
		SYNTAX		INTEGER { disable(0), enable(1) }
		MAX-ACCESS		read-write
		STATUS			current
		DESCRIPTION
				"TYPE: - Checkbox
				 PAGE: - Setup- Blanking
					Line 16  cmdID= 1260 "
		::= { iqmux60CmdEntry 1260 }


	iqmux60BlankingVIPass625Line329 OBJECT-TYPE
		SYNTAX		INTEGER { disable(0), enable(1) }
		MAX-ACCESS		read-write
		STATUS			current
		DESCRIPTION
				"TYPE: - Checkbox
				 PAGE: - Setup- Blanking
					Line 329  cmdID= 1281 "
		::= { iqmux60CmdEntry 1281 }


	iqmux60BlankingVIPass625Line17 OBJECT-TYPE
		SYNTAX		INTEGER { disable(0), enable(1) }
		MAX-ACCESS		read-write
		STATUS			current
		DESCRIPTION
				"TYPE: - Checkbox
				 PAGE: - Setup- Blanking
					Line 17  cmdID= 1261 "
		::= { iqmux60CmdEntry 1261 }


	iqmux60BlankingVIPass625Line330 OBJECT-TYPE
		SYNTAX		INTEGER { disable(0), enable(1) }
		MAX-ACCESS		read-write
		STATUS			current
		DESCRIPTION
				"TYPE: - Checkbox
				 PAGE: - Setup- Blanking
					Line 330  cmdID= 1282 "
		::= { iqmux60CmdEntry 1282 }


	iqmux60BlankingVIPass625Line18 OBJECT-TYPE
		SYNTAX		INTEGER { disable(0), enable(1) }
		MAX-ACCESS		read-write
		STATUS			current
		DESCRIPTION
				"TYPE: - Checkbox
				 PAGE: - Setup- Blanking
					Line 18  cmdID= 1262 "
		::= { iqmux60CmdEntry 1262 }


	iqmux60BlankingVIPass625Line331 OBJECT-TYPE
		SYNTAX		INTEGER { disable(0), enable(1) }
		MAX-ACCESS		read-write
		STATUS			current
		DESCRIPTION
				"TYPE: - Checkbox
				 PAGE: - Setup- Blanking
					Line 331  cmdID= 1283 "
		::= { iqmux60CmdEntry 1283 }


	iqmux60BlankingVIPass625Line19 OBJECT-TYPE
		SYNTAX		INTEGER { disable(0), enable(1) }
		MAX-ACCESS		read-write
		STATUS			current
		DESCRIPTION
				"TYPE: - Checkbox
				 PAGE: - Setup- Blanking
					Line 19  cmdID= 1263 "
		::= { iqmux60CmdEntry 1263 }


	iqmux60BlankingVIPass625Line332 OBJECT-TYPE
		SYNTAX		INTEGER { disable(0), enable(1) }
		MAX-ACCESS		read-write
		STATUS			current
		DESCRIPTION
				"TYPE: - Checkbox
				 PAGE: - Setup- Blanking
					Line 332  cmdID= 1284 "
		::= { iqmux60CmdEntry 1284 }


	iqmux60BlankingVIPass625Line20 OBJECT-TYPE
		SYNTAX		INTEGER { disable(0), enable(1) }
		MAX-ACCESS		read-write
		STATUS			current
		DESCRIPTION
				"TYPE: - Checkbox
				 PAGE: - Setup- Blanking
					Line 20  cmdID= 1264 "
		::= { iqmux60CmdEntry 1264 }


	iqmux60BlankingVIPass625Line333 OBJECT-TYPE
		SYNTAX		INTEGER { disable(0), enable(1) }
		MAX-ACCESS		read-write
		STATUS			current
		DESCRIPTION
				"TYPE: - Checkbox
				 PAGE: - Setup- Blanking
					Line 333  cmdID= 1285 "
		::= { iqmux60CmdEntry 1285 }


	iqmux60BlankingVIPass625Line21 OBJECT-TYPE
		SYNTAX		INTEGER { disable(0), enable(1) }
		MAX-ACCESS		read-write
		STATUS			current
		DESCRIPTION
				"TYPE: - Checkbox
				 PAGE: - Setup- Blanking
					Line 21  cmdID= 1265 "
		::= { iqmux60CmdEntry 1265 }


	iqmux60BlankingVIPass625Line334 OBJECT-TYPE
		SYNTAX		INTEGER { disable(0), enable(1) }
		MAX-ACCESS		read-write
		STATUS			current
		DESCRIPTION
				"TYPE: - Checkbox
				 PAGE: - Setup- Blanking
					Line 334  cmdID= 1286 "
		::= { iqmux60CmdEntry 1286 }


	iqmux60BlankingVIPass625Line22 OBJECT-TYPE
		SYNTAX		INTEGER { disable(0), enable(1) }
		MAX-ACCESS		read-write
		STATUS			current
		DESCRIPTION
				"TYPE: - Checkbox
				 PAGE: - Setup- Blanking
					Line 22  cmdID= 1266 "
		::= { iqmux60CmdEntry 1266 }


	iqmux60BlankingVIPass625Line335 OBJECT-TYPE
		SYNTAX		INTEGER { disable(0), enable(1) }
		MAX-ACCESS		read-write
		STATUS			current
		DESCRIPTION
				"TYPE: - Checkbox
				 PAGE: - Setup- Blanking
					Line 335  cmdID= 1287 "
		::= { iqmux60CmdEntry 1287 }


	iqmux60BlankingVIPass625Line23 OBJECT-TYPE
		SYNTAX		INTEGER { disable(0), enable(1) }
		MAX-ACCESS		read-write
		STATUS			current
		DESCRIPTION
				"TYPE: - Checkbox
				 PAGE: - Setup- Blanking
					Line 23  cmdID= 1267 "
		::= { iqmux60CmdEntry 1267 }


	iqmux60SetupBlankingHancBlank OBJECT-TYPE
		SYNTAX		INTEGER { disable(0), enable(1) }
		MAX-ACCESS		read-write
		STATUS			current
		DESCRIPTION
				"TYPE: - Checkbox
				 PAGE: - Setup- Blanking
					Hanc Blank  cmdID= 2971 "
		::= { iqmux60CmdEntry 2971 }


	iqmux60SetupAudioToneIdentEnable OBJECT-TYPE
		SYNTAX		INTEGER { disable(0), enable(1) }
		MAX-ACCESS		read-write
		STATUS			current
		DESCRIPTION
				"TYPE: - Checkbox
				 PAGE: - Setup- Audio Tone
					Ident Enable  cmdID= 2489 "
		::= { iqmux60CmdEntry 2489 }


	iqmux60SetupAudioToneFrequency OBJECT-TYPE
		SYNTAX		INTEGER
		MAX-ACCESS		read-write
		STATUS			current
		DESCRIPTION
				"TYPE: - Number
				 PAGE: - Setup- Audio Tone
					Frequency  cmdID= 2487  min= 100  max= 15000  step= 100  format= %.1f Hz  div_scale= 1
					Min = 100.0 Hz  Max = 15000.0 Hz  Step = 100.0 Hz "
		::= { iqmux60CmdEntry 2487 }


	iqmux60SetupAudioToneFrequencyR OBJECT-TYPE
		SYNTAX		INTEGER
		MAX-ACCESS		read-write
		STATUS			current
		DESCRIPTION
				"TYPE: - Number
				 PAGE: - Setup- Audio Tone
					Frequency R  cmdID= 2488  min= 100  max= 15000  step= 100  format= %.1f Hz  div_scale= 1
					Min = 100.0 Hz  Max = 15000.0 Hz  Step = 100.0 Hz "
		::= { iqmux60CmdEntry 2488 }


	iqmux60SetupAudioToneHeadRoom OBJECT-TYPE
		SYNTAX		INTEGER
		MAX-ACCESS		read-write
		STATUS			current
		DESCRIPTION
				"TYPE: - Number
				 PAGE: - Setup- Audio Tone
					HeadRoom  cmdID= 3055  min= 4  max= 24  step= 1  format= %.1f dB  div_scale= 1
					Min = 4.0 dB  Max = 24.0 dB  Step = 1.0 dB "
		::= { iqmux60CmdEntry 3055 }


	iqmux60SetupAudioToneADCLineUp OBJECT-TYPE
		SYNTAX		INTEGER
		MAX-ACCESS		read-write
		STATUS			current
		DESCRIPTION
				"TYPE: - Number
				 PAGE: - Setup- Audio Tone
					ADC Line Up  cmdID= 3545  min= -200  max= 200  step= 10  format= %2.0f dBu  div_scale= 10
					Min = -20 dBu  Max = 20 dBu  Step =  1 dBu "
		::= { iqmux60CmdEntry 3545 }


	iqmux60SetupSlewRate OBJECT-TYPE
		SYNTAX		INTEGER {
							val_Instant(0),
							val_Fast(1),
							val_Medium(2),
							val_Slow(3),
							val_Slowest(4)
							}
		MAX-ACCESS		read-write
		STATUS			current
		DESCRIPTION
				"TYPE: - RadiobuttonList
				 PAGE: - Setup
					Slew Rate  cmdID= 2972
					instant  value= 0
					fast  value= 1
					medium  value= 2
					slow  value= 3
					slowest  value= 4  "
		::= { iqmux60CmdEntry 2972 }


	iqmux60SetupChannelStatus OBJECT-TYPE
		SYNTAX		RollCallString
		MAX-ACCESS		read-write
		STATUS			current
		DESCRIPTION
				"TYPE: - Editstring
				 PAGE: - Setup
					Channel Status  cmdID= 3060  "
		::= { iqmux60CmdEntry 3060 }


	iqmux60GPIIOGPIInputDisableInputs OBJECT-TYPE
		SYNTAX		INTEGER { disable(0), enable(1) }
		MAX-ACCESS		read-write
		STATUS			current
		DESCRIPTION
				"TYPE: - Checkbox
				 PAGE: - Setup- GPI I/O
					Disable Inputs  cmdID= 2605 "
		::= { iqmux60CmdEntry 2605 }


	iqmux60GPIIOGPIInputInputTimerEnable OBJECT-TYPE
		SYNTAX		INTEGER { disable(0), enable(1) }
		MAX-ACCESS		read-write
		STATUS			current
		DESCRIPTION
				"TYPE: - Checkbox
				 PAGE: - Setup- GPI I/O
					InputTimer Enable  cmdID= 3053 "
		::= { iqmux60CmdEntry 3053 }


	iqmux60GPIIOGPIInputTimerActiveHigh OBJECT-TYPE
		SYNTAX		INTEGER { disable(0), enable(1) }
		MAX-ACCESS		read-write
		STATUS			current
		DESCRIPTION
				"TYPE: - Checkbox
				 PAGE: - Setup- GPI I/O
					TimerActive High  cmdID= 3054 "
		::= { iqmux60CmdEntry 3054 }


	iqmux60GPIIOGPIInputInputSelection OBJECT-TYPE
		SYNTAX		INTEGER
		MAX-ACCESS		read-write
		STATUS			current
		DESCRIPTION
				"TYPE: - Number
				 PAGE: - Setup- GPI I/O
					Input Selection  cmdID= 2011  min= -1  max= 12  step= 1  format= %.0f  div_scale= 1
					Min = -1  Max = 12  Step = 1 "
		::= { iqmux60CmdEntry 2011 }


	iqmux60GPIIOGPIInputGPIInStatus OBJECT-TYPE
		SYNTAX		RollCallString
		MAX-ACCESS		read-only
		STATUS			current
		DESCRIPTION
				"TYPE: - Display
				 PAGE: - Setup- GPI I/O
					GPI In Status  cmdID= 2048  format=   "
		::= { iqmux60CmdEntry 2048 }


	iqmux60GPIIOGPIOutputOutActiveHigh OBJECT-TYPE
		SYNTAX		INTEGER { disable(0), enable(1) }
		MAX-ACCESS		read-write
		STATUS			current
		DESCRIPTION
				"TYPE: - Checkbox
				 PAGE: - Setup- GPI I/O
					Out Active High  cmdID= 3540 "
		::= { iqmux60CmdEntry 3540 }


	iqmux60GPIIOGPIOutputOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2013
					input Present  value= 0
					standard 625  value= 1
					video Delay  value= 2
					unused  value= 3  "
		::= { iqmux60CmdEntry 2013 }


	iqmux60GPIIOGPIOutputGPIOutStatus OBJECT-TYPE
		SYNTAX		RollCallString
		MAX-ACCESS		read-only
		STATUS			current
		DESCRIPTION
				"TYPE: - Display
				 PAGE: - Setup- GPI I/O
					GPI Out Status  cmdID= 2049  format=   "
		::= { iqmux60CmdEntry 2049 }


	iqmux60GPIIOGPIInputOutputGPIO1 OBJECT-TYPE
		SYNTAX		INTEGER { disable(0), enable(1) }
		MAX-ACCESS		read-write
		STATUS			current
		DESCRIPTION
				"TYPE: - Checkbox
				 PAGE: - Setup- GPI I/O
					GPI/O 1  cmdID= 2014 "
		::= { iqmux60CmdEntry 2014 }


	iqmux60SetupGPIIOInputSelection OBJECT-TYPE
		SYNTAX		INTEGER
		MAX-ACCESS		read-write
		STATUS			current
		DESCRIPTION
				"TYPE: - Number
				 PAGE: - Setup- GPI I/O
					Input Selection  cmdID= 2875  min= -1  max= 12  step= 1  format= %.0f  div_scale= 1
					Min = -1  Max = 12  Step = 1 "
		::= { iqmux60CmdEntry 2875 }


	iqmux60SetupGPIIOOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2877
					input Present  value= 0
					standard 625  value= 1
					video Delay  value= 2
					unused  value= 3  "
		::= { iqmux60CmdEntry 2877 }


	iqmux60SetupRollTrackRollTrackIndex OBJECT-TYPE
		SYNTAX		INTEGER
		MAX-ACCESS		read-write
		STATUS			current
		DESCRIPTION
				"TYPE: - Number
				 PAGE: - Setup- RollTrack
					RollTrack Index  cmdID= 1495  min= 0  max= 49  step= 1  format= %.0f  div_scale= 1
					Min = 0  Max = 49  Step = 1 "
		::= { iqmux60CmdEntry 1495 }


	iqmux60SetupRollTrackRollTrackSource OBJECT-TYPE
		SYNTAX		INTEGER
		MAX-ACCESS		read-write
		STATUS			current
		DESCRIPTION
				"TYPE: - Number
				 PAGE: - Setup- RollTrack
					RollTrack Source  cmdID= 1496  min= -1  max= 36  step= 1  format= %.0f  div_scale= 1
					Min = -1  Max = 36  Step = 1 "
		::= { iqmux60CmdEntry 1496 }


	iqmux60SetupRollTrackRollTrackDisable OBJECT-TYPE
		SYNTAX		INTEGER { disable(0), enable(1) }
		MAX-ACCESS		read-write
		STATUS			current
		DESCRIPTION
				"TYPE: - Checkbox
				 PAGE: - Setup- RollTrack
					RollTrack Disable  cmdID= 1513 "
		::= { iqmux60CmdEntry 1513 }


	iqmux60SetupRollTrackRollTrackAddress OBJECT-TYPE
		SYNTAX		RollCallString
		MAX-ACCESS		read-write
		STATUS			current
		DESCRIPTION
				"TYPE: - Editstring
				 PAGE: - Setup- RollTrack
					RollTrack Address  cmdID= 1497  "
		::= { iqmux60CmdEntry 1497 }


	iqmux60SetupRollTrackRollTrackCommand OBJECT-TYPE
		SYNTAX		RollCallString
		MAX-ACCESS		read-write
		STATUS			current
		DESCRIPTION
				"TYPE: - Editstring
				 PAGE: - Setup- RollTrack
					RollTrack Command  cmdID= 1498  "
		::= { iqmux60CmdEntry 1498 }


	iqmux60SetupRollTrackRollTrackSending OBJECT-TYPE
		SYNTAX		RollCallString
		MAX-ACCESS		read-only
		STATUS			current
		DESCRIPTION
				"TYPE: - Display
				 PAGE: - Setup- RollTrack
					RollTrack Sending  cmdID= 1514  format=   "
		::= { iqmux60CmdEntry 1514 }


	iqmux60SetupRollTrackRollTrackStatus OBJECT-TYPE
		SYNTAX		RollCallString
		MAX-ACCESS		read-only
		STATUS			current
		DESCRIPTION
				"TYPE: - Display
				 PAGE: - Setup- RollTrack
					RollTrack Status  cmdID= 1511  format=   "
		::= { iqmux60CmdEntry 1511 }


	iqmux60SetupRollTrackRollTrackIndexExt OBJECT-TYPE
		SYNTAX		INTEGER
		MAX-ACCESS		read-write
		STATUS			current
		DESCRIPTION
				"TYPE: - Number
				 PAGE: - Setup- RollTrack
					RollTrack Index  cmdID= 2870  min= 0  max= 49  step= 1  format= %.0f  div_scale= 1
					Min = 0  Max = 49  Step = 1 "
		::= { iqmux60CmdEntry 2870 }


	iqmux60SetupRollTrackRollTrackSourceExt OBJECT-TYPE
		SYNTAX		INTEGER
		MAX-ACCESS		read-write
		STATUS			current
		DESCRIPTION
				"TYPE: - Number
				 PAGE: - Setup- RollTrack
					RollTrack Source  cmdID= 2871  min= -1  max= 36  step= 1  format= %.0f  div_scale= 1
					Min = -1  Max = 36  Step = 1 "
		::= { iqmux60CmdEntry 2871 }


	iqmux60SetupRollTrackRollTrackAddressExt OBJECT-TYPE
		SYNTAX		RollCallString
		MAX-ACCESS		read-write
		STATUS			current
		DESCRIPTION
				"TYPE: - Editstring
				 PAGE: - Setup- RollTrack
					RollTrack Address  cmdID= 2872  "
		::= { iqmux60CmdEntry 2872 }


	iqmux60SetupRollTrackRollTrackCommandExt OBJECT-TYPE
		SYNTAX		RollCallString
		MAX-ACCESS		read-write
		STATUS			current
		DESCRIPTION
				"TYPE: - Editstring
				 PAGE: - Setup- RollTrack
					RollTrack Command  cmdID= 2873  "
		::= { iqmux60CmdEntry 2873 }


	iqmux60SetupLoggingInput OBJECT-TYPE
		SYNTAX		INTEGER { disable(0), enable(1) }
		MAX-ACCESS		read-write
		STATUS			current
		DESCRIPTION
				"TYPE: - Checkbox
				 PAGE: - Setup- Logging
					Input  cmdID= 1060 "
		::= { iqmux60CmdEntry 1060 }


	iqmux60SetupLoggingStd OBJECT-TYPE
		SYNTAX		INTEGER { disable(0), enable(1) }
		MAX-ACCESS		read-write
		STATUS			current
		DESCRIPTION
				"TYPE: - Checkbox
				 PAGE: - Setup- Logging
					Std  cmdID= 1061 "
		::= { iqmux60CmdEntry 1061 }


	iqmux60SetupLoggingInput1 OBJECT-TYPE
		SYNTAX		INTEGER { disable(0), enable(1) }
		MAX-ACCESS		read-write
		STATUS			current
		DESCRIPTION
				"TYPE: - Checkbox
				 PAGE: - Setup- Logging
					Input1  cmdID= 1094 "
		::= { iqmux60CmdEntry 1094 }


	iqmux60SetupLoggingStd1 OBJECT-TYPE
		SYNTAX		INTEGER { disable(0), enable(1) }
		MAX-ACCESS		read-write
		STATUS			current
		DESCRIPTION
				"TYPE: - Checkbox
				 PAGE: - Setup- Logging
					Std1  cmdID= 1097 "
		::= { iqmux60CmdEntry 1097 }


	iqmux60SetupLoggingInput2 OBJECT-TYPE
		SYNTAX		INTEGER { disable(0), enable(1) }
		MAX-ACCESS		read-write
		STATUS			current
		DESCRIPTION
				"TYPE: - Checkbox
				 PAGE: - Setup- Logging
					Input2  cmdID= 1095 "
		::= { iqmux60CmdEntry 1095 }


	iqmux60SetupLoggingStd2 OBJECT-TYPE
		SYNTAX		INTEGER { disable(0), enable(1) }
		MAX-ACCESS		read-write
		STATUS			current
		DESCRIPTION
				"TYPE: - Checkbox
				 PAGE: - Setup- Logging
					Std2  cmdID= 1098 "
		::= { iqmux60CmdEntry 1098 }


	iqmux60SetupLoggingEDH OBJECT-TYPE
		SYNTAX		INTEGER { disable(0), enable(1) }
		MAX-ACCESS		read-write
		STATUS			current
		DESCRIPTION
				"TYPE: - Checkbox
				 PAGE: - Setup- Logging
					EDH  cmdID= 1064 "
		::= { iqmux60CmdEntry 1064 }


	iqmux60SetupLoggingEDHErrors OBJECT-TYPE
		SYNTAX		INTEGER { disable(0), enable(1) }
		MAX-ACCESS		read-write
		STATUS			current
		DESCRIPTION
				"TYPE: - Checkbox
				 PAGE: - Setup- Logging
					EDH Errors  cmdID= 1070 "
		::= { iqmux60CmdEntry 1070 }


	iqmux60SetupLoggingRollTrack OBJECT-TYPE
		SYNTAX		INTEGER { disable(0), enable(1) }
		MAX-ACCESS		read-write
		STATUS			current
		DESCRIPTION
				"TYPE: - Checkbox
				 PAGE: - Setup- Logging
					RollTrack  cmdID= 1106 "
		::= { iqmux60CmdEntry 1106 }


	iqmux60SetupLoggingDeembed1 OBJECT-TYPE
		SYNTAX		INTEGER { disable(0), enable(1) }
		MAX-ACCESS		read-write
		STATUS			current
		DESCRIPTION
				"TYPE: - Checkbox
				 PAGE: - Setup- Logging
					De-embed 1  cmdID= 1120 "
		::= { iqmux60CmdEntry 1120 }


	iqmux60SetupLoggingDeembed2 OBJECT-TYPE
		SYNTAX		INTEGER { disable(0), enable(1) }
		MAX-ACCESS		read-write
		STATUS			current
		DESCRIPTION
				"TYPE: - Checkbox
				 PAGE: - Setup- Logging
					De-embed 2  cmdID= 1121 "
		::= { iqmux60CmdEntry 1121 }


	iqmux60SetupLoggingDeembed3 OBJECT-TYPE
		SYNTAX		INTEGER { disable(0), enable(1) }
		MAX-ACCESS		read-write
		STATUS			current
		DESCRIPTION
				"TYPE: - Checkbox
				 PAGE: - Setup- Logging
					De-embed 3  cmdID= 1122 "
		::= { iqmux60CmdEntry 1122 }


	iqmux60SetupLoggingDeembed4 OBJECT-TYPE
		SYNTAX		INTEGER { disable(0), enable(1) }
		MAX-ACCESS		read-write
		STATUS			current
		DESCRIPTION
				"TYPE: - Checkbox
				 PAGE: - Setup- Logging
					De-embed 4  cmdID= 1123 "
		::= { iqmux60CmdEntry 1123 }


	iqmux60SetupLoggingDeembed5 OBJECT-TYPE
		SYNTAX		INTEGER { disable(0), enable(1) }
		MAX-ACCESS		read-write
		STATUS			current
		DESCRIPTION
				"TYPE: - Checkbox
				 PAGE: - Setup- Logging
					De-embed 5  cmdID= 1124 "
		::= { iqmux60CmdEntry 1124 }


	iqmux60SetupLoggingDeembed6 OBJECT-TYPE
		SYNTAX		INTEGER { disable(0), enable(1) }
		MAX-ACCESS		read-write
		STATUS			current
		DESCRIPTION
				"TYPE: - Checkbox
				 PAGE: - Setup- Logging
					De-embed 6  cmdID= 1125 "
		::= { iqmux60CmdEntry 1125 }


	iqmux60SetupLoggingDeembed7 OBJECT-TYPE
		SYNTAX		INTEGER { disable(0), enable(1) }
		MAX-ACCESS		read-write
		STATUS			current
		DESCRIPTION
				"TYPE: - Checkbox
				 PAGE: - Setup- Logging
					De-embed 7  cmdID= 1126 "
		::= { iqmux60CmdEntry 1126 }


	iqmux60SetupLoggingDeembed8 OBJECT-TYPE
		SYNTAX		INTEGER { disable(0), enable(1) }
		MAX-ACCESS		read-write
		STATUS			current
		DESCRIPTION
				"TYPE: - Checkbox
				 PAGE: - Setup- Logging
					De-embed 8  cmdID= 1127 "
		::= { iqmux60CmdEntry 1127 }


	iqmux60SetupLoggingnPCM1 OBJECT-TYPE
		SYNTAX		INTEGER { disable(0), enable(1) }
		MAX-ACCESS		read-write
		STATUS			current
		DESCRIPTION
				"TYPE: - Checkbox
				 PAGE: - Setup- Logging
					nPCM 1  cmdID= 1128 "
		::= { iqmux60CmdEntry 1128 }


	iqmux60SetupLoggingnPCM2 OBJECT-TYPE
		SYNTAX		INTEGER { disable(0), enable(1) }
		MAX-ACCESS		read-write
		STATUS			current
		DESCRIPTION
				"TYPE: - Checkbox
				 PAGE: - Setup- Logging
					nPCM 2  cmdID= 1129 "
		::= { iqmux60CmdEntry 1129 }


	iqmux60SetupLoggingnPCM3 OBJECT-TYPE
		SYNTAX		INTEGER { disable(0), enable(1) }
		MAX-ACCESS		read-write
		STATUS			current
		DESCRIPTION
				"TYPE: - Checkbox
				 PAGE: - Setup- Logging
					nPCM 3  cmdID= 1130 "
		::= { iqmux60CmdEntry 1130 }


	iqmux60SetupLoggingnPCM4 OBJECT-TYPE
		SYNTAX		INTEGER { disable(0), enable(1) }
		MAX-ACCESS		read-write
		STATUS			current
		DESCRIPTION
				"TYPE: - Checkbox
				 PAGE: - Setup- Logging
					nPCM 4  cmdID= 1131 "
		::= { iqmux60CmdEntry 1131 }


	iqmux60SetupLoggingnPCM5 OBJECT-TYPE
		SYNTAX		INTEGER { disable(0), enable(1) }
		MAX-ACCESS		read-write
		STATUS			current
		DESCRIPTION
				"TYPE: - Checkbox
				 PAGE: - Setup- Logging
					nPCM 5  cmdID= 1132 "
		::= { iqmux60CmdEntry 1132 }


	iqmux60SetupLoggingnPCM6 OBJECT-TYPE
		SYNTAX		INTEGER { disable(0), enable(1) }
		MAX-ACCESS		read-write
		STATUS			current
		DESCRIPTION
				"TYPE: - Checkbox
				 PAGE: - Setup- Logging
					nPCM 6  cmdID= 1133 "
		::= { iqmux60CmdEntry 1133 }


	iqmux60SetupLoggingnPCM7 OBJECT-TYPE
		SYNTAX		INTEGER { disable(0), enable(1) }
		MAX-ACCESS		read-write
		STATUS			current
		DESCRIPTION
				"TYPE: - Checkbox
				 PAGE: - Setup- Logging
					nPCM 7  cmdID= 1134 "
		::= { iqmux60CmdEntry 1134 }


	iqmux60SetupLoggingnPCM8 OBJECT-TYPE
		SYNTAX		INTEGER { disable(0), enable(1) }
		MAX-ACCESS		read-write
		STATUS			current
		DESCRIPTION
				"TYPE: - Checkbox
				 PAGE: - Setup- Logging
					nPCM 8  cmdID= 1135 "
		::= { iqmux60CmdEntry 1135 }


	iqmux60SetupLoggingAES1 OBJECT-TYPE
		SYNTAX		INTEGER { disable(0), enable(1) }
		MAX-ACCESS		read-write
		STATUS			current
		DESCRIPTION
				"TYPE: - Checkbox
				 PAGE: - Setup- Logging
					AES 1  cmdID= 1108 "
		::= { iqmux60CmdEntry 1108 }


	iqmux60SetupLoggingAES2 OBJECT-TYPE
		SYNTAX		INTEGER { disable(0), enable(1) }
		MAX-ACCESS		read-write
		STATUS			current
		DESCRIPTION
				"TYPE: - Checkbox
				 PAGE: - Setup- Logging
					AES 2  cmdID= 1109 "
		::= { iqmux60CmdEntry 1109 }


	iqmux60SetupLoggingBusAL OBJECT-TYPE
		SYNTAX		INTEGER { disable(0), enable(1) }
		MAX-ACCESS		read-write
		STATUS			current
		DESCRIPTION
				"TYPE: - Checkbox
				 PAGE: - Setup- Logging
					Bus AL  cmdID= 1112 "
		::= { iqmux60CmdEntry 1112 }


	iqmux60SetupLoggingBusAR OBJECT-TYPE
		SYNTAX		INTEGER { disable(0), enable(1) }
		MAX-ACCESS		read-write
		STATUS			current
		DESCRIPTION
				"TYPE: - Checkbox
				 PAGE: - Setup- Logging
					Bus AR  cmdID= 1113 "
		::= { iqmux60CmdEntry 1113 }


	iqmux60SetupLoggingBusBL OBJECT-TYPE
		SYNTAX		INTEGER { disable(0), enable(1) }
		MAX-ACCESS		read-write
		STATUS			current
		DESCRIPTION
				"TYPE: - Checkbox
				 PAGE: - Setup- Logging
					Bus BL  cmdID= 1114 "
		::= { iqmux60CmdEntry 1114 }


	iqmux60SetupLoggingBusBR OBJECT-TYPE
		SYNTAX		INTEGER { disable(0), enable(1) }
		MAX-ACCESS		read-write
		STATUS			current
		DESCRIPTION
				"TYPE: - Checkbox
				 PAGE: - Setup- Logging
					Bus BR  cmdID= 1115 "
		::= { iqmux60CmdEntry 1115 }


	iqmux60SetupLoggingBusCL OBJECT-TYPE
		SYNTAX		INTEGER { disable(0), enable(1) }
		MAX-ACCESS		read-write
		STATUS			current
		DESCRIPTION
				"TYPE: - Checkbox
				 PAGE: - Setup- Logging
					Bus CL  cmdID= 1116 "
		::= { iqmux60CmdEntry 1116 }


	iqmux60SetupLoggingBusCR OBJECT-TYPE
		SYNTAX		INTEGER { disable(0), enable(1) }
		MAX-ACCESS		read-write
		STATUS			current
		DESCRIPTION
				"TYPE: - Checkbox
				 PAGE: - Setup- Logging
					Bus CR  cmdID= 1117 "
		::= { iqmux60CmdEntry 1117 }


	iqmux60SetupLoggingBusDL OBJECT-TYPE
		SYNTAX		INTEGER { disable(0), enable(1) }
		MAX-ACCESS		read-write
		STATUS			current
		DESCRIPTION
				"TYPE: - Checkbox
				 PAGE: - Setup- Logging
					Bus DL  cmdID= 1118 "
		::= { iqmux60CmdEntry 1118 }


	iqmux60SetupLoggingBusDR OBJECT-TYPE
		SYNTAX		INTEGER { disable(0), enable(1) }
		MAX-ACCESS		read-write
		STATUS			current
		DESCRIPTION
				"TYPE: - Checkbox
				 PAGE: - Setup- Logging
					Bus DR  cmdID= 1119 "
		::= { iqmux60CmdEntry 1119 }


	iqmux60SetupLoggingFault OBJECT-TYPE
		SYNTAX		INTEGER { disable(0), enable(1) }
		MAX-ACCESS		read-write
		STATUS			current
		DESCRIPTION
				"TYPE: - Checkbox
				 PAGE: - Setup- Logging
					Fault  cmdID= 1069 "
		::= { iqmux60CmdEntry 1069 }


	iqmux60SetupLoggingStatusINPUT OBJECT-TYPE
		SYNTAX		RollCallString
		MAX-ACCESS		read-only
		STATUS			current
		DESCRIPTION
				"TYPE: - Display
				 PAGE: - Setup- Logging Status
					INPUT=  cmdID= 2980  format=   "
		::= { iqmux60CmdEntry 2980 }


	iqmux60SetupLoggingStatusSTD OBJECT-TYPE
		SYNTAX		RollCallString
		MAX-ACCESS		read-only
		STATUS			current
		DESCRIPTION
				"TYPE: - Display
				 PAGE: - Setup- Logging Status
					STD=  cmdID= 2981  format=   "
		::= { iqmux60CmdEntry 2981 }


	iqmux60SetupLoggingStatusINPUT1 OBJECT-TYPE
		SYNTAX		RollCallString
		MAX-ACCESS		read-only
		STATUS			current
		DESCRIPTION
				"TYPE: - Display
				 PAGE: - Setup- Logging Status
					INPUT1=  cmdID= 2982  format=   "
		::= { iqmux60CmdEntry 2982 }


	iqmux60SetupLoggingStatusSTD1 OBJECT-TYPE
		SYNTAX		RollCallString
		MAX-ACCESS		read-only
		STATUS			current
		DESCRIPTION
				"TYPE: - Display
				 PAGE: - Setup- Logging Status
					STD1=  cmdID= 2983  format=   "
		::= { iqmux60CmdEntry 2983 }


	iqmux60SetupLoggingStatusINPUT2 OBJECT-TYPE
		SYNTAX		RollCallString
		MAX-ACCESS		read-only
		STATUS			current
		DESCRIPTION
				"TYPE: - Display
				 PAGE: - Setup- Logging Status
					INPUT2=  cmdID= 2984  format=   "
		::= { iqmux60CmdEntry 2984 }


	iqmux60SetupLoggingStatusSTD2 OBJECT-TYPE
		SYNTAX		RollCallString
		MAX-ACCESS		read-only
		STATUS			current
		DESCRIPTION
				"TYPE: - Display
				 PAGE: - Setup- Logging Status
					STD2=  cmdID= 2985  format=   "
		::= { iqmux60CmdEntry 2985 }


	iqmux60SetupLoggingStatusEDH OBJECT-TYPE
		SYNTAX		RollCallString
		MAX-ACCESS		read-only
		STATUS			current
		DESCRIPTION
				"TYPE: - Display
				 PAGE: - Setup- Logging Status
					EDH=  cmdID= 2987  format=   "
		::= { iqmux60CmdEntry 2987 }


	iqmux60SetupLoggingStatusERRSEC OBJECT-TYPE
		SYNTAX		RollCallString
		MAX-ACCESS		read-only
		STATUS			current
		DESCRIPTION
				"TYPE: - Display
				 PAGE: - Setup- Logging Status
					ERRSEC=  cmdID= 2988  format=   "
		::= { iqmux60CmdEntry 2988 }


	iqmux60SetupLoggingStatusROLLTRACK OBJECT-TYPE
		SYNTAX		RollCallString
		MAX-ACCESS		read-only
		STATUS			current
		DESCRIPTION
				"TYPE: - Display
				 PAGE: - Setup- Logging Status
					ROLLTRACK=  cmdID= 2989  format=   "
		::= { iqmux60CmdEntry 2989 }


	iqmux60SetupLoggingStatusDEEMBED1 OBJECT-TYPE
		SYNTAX		RollCallString
		MAX-ACCESS		read-only
		STATUS			current
		DESCRIPTION
				"TYPE: - Display
				 PAGE: - Setup- Logging Status
					DEEMBED1=  cmdID= 3014  format=   "
		::= { iqmux60CmdEntry 3014 }


	iqmux60SetupLoggingStatusDEEMBED2 OBJECT-TYPE
		SYNTAX		RollCallString
		MAX-ACCESS		read-only
		STATUS			current
		DESCRIPTION
				"TYPE: - Display
				 PAGE: - Setup- Logging Status
					DEEMBED2=  cmdID= 3015  format=   "
		::= { iqmux60CmdEntry 3015 }


	iqmux60SetupLoggingStatusDEEMBED3 OBJECT-TYPE
		SYNTAX		RollCallString
		MAX-ACCESS		read-only
		STATUS			current
		DESCRIPTION
				"TYPE: - Display
				 PAGE: - Setup- Logging Status
					DEEMBED3=  cmdID= 3016  format=   "
		::= { iqmux60CmdEntry 3016 }


	iqmux60SetupLoggingStatusDEEMBED4 OBJECT-TYPE
		SYNTAX		RollCallString
		MAX-ACCESS		read-only
		STATUS			current
		DESCRIPTION
				"TYPE: - Display
				 PAGE: - Setup- Logging Status
					DEEMBED4=  cmdID= 3017  format=   "
		::= { iqmux60CmdEntry 3017 }


	iqmux60SetupLoggingStatusDEEMBED5 OBJECT-TYPE
		SYNTAX		RollCallString
		MAX-ACCESS		read-only
		STATUS			current
		DESCRIPTION
				"TYPE: - Display
				 PAGE: - Setup- Logging Status
					DEEMBED5=  cmdID= 3018  format=   "
		::= { iqmux60CmdEntry 3018 }


	iqmux60SetupLoggingStatusDEEMBED6 OBJECT-TYPE
		SYNTAX		RollCallString
		MAX-ACCESS		read-only
		STATUS			current
		DESCRIPTION
				"TYPE: - Display
				 PAGE: - Setup- Logging Status
					DEEMBED6=  cmdID= 3019  format=   "
		::= { iqmux60CmdEntry 3019 }


	iqmux60SetupLoggingStatusDEEMBED7 OBJECT-TYPE
		SYNTAX		RollCallString
		MAX-ACCESS		read-only
		STATUS			current
		DESCRIPTION
				"TYPE: - Display
				 PAGE: - Setup- Logging Status
					DEEMBED7=  cmdID= 3020  format=   "
		::= { iqmux60CmdEntry 3020 }


	iqmux60SetupLoggingStatusDEEMBED8 OBJECT-TYPE
		SYNTAX		RollCallString
		MAX-ACCESS		read-only
		STATUS			current
		DESCRIPTION
				"TYPE: - Display
				 PAGE: - Setup- Logging Status
					DEEMBED8=  cmdID= 3021  format=   "
		::= { iqmux60CmdEntry 3021 }


	iqmux60SetupLoggingStatusNPCM1 OBJECT-TYPE
		SYNTAX		RollCallString
		MAX-ACCESS		read-only
		STATUS			current
		DESCRIPTION
				"TYPE: - Display
				 PAGE: - Setup- Logging Status
					NPCM1=  cmdID= 3022  format=   "
		::= { iqmux60CmdEntry 3022 }


	iqmux60SetupLoggingStatusNPCM2 OBJECT-TYPE
		SYNTAX		RollCallString
		MAX-ACCESS		read-only
		STATUS			current
		DESCRIPTION
				"TYPE: - Display
				 PAGE: - Setup- Logging Status
					NPCM2=  cmdID= 3023  format=   "
		::= { iqmux60CmdEntry 3023 }


	iqmux60SetupLoggingStatusNPCM3 OBJECT-TYPE
		SYNTAX		RollCallString
		MAX-ACCESS		read-only
		STATUS			current
		DESCRIPTION
				"TYPE: - Display
				 PAGE: - Setup- Logging Status
					NPCM3=  cmdID= 3024  format=   "
		::= { iqmux60CmdEntry 3024 }


	iqmux60SetupLoggingStatusNPCM4 OBJECT-TYPE
		SYNTAX		RollCallString
		MAX-ACCESS		read-only
		STATUS			current
		DESCRIPTION
				"TYPE: - Display
				 PAGE: - Setup- Logging Status
					NPCM4=  cmdID= 3025  format=   "
		::= { iqmux60CmdEntry 3025 }


	iqmux60SetupLoggingStatusNPCM5 OBJECT-TYPE
		SYNTAX		RollCallString
		MAX-ACCESS		read-only
		STATUS			current
		DESCRIPTION
				"TYPE: - Display
				 PAGE: - Setup- Logging Status
					NPCM5=  cmdID= 3026  format=   "
		::= { iqmux60CmdEntry 3026 }


	iqmux60SetupLoggingStatusNPCM6 OBJECT-TYPE
		SYNTAX		RollCallString
		MAX-ACCESS		read-only
		STATUS			current
		DESCRIPTION
				"TYPE: - Display
				 PAGE: - Setup- Logging Status
					NPCM6=  cmdID= 3027  format=   "
		::= { iqmux60CmdEntry 3027 }


	iqmux60SetupLoggingStatusNPCM7 OBJECT-TYPE
		SYNTAX		RollCallString
		MAX-ACCESS		read-only
		STATUS			current
		DESCRIPTION
				"TYPE: - Display
				 PAGE: - Setup- Logging Status
					NPCM7=  cmdID= 3028  format=   "
		::= { iqmux60CmdEntry 3028 }


	iqmux60SetupLoggingStatusNPCM8 OBJECT-TYPE
		SYNTAX		RollCallString
		MAX-ACCESS		read-only
		STATUS			current
		DESCRIPTION
				"TYPE: - Display
				 PAGE: - Setup- Logging Status
					NPCM8=  cmdID= 3029  format=   "
		::= { iqmux60CmdEntry 3029 }


	iqmux60SetupLoggingStatusAES1 OBJECT-TYPE
		SYNTAX		RollCallString
		MAX-ACCESS		read-only
		STATUS			current
		DESCRIPTION
				"TYPE: - Display
				 PAGE: - Setup- Logging Status
					AES1=  cmdID= 2994  format=   "
		::= { iqmux60CmdEntry 2994 }


	iqmux60SetupLoggingStatusAES2 OBJECT-TYPE
		SYNTAX		RollCallString
		MAX-ACCESS		read-only
		STATUS			current
		DESCRIPTION
				"TYPE: - Display
				 PAGE: - Setup- Logging Status
					AES2=  cmdID= 2995  format=   "
		::= { iqmux60CmdEntry 2995 }


	iqmux60SetupLoggingStatusBUSAL OBJECT-TYPE
		SYNTAX		RollCallString
		MAX-ACCESS		read-only
		STATUS			current
		DESCRIPTION
				"TYPE: - Display
				 PAGE: - Setup- Logging Status
					BUSAL=  cmdID= 2998  format=   "
		::= { iqmux60CmdEntry 2998 }


	iqmux60SetupLoggingStatusBUSAR OBJECT-TYPE
		SYNTAX		RollCallString
		MAX-ACCESS		read-only
		STATUS			current
		DESCRIPTION
				"TYPE: - Display
				 PAGE: - Setup- Logging Status
					BUSAR=  cmdID= 2999  format=   "
		::= { iqmux60CmdEntry 2999 }


	iqmux60SetupLoggingStatusBUSBL OBJECT-TYPE
		SYNTAX		RollCallString
		MAX-ACCESS		read-only
		STATUS			current
		DESCRIPTION
				"TYPE: - Display
				 PAGE: - Setup- Logging Status
					BUSBL=  cmdID= 3000  format=   "
		::= { iqmux60CmdEntry 3000 }


	iqmux60SetupLoggingStatusBUSBR OBJECT-TYPE
		SYNTAX		RollCallString
		MAX-ACCESS		read-only
		STATUS			current
		DESCRIPTION
				"TYPE: - Display
				 PAGE: - Setup- Logging Status
					BUSBR=  cmdID= 3001  format=   "
		::= { iqmux60CmdEntry 3001 }


	iqmux60SetupLoggingStatusBUSCL OBJECT-TYPE
		SYNTAX		RollCallString
		MAX-ACCESS		read-only
		STATUS			current
		DESCRIPTION
				"TYPE: - Display
				 PAGE: - Setup- Logging Status
					BUSCL=  cmdID= 3002  format=   "
		::= { iqmux60CmdEntry 3002 }


	iqmux60SetupLoggingStatusBUSCR OBJECT-TYPE
		SYNTAX		RollCallString
		MAX-ACCESS		read-only
		STATUS			current
		DESCRIPTION
				"TYPE: - Display
				 PAGE: - Setup- Logging Status
					BUSCR=  cmdID= 3003  format=   "
		::= { iqmux60CmdEntry 3003 }


	iqmux60SetupLoggingStatusBUSDL OBJECT-TYPE
		SYNTAX		RollCallString
		MAX-ACCESS		read-only
		STATUS			current
		DESCRIPTION
				"TYPE: - Display
				 PAGE: - Setup- Logging Status
					BUSDL=  cmdID= 3004  format=   "
		::= { iqmux60CmdEntry 3004 }


	iqmux60SetupLoggingStatusBUSDR OBJECT-TYPE
		SYNTAX		RollCallString
		MAX-ACCESS		read-only
		STATUS			current
		DESCRIPTION
				"TYPE: - Display
				 PAGE: - Setup- Logging Status
					BUSDR=  cmdID= 3005  format=   "
		::= { iqmux60CmdEntry 3005 }


	iqmux60SetupLoggingStatusFAULT OBJECT-TYPE
		SYNTAX		RollCallString
		MAX-ACCESS		read-only
		STATUS			current
		DESCRIPTION
				"TYPE: - Display
				 PAGE: - Setup- Logging Status
					FAULT=  cmdID= 2990  format=   "
		::= { iqmux60CmdEntry 2990 }


	iqmux60SetupInformationWindow OBJECT-TYPE
		SYNTAX		INTEGER {
							val_Input_Status(0),
							val_EDH_ANC_Status(1),
							val_Audio_Input_Status(2)
							}
		MAX-ACCESS		read-write
		STATUS			current
		DESCRIPTION
				"TYPE: - Button
				 PAGE: - Setup- Information Window
					input Status  cmdID= 1915  value= 0
					eDH & ANC Status  cmdID= 1915  value= 1
					audio Input Status  cmdID= 1915  value= 2  "
		::= { iqmux60CmdEntry 1915 }


	iqmux60SetupInformationWindowResetErrors OBJECT-TYPE
		SYNTAX		INTEGER { noAction(0),reset_Errors(1) }
		MAX-ACCESS		read-write
		STATUS			current
		DESCRIPTION
				"TYPE: - Button
				 PAGE: - Setup- Information Window
					reset Errors  cmdID= 2978  value= 1  "
		::= { iqmux60CmdEntry 2978 }


	iqmux60SetupDefaultOutput OBJECT-TYPE
		SYNTAX		INTEGER {
							val_Video(1),
							val_Freeze(2),
							val_Pattern(3)
							}
		MAX-ACCESS		read-write
		STATUS			current
		DESCRIPTION
				"TYPE: - Button
				 PAGE: - Setup- Default Output
					video  cmdID= 1202  value= 1
					freeze  cmdID= 1202  value= 2
					pattern  cmdID= 1202  value= 3  "
		::= { iqmux60CmdEntry 1202 }


	iqmux60SetupDefaultPattern OBJECT-TYPE
		SYNTAX		INTEGER {
							val_Black(0),
							val_EBU_Colour_Bars(1),
							val_Val_100_Colour_Bars(2),
							val_Ramp(3),
							val_Multiburst(4),
							val_Pulse_Bar(5)
							}
		MAX-ACCESS		read-write
		STATUS			current
		DESCRIPTION
				"TYPE: - Button
				 PAGE: - Setup- Default Output
					black  cmdID= 1038  value= 0
					eBU Colour Bars  cmdID= 1038  value= 1
					100% Colour Bars  cmdID= 1038  value= 2
					ramp  cmdID= 1038  value= 3
					multiburst  cmdID= 1038  value= 4
					pulse & Bar  cmdID= 1038  value= 5  "
		::= { iqmux60CmdEntry 1038 }


	iqmux60SetupUnitSoftwareVersion OBJECT-TYPE
		SYNTAX		RollCallString
		MAX-ACCESS		read-only
		STATUS			current
		DESCRIPTION
				"TYPE: - Display
				 PAGE: - Setup- Unit
					Software Version  cmdID= 2  format=   "
		::= { iqmux60CmdEntry 2 }


	iqmux60SetupUnitSerialNo OBJECT-TYPE
		SYNTAX		RollCallString
		MAX-ACCESS		read-only
		STATUS			current
		DESCRIPTION
				"TYPE: - Display
				 PAGE: - Setup- Unit
					Serial No  cmdID= 1  format=   "
		::= { iqmux60CmdEntry 1 }


	iqmux60SetupUnitPresetUnit OBJECT-TYPE
		SYNTAX		INTEGER { noAction(0),preset_Unit(1) }
		MAX-ACCESS		read-write
		STATUS			current
		DESCRIPTION
				"TYPE: - Button
				 PAGE: - Setup- Unit
					preset Unit  cmdID= 3  value= 1  "
		::= { iqmux60CmdEntry 3 }


	iqmux60SetupUnitRestart OBJECT-TYPE
		SYNTAX		INTEGER { noAction(0),restart(1) }
		MAX-ACCESS		read-write
		STATUS			current
		DESCRIPTION
				"TYPE: - Button
				 PAGE: - Setup- Unit
					restart  cmdID= 4  value= 1  "
		::= { iqmux60CmdEntry 4 }


	iqmux60SetupUnitBuildNo OBJECT-TYPE
		SYNTAX		RollCallString
		MAX-ACCESS		read-only
		STATUS			current
		DESCRIPTION
				"TYPE: - Display
				 PAGE: - Setup- Unit
					Build No  cmdID= 5  format=   "
		::= { iqmux60CmdEntry 5 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S12345678
--				:
-- Comments		: Serial Number of module
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE              The unit is not locked to the input signal
--				: FAIL              EDH errors have been found on the input signal
--              : OK                No EDH errors found on the input signal
--              : RESET             EDH statistics have been reset
-- Comments		:
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: STDERR            Input signal standard not recognized or no signal
--				: UNKNOWN           Not a selected input standard
--              : 525               Input standard 525
--              : 625               Input standard 625
-- Comments		:
--
---------------------------------------------------------------------------------------------------
-- Header		: STD1
--
-- MIB ref		: swCardEventLogSlotXX       .4.83.84.68.49
-- absolute OID	: 1.3.6.1.4.1.7995.2.6.1.1.XX.4.83.84.68.49
-- Vary			: YES
--
-- Value(s)		: ERR               Not a selected input standard Input 1
--				: 525               Input 1 standard 525
--              : 625               Input 1 standard 625
-- Comments		:
--
---------------------------------------------------------------------------------------------------
-- Header		: STD2
--
-- MIB ref		: swCardEventLogSlotXX       .4.83.84.68.50
-- absolute OID	: 1.3.6.1.4.1.7995.2.6.1.1.XX.4.83.84.68.50
-- Vary			: YES
--
-- Value(s)		: ERR               Not a selected input standard Input 1
--				: 525               Input 1 standard 525
--              : 625               Input 1 standard 625
-- Comments		:
--
---------------------------------------------------------------------------------------------------
-- Header		: AES_1
--
-- MIB ref		: swCardEventLogSlotXX       .5.65.69.83.95.49
-- absolute OID	: 1.3.6.1.4.1.7995.2.6.1.1.XX.5.65.69.83.95.49
-- Vary			: YES
--
-- Value(s)		: NONPCM            Non-PCM signal present on AES input 1
--				: OK                Valid signal present on AES input 1
--              : LOST              Signal not present at AES input 1
-- Comments		:
--
---------------------------------------------------------------------------------------------------
-- Header		: AES_2
--
-- MIB ref		: swCardEventLogSlotXX       .5.65.69.83.95.50
-- absolute OID	: 1.3.6.1.4.1.7995.2.6.1.1.XX.5.65.69.83.95.50
-- Vary			: YES
--
-- Value(s)		: NONPCM            Non-PCM signal present on AES input 1
--				: OK                Valid signal present on AES input 1
--              : LOST              Signal not present at AES input 1
-- Comments		:
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: NONE              No Internal errors detected
--				: FAIL              Internal error detected
--              : FAIL.FPGA_LOAD    Fpga load failure detected
-- Comments		:
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: OK                Valid input signal
--				: ERR               Invalid input signal
--              : LOST              Input signal lost
-- Comments		:
--
---------------------------------------------------------------------------------------------------
-- Header		: BUS_AL
--
-- MIB ref		: swCardEventLogSlotXX       .6.66.85.83.95.65.76
-- absolute OID	: 1.3.6.1.4.1.7995.2.6.1.1.XX.6.66.85.83.95.65.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_AR
--
-- MIB ref		: swCardEventLogSlotXX       .6.66.85.83.95.65.82
-- absolute OID	: 1.3.6.1.4.1.7995.2.6.1.1.XX.6.66.85.83.95.65.82
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_BL
--
-- MIB ref		: swCardEventLogSlotXX       .6.66.85.83.95.66.76
-- absolute OID	: 1.3.6.1.4.1.7995.2.6.1.1.XX.6.66.85.83.95.66.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_BR
--
-- MIB ref		: swCardEventLogSlotXX       .6.66.85.83.95.66.82
-- absolute OID	: 1.3.6.1.4.1.7995.2.6.1.1.XX.6.66.85.83.95.66.82
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_CL
--
-- MIB ref		: swCardEventLogSlotXX       .6.66.85.83.95.67.76
-- absolute OID	: 1.3.6.1.4.1.7995.2.6.1.1.XX.6.66.85.83.95.67.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_CR
--
-- MIB ref		: swCardEventLogSlotXX       .6.66.85.83.95.67.82
-- absolute OID	: 1.3.6.1.4.1.7995.2.6.1.1.XX.6.66.85.83.95.67.82
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_DL
--
-- MIB ref		: swCardEventLogSlotXX       .6.66.85.83.95.68.76
-- absolute OID	: 1.3.6.1.4.1.7995.2.6.1.1.XX.6.66.85.83.95.68.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_DR
--
-- MIB ref		: swCardEventLogSlotXX       .6.66.85.83.95.68.82
-- absolute OID	: 1.3.6.1.4.1.7995.2.6.1.1.XX.6.66.85.83.95.68.82
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
--
-- Value(s)		: 0s                Number or Errored Seconds
--				:
-- Comments		: Runtime string
--
---------------------------------------------------------------------------------------------------
-- Header		: INPUT1
--
-- MIB ref		: swCardEventLogSlotXX       .6.73.78.80.85.84.49
-- absolute OID	: 1.3.6.1.4.1.7995.2.6.1.1.XX.6.73.78.80.85.84.49
-- Vary			: YES
--
-- Value(s)		: OK                Valid input 1 signal
--				: ERR               Invalid input 1 signal
--              : LOST              Input 1 signal lost
-- Comments		:
--
---------------------------------------------------------------------------------------------------
-- Header		: INPUT2
--
-- MIB ref		: swCardEventLogSlotXX       .6.73.78.80.85.84.50
-- absolute OID	: 1.3.6.1.4.1.7995.2.6.1.1.XX.6.73.78.80.85.84.50
-- Vary			: YES
--
-- Value(s)		: OK                Valid input 1 signal
--				: ERR               Invalid input 1 signal
--              : LOST              Input 1 signal lost
-- Comments		:
--
---------------------------------------------------------------------------------------------------
-- Header		: NPCM_1
--
-- MIB ref		: swCardEventLogSlotXX       .6.78.80.67.77.95.49
-- absolute OID	: 1.3.6.1.4.1.7995.2.6.1.1.XX.6.78.80.67.77.95.49
-- Vary			: YES
--
-- Value(s)		: NONE              Non-PCM not present on pair 1 of selected SDI input
--				: OK                Non-PCM present on pair 1 of selected SDI input
-- Comments		:
--
---------------------------------------------------------------------------------------------------
-- Header		: NPCM_2
--
-- MIB ref		: swCardEventLogSlotXX       .6.78.80.67.77.95.50
-- absolute OID	: 1.3.6.1.4.1.7995.2.6.1.1.XX.6.78.80.67.77.95.50
-- Vary			: YES
--
-- Value(s)		: NONE              Non-PCM not present on pair 1 of selected SDI input
--				: OK                Non-PCM present on pair 1 of selected SDI input
-- Comments		:
--
---------------------------------------------------------------------------------------------------
-- Header		: NPCM_3
--
-- MIB ref		: swCardEventLogSlotXX       .6.78.80.67.77.95.51
-- absolute OID	: 1.3.6.1.4.1.7995.2.6.1.1.XX.6.78.80.67.77.95.51
-- Vary			: YES
--
-- Value(s)		: NONE              Non-PCM not present on pair 1 of selected SDI input
--				: OK                Non-PCM present on pair 1 of selected SDI input
-- Comments		:
--
---------------------------------------------------------------------------------------------------
-- Header		: NPCM_4
--
-- MIB ref		: swCardEventLogSlotXX       .6.78.80.67.77.95.52
-- absolute OID	: 1.3.6.1.4.1.7995.2.6.1.1.XX.6.78.80.67.77.95.52
-- Vary			: YES
--
-- Value(s)		: NONE              Non-PCM not present on pair 1 of selected SDI input
--				: OK                Non-PCM present on pair 1 of selected SDI input
-- Comments		:
--
---------------------------------------------------------------------------------------------------
-- Header		: NPCM_5
--
-- MIB ref		: swCardEventLogSlotXX       .6.78.80.67.77.95.53
-- absolute OID	: 1.3.6.1.4.1.7995.2.6.1.1.XX.6.78.80.67.77.95.53
-- Vary			: YES
--
-- Value(s)		: NONE              Non-PCM not present on pair 1 of selected SDI input
--				: OK                Non-PCM present on pair 1 of selected SDI input
-- Comments		:
--
---------------------------------------------------------------------------------------------------
-- Header		: NPCM_6
--
-- MIB ref		: swCardEventLogSlotXX       .6.78.80.67.77.95.54
-- absolute OID	: 1.3.6.1.4.1.7995.2.6.1.1.XX.6.78.80.67.77.95.54
-- Vary			: YES
--
-- Value(s)		: NONE              Non-PCM not present on pair 1 of selected SDI input
--				: OK                Non-PCM present on pair 1 of selected SDI input
-- Comments		:
--
---------------------------------------------------------------------------------------------------
-- Header		: NPCM_7
--
-- MIB ref		: swCardEventLogSlotXX       .6.78.80.67.77.95.55
-- absolute OID	: 1.3.6.1.4.1.7995.2.6.1.1.XX.6.78.80.67.77.95.55
-- Vary			: YES
--
-- Value(s)		: NONE              Non-PCM not present on pair 1 of selected SDI input
--				: OK                Non-PCM present on pair 1 of selected SDI input
-- Comments		:
--
---------------------------------------------------------------------------------------------------
-- Header		: NPCM_8
--
-- MIB ref		: swCardEventLogSlotXX       .6.78.80.67.77.95.56
-- absolute OID	: 1.3.6.1.4.1.7995.2.6.1.1.XX.6.78.80.67.77.95.56
-- Vary			: YES
--
-- Value(s)		: NONE              Non-PCM not present on pair 1 of selected SDI input
--				: OK                Non-PCM present on pair 1 of selected SDI input
-- Comments		:
--              :
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number of connected control sessions to this card.
--              : Generated by gateway card.
--
---------------------------------------------------------------------------------------------------
-- Header		: DEEMBED_1
--
-- MIB ref		: swCardEventLogSlotXX       .9.68.69.69.77.66.69.68.95.49
-- absolute OID	: 1.3.6.1.4.1.7995.2.6.1.1.XX.9.68.69.69.77.66.69.68.95.49
-- Vary			: YES
--
-- Value(s)		: NONE              Nothing present on pair 1
--				: OK                Embedded pair 1 present on selected SDI input
-- Comments		:
--
---------------------------------------------------------------------------------------------------
-- Header		: DEEMBED_2
--
-- MIB ref		: swCardEventLogSlotXX       .9.68.69.69.77.66.69.68.95.50
-- absolute OID	: 1.3.6.1.4.1.7995.2.6.1.1.XX.9.68.69.69.77.66.69.68.95.50
-- Vary			: YES
--
-- Value(s)		: NONE              Nothing present on pair 2
--				: OK                Embedded pair 2 present on selected SDI input
-- Comments		:
--
---------------------------------------------------------------------------------------------------
-- Header		: DEEMBED_3
--
-- MIB ref		: swCardEventLogSlotXX       .9.68.69.69.77.66.69.68.95.51
-- absolute OID	: 1.3.6.1.4.1.7995.2.6.1.1.XX.9.68.69.69.77.66.69.68.95.51
-- Vary			: YES
--
-- Value(s)		: NONE              Nothing present on pair 3
--				: OK                Embedded pair 3 present on selected SDI input
-- Comments		:
--
---------------------------------------------------------------------------------------------------
-- Header		: DEEMBED_4
--
-- MIB ref		: swCardEventLogSlotXX       .9.68.69.69.77.66.69.68.95.52
-- absolute OID	: 1.3.6.1.4.1.7995.2.6.1.1.XX.9.68.69.69.77.66.69.68.95.52
-- Vary			: YES
--
-- Value(s)		: NONE              Nothing present on pair 4
--				: OK                Embedded pair 4 present on selected SDI input
-- Comments		:
--
---------------------------------------------------------------------------------------------------
-- Header		: DEEMBED_5
--
-- MIB ref		: swCardEventLogSlotXX       .9.68.69.69.77.66.69.68.95.53
-- absolute OID	: 1.3.6.1.4.1.7995.2.6.1.1.XX.9.68.69.69.77.66.69.68.95.53
-- Vary			: YES
--
-- Value(s)		: NONE              Nothing present on pair 5
--				: OK                Embedded pair 5 present on selected SDI input
-- Comments		:
--
---------------------------------------------------------------------------------------------------
-- Header		: DEEMBED_6
--
-- MIB ref		: swCardEventLogSlotXX       .9.68.69.69.77.66.69.68.95.54
-- absolute OID	: 1.3.6.1.4.1.7995.2.6.1.1.XX.9.68.69.69.77.66.69.68.95.54
-- Vary			: YES
--
-- Value(s)		: NONE              Nothing present on pair 6
--				: OK                Embedded pair 6 present on selected SDI input
-- Comments		:
--
---------------------------------------------------------------------------------------------------
-- Header		: DEEMBED_7
--
-- MIB ref		: swCardEventLogSlotXX       .9.68.69.69.77.66.69.68.95.55
-- absolute OID	: 1.3.6.1.4.1.7995.2.6.1.1.XX.9.68.69.69.77.66.69.68.95.55
-- Vary			: YES
--
-- Value(s)		: NONE              Nothing present on pair 7
--				: OK                Embedded pair 7 present on selected SDI input
-- Comments		:
--
---------------------------------------------------------------------------------------------------
-- Header		: DEEMBED_8
--
-- MIB ref		: swCardEventLogSlotXX       .9.68.69.69.77.66.69.68.95.56
-- absolute OID	: 1.3.6.1.4.1.7995.2.6.1.1.XX.9.68.69.69.77.66.69.68.95.56
-- Vary			: YES
--
-- Value(s)		: NONE              Nothing present on pair 8
--				: OK                Embedded pair 8 present on selected SDI input
-- Comments		:
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: OK                RollTrack message sent and received OK
--				: FAIL              RollTrack message not acknowledged
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2006-07-13T16:18:10Z
--				: -
-- Comments		: Last known restart time of module, generated by gateway
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2006-07-13T16:23:36Z
--				:
-- Comments		: Time of last control update. Generated by gateway
--
---------------------------------------------------------------------------------------------------
