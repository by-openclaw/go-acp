-- ************************************************************************************
--        Snell Card:IQHCO31
--        Module Id#:575
--       Command Set:20
--          Filename:SNELL-IQHCO31-CMD-MIB.mib
--            Author:N Hewer
--              Date:13/11/2014
--              Time:15:11
--
-- Copyright (c) 2010 Snell Ltd
-- All rights reserved.
--
-- ************************************************************************************

SNELL-IQHCO31-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQHCO31,
    moduleIQHCO31MIB
        FROM SNELL-WILCOX-PRODUCT-REG;

 moduleIQHCO31CmdMi MODULE-IDENTITY
    LAST-UPDATED "1411131511Z"
    ORGANIZATION "Snell Ltd"
    CONTACT-INFO
        "Primary Author:N Hewer

         postal:    Southleigh Park House
                    Eastleigh Road
                    Havant, Hants
                    PO9 2PE
         phone:     +44 (0)23 92489000
         email:     snmp.support@snellgroup.com"
    DESCRIPTION
        "This file defines the Snell card, command set  translations."
    ::= { moduleIQHCO31MIB 1 }




--********************************************************************************
--*
--*  Snell Card:
--*  command set:
--*  list commands/menus:
--*
--******************************************************************************
	iqhco31CmdTable OBJECT-TYPE
		SYNTAX			SEQUENCE OF Iqhco31CmdEntry
		MAX-ACCESS		not-accessible
		STATUS			current
		DESCRIPTION
				"Note the instance of this table is relected in the command set Version"
		::= { moduleIQHCO31 1 }

	iqhco31CmdEntry OBJECT-TYPE
		SYNTAX		Iqhco31CmdEntry
		MAX-ACCESS		not-accessible
		STATUS			current
		DESCRIPTION
				"Entry in command table."
		INDEX	{ iqhco31SlotIndex }
		::= { iqhco31CmdTable 1 }

	Iqhco31CmdEntry ::=
		SEQUENCE {
			iqhco31SlotIndex
				Unsigned32,
			iqhco31MasterValidValidInputStds108050pB
				INTEGER,
			iqhco31MasterValidValidInputStds108059pB
				INTEGER,
			iqhco31MasterValidValidInputStds108050pA
				INTEGER,
			iqhco31MasterValidValidInputStds108059pA
				INTEGER,
			iqhco31MasterValidValidInputStds108029i
				INTEGER,
			iqhco31MasterValidValidInputStds108025i
				INTEGER,
			iqhco31MasterValidValidInputStds72059p
				INTEGER,
			iqhco31MasterValidValidInputStds72050p
				INTEGER,
			iqhco31MasterValidValidInputStds52529i
				INTEGER,
			iqhco31MasterValidValidInputStds62525i
				INTEGER,
			iqhco31MasterValidCRCEDHErroredsecErrSecEnable
				INTEGER,
			iqhco31MasterValidCRCEDHErroredsecErrSecDecision
				RollCallString,
			iqhco31MasterValidCRCEDHErroredsecCarrierDecision
				RollCallString,
			iqhco31MasterValidCRCEDHErroredsecStdDecision
				RollCallString,
			iqhco31MasterValidCRCEDHErroredsecInputStd
				RollCallString,
			iqhco31MasterValidCRCEDHErroredsecFreezeEnable
				INTEGER,
			iqhco31MasterValidCRCEDHErroredsecFreezeDecision
				RollCallString,
			iqhco31MasterValidCRCEDHErroredsecBlackEnable
				INTEGER,
			iqhco31MasterValidCRCEDHErroredsecBlackDecision
				RollCallString,
			iqhco31MasterValidCRCEDHErroredsecBlackThreshold
				INTEGER,
			iqhco31MasterValidVideoValidTimersBlackFailDelay
				INTEGER,
			iqhco31MasterValidVideoValidTimersBlackRecoverDelay
				INTEGER,
			iqhco31MasterValidVideoValidTimersFreezeFailDelay
				INTEGER,
			iqhco31MasterValidVideoValidTimersFreezeRecoverDela
				INTEGER,
			iqhco31MasterValidVideoValidTimersErrsecFailDelay
				INTEGER,
			iqhco31MasterValidVideoValidTimersErrsecRecoverDela
				INTEGER,
			iqhco31MasterValidVideoValidTimersValidFailDelay
				INTEGER,
			iqhco31MasterValidVideoValidTimersValidRecoverDelay
				INTEGER,
			iqhco31MasterValidValidAudioDecision
				RollCallString,
			iqhco31ValidAudioMasterPair1Decision
				RollCallString,
			iqhco31ValidAudioMasterPair1CurrentType
				RollCallString,
			iqhco31ValidAudioMasterPair1
				INTEGER,
			iqhco31ValidAudioMasterPair1Ch1State
				RollCallString,
			iqhco31ValidAudioMasterPair1Ch2State
				RollCallString,
			iqhco31ValidAudioMasterPair1Mute
				INTEGER,
			iqhco31ValidAudioMasterPair1Lowlevel
				INTEGER,
			iqhco31ValidAudioMasterPair1Overload
				INTEGER,
			iqhco31ValidAudioMasterPair2Decision
				RollCallString,
			iqhco31ValidAudioMasterPair2CurrentType
				RollCallString,
			iqhco31ValidAudioMasterPair2
				INTEGER,
			iqhco31ValidAudioMasterPair2Ch1State
				RollCallString,
			iqhco31ValidAudioMasterPair2Ch2State
				RollCallString,
			iqhco31ValidAudioMasterPair2Mute
				INTEGER,
			iqhco31ValidAudioMasterPair2Lowlevel
				INTEGER,
			iqhco31ValidAudioMasterPair2Overload
				INTEGER,
			iqhco31ValidAudioMasterPair3Decision
				RollCallString,
			iqhco31ValidAudioMasterPair3CurrentType
				RollCallString,
			iqhco31ValidAudioMasterPair3
				INTEGER,
			iqhco31ValidAudioMasterPair3Ch1State
				RollCallString,
			iqhco31ValidAudioMasterPair3Ch2State
				RollCallString,
			iqhco31ValidAudioMasterPair3Mute
				INTEGER,
			iqhco31ValidAudioMasterPair3Lowlevel
				INTEGER,
			iqhco31ValidAudioMasterPair3Overload
				INTEGER,
			iqhco31ValidAudioMasterPair4Decision
				RollCallString,
			iqhco31ValidAudioMasterPair4CurrentType
				RollCallString,
			iqhco31ValidAudioMasterPair4
				INTEGER,
			iqhco31ValidAudioMasterPair4Ch1State
				RollCallString,
			iqhco31ValidAudioMasterPair4Ch2State
				RollCallString,
			iqhco31ValidAudioMasterPair4Mute
				INTEGER,
			iqhco31ValidAudioMasterPair4Lowlevel
				INTEGER,
			iqhco31ValidAudioMasterPair4Overload
				INTEGER,
			iqhco31ValidAudioMasterPair5Decision
				RollCallString,
			iqhco31ValidAudioMasterPair5CurrentType
				RollCallString,
			iqhco31ValidAudioMasterPair5
				INTEGER,
			iqhco31ValidAudioMasterPair5Ch1State
				RollCallString,
			iqhco31ValidAudioMasterPair5Ch2State
				RollCallString,
			iqhco31ValidAudioMasterPair5Mute
				INTEGER,
			iqhco31ValidAudioMasterPair5Lowlevel
				INTEGER,
			iqhco31ValidAudioMasterPair5Overload
				INTEGER,
			iqhco31ValidAudioMasterPair6Decision
				RollCallString,
			iqhco31ValidAudioMasterPair6CurrentType
				RollCallString,
			iqhco31ValidAudioMasterPair6
				INTEGER,
			iqhco31ValidAudioMasterPair6Ch1State
				RollCallString,
			iqhco31ValidAudioMasterPair6Ch2State
				RollCallString,
			iqhco31ValidAudioMasterPair6Mute
				INTEGER,
			iqhco31ValidAudioMasterPair6Lowlevel
				INTEGER,
			iqhco31ValidAudioMasterPair6Overload
				INTEGER,
			iqhco31ValidAudioMasterPair7Decision
				RollCallString,
			iqhco31ValidAudioMasterPair7CurrentType
				RollCallString,
			iqhco31ValidAudioMasterPair7
				INTEGER,
			iqhco31ValidAudioMasterPair7Ch1State
				RollCallString,
			iqhco31ValidAudioMasterPair7Ch2State
				RollCallString,
			iqhco31ValidAudioMasterPair7Mute
				INTEGER,
			iqhco31ValidAudioMasterPair7Lowlevel
				INTEGER,
			iqhco31ValidAudioMasterPair7Overload
				INTEGER,
			iqhco31ValidAudioMasterPair8Decision
				RollCallString,
			iqhco31ValidAudioMasterPair8CurrentType
				RollCallString,
			iqhco31ValidAudioMasterPair8
				INTEGER,
			iqhco31ValidAudioMasterPair8Ch1State
				RollCallString,
			iqhco31ValidAudioMasterPair8Ch2State
				RollCallString,
			iqhco31ValidAudioMasterPair8Mute
				INTEGER,
			iqhco31ValidAudioMasterPair8Lowlevel
				INTEGER,
			iqhco31ValidAudioMasterPair8Overload
				INTEGER,
			iqhco31MasterValidValidAudioLowlevel
				INTEGER,
			iqhco31MasterValidValidAudioOverloadLevel
				INTEGER,
			iqhco31MasterValidValidAudioTypeFailTimer
				INTEGER,
			iqhco31MasterValidValidAudioTypeRecoverTimer
				INTEGER,
			iqhco31MasterValidValidAudioMuteFailTimer
				INTEGER,
			iqhco31MasterValidValidAudioMuteRecoverTimer
				INTEGER,
			iqhco31MasterValidValidAudioLowFailTimer
				INTEGER,
			iqhco31MasterValidValidAudioLowRecoverTimer
				INTEGER,
			iqhco31MasterValidValidAudioOverFailTimer
				INTEGER,
			iqhco31MasterValidValidAudioOverRecoverTimer
				INTEGER,
			iqhco31MasterVideoMasterDefaultOutput
				INTEGER,
			iqhco31VideoMasterVideoProcampProcAmpEnable
				INTEGER,
			iqhco31VideoMasterVideoProcampBlackLevel
				INTEGER,
			iqhco31VideoMasterVideoProcampHueAdjust
				INTEGER,
			iqhco31VideoMasterVideoProcampMasterVideoGain
				INTEGER,
			iqhco31VideoMasterVideoProcampYGain
				INTEGER,
			iqhco31VideoMasterVideoProcampCbCrGain
				INTEGER,
			iqhco31VideoMasterVideoProcampYCTiming
				INTEGER,
			iqhco31VideoMasterVideoProcampPictureposition
				INTEGER,
			iqhco31VideoMasterVideoProcampModalIndex
				INTEGER,
			iqhco31VideoMasterVideoProcampYCTimingnm
				INTEGER,
			iqhco31VideoMasterVideoProcampPicturepositionnm
				INTEGER,
			iqhco31VideoMasterBlankingBlankVANC
				INTEGER,
			iqhco31Blanking625BlankLinesLine233951
				INTEGER,
			iqhco31Blanking625BlankLinesLine3363952
				INTEGER,
			iqhco31Blanking525BlankLinesLine213953
				INTEGER,
			iqhco31Blanking525BlankLinesLine223955
				INTEGER,
			iqhco31Blanking525BlankLinesLine2833954
				INTEGER,
			iqhco31Blanking525BlankLinesLine2843956
				INTEGER,
			iqhco31VideoMasterBlankingBlankHANC
				INTEGER,
			iqhco31VideoMasterCaption
				INTEGER,
			iqhco31VideoMasterCaptionEditCaption
				RollCallString,
			iqhco31MasterVideoMasterPattern
				INTEGER,
			iqhco31VideoMasterFreeze
				INTEGER,
			iqhco31VideoMasterFreezeManualFreeze
				INTEGER,
			iqhco31AudioMasterEmbeddersEnable5066
				INTEGER,
			iqhco31AudioMasterEmbeddersEnable5067
				INTEGER,
			iqhco31AudioMasterEmbeddersEnable5068
				INTEGER,
			iqhco31AudioMasterEmbeddersEnable5069
				INTEGER,
			iqhco31AudioDelayDelaysVideoDelay5078
				INTEGER,
			iqhco31AudioDelayDelaysManualDelay5079
				INTEGER,
			iqhco31AudioDelayDelaysTrack14Delay5080
				INTEGER,
			iqhco31AudioDelayDelaysTrack15Delay5081
				INTEGER,
			iqhco31AudioDelayDelaysTrack16Delay5082
				INTEGER,
			iqhco31AudioDelayDelaysTrack17Delay5083
				INTEGER,
			iqhco31AudioDelayDelaysCoarseDelay5075
				INTEGER,
			iqhco31AudioDelayDelaysFineDelay5077
				INTEGER,
			iqhco31AudioDelayDelayStatusTotalDelay5084
				RollCallString,
			iqhco31AudioDelayDelayStatusVideoDelay5074
				RollCallString,
			iqhco31AudioDelayDelayStatusManualDelay5076
				RollCallString,
			iqhco31AudioDelayDelayStatusTrack14Delay
				RollCallString,
			iqhco31AudioDelayDelayStatusTrack15Delay
				RollCallString,
			iqhco31AudioDelayDelayStatusTrack16Delay
				RollCallString,
			iqhco31AudioDelayDelayStatusTrack17Delay
				RollCallString,
			iqhco31BackupValidValidInputStds108050pB
				INTEGER,
			iqhco31BackupValidValidInputStds108059pB
				INTEGER,
			iqhco31BackupValidValidInputStds108050pA
				INTEGER,
			iqhco31BackupValidValidInputStds108059pA
				INTEGER,
			iqhco31BackupValidValidInputStds108029i
				INTEGER,
			iqhco31BackupValidValidInputStds108025i
				INTEGER,
			iqhco31BackupValidValidInputStds72059p
				INTEGER,
			iqhco31BackupValidValidInputStds72050p
				INTEGER,
			iqhco31BackupValidValidInputStds52529i
				INTEGER,
			iqhco31BackupValidValidInputStds62525i
				INTEGER,
			iqhco31BackupValidCRCEDHErroredsecErrSecEnable
				INTEGER,
			iqhco31BackupValidCRCEDHErroredsecErrSecDecision
				RollCallString,
			iqhco31BackupValidCRCEDHErroredsecCarrierDecision
				RollCallString,
			iqhco31BackupValidCRCEDHErroredsecStdDecision
				RollCallString,
			iqhco31BackupValidCRCEDHErroredsecInputStd
				RollCallString,
			iqhco31BackupValidCRCEDHErroredsecFreezeEnable
				INTEGER,
			iqhco31BackupValidCRCEDHErroredsecFreezeDecision
				RollCallString,
			iqhco31BackupValidCRCEDHErroredsecBlackEnable
				INTEGER,
			iqhco31BackupValidCRCEDHErroredsecBlackDecision
				RollCallString,
			iqhco31BackupValidCRCEDHErroredsecBlackThreshold
				INTEGER,
			iqhco31BackupValidVideoValidTimersBlackFailDelay
				INTEGER,
			iqhco31BackupValidVideoValidTimersBlackRecoverDelay
				INTEGER,
			iqhco31BackupValidVideoValidTimersFreezeFailDelay
				INTEGER,
			iqhco31BackupValidVideoValidTimersFreezeRecoverDela
				INTEGER,
			iqhco31BackupValidVideoValidTimersErrsecFailDelay
				INTEGER,
			iqhco31BackupValidVideoValidTimersErrsecRecoverDela
				INTEGER,
			iqhco31BackupValidVideoValidTimersValidFailDelay
				INTEGER,
			iqhco31BackupValidVideoValidTimersValidRecoverDelay
				INTEGER,
			iqhco31BackupValidValidAudioDecision
				RollCallString,
			iqhco31ValidAudioBackupPair1Decision
				RollCallString,
			iqhco31ValidAudioBackupPair1CurrentType
				RollCallString,
			iqhco31ValidAudioBackupPair1
				INTEGER,
			iqhco31ValidAudioBackupPair1Ch1State
				RollCallString,
			iqhco31ValidAudioBackupPair1Ch2State
				RollCallString,
			iqhco31ValidAudioBackupPair1Mute
				INTEGER,
			iqhco31ValidAudioBackupPair1Lowlevel
				INTEGER,
			iqhco31ValidAudioBackupPair1Overload
				INTEGER,
			iqhco31ValidAudioBackupPair2Decision
				RollCallString,
			iqhco31ValidAudioBackupPair2CurrentType
				RollCallString,
			iqhco31ValidAudioBackupPair2
				INTEGER,
			iqhco31ValidAudioBackupPair2Ch1State
				RollCallString,
			iqhco31ValidAudioBackupPair2Ch2State
				RollCallString,
			iqhco31ValidAudioBackupPair2Mute
				INTEGER,
			iqhco31ValidAudioBackupPair2Lowlevel
				INTEGER,
			iqhco31ValidAudioBackupPair2Overload
				INTEGER,
			iqhco31ValidAudioBackupPair3Decision
				RollCallString,
			iqhco31ValidAudioBackupPair3CurrentType
				RollCallString,
			iqhco31ValidAudioBackupPair3
				INTEGER,
			iqhco31ValidAudioBackupPair3Ch1State
				RollCallString,
			iqhco31ValidAudioBackupPair3Ch2State
				RollCallString,
			iqhco31ValidAudioBackupPair3Mute
				INTEGER,
			iqhco31ValidAudioBackupPair3Lowlevel
				INTEGER,
			iqhco31ValidAudioBackupPair3Overload
				INTEGER,
			iqhco31ValidAudioBackupPair4Decision
				RollCallString,
			iqhco31ValidAudioBackupPair4CurrentType
				RollCallString,
			iqhco31ValidAudioBackupPair4
				INTEGER,
			iqhco31ValidAudioBackupPair4Ch1State
				RollCallString,
			iqhco31ValidAudioBackupPair4Ch2State
				RollCallString,
			iqhco31ValidAudioBackupPair4Mute
				INTEGER,
			iqhco31ValidAudioBackupPair4Lowlevel
				INTEGER,
			iqhco31ValidAudioBackupPair4Overload
				INTEGER,
			iqhco31ValidAudioBackupPair5Decision
				RollCallString,
			iqhco31ValidAudioBackupPair5CurrentType
				RollCallString,
			iqhco31ValidAudioBackupPair5
				INTEGER,
			iqhco31ValidAudioBackupPair5Ch1State
				RollCallString,
			iqhco31ValidAudioBackupPair5Ch2State
				RollCallString,
			iqhco31ValidAudioBackupPair5Mute
				INTEGER,
			iqhco31ValidAudioBackupPair5Lowlevel
				INTEGER,
			iqhco31ValidAudioBackupPair5Overload
				INTEGER,
			iqhco31ValidAudioBackupPair6Decision
				RollCallString,
			iqhco31ValidAudioBackupPair6CurrentType
				RollCallString,
			iqhco31ValidAudioBackupPair6
				INTEGER,
			iqhco31ValidAudioBackupPair6Ch1State
				RollCallString,
			iqhco31ValidAudioBackupPair6Ch2State
				RollCallString,
			iqhco31ValidAudioBackupPair6Mute
				INTEGER,
			iqhco31ValidAudioBackupPair6Lowlevel
				INTEGER,
			iqhco31ValidAudioBackupPair6Overload
				INTEGER,
			iqhco31ValidAudioBackupPair7Decision
				RollCallString,
			iqhco31ValidAudioBackupPair7CurrentType
				RollCallString,
			iqhco31ValidAudioBackupPair7
				INTEGER,
			iqhco31ValidAudioBackupPair7Ch1State
				RollCallString,
			iqhco31ValidAudioBackupPair7Ch2State
				RollCallString,
			iqhco31ValidAudioBackupPair7Mute
				INTEGER,
			iqhco31ValidAudioBackupPair7Lowlevel
				INTEGER,
			iqhco31ValidAudioBackupPair7Overload
				INTEGER,
			iqhco31ValidAudioBackupPair8Decision
				RollCallString,
			iqhco31ValidAudioBackupPair8CurrentType
				RollCallString,
			iqhco31ValidAudioBackupPair8
				INTEGER,
			iqhco31ValidAudioBackupPair8Ch1State
				RollCallString,
			iqhco31ValidAudioBackupPair8Ch2State
				RollCallString,
			iqhco31ValidAudioBackupPair8Mute
				INTEGER,
			iqhco31ValidAudioBackupPair8Lowlevel
				INTEGER,
			iqhco31ValidAudioBackupPair8Overload
				INTEGER,
			iqhco31BackupValidValidAudioLowlevel
				INTEGER,
			iqhco31BackupValidValidAudioOverloadLevel
				INTEGER,
			iqhco31BackupValidValidAudioTypeFailTimer
				INTEGER,
			iqhco31BackupValidValidAudioTypeRecoverTimer
				INTEGER,
			iqhco31BackupValidValidAudioMuteFailTimer
				INTEGER,
			iqhco31BackupValidValidAudioMuteRecoverTimer
				INTEGER,
			iqhco31BackupValidValidAudioLowFailTimer
				INTEGER,
			iqhco31BackupValidValidAudioLowRecoverTimer
				INTEGER,
			iqhco31BackupValidValidAudioOverFailTimer
				INTEGER,
			iqhco31BackupValidValidAudioOverRecoverTimer
				INTEGER,
			iqhco31BackupVideoBackupDefaultOutput
				INTEGER,
			iqhco31VideoBackupVideoProcampProcAmpEnable
				INTEGER,
			iqhco31VideoBackupVideoProcampBlackLevel
				INTEGER,
			iqhco31VideoBackupVideoProcampHueAdjust
				INTEGER,
			iqhco31VideoBackupVideoProcampMasterVideoGain
				INTEGER,
			iqhco31VideoBackupVideoProcampYGain
				INTEGER,
			iqhco31VideoBackupVideoProcampCbCrGain
				INTEGER,
			iqhco31VideoBackupVideoProcampYCTiming
				INTEGER,
			iqhco31VideoBackupVideoProcampPictureposition
				INTEGER,
			iqhco31VideoBackupVideoProcampModalIndex
				INTEGER,
			iqhco31VideoBackupVideoProcampYCTimingnm
				INTEGER,
			iqhco31VideoBackupVideoProcampPicturepositionnm
				INTEGER,
			iqhco31VideoBackupBlankingBlankVANC
				INTEGER,
			iqhco31Blanking625BlankLinesLine233971
				INTEGER,
			iqhco31Blanking625BlankLinesLine3363972
				INTEGER,
			iqhco31Blanking525BlankLinesLine213973
				INTEGER,
			iqhco31Blanking525BlankLinesLine223975
				INTEGER,
			iqhco31Blanking525BlankLinesLine2833974
				INTEGER,
			iqhco31Blanking525BlankLinesLine2843976
				INTEGER,
			iqhco31VideoBackupBlankingBlankHANC
				INTEGER,
			iqhco31VideoBackupCaption
				INTEGER,
			iqhco31VideoBackupCaptionEditCaption
				RollCallString,
			iqhco31BackupVideoBackupPattern
				INTEGER,
			iqhco31VideoBackupFreeze
				INTEGER,
			iqhco31VideoBackupFreezeManualFreeze
				INTEGER,
			iqhco31AudioBackupEmbeddersEnable5070
				INTEGER,
			iqhco31AudioBackupEmbeddersEnable5071
				INTEGER,
			iqhco31AudioBackupEmbeddersEnable5072
				INTEGER,
			iqhco31AudioBackupEmbeddersEnable5073
				INTEGER,
			iqhco31AudioDelayDelaysVideoDelay5089
				INTEGER,
			iqhco31AudioDelayDelaysManualDelay5090
				INTEGER,
			iqhco31AudioDelayDelaysTrack14Delay5091
				INTEGER,
			iqhco31AudioDelayDelaysTrack15Delay5092
				INTEGER,
			iqhco31AudioDelayDelaysTrack16Delay5093
				INTEGER,
			iqhco31AudioDelayDelaysTrack17Delay5094
				INTEGER,
			iqhco31AudioDelayDelaysCoarseDelay5086
				INTEGER,
			iqhco31AudioDelayDelaysFineDelay5088
				INTEGER,
			iqhco31AudioDelayDelayStatusTotalDelay5095
				RollCallString,
			iqhco31AudioDelayDelayStatusVideoDelay5085
				RollCallString,
			iqhco31AudioDelayDelayStatusManualDelay5087
				RollCallString,
			iqhco31RulesRulesVideoMasterCurrentOutput
				RollCallString,
			iqhco31RulesRulesVideoMasterSwitchtoMaster
				INTEGER,
			iqhco31RulesRulesVideoMasterActive
				RollCallString,
			iqhco31RulesRulesVideoMaster5602
				INTEGER,
			iqhco31RulesRulesVideoMaster5603
				INTEGER,
			iqhco31RulesRulesVideoMaster5604
				INTEGER,
			iqhco31RulesRulesVideoMaster5605
				INTEGER,
			iqhco31RulesRulesVideoMaster5606
				INTEGER,
			iqhco31RulesRulesVideoMaster5607
				INTEGER,
			iqhco31RulesRulesVideoMaster5608
				INTEGER,
			iqhco31RulesRulesVideoMaster5609
				INTEGER,
			iqhco31RulesRulesVideoMaster5610
				INTEGER,
			iqhco31RulesRulesVideoMaster5611
				INTEGER,
			iqhco31RulesRulesVideoBackupSwitchtoBackup
				INTEGER,
			iqhco31RulesRulesVideoBackupActive
				RollCallString,
			iqhco31RulesRulesVideoBackup5622
				INTEGER,
			iqhco31RulesRulesVideoBackup5623
				INTEGER,
			iqhco31RulesRulesVideoBackup5624
				INTEGER,
			iqhco31RulesRulesVideoBackup5625
				INTEGER,
			iqhco31RulesRulesVideoBackup5626
				INTEGER,
			iqhco31RulesRulesVideoBackup5627
				INTEGER,
			iqhco31RulesRulesVideoBackup5628
				INTEGER,
			iqhco31RulesRulesVideoBackup5629
				INTEGER,
			iqhco31RulesRulesVideoBackup5630
				INTEGER,
			iqhco31RulesRulesVideoBackup5631
				INTEGER,
			iqhco31GPIEnableGPIO1GPIO1State
				RollCallString,
			iqhco31GPIEnableGPIO1
				INTEGER,
			iqhco31GPIEnableGPIO1GPO1Invert
				INTEGER,
			iqhco31GPIEnableGPIO2GPIO2State
				RollCallString,
			iqhco31GPIEnableGPIO2
				INTEGER,
			iqhco31GPIEnableGPIO2GPO2Invert
				INTEGER,
			iqhco31GPIEnableGPIO3GPIO3State
				RollCallString,
			iqhco31GPIEnableGPIO3
				INTEGER,
			iqhco31GPIEnableGPIO3GPO3Invert
				INTEGER,
			iqhco31GPIEnableGPIO4GPIO4State
				RollCallString,
			iqhco31GPIEnableGPIO4
				INTEGER,
			iqhco31GPIEnableGPIO4GPO4Invert
				INTEGER,
			iqhco31RulesGPIEnableNoGPIsonRear
				RollCallString,
			iqhco31RulesRulesGPI1outActive
				RollCallString,
			iqhco31RulesRulesGPI1out5672
				INTEGER,
			iqhco31RulesRulesGPI1out5662
				INTEGER,
			iqhco31RulesRulesGPI1out5663
				INTEGER,
			iqhco31RulesRulesGPI1out5664
				INTEGER,
			iqhco31RulesRulesGPI1out5665
				INTEGER,
			iqhco31RulesRulesGPI1out5666
				INTEGER,
			iqhco31RulesRulesGPI1out5667
				INTEGER,
			iqhco31RulesRulesGPI1out5668
				INTEGER,
			iqhco31RulesRulesGPI1out5669
				INTEGER,
			iqhco31RulesRulesGPI1out5670
				INTEGER,
			iqhco31RulesRulesGPI1out
				INTEGER,
			iqhco31RulesRulesGPI2outActive
				RollCallString,
			iqhco31RulesRulesGPI2out5692
				INTEGER,
			iqhco31RulesRulesGPI2out5682
				INTEGER,
			iqhco31RulesRulesGPI2out5683
				INTEGER,
			iqhco31RulesRulesGPI2out5684
				INTEGER,
			iqhco31RulesRulesGPI2out5685
				INTEGER,
			iqhco31RulesRulesGPI2out5686
				INTEGER,
			iqhco31RulesRulesGPI2out5687
				INTEGER,
			iqhco31RulesRulesGPI2out5688
				INTEGER,
			iqhco31RulesRulesGPI2out5689
				INTEGER,
			iqhco31RulesRulesGPI2out5690
				INTEGER,
			iqhco31RulesRulesGPI2out
				INTEGER,
			iqhco31RulesRulesGPI3outActive
				RollCallString,
			iqhco31RulesRulesGPI3out5712
				INTEGER,
			iqhco31RulesRulesGPI3out5702
				INTEGER,
			iqhco31RulesRulesGPI3out5703
				INTEGER,
			iqhco31RulesRulesGPI3out5704
				INTEGER,
			iqhco31RulesRulesGPI3out5705
				INTEGER,
			iqhco31RulesRulesGPI3out5706
				INTEGER,
			iqhco31RulesRulesGPI3out5707
				INTEGER,
			iqhco31RulesRulesGPI3out5708
				INTEGER,
			iqhco31RulesRulesGPI3out5709
				INTEGER,
			iqhco31RulesRulesGPI3out5710
				INTEGER,
			iqhco31RulesRulesGPI3out
				INTEGER,
			iqhco31RulesRulesGPI4outActive
				RollCallString,
			iqhco31RulesRulesGPI4out5732
				INTEGER,
			iqhco31RulesRulesGPI4out5722
				INTEGER,
			iqhco31RulesRulesGPI4out5723
				INTEGER,
			iqhco31RulesRulesGPI4out5724
				INTEGER,
			iqhco31RulesRulesGPI4out5725
				INTEGER,
			iqhco31RulesRulesGPI4out5726
				INTEGER,
			iqhco31RulesRulesGPI4out5727
				INTEGER,
			iqhco31RulesRulesGPI4out5728
				INTEGER,
			iqhco31RulesRulesGPI4out5729
				INTEGER,
			iqhco31RulesRulesGPI4out5730
				INTEGER,
			iqhco31RulesRulesGPI4out
				INTEGER,
			iqhco31RulesRollTrackEnableEnable6649
				INTEGER,
			iqhco31RulesRollTrackEnableEnable6651
				INTEGER,
			iqhco31RulesRollTrackEnableEnable6653
				INTEGER,
			iqhco31RulesRollTrackEnableEnable6655
				INTEGER,
			iqhco31RulesRollTrackEnableState6648
				RollCallString,
			iqhco31RulesRollTrackEnableState6650
				RollCallString,
			iqhco31RulesRollTrackEnableState6652
				RollCallString,
			iqhco31RulesRollTrackEnableState6654
				RollCallString,
			iqhco31RulesRulesRollTack101Active
				RollCallString,
			iqhco31RulesRulesRollTack1015752
				INTEGER,
			iqhco31RulesRulesRollTack1015742
				INTEGER,
			iqhco31RulesRulesRollTack1015743
				INTEGER,
			iqhco31RulesRulesRollTack1015744
				INTEGER,
			iqhco31RulesRulesRollTack1015745
				INTEGER,
			iqhco31RulesRulesRollTack1015746
				INTEGER,
			iqhco31RulesRulesRollTack1015747
				INTEGER,
			iqhco31RulesRulesRollTack1015748
				INTEGER,
			iqhco31RulesRulesRollTack1015749
				INTEGER,
			iqhco31RulesRulesRollTack1015750
				INTEGER,
			iqhco31RulesRulesRollTack101
				INTEGER,
			iqhco31RulesRulesRollTack102Active
				RollCallString,
			iqhco31RulesRulesRollTack1025772
				INTEGER,
			iqhco31RulesRulesRollTack1025762
				INTEGER,
			iqhco31RulesRulesRollTack1025763
				INTEGER,
			iqhco31RulesRulesRollTack1025764
				INTEGER,
			iqhco31RulesRulesRollTack1025765
				INTEGER,
			iqhco31RulesRulesRollTack1025766
				INTEGER,
			iqhco31RulesRulesRollTack1025767
				INTEGER,
			iqhco31RulesRulesRollTack1025768
				INTEGER,
			iqhco31RulesRulesRollTack1025769
				INTEGER,
			iqhco31RulesRulesRollTack1025770
				INTEGER,
			iqhco31RulesRulesRollTack102
				INTEGER,
			iqhco31RulesRulesRollTack103Active
				RollCallString,
			iqhco31RulesRulesRollTack1035792
				INTEGER,
			iqhco31RulesRulesRollTack1035782
				INTEGER,
			iqhco31RulesRulesRollTack1035783
				INTEGER,
			iqhco31RulesRulesRollTack1035784
				INTEGER,
			iqhco31RulesRulesRollTack1035785
				INTEGER,
			iqhco31RulesRulesRollTack1035786
				INTEGER,
			iqhco31RulesRulesRollTack1035787
				INTEGER,
			iqhco31RulesRulesRollTack1035788
				INTEGER,
			iqhco31RulesRulesRollTack1035789
				INTEGER,
			iqhco31RulesRulesRollTack1035790
				INTEGER,
			iqhco31RulesRulesRollTack103
				INTEGER,
			iqhco31RulesRulesRollTack104Active
				RollCallString,
			iqhco31RulesRulesRollTack1045812
				INTEGER,
			iqhco31RulesRulesRollTack1045802
				INTEGER,
			iqhco31RulesRulesRollTack1045803
				INTEGER,
			iqhco31RulesRulesRollTack1045804
				INTEGER,
			iqhco31RulesRulesRollTack1045805
				INTEGER,
			iqhco31RulesRulesRollTack1045806
				INTEGER,
			iqhco31RulesRulesRollTack1045807
				INTEGER,
			iqhco31RulesRulesRollTack1045808
				INTEGER,
			iqhco31RulesRulesRollTack1045809
				INTEGER,
			iqhco31RulesRulesRollTack1045810
				INTEGER,
			iqhco31RulesRulesRollTack104
				INTEGER,
			iqhco31RulesPresetsPriorityMaster6660
				INTEGER,
			iqhco31RulesPresetsPriorityBackup6661
				INTEGER,
			iqhco31RulesPresetsNoPriority6662
				INTEGER,
			iqhco31RulesPresetsPriorityMaster6663
				INTEGER,
			iqhco31RulesPresetsPriorityBackup6664
				INTEGER,
			iqhco31RulesPresetsNoPriority6665
				INTEGER,
			iqhco31RulesPresetsPriorityMaster
				INTEGER,
			iqhco31RulesPresetsPriorityBackup
				INTEGER,
			iqhco31RulesPresetsNoPriority
				INTEGER,
			iqhco31OutputsMasterSelect
				INTEGER,
			iqhco31OutputsMonitorSelect
				INTEGER,
			iqhco31OutputsRulesSelection
				INTEGER,
			iqhco31AESOut12AESOut1SourceLR
				INTEGER,
			iqhco31AESOut12AESOut2SourceLR
				INTEGER,
			iqhco31OutputsToneFrequency
				INTEGER,
			iqhco31OutputsToneChannelident
				INTEGER,
			iqhco31CommonGenlock
				INTEGER,
			iqhco31CommonGenlockFreerunFrequency
				INTEGER,
			iqhco31CommonGenlockGenlockHPhase3790
				INTEGER,
			iqhco31CommonGenlockGenlockVPhase3791
				INTEGER,
			iqhco31CommonGenlockMasterFdelay
				INTEGER,
			iqhco31CommonGenlockBackupFdelay
				INTEGER,
			iqhco31CommonGenlockGenlocksaveindex
				INTEGER,
			iqhco31CommonGenlockGenlockHPhase3992
				INTEGER,
			iqhco31CommonGenlockGenlockVPhase3993
				INTEGER,
			iqhco31CommonGenlockReferenceSelect
				INTEGER,
			iqhco31CommonGenlockDefaultFormat
				INTEGER,
			iqhco31CommonMemoriesSelMemory
				INTEGER,
			iqhco31CommonMemoriesSetMemName
				RollCallString,
			iqhco31CommonMemoriesRecallMemory
				INTEGER,
			iqhco31CommonMemoriesSaveMemory
				INTEGER,
			iqhco31CommonMemoriesLastUserMemory
				RollCallString,
			iqhco31CommonMemoriesClearMemory
				INTEGER,
			iqhco31MemoriesMemoryNamesMemory1Name
				RollCallString,
			iqhco31MemoriesMemoryNamesMemory2Name
				RollCallString,
			iqhco31MemoriesMemoryNamesMemory3Name
				RollCallString,
			iqhco31MemoriesMemoryNamesMemory4Name
				RollCallString,
			iqhco31MemoriesMemoryNamesMemory5Name
				RollCallString,
			iqhco31MemoriesMemoryNamesMemory6Name
				RollCallString,
			iqhco31MemoriesMemoryNamesMemory7Name
				RollCallString,
			iqhco31MemoriesMemoryNamesMemory8Name
				RollCallString,
			iqhco31MemoriesMemoryNamesMemory9Name
				RollCallString,
			iqhco31MemoriesMemoryNamesMemory10Name
				RollCallString,
			iqhco31MemoriesMemoryNamesMemory11Name
				RollCallString,
			iqhco31MemoriesMemoryNamesMemory12Name
				RollCallString,
			iqhco31MemoriesMemoryNamesMemory13Name
				RollCallString,
			iqhco31MemoriesMemoryNamesMemory14Name
				RollCallString,
			iqhco31MemoriesMemoryNamesMemory15Name
				RollCallString,
			iqhco31MemoriesMemoryNamesMemory16Name
				RollCallString,
			iqhco31LoggingLogMiscSlotStarten
				INTEGER,
			iqhco31LoggingLogMiscSlotStart
				RollCallString,
			iqhco31LoggingLogMiscSlotWidthen
				INTEGER,
			iqhco31LoggingLogMiscSlotWidth
				RollCallString,
			iqhco31LoggingLogMiscRearStatusen
				INTEGER,
			iqhco31LoggingLogMiscRearStatus
				RollCallString,
			iqhco31LoggingLogMiscRearIDen
				INTEGER,
			iqhco31LoggingLogMiscRearID
				RollCallString,
			iqhco31LoggingLogMiscFirmwareVersionen
				INTEGER,
			iqhco31LoggingLogMiscFirmwareVersion
				RollCallString,
			iqhco31LoggingLogMiscLicensedOptionsen
				INTEGER,
			iqhco31LoggingLogMiscLicensedOptions
				RollCallString,
			iqhco31LoggingLogMiscBuildNumberen
				INTEGER,
			iqhco31LoggingLogMiscBuildNumber
				RollCallString,
			iqhco31LoggingLogMiscOSVersionen
				INTEGER,
			iqhco31LoggingLogMiscOSVersion
				RollCallString,
			iqhco31LoggingLogMiscHardwareVersionen
				INTEGER,
			iqhco31LoggingLogMiscHardwareVersion
				RollCallString,
			iqhco31LoggingLogMiscUptimeen
				INTEGER,
			iqhco31LoggingLogMiscUptime
				RollCallString,
			iqhco31LoggingLogMiscSerialNumberen
				INTEGER,
			iqhco31LoggingLogMiscSerialNumber
				RollCallString,
			iqhco31LoggingLogVideoInput1Input1en
				INTEGER,
			iqhco31LoggingLogVideoInput1Input1
				RollCallString,
			iqhco31LoggingLogVideoInput1Input1Standarden
				INTEGER,
			iqhco31LoggingLogVideoInput1Input1Standard
				RollCallString,
			iqhco31LoggingLogVideoInput1In1SDIERRSen
				INTEGER,
			iqhco31LoggingLogVideoInput1In1SDIERRS
				RollCallString,
			iqhco31LoggingLogVideoInput1In1SDIANCERRSen
				INTEGER,
			iqhco31LoggingLogVideoInput1In1SDIANCERRS
				RollCallString,
			iqhco31LoggingLogVideoInput1Input1Typeen
				INTEGER,
			iqhco31LoggingLogVideoInput1Input1Type
				RollCallString,
			iqhco31LoggingLogVideoInput1Input1Identen
				INTEGER,
			iqhco31LoggingLogVideoInput1Input1Ident
				RollCallString,
			iqhco31LoggingLogVideoInput1In1BlackERRSen
				INTEGER,
			iqhco31LoggingLogVideoInput1In1BlackERRS
				RollCallString,
			iqhco31LoggingLogVideoInput1In1FreezeERRSen
				INTEGER,
			iqhco31LoggingLogVideoInput1In1FreezeERRS
				RollCallString,
			iqhco31LoggingLogVideoInput2Input2en
				INTEGER,
			iqhco31LoggingLogVideoInput2Input2
				RollCallString,
			iqhco31LoggingLogVideoInput2Input2Standarden
				INTEGER,
			iqhco31LoggingLogVideoInput2Input2Standard
				RollCallString,
			iqhco31LoggingLogVideoInput2In2SDIERRSen
				INTEGER,
			iqhco31LoggingLogVideoInput2In2SDIERRS
				RollCallString,
			iqhco31LoggingLogVideoInput2In2SDIANCERRSen
				INTEGER,
			iqhco31LoggingLogVideoInput2In2SDIANCERRS
				RollCallString,
			iqhco31LoggingLogVideoInput2Input2Typeen
				INTEGER,
			iqhco31LoggingLogVideoInput2Input2Type
				RollCallString,
			iqhco31LoggingLogVideoInput2Input2Identen
				INTEGER,
			iqhco31LoggingLogVideoInput2Input2Ident
				RollCallString,
			iqhco31LoggingLogVideoInput2In2BlackERRSen
				INTEGER,
			iqhco31LoggingLogVideoInput2In2BlackERRS
				RollCallString,
			iqhco31LoggingLogVideoInput2In2FreezeERRSen
				INTEGER,
			iqhco31LoggingLogVideoInput2In2FreezeERRS
				RollCallString,
			iqhco31LoggingLogReferenceRef1Stateen
				INTEGER,
			iqhco31LoggingLogReferenceRef1State
				RollCallString,
			iqhco31LoggingLogReferenceRef1Standarden
				INTEGER,
			iqhco31LoggingLogReferenceRef1Standard
				RollCallString,
			iqhco31LoggingLogReferenceRef1Typeen
				INTEGER,
			iqhco31LoggingLogReferenceRef1Type
				RollCallString,
			iqhco31LoggingLogReferenceGenlock1Stateen
				INTEGER,
			iqhco31LoggingLogReferenceGenlock1State
				RollCallString,
			iqhco31LoggingLogAudioInput1Input1Audio11en
				INTEGER,
			iqhco31LoggingLogAudioInput1Input1Audio11
				RollCallString,
			iqhco31LoggingLogAudioInput1Input1Audio12en
				INTEGER,
			iqhco31LoggingLogAudioInput1Input1Audio12
				RollCallString,
			iqhco31LoggingLogAudioInput1Input1Audio21en
				INTEGER,
			iqhco31LoggingLogAudioInput1Input1Audio21
				RollCallString,
			iqhco31LoggingLogAudioInput1Input1Audio22en
				INTEGER,
			iqhco31LoggingLogAudioInput1Input1Audio22
				RollCallString,
			iqhco31LoggingLogAudioInput1Input1Audio31en
				INTEGER,
			iqhco31LoggingLogAudioInput1Input1Audio31
				RollCallString,
			iqhco31LoggingLogAudioInput1Input1Audio32en
				INTEGER,
			iqhco31LoggingLogAudioInput1Input1Audio32
				RollCallString,
			iqhco31LoggingLogAudioInput1Input1Audio41en
				INTEGER,
			iqhco31LoggingLogAudioInput1Input1Audio41
				RollCallString,
			iqhco31LoggingLogAudioInput1Input1Audio42en
				INTEGER,
			iqhco31LoggingLogAudioInput1Input1Audio42
				RollCallString,
			iqhco31LoggingLogAudioInput1Input1Audio51en
				INTEGER,
			iqhco31LoggingLogAudioInput1Input1Audio51
				RollCallString,
			iqhco31LoggingLogAudioInput1Input1Audio52en
				INTEGER,
			iqhco31LoggingLogAudioInput1Input1Audio52
				RollCallString,
			iqhco31LoggingLogAudioInput1Input1Audio61en
				INTEGER,
			iqhco31LoggingLogAudioInput1Input1Audio61
				RollCallString,
			iqhco31LoggingLogAudioInput1Input1Audio62en
				INTEGER,
			iqhco31LoggingLogAudioInput1Input1Audio62
				RollCallString,
			iqhco31LoggingLogAudioInput1Input1Audio71en
				INTEGER,
			iqhco31LoggingLogAudioInput1Input1Audio71
				RollCallString,
			iqhco31LoggingLogAudioInput1Input1Audio72en
				INTEGER,
			iqhco31LoggingLogAudioInput1Input1Audio72
				RollCallString,
			iqhco31LoggingLogAudioInput1Input1Audio81en
				INTEGER,
			iqhco31LoggingLogAudioInput1Input1Audio81
				RollCallString,
			iqhco31LoggingLogAudioInput1Input1Audio82en
				INTEGER,
			iqhco31LoggingLogAudioInput1Input1Audio82
				RollCallString,
			iqhco31LoggingLogAudioInput2Input2Audio11en
				INTEGER,
			iqhco31LoggingLogAudioInput2Input2Audio11
				RollCallString,
			iqhco31LoggingLogAudioInput2Input2Audio12en
				INTEGER,
			iqhco31LoggingLogAudioInput2Input2Audio12
				RollCallString,
			iqhco31LoggingLogAudioInput2Input2Audio21en
				INTEGER,
			iqhco31LoggingLogAudioInput2Input2Audio21
				RollCallString,
			iqhco31LoggingLogAudioInput2Input2Audio22en
				INTEGER,
			iqhco31LoggingLogAudioInput2Input2Audio22
				RollCallString,
			iqhco31LoggingLogAudioInput2Input2Audio31en
				INTEGER,
			iqhco31LoggingLogAudioInput2Input2Audio31
				RollCallString,
			iqhco31LoggingLogAudioInput2Input2Audio32en
				INTEGER,
			iqhco31LoggingLogAudioInput2Input2Audio32
				RollCallString,
			iqhco31LoggingLogAudioInput2Input2Audio41en
				INTEGER,
			iqhco31LoggingLogAudioInput2Input2Audio41
				RollCallString,
			iqhco31LoggingLogAudioInput2Input2Audio42en
				INTEGER,
			iqhco31LoggingLogAudioInput2Input2Audio42
				RollCallString,
			iqhco31LoggingLogAudioInput2Input2Audio51en
				INTEGER,
			iqhco31LoggingLogAudioInput2Input2Audio51
				RollCallString,
			iqhco31LoggingLogAudioInput2Input2Audio52en
				INTEGER,
			iqhco31LoggingLogAudioInput2Input2Audio52
				RollCallString,
			iqhco31LoggingLogAudioInput2Input2Audio61en
				INTEGER,
			iqhco31LoggingLogAudioInput2Input2Audio61
				RollCallString,
			iqhco31LoggingLogAudioInput2Input2Audio62en
				INTEGER,
			iqhco31LoggingLogAudioInput2Input2Audio62
				RollCallString,
			iqhco31LoggingLogAudioInput2Input2Audio71en
				INTEGER,
			iqhco31LoggingLogAudioInput2Input2Audio71
				RollCallString,
			iqhco31LoggingLogAudioInput2Input2Audio72en
				INTEGER,
			iqhco31LoggingLogAudioInput2Input2Audio72
				RollCallString,
			iqhco31LoggingLogAudioInput2Input2Audio81en
				INTEGER,
			iqhco31LoggingLogAudioInput2Input2Audio81
				RollCallString,
			iqhco31LoggingLogAudioInput2Input2Audio82en
				INTEGER,
			iqhco31LoggingLogAudioInput2Input2Audio82
				RollCallString,
			iqhco31LoggingLogVideoOutputOutput1Typeen
				INTEGER,
			iqhco31LoggingLogVideoOutputOutput1Type
				RollCallString,
			iqhco31LoggingLogVideoOutputOutput1Stateen
				INTEGER,
			iqhco31LoggingLogVideoOutputOutput1State
				RollCallString,
			iqhco31LoggingLogVideoOutputOutput1Stden
				INTEGER,
			iqhco31LoggingLogVideoOutputOutput1Std
				RollCallString,
			iqhco31LoggingLogVideoOutputOutput1en
				INTEGER,
			iqhco31LoggingLogVideoOutputOutput1
				RollCallString,
			iqhco31LoggingLogChangeoverMasterStateen
				INTEGER,
			iqhco31LoggingLogChangeoverMasterState
				RollCallString,
			iqhco31LoggingLogChangeoverBackupStateen
				INTEGER,
			iqhco31LoggingLogChangeoverBackupState
				RollCallString,
			iqhco31LoggingLogChangeoverRulesStateen
				INTEGER,
			iqhco31LoggingLogChangeoverRulesState
				RollCallString,
			iqhco31LoggingLogChangeoverGpi1Stateen
				INTEGER,
			iqhco31LoggingLogChangeoverGpi1State
				RollCallString,
			iqhco31LoggingLogChangeoverGpi2Stateen
				INTEGER,
			iqhco31LoggingLogChangeoverGpi2State
				RollCallString,
			iqhco31LoggingLogChangeoverGpi3Stateen
				INTEGER,
			iqhco31LoggingLogChangeoverGpi3State
				RollCallString,
			iqhco31LoggingLogChangeoverGpi4Stateen
				INTEGER,
			iqhco31LoggingLogChangeoverGpi4State
				RollCallString,
			iqhco31LoggingLogChangeoverRollCall101State4420
				INTEGER,
			iqhco31LoggingLogChangeoverRollCall101State4421
				RollCallString,
			iqhco31LoggingLogChangeoverRollCall102State4424
				INTEGER,
			iqhco31LoggingLogChangeoverRollCall102State4425
				RollCallString,
			iqhco31LoggingLogChangeoverRollCall103State4428
				INTEGER,
			iqhco31LoggingLogChangeoverRollCall103State4429
				RollCallString,
			iqhco31LoggingLogChangeoverRollCall104State4432
				INTEGER,
			iqhco31LoggingLogChangeoverRollCall104State4433
				RollCallString,
			iqhco31LoggingLogChangeoverRollTrkOut1State4436
				INTEGER,
			iqhco31LoggingLogChangeoverRollTrkOut1State4437
				RollCallString,
			iqhco31LoggingLogChangeoverRollTrkOut2State4440
				INTEGER,
			iqhco31LoggingLogChangeoverRollTrkOut2State4441
				RollCallString,
			iqhco31LoggingLogChangeoverRollTrkOut3State4444
				INTEGER,
			iqhco31LoggingLogChangeoverRollTrkOut3State4445
				RollCallString,
			iqhco31LoggingLogChangeoverRollTrkOut4State4448
				INTEGER,
			iqhco31LoggingLogChangeoverRollTrkOut4State4449
				RollCallString,
			iqhco31SetupRollTracksRollTrackIndex1495
				INTEGER,
			iqhco31SetupRollTracksRollTrackSource1496
				INTEGER,
			iqhco31SetupRollTracksRollTrackDisable
				INTEGER,
			iqhco31SetupRollTracksRollTrackAddress1497
				RollCallString,
			iqhco31SetupRollTracksRollTrackCommand1498
				RollCallString,
			iqhco31SetupRollTracksRollTrackSending
				RollCallString,
			iqhco31SetupRollTracksRollTrackStatus
				RollCallString,
			iqhco31SetupRollTracksRollTrackIndex2870
				INTEGER,
			iqhco31SetupRollTracksRollTrackSource2871
				INTEGER,
			iqhco31SetupRollTracksRollTrackAddress2872
				RollCallString,
			iqhco31SetupRollTracksRollTrackCommand2873
				RollCallString,
			iqhco31CommonStatusStatusDisplay
				INTEGER,
			iqhco31CommonStatusProduct
				RollCallString,
			iqhco31CommonStatusSoftwareVersion
				RollCallString,
			iqhco31CommonStatusSerialNo
				RollCallString,
			iqhco31CommonStatusFactoryDefaults
				INTEGER,
			iqhco31CommonStatusDefaultSetting
				INTEGER,
			iqhco31CommonStatusRestart
				INTEGER,
			iqhco31CommonStatusBuild
				RollCallString,
			iqhco31CommonStatusPCB
				RollCallString,
			iqhco31CommonStatusKOSVersion
				RollCallString,
			iqhco31CommonStatusFirmwareVersion
				RollCallString,
			iqhco31CommonStatusUpTime
				RollCallString
		}

	iqhco31SlotIndex OBJECT-TYPE
		SYNTAX		Unsigned32
		MAX-ACCESS		not-accessible
		STATUS			current
		DESCRIPTION
				"The unique Index value for each slot.  Its value
					ranges between 1 and the value of slotNumber."
		::= { iqhco31CmdEntry 0 }


	iqhco31MasterValidValidInputStds108050pB OBJECT-TYPE
		SYNTAX		INTEGER { disable(0), enable(1) }
		MAX-ACCESS		read-write
		STATUS			current
		DESCRIPTION
				"TYPE: - Checkbox
				 PAGE: - Master- Video Master- Master Valid
					1080/50p-B  cmdID= 5225 "
		::= { iqhco31CmdEntry 5225 }


	iqhco31MasterValidValidInputStds108059pB OBJECT-TYPE
		SYNTAX		INTEGER { disable(0), enable(1) }
		MAX-ACCESS		read-write
		STATUS			current
		DESCRIPTION
				"TYPE: - Checkbox
				 PAGE: - Master- Video Master- Master Valid
					1080/59p-B  cmdID= 5226 "
		::= { iqhco31CmdEntry 5226 }


	iqhco31MasterValidValidInputStds108050pA OBJECT-TYPE
		SYNTAX		INTEGER { disable(0), enable(1) }
		MAX-ACCESS		read-write
		STATUS			current
		DESCRIPTION
				"TYPE: - Checkbox
				 PAGE: - Master- Video Master- Master Valid
					1080/50p-A  cmdID= 5222 "
		::= { iqhco31CmdEntry 5222 }


	iqhco31MasterValidValidInputStds108059pA OBJECT-TYPE
		SYNTAX		INTEGER { disable(0), enable(1) }
		MAX-ACCESS		read-write
		STATUS			current
		DESCRIPTION
				"TYPE: - Checkbox
				 PAGE: - Master- Video Master- Master Valid
					1080/59p-A  cmdID= 5223 "
		::= { iqhco31CmdEntry 5223 }


	iqhco31MasterValidValidInputStds108029i OBJECT-TYPE
		SYNTAX		INTEGER { disable(0), enable(1) }
		MAX-ACCESS		read-write
		STATUS			current
		DESCRIPTION
				"TYPE: - Checkbox
				 PAGE: - Master- Video Master- Master Valid
					1080/29i  cmdID= 5218 "
		::= { iqhco31CmdEntry 5218 }


	iqhco31MasterValidValidInputStds108025i OBJECT-TYPE
		SYNTAX		INTEGER { disable(0), enable(1) }
		MAX-ACCESS		read-write
		STATUS			current
		DESCRIPTION
				"TYPE: - Checkbox
				 PAGE: - Master- Video Master- Master Valid
					1080/25i  cmdID= 5217 "
		::= { iqhco31CmdEntry 5217 }


	iqhco31MasterValidValidInputStds72059p OBJECT-TYPE
		SYNTAX		INTEGER { disable(0), enable(1) }
		MAX-ACCESS		read-write
		STATUS			current
		DESCRIPTION
				"TYPE: - Checkbox
				 PAGE: - Master- Video Master- Master Valid
					720/59p  cmdID= 5210 "
		::= { iqhco31CmdEntry 5210 }


	iqhco31MasterValidValidInputStds72050p OBJECT-TYPE
		SYNTAX		INTEGER { disable(0), enable(1) }
		MAX-ACCESS		read-write
		STATUS			current
		DESCRIPTION
				"TYPE: - Checkbox
				 PAGE: - Master- Video Master- Master Valid
					720/50p  cmdID= 5209 "
		::= { iqhco31CmdEntry 5209 }


	iqhco31MasterValidValidInputStds52529i OBJECT-TYPE
		SYNTAX		INTEGER { disable(0), enable(1) }
		MAX-ACCESS		read-write
		STATUS			current
		DESCRIPTION
				"TYPE: - Checkbox
				 PAGE: - Master- Video Master- Master Valid
					525/29i  cmdID= 5203 "
		::= { iqhco31CmdEntry 5203 }


	iqhco31MasterValidValidInputStds62525i OBJECT-TYPE
		SYNTAX		INTEGER { disable(0), enable(1) }
		MAX-ACCESS		read-write
		STATUS			current
		DESCRIPTION
				"TYPE: - Checkbox
				 PAGE: - Master- Video Master- Master Valid
					625/25i  cmdID= 5202 "
		::= { iqhco31CmdEntry 5202 }


	iqhco31MasterValidCRCEDHErroredsecErrSecEnable OBJECT-TYPE
		SYNTAX		INTEGER { disable(0), enable(1) }
		MAX-ACCESS		read-write
		STATUS			current
		DESCRIPTION
				"TYPE: - Checkbox
				 PAGE: - Master- Video Master- Master Valid
					ErrSec Enable  cmdID= 5354 "
		::= { iqhco31CmdEntry 5354 }


	iqhco31MasterValidCRCEDHErroredsecErrSecDecision OBJECT-TYPE
		SYNTAX		RollCallString
		MAX-ACCESS		read-only
		STATUS			current
		DESCRIPTION
				"TYPE: - Display
				 PAGE: - Master- Video Master- Master Valid
					ErrSec Decision  cmdID= 5353  format=   "
		::= { iqhco31CmdEntry 5353 }


	iqhco31MasterValidCRCEDHErroredsecCarrierDecision OBJECT-TYPE
		SYNTAX		RollCallString
		MAX-ACCESS		read-only
		STATUS			current
		DESCRIPTION
				"TYPE: - Display
				 PAGE: - Master- Video Master- Master Valid
					Carrier Decision  cmdID= 5351  format=   "
		::= { iqhco31CmdEntry 5351 }


	iqhco31MasterValidCRCEDHErroredsecStdDecision OBJECT-TYPE
		SYNTAX		RollCallString
		MAX-ACCESS		read-only
		STATUS			current
		DESCRIPTION
				"TYPE: - Display
				 PAGE: - Master- Video Master- Master Valid
					Std Decision  cmdID= 5352  format=   "
		::= { iqhco31CmdEntry 5352 }


	iqhco31MasterValidCRCEDHErroredsecInputStd OBJECT-TYPE
		SYNTAX		RollCallString
		MAX-ACCESS		read-only
		STATUS			current
		DESCRIPTION
				"TYPE: - Display
				 PAGE: - Master- Video Master- Master Valid
					Input Std  cmdID= 5399  format=   "
		::= { iqhco31CmdEntry 5399 }


	iqhco31MasterValidCRCEDHErroredsecFreezeEnable OBJECT-TYPE
		SYNTAX		INTEGER { disable(0), enable(1) }
		MAX-ACCESS		read-write
		STATUS			current
		DESCRIPTION
				"TYPE: - Checkbox
				 PAGE: - Master- Video Master- Master Valid
					Freeze Enable  cmdID= 5356 "
		::= { iqhco31CmdEntry 5356 }


	iqhco31MasterValidCRCEDHErroredsecFreezeDecision OBJECT-TYPE
		SYNTAX		RollCallString
		MAX-ACCESS		read-only
		STATUS			current
		DESCRIPTION
				"TYPE: - Display
				 PAGE: - Master- Video Master- Master Valid
					Freeze Decision  cmdID= 5355  format=   "
		::= { iqhco31CmdEntry 5355 }


	iqhco31MasterValidCRCEDHErroredsecBlackEnable OBJECT-TYPE
		SYNTAX		INTEGER { disable(0), enable(1) }
		MAX-ACCESS		read-write
		STATUS			current
		DESCRIPTION
				"TYPE: - Checkbox
				 PAGE: - Master- Video Master- Master Valid
					Black Enable  cmdID= 5358 "
		::= { iqhco31CmdEntry 5358 }


	iqhco31MasterValidCRCEDHErroredsecBlackDecision OBJECT-TYPE
		SYNTAX		RollCallString
		MAX-ACCESS		read-only
		STATUS			current
		DESCRIPTION
				"TYPE: - Display
				 PAGE: - Master- Video Master- Master Valid
					Black Decision  cmdID= 5357  format=   "
		::= { iqhco31CmdEntry 5357 }


	iqhco31MasterValidCRCEDHErroredsecBlackThreshold OBJECT-TYPE
		SYNTAX		INTEGER
		MAX-ACCESS		read-write
		STATUS			current
		DESCRIPTION
				"TYPE: - Number
				 PAGE: - Master- Video Master- Master Valid
					Black Threshold  cmdID= 5578  min= 0  max= 153  step= 1  format= %.0f mV  div_scale= 1 
					Min = 0 mV  Max = 153 mV  Step = 1 mV "
		::= { iqhco31CmdEntry 5578 }


	iqhco31MasterValidVideoValidTimersBlackFailDelay OBJECT-TYPE
		SYNTAX		INTEGER
		MAX-ACCESS		read-write
		STATUS			current
		DESCRIPTION
				"TYPE: - Number
				 PAGE: - Master- Video Master- Master Valid
					Black Fail Delay  cmdID= 5550  min= 2  max= 100  step= 1  format= %.1f s  div_scale= 10 
					Min = 0.2 s  Max = 10.0 s  Step = 0.1 s "
		::= { iqhco31CmdEntry 5550 }


	iqhco31MasterValidVideoValidTimersBlackRecoverDelay OBJECT-TYPE
		SYNTAX		INTEGER
		MAX-ACCESS		read-write
		STATUS			current
		DESCRIPTION
				"TYPE: - Number
				 PAGE: - Master- Video Master- Master Valid
					Black Recover Delay  cmdID= 5551  min= 2  max= 100  step= 1  format= %.1f s  div_scale= 10 
					Min = 0.2 s  Max = 10.0 s  Step = 0.1 s "
		::= { iqhco31CmdEntry 5551 }


	iqhco31MasterValidVideoValidTimersFreezeFailDelay OBJECT-TYPE
		SYNTAX		INTEGER
		MAX-ACCESS		read-write
		STATUS			current
		DESCRIPTION
				"TYPE: - Number
				 PAGE: - Master- Video Master- Master Valid
					Freeze Fail Delay  cmdID= 5552  min= 2  max= 100  step= 1  format= %.1f s  div_scale= 10 
					Min = 0.2 s  Max = 10.0 s  Step = 0.1 s "
		::= { iqhco31CmdEntry 5552 }


	iqhco31MasterValidVideoValidTimersFreezeRecoverDela OBJECT-TYPE
		SYNTAX		INTEGER
		MAX-ACCESS		read-write
		STATUS			current
		DESCRIPTION
				"TYPE: - Number
				 PAGE: - Master- Video Master- Master Valid
					Freeze Recover Dela  cmdID= 5553  min= 2  max= 100  step= 1  format= %.1f s  div_scale= 10 
					Min = 0.2 s  Max = 10.0 s  Step = 0.1 s "
		::= { iqhco31CmdEntry 5553 }


	iqhco31MasterValidVideoValidTimersErrsecFailDelay OBJECT-TYPE
		SYNTAX		INTEGER
		MAX-ACCESS		read-write
		STATUS			current
		DESCRIPTION
				"TYPE: - Number
				 PAGE: - Master- Video Master- Master Valid
					Errsec Fail Delay  cmdID= 5554  min= 0  max= 10  step= 1  format= %.0f s  div_scale= 1 
					Min = 0 s  Max = 10 s  Step = 1 s "
		::= { iqhco31CmdEntry 5554 }


	iqhco31MasterValidVideoValidTimersErrsecRecoverDela OBJECT-TYPE
		SYNTAX		INTEGER
		MAX-ACCESS		read-write
		STATUS			current
		DESCRIPTION
				"TYPE: - Number
				 PAGE: - Master- Video Master- Master Valid
					Errsec Recover Dela  cmdID= 5555  min= 0  max= 10  step= 1  format= %.0f s  div_scale= 1 
					Min = 0 s  Max = 10 s  Step = 1 s "
		::= { iqhco31CmdEntry 5555 }


	iqhco31MasterValidVideoValidTimersValidFailDelay OBJECT-TYPE
		SYNTAX		INTEGER
		MAX-ACCESS		read-write
		STATUS			current
		DESCRIPTION
				"TYPE: - Number
				 PAGE: - Master- Video Master- Master Valid
					Valid Fail Delay  cmdID= 5562  min= 0  max= 100  step= 1  format= %.1f s  div_scale= 10 
					Min = 0.0 s  Max = 10.0 s  Step = 0.1 s "
		::= { iqhco31CmdEntry 5562 }


	iqhco31MasterValidVideoValidTimersValidRecoverDelay OBJECT-TYPE
		SYNTAX		INTEGER
		MAX-ACCESS		read-write
		STATUS			current
		DESCRIPTION
				"TYPE: - Number
				 PAGE: - Master- Video Master- Master Valid
					Valid Recover Delay  cmdID= 5563  min= 2  max= 100  step= 1  format= %.1f s  div_scale= 10 
					Min = 0.2 s  Max = 10.0 s  Step = 0.1 s "
		::= { iqhco31CmdEntry 5563 }


	iqhco31MasterValidValidAudioDecision OBJECT-TYPE
		SYNTAX		RollCallString
		MAX-ACCESS		read-only
		STATUS			current
		DESCRIPTION
				"TYPE: - Display
				 PAGE: - Master- Video Master- Master Valid- Valid Audio
					Decision  cmdID= 5350  format=   "
		::= { iqhco31CmdEntry 5350 }


	iqhco31ValidAudioMasterPair1Decision OBJECT-TYPE
		SYNTAX		RollCallString
		MAX-ACCESS		read-only
		STATUS			current
		DESCRIPTION
				"TYPE: - Display
				 PAGE: - Master- Video Master- Master Valid- Valid Audio
					Decision  cmdID= 5359  format=   "
		::= { iqhco31CmdEntry 5359 }


	iqhco31ValidAudioMasterPair1CurrentType OBJECT-TYPE
		SYNTAX		RollCallString
		MAX-ACCESS		read-only
		STATUS			current
		DESCRIPTION
				"TYPE: - Display
				 PAGE: - Master- Video Master- Master Valid- Valid Audio
					Current Type  cmdID= 5360  format=   "
		::= { iqhco31CmdEntry 5360 }


	iqhco31ValidAudioMasterPair1 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5361  value= 0  
					DolbyE  cmdID= 5361  value= 1  
					Data  cmdID= 5361  value= 2  
					None  cmdID= 5361  value= 3  
					Any  cmdID= 5361  value= 4  
					Ignored  cmdID= 5361  value= 5  "
		::= { iqhco31CmdEntry 5361 }


	iqhco31ValidAudioMasterPair1Ch1State OBJECT-TYPE
		SYNTAX		RollCallString
		MAX-ACCESS		read-only
		STATUS			current
		DESCRIPTION
				"TYPE: - Display
				 PAGE: - Master- Video Master- Master Valid- Valid Audio
					Ch1 State  cmdID= 7008  format=   "
		::= { iqhco31CmdEntry 7008 }


	iqhco31ValidAudioMasterPair1Ch2State OBJECT-TYPE
		SYNTAX		RollCallString
		MAX-ACCESS		read-only
		STATUS			current
		DESCRIPTION
				"TYPE: - Display
				 PAGE: - Master- Video Master- Master Valid- Valid Audio
					Ch2 State  cmdID= 7009  format=   "
		::= { iqhco31CmdEntry 7009 }


	iqhco31ValidAudioMasterPair1Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5450 "
		::= { iqhco31CmdEntry 5450 }


	iqhco31ValidAudioMasterPair1Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5362 "
		::= { iqhco31CmdEntry 5362 }


	iqhco31ValidAudioMasterPair1Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5363 "
		::= { iqhco31CmdEntry 5363 }


	iqhco31ValidAudioMasterPair2Decision OBJECT-TYPE
		SYNTAX		RollCallString
		MAX-ACCESS		read-only
		STATUS			current
		DESCRIPTION
				"TYPE: - Display
				 PAGE: - Master- Video Master- Master Valid- Valid Audio
					Decision  cmdID= 5364  format=   "
		::= { iqhco31CmdEntry 5364 }


	iqhco31ValidAudioMasterPair2CurrentType OBJECT-TYPE
		SYNTAX		RollCallString
		MAX-ACCESS		read-only
		STATUS			current
		DESCRIPTION
				"TYPE: - Display
				 PAGE: - Master- Video Master- Master Valid- Valid Audio
					Current Type  cmdID= 5365  format=   "
		::= { iqhco31CmdEntry 5365 }


	iqhco31ValidAudioMasterPair2 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5366  value= 0  
					DolbyE  cmdID= 5366  value= 1  
					Data  cmdID= 5366  value= 2  
					None  cmdID= 5366  value= 3  
					Any  cmdID= 5366  value= 4  
					Ignored  cmdID= 5366  value= 5  "
		::= { iqhco31CmdEntry 5366 }


	iqhco31ValidAudioMasterPair2Ch1State OBJECT-TYPE
		SYNTAX		RollCallString
		MAX-ACCESS		read-only
		STATUS			current
		DESCRIPTION
				"TYPE: - Display
				 PAGE: - Master- Video Master- Master Valid- Valid Audio
					Ch1 State  cmdID= 7010  format=   "
		::= { iqhco31CmdEntry 7010 }


	iqhco31ValidAudioMasterPair2Ch2State OBJECT-TYPE
		SYNTAX		RollCallString
		MAX-ACCESS		read-only
		STATUS			current
		DESCRIPTION
				"TYPE: - Display
				 PAGE: - Master- Video Master- Master Valid- Valid Audio
					Ch2 State  cmdID= 7011  format=   "
		::= { iqhco31CmdEntry 7011 }


	iqhco31ValidAudioMasterPair2Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5451 "
		::= { iqhco31CmdEntry 5451 }


	iqhco31ValidAudioMasterPair2Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5367 "
		::= { iqhco31CmdEntry 5367 }


	iqhco31ValidAudioMasterPair2Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5368 "
		::= { iqhco31CmdEntry 5368 }


	iqhco31ValidAudioMasterPair3Decision OBJECT-TYPE
		SYNTAX		RollCallString
		MAX-ACCESS		read-only
		STATUS			current
		DESCRIPTION
				"TYPE: - Display
				 PAGE: - Master- Video Master- Master Valid- Valid Audio
					Decision  cmdID= 5369  format=   "
		::= { iqhco31CmdEntry 5369 }


	iqhco31ValidAudioMasterPair3CurrentType OBJECT-TYPE
		SYNTAX		RollCallString
		MAX-ACCESS		read-only
		STATUS			current
		DESCRIPTION
				"TYPE: - Display
				 PAGE: - Master- Video Master- Master Valid- Valid Audio
					Current Type  cmdID= 5370  format=   "
		::= { iqhco31CmdEntry 5370 }


	iqhco31ValidAudioMasterPair3 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5371  value= 0  
					DolbyE  cmdID= 5371  value= 1  
					Data  cmdID= 5371  value= 2  
					None  cmdID= 5371  value= 3  
					Any  cmdID= 5371  value= 4  
					Ignored  cmdID= 5371  value= 5  "
		::= { iqhco31CmdEntry 5371 }


	iqhco31ValidAudioMasterPair3Ch1State OBJECT-TYPE
		SYNTAX		RollCallString
		MAX-ACCESS		read-only
		STATUS			current
		DESCRIPTION
				"TYPE: - Display
				 PAGE: - Master- Video Master- Master Valid- Valid Audio
					Ch1 State  cmdID= 7012  format=   "
		::= { iqhco31CmdEntry 7012 }


	iqhco31ValidAudioMasterPair3Ch2State OBJECT-TYPE
		SYNTAX		RollCallString
		MAX-ACCESS		read-only
		STATUS			current
		DESCRIPTION
				"TYPE: - Display
				 PAGE: - Master- Video Master- Master Valid- Valid Audio
					Ch2 State  cmdID= 7013  format=   "
		::= { iqhco31CmdEntry 7013 }


	iqhco31ValidAudioMasterPair3Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5452 "
		::= { iqhco31CmdEntry 5452 }


	iqhco31ValidAudioMasterPair3Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5372 "
		::= { iqhco31CmdEntry 5372 }


	iqhco31ValidAudioMasterPair3Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5373 "
		::= { iqhco31CmdEntry 5373 }


	iqhco31ValidAudioMasterPair4Decision OBJECT-TYPE
		SYNTAX		RollCallString
		MAX-ACCESS		read-only
		STATUS			current
		DESCRIPTION
				"TYPE: - Display
				 PAGE: - Master- Video Master- Master Valid- Valid Audio
					Decision  cmdID= 5374  format=   "
		::= { iqhco31CmdEntry 5374 }


	iqhco31ValidAudioMasterPair4CurrentType OBJECT-TYPE
		SYNTAX		RollCallString
		MAX-ACCESS		read-only
		STATUS			current
		DESCRIPTION
				"TYPE: - Display
				 PAGE: - Master- Video Master- Master Valid- Valid Audio
					Current Type  cmdID= 5375  format=   "
		::= { iqhco31CmdEntry 5375 }


	iqhco31ValidAudioMasterPair4 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5376  value= 0  
					DolbyE  cmdID= 5376  value= 1  
					Data  cmdID= 5376  value= 2  
					None  cmdID= 5376  value= 3  
					Any  cmdID= 5376  value= 4  
					Ignored  cmdID= 5376  value= 5  "
		::= { iqhco31CmdEntry 5376 }


	iqhco31ValidAudioMasterPair4Ch1State OBJECT-TYPE
		SYNTAX		RollCallString
		MAX-ACCESS		read-only
		STATUS			current
		DESCRIPTION
				"TYPE: - Display
				 PAGE: - Master- Video Master- Master Valid- Valid Audio
					Ch1 State  cmdID= 7014  format=   "
		::= { iqhco31CmdEntry 7014 }


	iqhco31ValidAudioMasterPair4Ch2State OBJECT-TYPE
		SYNTAX		RollCallString
		MAX-ACCESS		read-only
		STATUS			current
		DESCRIPTION
				"TYPE: - Display
				 PAGE: - Master- Video Master- Master Valid- Valid Audio
					Ch2 State  cmdID= 7015  format=   "
		::= { iqhco31CmdEntry 7015 }


	iqhco31ValidAudioMasterPair4Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5453 "
		::= { iqhco31CmdEntry 5453 }


	iqhco31ValidAudioMasterPair4Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5377 "
		::= { iqhco31CmdEntry 5377 }


	iqhco31ValidAudioMasterPair4Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5378 "
		::= { iqhco31CmdEntry 5378 }


	iqhco31ValidAudioMasterPair5Decision OBJECT-TYPE
		SYNTAX		RollCallString
		MAX-ACCESS		read-only
		STATUS			current
		DESCRIPTION
				"TYPE: - Display
				 PAGE: - Master- Video Master- Master Valid- Valid Audio
					Decision  cmdID= 5379  format=   "
		::= { iqhco31CmdEntry 5379 }


	iqhco31ValidAudioMasterPair5CurrentType OBJECT-TYPE
		SYNTAX		RollCallString
		MAX-ACCESS		read-only
		STATUS			current
		DESCRIPTION
				"TYPE: - Display
				 PAGE: - Master- Video Master- Master Valid- Valid Audio
					Current Type  cmdID= 5380  format=   "
		::= { iqhco31CmdEntry 5380 }


	iqhco31ValidAudioMasterPair5 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5381  value= 0  
					DolbyE  cmdID= 5381  value= 1  
					Data  cmdID= 5381  value= 2  
					None  cmdID= 5381  value= 3  
					Any  cmdID= 5381  value= 4  
					Ignored  cmdID= 5381  value= 5  "
		::= { iqhco31CmdEntry 5381 }


	iqhco31ValidAudioMasterPair5Ch1State OBJECT-TYPE
		SYNTAX		RollCallString
		MAX-ACCESS		read-only
		STATUS			current
		DESCRIPTION
				"TYPE: - Display
				 PAGE: - Master- Video Master- Master Valid- Valid Audio
					Ch1 State  cmdID= 7016  format=   "
		::= { iqhco31CmdEntry 7016 }


	iqhco31ValidAudioMasterPair5Ch2State OBJECT-TYPE
		SYNTAX		RollCallString
		MAX-ACCESS		read-only
		STATUS			current
		DESCRIPTION
				"TYPE: - Display
				 PAGE: - Master- Video Master- Master Valid- Valid Audio
					Ch2 State  cmdID= 7017  format=   "
		::= { iqhco31CmdEntry 7017 }


	iqhco31ValidAudioMasterPair5Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5454 "
		::= { iqhco31CmdEntry 5454 }


	iqhco31ValidAudioMasterPair5Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5382 "
		::= { iqhco31CmdEntry 5382 }


	iqhco31ValidAudioMasterPair5Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5383 "
		::= { iqhco31CmdEntry 5383 }


	iqhco31ValidAudioMasterPair6Decision OBJECT-TYPE
		SYNTAX		RollCallString
		MAX-ACCESS		read-only
		STATUS			current
		DESCRIPTION
				"TYPE: - Display
				 PAGE: - Master- Video Master- Master Valid- Valid Audio
					Decision  cmdID= 5384  format=   "
		::= { iqhco31CmdEntry 5384 }


	iqhco31ValidAudioMasterPair6CurrentType OBJECT-TYPE
		SYNTAX		RollCallString
		MAX-ACCESS		read-only
		STATUS			current
		DESCRIPTION
				"TYPE: - Display
				 PAGE: - Master- Video Master- Master Valid- Valid Audio
					Current Type  cmdID= 5385  format=   "
		::= { iqhco31CmdEntry 5385 }


	iqhco31ValidAudioMasterPair6 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5386  value= 0  
					DolbyE  cmdID= 5386  value= 1  
					Data  cmdID= 5386  value= 2  
					None  cmdID= 5386  value= 3  
					Any  cmdID= 5386  value= 4  
					Ignored  cmdID= 5386  value= 5  "
		::= { iqhco31CmdEntry 5386 }


	iqhco31ValidAudioMasterPair6Ch1State OBJECT-TYPE
		SYNTAX		RollCallString
		MAX-ACCESS		read-only
		STATUS			current
		DESCRIPTION
				"TYPE: - Display
				 PAGE: - Master- Video Master- Master Valid- Valid Audio
					Ch1 State  cmdID= 7018  format=   "
		::= { iqhco31CmdEntry 7018 }


	iqhco31ValidAudioMasterPair6Ch2State OBJECT-TYPE
		SYNTAX		RollCallString
		MAX-ACCESS		read-only
		STATUS			current
		DESCRIPTION
				"TYPE: - Display
				 PAGE: - Master- Video Master- Master Valid- Valid Audio
					Ch2 State  cmdID= 7019  format=   "
		::= { iqhco31CmdEntry 7019 }


	iqhco31ValidAudioMasterPair6Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5455 "
		::= { iqhco31CmdEntry 5455 }


	iqhco31ValidAudioMasterPair6Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5387 "
		::= { iqhco31CmdEntry 5387 }


	iqhco31ValidAudioMasterPair6Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5388 "
		::= { iqhco31CmdEntry 5388 }


	iqhco31ValidAudioMasterPair7Decision OBJECT-TYPE
		SYNTAX		RollCallString
		MAX-ACCESS		read-only
		STATUS			current
		DESCRIPTION
				"TYPE: - Display
				 PAGE: - Master- Video Master- Master Valid- Valid Audio
					Decision  cmdID= 5389  format=   "
		::= { iqhco31CmdEntry 5389 }


	iqhco31ValidAudioMasterPair7CurrentType OBJECT-TYPE
		SYNTAX		RollCallString
		MAX-ACCESS		read-only
		STATUS			current
		DESCRIPTION
				"TYPE: - Display
				 PAGE: - Master- Video Master- Master Valid- Valid Audio
					Current Type  cmdID= 5390  format=   "
		::= { iqhco31CmdEntry 5390 }


	iqhco31ValidAudioMasterPair7 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5391  value= 0  
					DolbyE  cmdID= 5391  value= 1  
					Data  cmdID= 5391  value= 2  
					None  cmdID= 5391  value= 3  
					Any  cmdID= 5391  value= 4  
					Ignored  cmdID= 5391  value= 5  "
		::= { iqhco31CmdEntry 5391 }


	iqhco31ValidAudioMasterPair7Ch1State OBJECT-TYPE
		SYNTAX		RollCallString
		MAX-ACCESS		read-only
		STATUS			current
		DESCRIPTION
				"TYPE: - Display
				 PAGE: - Master- Video Master- Master Valid- Valid Audio
					Ch1 State  cmdID= 7020  format=   "
		::= { iqhco31CmdEntry 7020 }


	iqhco31ValidAudioMasterPair7Ch2State OBJECT-TYPE
		SYNTAX		RollCallString
		MAX-ACCESS		read-only
		STATUS			current
		DESCRIPTION
				"TYPE: - Display
				 PAGE: - Master- Video Master- Master Valid- Valid Audio
					Ch2 State  cmdID= 7021  format=   "
		::= { iqhco31CmdEntry 7021 }


	iqhco31ValidAudioMasterPair7Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5456 "
		::= { iqhco31CmdEntry 5456 }


	iqhco31ValidAudioMasterPair7Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5392 "
		::= { iqhco31CmdEntry 5392 }


	iqhco31ValidAudioMasterPair7Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5393 "
		::= { iqhco31CmdEntry 5393 }


	iqhco31ValidAudioMasterPair8Decision OBJECT-TYPE
		SYNTAX		RollCallString
		MAX-ACCESS		read-only
		STATUS			current
		DESCRIPTION
				"TYPE: - Display
				 PAGE: - Master- Video Master- Master Valid- Valid Audio
					Decision  cmdID= 5394  format=   "
		::= { iqhco31CmdEntry 5394 }


	iqhco31ValidAudioMasterPair8CurrentType OBJECT-TYPE
		SYNTAX		RollCallString
		MAX-ACCESS		read-only
		STATUS			current
		DESCRIPTION
				"TYPE: - Display
				 PAGE: - Master- Video Master- Master Valid- Valid Audio
					Current Type  cmdID= 5395  format=   "
		::= { iqhco31CmdEntry 5395 }


	iqhco31ValidAudioMasterPair8 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5396  value= 0  
					DolbyE  cmdID= 5396  value= 1  
					Data  cmdID= 5396  value= 2  
					None  cmdID= 5396  value= 3  
					Any  cmdID= 5396  value= 4  
					Ignored  cmdID= 5396  value= 5  "
		::= { iqhco31CmdEntry 5396 }


	iqhco31ValidAudioMasterPair8Ch1State OBJECT-TYPE
		SYNTAX		RollCallString
		MAX-ACCESS		read-only
		STATUS			current
		DESCRIPTION
				"TYPE: - Display
				 PAGE: - Master- Video Master- Master Valid- Valid Audio
					Ch1 State  cmdID= 7022  format=   "
		::= { iqhco31CmdEntry 7022 }


	iqhco31ValidAudioMasterPair8Ch2State OBJECT-TYPE
		SYNTAX		RollCallString
		MAX-ACCESS		read-only
		STATUS			current
		DESCRIPTION
				"TYPE: - Display
				 PAGE: - Master- Video Master- Master Valid- Valid Audio
					Ch2 State  cmdID= 7023  format=   "
		::= { iqhco31CmdEntry 7023 }


	iqhco31ValidAudioMasterPair8Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5457 "
		::= { iqhco31CmdEntry 5457 }


	iqhco31ValidAudioMasterPair8Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5397 "
		::= { iqhco31CmdEntry 5397 }


	iqhco31ValidAudioMasterPair8Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5398 "
		::= { iqhco31CmdEntry 5398 }


	iqhco31MasterValidValidAudioLowlevel OBJECT-TYPE
		SYNTAX		INTEGER
		MAX-ACCESS		read-write
		STATUS			current
		DESCRIPTION
				"TYPE: - Number
				 PAGE: - Master- Video Master- Master Valid- Valid Audio
					Low-level  cmdID= 3061  min= -80  max= 0  step= 1  format= %1.0f dB  div_scale= 1 
					Min = -80 dB  Max = 0 dB  Step = 1 dB "
		::= { iqhco31CmdEntry 3061 }


	iqhco31MasterValidValidAudioOverloadLevel OBJECT-TYPE
		SYNTAX		INTEGER
		MAX-ACCESS		read-write
		STATUS			current
		DESCRIPTION
				"TYPE: - Number
				 PAGE: - Master- Video Master- Master Valid- Valid Audio
					Overload Level  cmdID= 3064  min= -80  max= 0  step= 1  format= %1.0f dB  div_scale= 1 
					Min = -80 dB  Max = 0 dB  Step = 1 dB "
		::= { iqhco31CmdEntry 3064 }


	iqhco31MasterValidValidAudioTypeFailTimer OBJECT-TYPE
		SYNTAX		INTEGER
		MAX-ACCESS		read-write
		STATUS			current
		DESCRIPTION
				"TYPE: - Number
				 PAGE: - Master- Video Master- Master Valid- Valid Audio
					Type Fail Timer  cmdID= 5556  min= 0  max= 10  step= 1  format= %1.0f sec  div_scale= 1 
					Min = 0 sec  Max = 10 sec  Step = 1 sec "
		::= { iqhco31CmdEntry 5556 }


	iqhco31MasterValidValidAudioTypeRecoverTimer OBJECT-TYPE
		SYNTAX		INTEGER
		MAX-ACCESS		read-write
		STATUS			current
		DESCRIPTION
				"TYPE: - Number
				 PAGE: - Master- Video Master- Master Valid- Valid Audio
					Type Recover Timer  cmdID= 5557  min= 0  max= 10  step= 1  format= %1.0f sec  div_scale= 1 
					Min = 0 sec  Max = 10 sec  Step = 1 sec "
		::= { iqhco31CmdEntry 5557 }


	iqhco31MasterValidValidAudioMuteFailTimer OBJECT-TYPE
		SYNTAX		INTEGER
		MAX-ACCESS		read-write
		STATUS			current
		DESCRIPTION
				"TYPE: - Number
				 PAGE: - Master- Video Master- Master Valid- Valid Audio
					Mute Fail Timer  cmdID= 5580  min= 0  max= 120  step= 1  format= %1.0f sec  div_scale= 1 
					Min = 0 sec  Max = 120 sec  Step = 1 sec "
		::= { iqhco31CmdEntry 5580 }


	iqhco31MasterValidValidAudioMuteRecoverTimer OBJECT-TYPE
		SYNTAX		INTEGER
		MAX-ACCESS		read-write
		STATUS			current
		DESCRIPTION
				"TYPE: - Number
				 PAGE: - Master- Video Master- Master Valid- Valid Audio
					Mute Recover Timer  cmdID= 5581  min= 0  max= 120  step= 1  format= %1.0f sec  div_scale= 1 
					Min = 0 sec  Max = 120 sec  Step = 1 sec "
		::= { iqhco31CmdEntry 5581 }


	iqhco31MasterValidValidAudioLowFailTimer OBJECT-TYPE
		SYNTAX		INTEGER
		MAX-ACCESS		read-write
		STATUS			current
		DESCRIPTION
				"TYPE: - Number
				 PAGE: - Master- Video Master- Master Valid- Valid Audio
					Low Fail Timer  cmdID= 5558  min= 0  max= 120  step= 1  format= %1.0f sec  div_scale= 1 
					Min = 0 sec  Max = 120 sec  Step = 1 sec "
		::= { iqhco31CmdEntry 5558 }


	iqhco31MasterValidValidAudioLowRecoverTimer OBJECT-TYPE
		SYNTAX		INTEGER
		MAX-ACCESS		read-write
		STATUS			current
		DESCRIPTION
				"TYPE: - Number
				 PAGE: - Master- Video Master- Master Valid- Valid Audio
					Low Recover Timer  cmdID= 5559  min= 0  max= 120  step= 1  format= %1.0f sec  div_scale= 1 
					Min = 0 sec  Max = 120 sec  Step = 1 sec "
		::= { iqhco31CmdEntry 5559 }


	iqhco31MasterValidValidAudioOverFailTimer OBJECT-TYPE
		SYNTAX		INTEGER
		MAX-ACCESS		read-write
		STATUS			current
		DESCRIPTION
				"TYPE: - Number
				 PAGE: - Master- Video Master- Master Valid- Valid Audio
					Over Fail Timer  cmdID= 5560  min= 0  max= 120  step= 1  format= %1.0f sec  div_scale= 1 
					Min = 0 sec  Max = 120 sec  Step = 1 sec "
		::= { iqhco31CmdEntry 5560 }


	iqhco31MasterValidValidAudioOverRecoverTimer OBJECT-TYPE
		SYNTAX		INTEGER
		MAX-ACCESS		read-write
		STATUS			current
		DESCRIPTION
				"TYPE: - Number
				 PAGE: - Master- Video Master- Master Valid- Valid Audio
					Over Recover Timer  cmdID= 5561  min= 0  max= 120  step= 1  format= %1.0f sec  div_scale= 1 
					Min = 0 sec  Max = 120 sec  Step = 1 sec "
		::= { iqhco31CmdEntry 5561 }


	iqhco31MasterVideoMasterDefaultOutput OBJECT-TYPE
		SYNTAX		INTEGER {
							val-Black(1),
							val-Freeze(2),
							val-Pattern(3),
							val-Master(0)
							}
		MAX-ACCESS		read-write
		STATUS			current
		DESCRIPTION
				"TYPE: - RadiobuttonList
				 PAGE: - Master- Video Master
					Default Output  cmdID= 2623 
					Black  value= 1  
					Freeze  value= 2  
					Pattern  value= 3  
					Master  value= 0  "
		::= { iqhco31CmdEntry 2623 }


	iqhco31VideoMasterVideoProcampProcAmpEnable OBJECT-TYPE
		SYNTAX		INTEGER { disable(0), enable(1) }
		MAX-ACCESS		read-write
		STATUS			current
		DESCRIPTION
				"TYPE: - Checkbox
				 PAGE: - Master- Video Master
					ProcAmp Enable  cmdID= 2864 "
		::= { iqhco31CmdEntry 2864 }


	iqhco31VideoMasterVideoProcampBlackLevel OBJECT-TYPE
		SYNTAX		INTEGER
		MAX-ACCESS		read-write
		STATUS			current
		DESCRIPTION
				"TYPE: - Number
				 PAGE: - Master- Video Master
					Black Level  cmdID= 2708  min= -1000  max= 1000  step= 8  format= %3.1fmV  div_scale= 10 
					Min = -100.0mV  Max = 100.0mV  Step = 0.8mV "
		::= { iqhco31CmdEntry 2708 }


	iqhco31VideoMasterVideoProcampHueAdjust OBJECT-TYPE
		SYNTAX		INTEGER
		MAX-ACCESS		read-write
		STATUS			current
		DESCRIPTION
				"TYPE: - Number
				 PAGE: - Master- Video Master
					Hue Adjust  cmdID= 3622  min= -180  max= 180  step= 1  format= %1.0fdeg  div_scale= 1 
					Min = -180deg  Max = 180deg  Step = 1deg "
		::= { iqhco31CmdEntry 3622 }


	iqhco31VideoMasterVideoProcampMasterVideoGain OBJECT-TYPE
		SYNTAX		INTEGER
		MAX-ACCESS		read-write
		STATUS			current
		DESCRIPTION
				"TYPE: - Number
				 PAGE: - Master- Video Master
					Master Video Gain  cmdID= 3780  min= -60  max= 60  step= 1  format= %0.1fdB  div_scale= 10 
					Min = -6.0dB  Max = 6.0dB  Step = 0.1dB "
		::= { iqhco31CmdEntry 3780 }


	iqhco31VideoMasterVideoProcampYGain OBJECT-TYPE
		SYNTAX		INTEGER
		MAX-ACCESS		read-write
		STATUS			current
		DESCRIPTION
				"TYPE: - Number
				 PAGE: - Master- Video Master
					Y Gain  cmdID= 2707  min= -60  max= 60  step= 1  format= %0.1fdB  div_scale= 10 
					Min = -6.0dB  Max = 6.0dB  Step = 0.1dB "
		::= { iqhco31CmdEntry 2707 }


	iqhco31VideoMasterVideoProcampCbCrGain OBJECT-TYPE
		SYNTAX		INTEGER
		MAX-ACCESS		read-write
		STATUS			current
		DESCRIPTION
				"TYPE: - Number
				 PAGE: - Master- Video Master
					Cb/Cr Gain  cmdID= 2706  min= -60  max= 60  step= 1  format= %0.1fdB  div_scale= 10 
					Min = -6.0dB  Max = 6.0dB  Step = 0.1dB "
		::= { iqhco31CmdEntry 2706 }


	iqhco31VideoMasterVideoProcampYCTiming OBJECT-TYPE
		SYNTAX		INTEGER
		MAX-ACCESS		read-write
		STATUS			current
		DESCRIPTION
				"TYPE: - Number
				 PAGE: - Master- Video Master
					Y/C Timing  cmdID= 2924  min= -8  max= 8  step= 2  format= %1.0f pixels  div_scale= 1 
					Min = -8 pixels  Max = 8 pixels  Step = 2 pixels "
		::= { iqhco31CmdEntry 2924 }


	iqhco31VideoMasterVideoProcampPictureposition OBJECT-TYPE
		SYNTAX		INTEGER
		MAX-ACCESS		read-write
		STATUS			current
		DESCRIPTION
				"TYPE: - Number
				 PAGE: - Master- Video Master
					Picture position  cmdID= 2709  min= -8  max= 8  step= 2  format= %1.0f pixels  div_scale= 1 
					Min = -8 pixels  Max = 8 pixels  Step = 2 pixels "
		::= { iqhco31CmdEntry 2709 }


	iqhco31VideoMasterVideoProcampModalIndex OBJECT-TYPE
		SYNTAX		INTEGER
		MAX-ACCESS		read-write
		STATUS			current
		DESCRIPTION
				"TYPE: - Number
				 PAGE: - Master- Video Master
					Modal Index  cmdID= 5006  min= 0  max= 1  step= 1  format= %1.0f  div_scale= 1 
					Min = 0  Max = 1  Step = 1 "
		::= { iqhco31CmdEntry 5006 }


	iqhco31VideoMasterVideoProcampYCTimingnm OBJECT-TYPE
		SYNTAX		INTEGER
		MAX-ACCESS		read-write
		STATUS			current
		DESCRIPTION
				"TYPE: - Number
				 PAGE: - Master- Video Master
					Y/C Timing nm  cmdID= 5008  min= -16  max= 16  step= 2  format= %1.0f pixels  div_scale= 1 
					Min = -16 pixels  Max = 16 pixels  Step = 2 pixels "
		::= { iqhco31CmdEntry 5008 }


	iqhco31VideoMasterVideoProcampPicturepositionnm OBJECT-TYPE
		SYNTAX		INTEGER
		MAX-ACCESS		read-write
		STATUS			current
		DESCRIPTION
				"TYPE: - Number
				 PAGE: - Master- Video Master
					Picture position nm  cmdID= 5007  min= -16  max= 16  step= 2  format= %1.0f pixels  div_scale= 1 
					Min = -16 pixels  Max = 16 pixels  Step = 2 pixels "
		::= { iqhco31CmdEntry 5007 }


	iqhco31VideoMasterBlankingBlankVANC OBJECT-TYPE
		SYNTAX		INTEGER { disable(0), enable(1) }
		MAX-ACCESS		read-write
		STATUS			current
		DESCRIPTION
				"TYPE: - Checkbox
				 PAGE: - Master- Video Master
					Blank VANC  cmdID= 3949 "
		::= { iqhco31CmdEntry 3949 }


	iqhco31Blanking625BlankLinesLine233951 OBJECT-TYPE
		SYNTAX		INTEGER { disable(0), enable(1) }
		MAX-ACCESS		read-write
		STATUS			current
		DESCRIPTION
				"TYPE: - Checkbox
				 PAGE: - Master- Video Master
					Line 23  cmdID= 3951 "
		::= { iqhco31CmdEntry 3951 }


	iqhco31Blanking625BlankLinesLine3363952 OBJECT-TYPE
		SYNTAX		INTEGER { disable(0), enable(1) }
		MAX-ACCESS		read-write
		STATUS			current
		DESCRIPTION
				"TYPE: - Checkbox
				 PAGE: - Master- Video Master
					Line 336  cmdID= 3952 "
		::= { iqhco31CmdEntry 3952 }


	iqhco31Blanking525BlankLinesLine213953 OBJECT-TYPE
		SYNTAX		INTEGER { disable(0), enable(1) }
		MAX-ACCESS		read-write
		STATUS			current
		DESCRIPTION
				"TYPE: - Checkbox
				 PAGE: - Master- Video Master
					Line 21  cmdID= 3953 "
		::= { iqhco31CmdEntry 3953 }


	iqhco31Blanking525BlankLinesLine223955 OBJECT-TYPE
		SYNTAX		INTEGER { disable(0), enable(1) }
		MAX-ACCESS		read-write
		STATUS			current
		DESCRIPTION
				"TYPE: - Checkbox
				 PAGE: - Master- Video Master
					Line 22  cmdID= 3955 "
		::= { iqhco31CmdEntry 3955 }


	iqhco31Blanking525BlankLinesLine2833954 OBJECT-TYPE
		SYNTAX		INTEGER { disable(0), enable(1) }
		MAX-ACCESS		read-write
		STATUS			current
		DESCRIPTION
				"TYPE: - Checkbox
				 PAGE: - Master- Video Master
					Line 283  cmdID= 3954 "
		::= { iqhco31CmdEntry 3954 }


	iqhco31Blanking525BlankLinesLine2843956 OBJECT-TYPE
		SYNTAX		INTEGER { disable(0), enable(1) }
		MAX-ACCESS		read-write
		STATUS			current
		DESCRIPTION
				"TYPE: - Checkbox
				 PAGE: - Master- Video Master
					Line 284  cmdID= 3956 "
		::= { iqhco31CmdEntry 3956 }


	iqhco31VideoMasterBlankingBlankHANC OBJECT-TYPE
		SYNTAX		INTEGER { disable(0), enable(1) }
		MAX-ACCESS		read-write
		STATUS			current
		DESCRIPTION
				"TYPE: - Checkbox
				 PAGE: - Master- Video Master
					Blank HANC  cmdID= 3947 "
		::= { iqhco31CmdEntry 3947 }


	iqhco31VideoMasterCaption OBJECT-TYPE
		SYNTAX		INTEGER {
							val-Animated-Off(0),
							val-Animated-Slow(1),
							val-Animated-Medium(2),
							val-Animated-Fast(3)
							}
		MAX-ACCESS		read-write
		STATUS			current
		DESCRIPTION
				"TYPE: - Button
				 PAGE: - Master- Video Master
					Animated Off  cmdID= 1037  value= 0  
					Animated Slow  cmdID= 1037  value= 1  
					Animated Medium  cmdID= 1037  value= 2  
					Animated Fast  cmdID= 1037  value= 3  "
		::= { iqhco31CmdEntry 1037 }


	iqhco31VideoMasterCaptionEditCaption OBJECT-TYPE
		SYNTAX		RollCallString
		MAX-ACCESS		read-write
		STATUS			current
		DESCRIPTION
				"TYPE: - Editstring
				 PAGE: - Master- Video Master
					Edit Caption  cmdID= 1041  "
		::= { iqhco31CmdEntry 1041 }


	iqhco31MasterVideoMasterPattern OBJECT-TYPE
		SYNTAX		INTEGER {
							val-Black(1),
							val-Bars(2)
							}
		MAX-ACCESS		read-write
		STATUS			current
		DESCRIPTION
				"TYPE: - RadiobuttonList
				 PAGE: - Master- Video Master
					Pattern  cmdID= 2624 
					Black  value= 1  
					Bars  value= 2  "
		::= { iqhco31CmdEntry 2624 }


	iqhco31VideoMasterFreeze OBJECT-TYPE
		SYNTAX		INTEGER {
							val-Field(0),
							val-Frame(1)
							}
		MAX-ACCESS		read-write
		STATUS			current
		DESCRIPTION
				"TYPE: - Button
				 PAGE: - Master- Video Master
					Field  cmdID= 5023  value= 0  
					Frame  cmdID= 5023  value= 1  "
		::= { iqhco31CmdEntry 5023 }


	iqhco31VideoMasterFreezeManualFreeze OBJECT-TYPE
		SYNTAX		INTEGER { disable(0), enable(1) }
		MAX-ACCESS		read-write
		STATUS			current
		DESCRIPTION
				"TYPE: - Checkbox
				 PAGE: - Master- Video Master
					Manual Freeze  cmdID= 5022 "
		::= { iqhco31CmdEntry 5022 }


	iqhco31AudioMasterEmbeddersEnable5066 OBJECT-TYPE
		SYNTAX		INTEGER { disable(0), enable(1) }
		MAX-ACCESS		read-write
		STATUS			current
		DESCRIPTION
				"TYPE: - Checkbox
				 PAGE: - Master- Audio Master
					Enable  cmdID= 5066 "
		::= { iqhco31CmdEntry 5066 }


	iqhco31AudioMasterEmbeddersEnable5067 OBJECT-TYPE
		SYNTAX		INTEGER { disable(0), enable(1) }
		MAX-ACCESS		read-write
		STATUS			current
		DESCRIPTION
				"TYPE: - Checkbox
				 PAGE: - Master- Audio Master
					Enable  cmdID= 5067 "
		::= { iqhco31CmdEntry 5067 }


	iqhco31AudioMasterEmbeddersEnable5068 OBJECT-TYPE
		SYNTAX		INTEGER { disable(0), enable(1) }
		MAX-ACCESS		read-write
		STATUS			current
		DESCRIPTION
				"TYPE: - Checkbox
				 PAGE: - Master- Audio Master
					Enable  cmdID= 5068 "
		::= { iqhco31CmdEntry 5068 }


	iqhco31AudioMasterEmbeddersEnable5069 OBJECT-TYPE
		SYNTAX		INTEGER { disable(0), enable(1) }
		MAX-ACCESS		read-write
		STATUS			current
		DESCRIPTION
				"TYPE: - Checkbox
				 PAGE: - Master- Audio Master
					Enable  cmdID= 5069 "
		::= { iqhco31CmdEntry 5069 }


	iqhco31AudioDelayDelaysVideoDelay5078 OBJECT-TYPE
		SYNTAX		INTEGER { disable(0), enable(1) }
		MAX-ACCESS		read-write
		STATUS			current
		DESCRIPTION
				"TYPE: - Checkbox
				 PAGE: - Master- Audio Master
					Video Delay  cmdID= 5078 "
		::= { iqhco31CmdEntry 5078 }


	iqhco31AudioDelayDelaysManualDelay5079 OBJECT-TYPE
		SYNTAX		INTEGER { disable(0), enable(1) }
		MAX-ACCESS		read-write
		STATUS			current
		DESCRIPTION
				"TYPE: - Checkbox
				 PAGE: - Master- Audio Master
					Manual Delay  cmdID= 5079 "
		::= { iqhco31CmdEntry 5079 }


	iqhco31AudioDelayDelaysTrack14Delay5080 OBJECT-TYPE
		SYNTAX		INTEGER { disable(0), enable(1) }
		MAX-ACCESS		read-write
		STATUS			current
		DESCRIPTION
				"TYPE: - Checkbox
				 PAGE: - Master- Audio Master
					Track 14 Delay  cmdID= 5080 "
		::= { iqhco31CmdEntry 5080 }


	iqhco31AudioDelayDelaysTrack15Delay5081 OBJECT-TYPE
		SYNTAX		INTEGER { disable(0), enable(1) }
		MAX-ACCESS		read-write
		STATUS			current
		DESCRIPTION
				"TYPE: - Checkbox
				 PAGE: - Master- Audio Master
					Track 15 Delay  cmdID= 5081 "
		::= { iqhco31CmdEntry 5081 }


	iqhco31AudioDelayDelaysTrack16Delay5082 OBJECT-TYPE
		SYNTAX		INTEGER { disable(0), enable(1) }
		MAX-ACCESS		read-write
		STATUS			current
		DESCRIPTION
				"TYPE: - Checkbox
				 PAGE: - Master- Audio Master
					Track 16 Delay  cmdID= 5082 "
		::= { iqhco31CmdEntry 5082 }


	iqhco31AudioDelayDelaysTrack17Delay5083 OBJECT-TYPE
		SYNTAX		INTEGER { disable(0), enable(1) }
		MAX-ACCESS		read-write
		STATUS			current
		DESCRIPTION
				"TYPE: - Checkbox
				 PAGE: - Master- Audio Master
					Track 17 Delay  cmdID= 5083 "
		::= { iqhco31CmdEntry 5083 }


	iqhco31AudioDelayDelaysCoarseDelay5075 OBJECT-TYPE
		SYNTAX		INTEGER
		MAX-ACCESS		read-write
		STATUS			current
		DESCRIPTION
				"TYPE: - Number
				 PAGE: - Master- Audio Master
					Coarse Delay  cmdID= 5075  min= 0  max= 1750  step= 5  format= %5.3fs  div_scale= 1000 
					Min = 0.000s  Max = 1.750s  Step = 0.005s "
		::= { iqhco31CmdEntry 5075 }


	iqhco31AudioDelayDelaysFineDelay5077 OBJECT-TYPE
		SYNTAX		INTEGER
		MAX-ACCESS		read-write
		STATUS			current
		DESCRIPTION
				"TYPE: - Number
				 PAGE: - Master- Audio Master
					Fine Delay  cmdID= 5077  min= -2500  max= 2500  step= 5  format= %0.1fms  div_scale= 10 
					Min = -250.0ms  Max = 250.0ms  Step = 0.5ms "
		::= { iqhco31CmdEntry 5077 }


	iqhco31AudioDelayDelayStatusTotalDelay5084 OBJECT-TYPE
		SYNTAX		RollCallString
		MAX-ACCESS		read-only
		STATUS			current
		DESCRIPTION
				"TYPE: - Display
				 PAGE: - Master- Audio Master
					Total Delay  cmdID= 5084  format=   "
		::= { iqhco31CmdEntry 5084 }


	iqhco31AudioDelayDelayStatusVideoDelay5074 OBJECT-TYPE
		SYNTAX		RollCallString
		MAX-ACCESS		read-only
		STATUS			current
		DESCRIPTION
				"TYPE: - Display
				 PAGE: - Master- Audio Master
					Video Delay  cmdID= 5074  format=   "
		::= { iqhco31CmdEntry 5074 }


	iqhco31AudioDelayDelayStatusManualDelay5076 OBJECT-TYPE
		SYNTAX		RollCallString
		MAX-ACCESS		read-only
		STATUS			current
		DESCRIPTION
				"TYPE: - Display
				 PAGE: - Master- Audio Master
					Manual Delay  cmdID= 5076  format=   "
		::= { iqhco31CmdEntry 5076 }


	iqhco31AudioDelayDelayStatusTrack14Delay OBJECT-TYPE
		SYNTAX		RollCallString
		MAX-ACCESS		read-only
		STATUS			current
		DESCRIPTION
				"TYPE: - Display
				 PAGE: - Master- Audio Master
					Track 14 Delay  cmdID= 3924  format=   "
		::= { iqhco31CmdEntry 3924 }


	iqhco31AudioDelayDelayStatusTrack15Delay OBJECT-TYPE
		SYNTAX		RollCallString
		MAX-ACCESS		read-only
		STATUS			current
		DESCRIPTION
				"TYPE: - Display
				 PAGE: - Master- Audio Master
					Track 15 Delay  cmdID= 3925  format=   "
		::= { iqhco31CmdEntry 3925 }


	iqhco31AudioDelayDelayStatusTrack16Delay OBJECT-TYPE
		SYNTAX		RollCallString
		MAX-ACCESS		read-only
		STATUS			current
		DESCRIPTION
				"TYPE: - Display
				 PAGE: - Master- Audio Master
					Track 16 Delay  cmdID= 3926  format=   "
		::= { iqhco31CmdEntry 3926 }


	iqhco31AudioDelayDelayStatusTrack17Delay OBJECT-TYPE
		SYNTAX		RollCallString
		MAX-ACCESS		read-only
		STATUS			current
		DESCRIPTION
				"TYPE: - Display
				 PAGE: - Master- Audio Master
					Track 17 Delay  cmdID= 3927  format=   "
		::= { iqhco31CmdEntry 3927 }


	iqhco31BackupValidValidInputStds108050pB OBJECT-TYPE
		SYNTAX		INTEGER { disable(0), enable(1) }
		MAX-ACCESS		read-write
		STATUS			current
		DESCRIPTION
				"TYPE: - Checkbox
				 PAGE: - Backup- Video Backup- Backup Valid
					1080/50p-B  cmdID= 5275 "
		::= { iqhco31CmdEntry 5275 }


	iqhco31BackupValidValidInputStds108059pB OBJECT-TYPE
		SYNTAX		INTEGER { disable(0), enable(1) }
		MAX-ACCESS		read-write
		STATUS			current
		DESCRIPTION
				"TYPE: - Checkbox
				 PAGE: - Backup- Video Backup- Backup Valid
					1080/59p-B  cmdID= 5276 "
		::= { iqhco31CmdEntry 5276 }


	iqhco31BackupValidValidInputStds108050pA OBJECT-TYPE
		SYNTAX		INTEGER { disable(0), enable(1) }
		MAX-ACCESS		read-write
		STATUS			current
		DESCRIPTION
				"TYPE: - Checkbox
				 PAGE: - Backup- Video Backup- Backup Valid
					1080/50p-A  cmdID= 5272 "
		::= { iqhco31CmdEntry 5272 }


	iqhco31BackupValidValidInputStds108059pA OBJECT-TYPE
		SYNTAX		INTEGER { disable(0), enable(1) }
		MAX-ACCESS		read-write
		STATUS			current
		DESCRIPTION
				"TYPE: - Checkbox
				 PAGE: - Backup- Video Backup- Backup Valid
					1080/59p-A  cmdID= 5273 "
		::= { iqhco31CmdEntry 5273 }


	iqhco31BackupValidValidInputStds108029i OBJECT-TYPE
		SYNTAX		INTEGER { disable(0), enable(1) }
		MAX-ACCESS		read-write
		STATUS			current
		DESCRIPTION
				"TYPE: - Checkbox
				 PAGE: - Backup- Video Backup- Backup Valid
					1080/29i  cmdID= 5268 "
		::= { iqhco31CmdEntry 5268 }


	iqhco31BackupValidValidInputStds108025i OBJECT-TYPE
		SYNTAX		INTEGER { disable(0), enable(1) }
		MAX-ACCESS		read-write
		STATUS			current
		DESCRIPTION
				"TYPE: - Checkbox
				 PAGE: - Backup- Video Backup- Backup Valid
					1080/25i  cmdID= 5267 "
		::= { iqhco31CmdEntry 5267 }


	iqhco31BackupValidValidInputStds72059p OBJECT-TYPE
		SYNTAX		INTEGER { disable(0), enable(1) }
		MAX-ACCESS		read-write
		STATUS			current
		DESCRIPTION
				"TYPE: - Checkbox
				 PAGE: - Backup- Video Backup- Backup Valid
					720/59p  cmdID= 5260 "
		::= { iqhco31CmdEntry 5260 }


	iqhco31BackupValidValidInputStds72050p OBJECT-TYPE
		SYNTAX		INTEGER { disable(0), enable(1) }
		MAX-ACCESS		read-write
		STATUS			current
		DESCRIPTION
				"TYPE: - Checkbox
				 PAGE: - Backup- Video Backup- Backup Valid
					720/50p  cmdID= 5259 "
		::= { iqhco31CmdEntry 5259 }


	iqhco31BackupValidValidInputStds52529i OBJECT-TYPE
		SYNTAX		INTEGER { disable(0), enable(1) }
		MAX-ACCESS		read-write
		STATUS			current
		DESCRIPTION
				"TYPE: - Checkbox
				 PAGE: - Backup- Video Backup- Backup Valid
					525/29i  cmdID= 5253 "
		::= { iqhco31CmdEntry 5253 }


	iqhco31BackupValidValidInputStds62525i OBJECT-TYPE
		SYNTAX		INTEGER { disable(0), enable(1) }
		MAX-ACCESS		read-write
		STATUS			current
		DESCRIPTION
				"TYPE: - Checkbox
				 PAGE: - Backup- Video Backup- Backup Valid
					625/25i  cmdID= 5252 "
		::= { iqhco31CmdEntry 5252 }


	iqhco31BackupValidCRCEDHErroredsecErrSecEnable OBJECT-TYPE
		SYNTAX		INTEGER { disable(0), enable(1) }
		MAX-ACCESS		read-write
		STATUS			current
		DESCRIPTION
				"TYPE: - Checkbox
				 PAGE: - Backup- Video Backup- Backup Valid
					ErrSec Enable  cmdID= 5404 "
		::= { iqhco31CmdEntry 5404 }


	iqhco31BackupValidCRCEDHErroredsecErrSecDecision OBJECT-TYPE
		SYNTAX		RollCallString
		MAX-ACCESS		read-only
		STATUS			current
		DESCRIPTION
				"TYPE: - Display
				 PAGE: - Backup- Video Backup- Backup Valid
					ErrSec Decision  cmdID= 5403  format=   "
		::= { iqhco31CmdEntry 5403 }


	iqhco31BackupValidCRCEDHErroredsecCarrierDecision OBJECT-TYPE
		SYNTAX		RollCallString
		MAX-ACCESS		read-only
		STATUS			current
		DESCRIPTION
				"TYPE: - Display
				 PAGE: - Backup- Video Backup- Backup Valid
					Carrier Decision  cmdID= 5401  format=   "
		::= { iqhco31CmdEntry 5401 }


	iqhco31BackupValidCRCEDHErroredsecStdDecision OBJECT-TYPE
		SYNTAX		RollCallString
		MAX-ACCESS		read-only
		STATUS			current
		DESCRIPTION
				"TYPE: - Display
				 PAGE: - Backup- Video Backup- Backup Valid
					Std Decision  cmdID= 5402  format=   "
		::= { iqhco31CmdEntry 5402 }


	iqhco31BackupValidCRCEDHErroredsecInputStd OBJECT-TYPE
		SYNTAX		RollCallString
		MAX-ACCESS		read-only
		STATUS			current
		DESCRIPTION
				"TYPE: - Display
				 PAGE: - Backup- Video Backup- Backup Valid
					Input Std  cmdID= 5449  format=   "
		::= { iqhco31CmdEntry 5449 }


	iqhco31BackupValidCRCEDHErroredsecFreezeEnable OBJECT-TYPE
		SYNTAX		INTEGER { disable(0), enable(1) }
		MAX-ACCESS		read-write
		STATUS			current
		DESCRIPTION
				"TYPE: - Checkbox
				 PAGE: - Backup- Video Backup- Backup Valid
					Freeze Enable  cmdID= 5406 "
		::= { iqhco31CmdEntry 5406 }


	iqhco31BackupValidCRCEDHErroredsecFreezeDecision OBJECT-TYPE
		SYNTAX		RollCallString
		MAX-ACCESS		read-only
		STATUS			current
		DESCRIPTION
				"TYPE: - Display
				 PAGE: - Backup- Video Backup- Backup Valid
					Freeze Decision  cmdID= 5405  format=   "
		::= { iqhco31CmdEntry 5405 }


	iqhco31BackupValidCRCEDHErroredsecBlackEnable OBJECT-TYPE
		SYNTAX		INTEGER { disable(0), enable(1) }
		MAX-ACCESS		read-write
		STATUS			current
		DESCRIPTION
				"TYPE: - Checkbox
				 PAGE: - Backup- Video Backup- Backup Valid
					Black Enable  cmdID= 5408 "
		::= { iqhco31CmdEntry 5408 }


	iqhco31BackupValidCRCEDHErroredsecBlackDecision OBJECT-TYPE
		SYNTAX		RollCallString
		MAX-ACCESS		read-only
		STATUS			current
		DESCRIPTION
				"TYPE: - Display
				 PAGE: - Backup- Video Backup- Backup Valid
					Black Decision  cmdID= 5407  format=   "
		::= { iqhco31CmdEntry 5407 }


	iqhco31BackupValidCRCEDHErroredsecBlackThreshold OBJECT-TYPE
		SYNTAX		INTEGER
		MAX-ACCESS		read-write
		STATUS			current
		DESCRIPTION
				"TYPE: - Number
				 PAGE: - Backup- Video Backup- Backup Valid
					Black Threshold  cmdID= 5579  min= 0  max= 153  step= 1  format= %.0f mV  div_scale= 1 
					Min = 0 mV  Max = 153 mV  Step = 1 mV "
		::= { iqhco31CmdEntry 5579 }


	iqhco31BackupValidVideoValidTimersBlackFailDelay OBJECT-TYPE
		SYNTAX		INTEGER
		MAX-ACCESS		read-write
		STATUS			current
		DESCRIPTION
				"TYPE: - Number
				 PAGE: - Backup- Video Backup- Backup Valid
					Black Fail Delay  cmdID= 5564  min= 2  max= 100  step= 1  format= %.1f s  div_scale= 10 
					Min = 0.2 s  Max = 10.0 s  Step = 0.1 s "
		::= { iqhco31CmdEntry 5564 }


	iqhco31BackupValidVideoValidTimersBlackRecoverDelay OBJECT-TYPE
		SYNTAX		INTEGER
		MAX-ACCESS		read-write
		STATUS			current
		DESCRIPTION
				"TYPE: - Number
				 PAGE: - Backup- Video Backup- Backup Valid
					Black Recover Delay  cmdID= 5565  min= 2  max= 100  step= 1  format= %.1f s  div_scale= 10 
					Min = 0.2 s  Max = 10.0 s  Step = 0.1 s "
		::= { iqhco31CmdEntry 5565 }


	iqhco31BackupValidVideoValidTimersFreezeFailDelay OBJECT-TYPE
		SYNTAX		INTEGER
		MAX-ACCESS		read-write
		STATUS			current
		DESCRIPTION
				"TYPE: - Number
				 PAGE: - Backup- Video Backup- Backup Valid
					Freeze Fail Delay  cmdID= 5566  min= 2  max= 100  step= 1  format= %.1f s  div_scale= 10 
					Min = 0.2 s  Max = 10.0 s  Step = 0.1 s "
		::= { iqhco31CmdEntry 5566 }


	iqhco31BackupValidVideoValidTimersFreezeRecoverDela OBJECT-TYPE
		SYNTAX		INTEGER
		MAX-ACCESS		read-write
		STATUS			current
		DESCRIPTION
				"TYPE: - Number
				 PAGE: - Backup- Video Backup- Backup Valid
					Freeze Recover Dela  cmdID= 5567  min= 2  max= 100  step= 1  format= %.1f s  div_scale= 10 
					Min = 0.2 s  Max = 10.0 s  Step = 0.1 s "
		::= { iqhco31CmdEntry 5567 }


	iqhco31BackupValidVideoValidTimersErrsecFailDelay OBJECT-TYPE
		SYNTAX		INTEGER
		MAX-ACCESS		read-write
		STATUS			current
		DESCRIPTION
				"TYPE: - Number
				 PAGE: - Backup- Video Backup- Backup Valid
					Errsec Fail Delay  cmdID= 5568  min= 0  max= 10  step= 1  format= %.0f s  div_scale= 1 
					Min = 0 s  Max = 10 s  Step = 1 s "
		::= { iqhco31CmdEntry 5568 }


	iqhco31BackupValidVideoValidTimersErrsecRecoverDela OBJECT-TYPE
		SYNTAX		INTEGER
		MAX-ACCESS		read-write
		STATUS			current
		DESCRIPTION
				"TYPE: - Number
				 PAGE: - Backup- Video Backup- Backup Valid
					Errsec Recover Dela  cmdID= 5569  min= 0  max= 10  step= 1  format= %.0f s  div_scale= 1 
					Min = 0 s  Max = 10 s  Step = 1 s "
		::= { iqhco31CmdEntry 5569 }


	iqhco31BackupValidVideoValidTimersValidFailDelay OBJECT-TYPE
		SYNTAX		INTEGER
		MAX-ACCESS		read-write
		STATUS			current
		DESCRIPTION
				"TYPE: - Number
				 PAGE: - Backup- Video Backup- Backup Valid
					Valid Fail Delay  cmdID= 5576  min= 0  max= 100  step= 1  format= %.1f s  div_scale= 10 
					Min = 0.0 s  Max = 10.0 s  Step = 0.1 s "
		::= { iqhco31CmdEntry 5576 }


	iqhco31BackupValidVideoValidTimersValidRecoverDelay OBJECT-TYPE
		SYNTAX		INTEGER
		MAX-ACCESS		read-write
		STATUS			current
		DESCRIPTION
				"TYPE: - Number
				 PAGE: - Backup- Video Backup- Backup Valid
					Valid Recover Delay  cmdID= 5577  min= 2  max= 100  step= 1  format= %.1f s  div_scale= 10 
					Min = 0.2 s  Max = 10.0 s  Step = 0.1 s "
		::= { iqhco31CmdEntry 5577 }


	iqhco31BackupValidValidAudioDecision OBJECT-TYPE
		SYNTAX		RollCallString
		MAX-ACCESS		read-only
		STATUS			current
		DESCRIPTION
				"TYPE: - Display
				 PAGE: - Backup- Video Backup- Backup Valid- Valid Audio
					Decision  cmdID= 5400  format=   "
		::= { iqhco31CmdEntry 5400 }


	iqhco31ValidAudioBackupPair1Decision OBJECT-TYPE
		SYNTAX		RollCallString
		MAX-ACCESS		read-only
		STATUS			current
		DESCRIPTION
				"TYPE: - Display
				 PAGE: - Backup- Video Backup- Backup Valid- Valid Audio
					Decision  cmdID= 5409  format=   "
		::= { iqhco31CmdEntry 5409 }


	iqhco31ValidAudioBackupPair1CurrentType OBJECT-TYPE
		SYNTAX		RollCallString
		MAX-ACCESS		read-only
		STATUS			current
		DESCRIPTION
				"TYPE: - Display
				 PAGE: - Backup- Video Backup- Backup Valid- Valid Audio
					Current Type  cmdID= 5410  format=   "
		::= { iqhco31CmdEntry 5410 }


	iqhco31ValidAudioBackupPair1 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5411  value= 0  
					DolbyE  cmdID= 5411  value= 1  
					Data  cmdID= 5411  value= 2  
					None  cmdID= 5411  value= 3  
					Any  cmdID= 5411  value= 4  
					Ignored  cmdID= 5411  value= 5  "
		::= { iqhco31CmdEntry 5411 }


	iqhco31ValidAudioBackupPair1Ch1State OBJECT-TYPE
		SYNTAX		RollCallString
		MAX-ACCESS		read-only
		STATUS			current
		DESCRIPTION
				"TYPE: - Display
				 PAGE: - Backup- Video Backup- Backup Valid- Valid Audio
					Ch1 State  cmdID= 7024  format=   "
		::= { iqhco31CmdEntry 7024 }


	iqhco31ValidAudioBackupPair1Ch2State OBJECT-TYPE
		SYNTAX		RollCallString
		MAX-ACCESS		read-only
		STATUS			current
		DESCRIPTION
				"TYPE: - Display
				 PAGE: - Backup- Video Backup- Backup Valid- Valid Audio
					Ch2 State  cmdID= 7025  format=   "
		::= { iqhco31CmdEntry 7025 }


	iqhco31ValidAudioBackupPair1Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5458 "
		::= { iqhco31CmdEntry 5458 }


	iqhco31ValidAudioBackupPair1Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5412 "
		::= { iqhco31CmdEntry 5412 }


	iqhco31ValidAudioBackupPair1Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5413 "
		::= { iqhco31CmdEntry 5413 }


	iqhco31ValidAudioBackupPair2Decision OBJECT-TYPE
		SYNTAX		RollCallString
		MAX-ACCESS		read-only
		STATUS			current
		DESCRIPTION
				"TYPE: - Display
				 PAGE: - Backup- Video Backup- Backup Valid- Valid Audio
					Decision  cmdID= 5414  format=   "
		::= { iqhco31CmdEntry 5414 }


	iqhco31ValidAudioBackupPair2CurrentType OBJECT-TYPE
		SYNTAX		RollCallString
		MAX-ACCESS		read-only
		STATUS			current
		DESCRIPTION
				"TYPE: - Display
				 PAGE: - Backup- Video Backup- Backup Valid- Valid Audio
					Current Type  cmdID= 5415  format=   "
		::= { iqhco31CmdEntry 5415 }


	iqhco31ValidAudioBackupPair2 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5416  value= 0  
					DolbyE  cmdID= 5416  value= 1  
					Data  cmdID= 5416  value= 2  
					None  cmdID= 5416  value= 3  
					Any  cmdID= 5416  value= 4  
					Ignored  cmdID= 5416  value= 5  "
		::= { iqhco31CmdEntry 5416 }


	iqhco31ValidAudioBackupPair2Ch1State OBJECT-TYPE
		SYNTAX		RollCallString
		MAX-ACCESS		read-only
		STATUS			current
		DESCRIPTION
				"TYPE: - Display
				 PAGE: - Backup- Video Backup- Backup Valid- Valid Audio
					Ch1 State  cmdID= 7026  format=   "
		::= { iqhco31CmdEntry 7026 }


	iqhco31ValidAudioBackupPair2Ch2State OBJECT-TYPE
		SYNTAX		RollCallString
		MAX-ACCESS		read-only
		STATUS			current
		DESCRIPTION
				"TYPE: - Display
				 PAGE: - Backup- Video Backup- Backup Valid- Valid Audio
					Ch2 State  cmdID= 7027  format=   "
		::= { iqhco31CmdEntry 7027 }


	iqhco31ValidAudioBackupPair2Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5459 "
		::= { iqhco31CmdEntry 5459 }


	iqhco31ValidAudioBackupPair2Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5417 "
		::= { iqhco31CmdEntry 5417 }


	iqhco31ValidAudioBackupPair2Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5418 "
		::= { iqhco31CmdEntry 5418 }


	iqhco31ValidAudioBackupPair3Decision OBJECT-TYPE
		SYNTAX		RollCallString
		MAX-ACCESS		read-only
		STATUS			current
		DESCRIPTION
				"TYPE: - Display
				 PAGE: - Backup- Video Backup- Backup Valid- Valid Audio
					Decision  cmdID= 5419  format=   "
		::= { iqhco31CmdEntry 5419 }


	iqhco31ValidAudioBackupPair3CurrentType OBJECT-TYPE
		SYNTAX		RollCallString
		MAX-ACCESS		read-only
		STATUS			current
		DESCRIPTION
				"TYPE: - Display
				 PAGE: - Backup- Video Backup- Backup Valid- Valid Audio
					Current Type  cmdID= 5420  format=   "
		::= { iqhco31CmdEntry 5420 }


	iqhco31ValidAudioBackupPair3 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5421  value= 0  
					DolbyE  cmdID= 5421  value= 1  
					Data  cmdID= 5421  value= 2  
					None  cmdID= 5421  value= 3  
					Any  cmdID= 5421  value= 4  
					Ignored  cmdID= 5421  value= 5  "
		::= { iqhco31CmdEntry 5421 }


	iqhco31ValidAudioBackupPair3Ch1State OBJECT-TYPE
		SYNTAX		RollCallString
		MAX-ACCESS		read-only
		STATUS			current
		DESCRIPTION
				"TYPE: - Display
				 PAGE: - Backup- Video Backup- Backup Valid- Valid Audio
					Ch1 State  cmdID= 7028  format=   "
		::= { iqhco31CmdEntry 7028 }


	iqhco31ValidAudioBackupPair3Ch2State OBJECT-TYPE
		SYNTAX		RollCallString
		MAX-ACCESS		read-only
		STATUS			current
		DESCRIPTION
				"TYPE: - Display
				 PAGE: - Backup- Video Backup- Backup Valid- Valid Audio
					Ch2 State  cmdID= 7029  format=   "
		::= { iqhco31CmdEntry 7029 }


	iqhco31ValidAudioBackupPair3Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5460 "
		::= { iqhco31CmdEntry 5460 }


	iqhco31ValidAudioBackupPair3Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5422 "
		::= { iqhco31CmdEntry 5422 }


	iqhco31ValidAudioBackupPair3Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5423 "
		::= { iqhco31CmdEntry 5423 }


	iqhco31ValidAudioBackupPair4Decision OBJECT-TYPE
		SYNTAX		RollCallString
		MAX-ACCESS		read-only
		STATUS			current
		DESCRIPTION
				"TYPE: - Display
				 PAGE: - Backup- Video Backup- Backup Valid- Valid Audio
					Decision  cmdID= 5424  format=   "
		::= { iqhco31CmdEntry 5424 }


	iqhco31ValidAudioBackupPair4CurrentType OBJECT-TYPE
		SYNTAX		RollCallString
		MAX-ACCESS		read-only
		STATUS			current
		DESCRIPTION
				"TYPE: - Display
				 PAGE: - Backup- Video Backup- Backup Valid- Valid Audio
					Current Type  cmdID= 5425  format=   "
		::= { iqhco31CmdEntry 5425 }


	iqhco31ValidAudioBackupPair4 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5426  value= 0  
					DolbyE  cmdID= 5426  value= 1  
					Data  cmdID= 5426  value= 2  
					None  cmdID= 5426  value= 3  
					Any  cmdID= 5426  value= 4  
					Ignored  cmdID= 5426  value= 5  "
		::= { iqhco31CmdEntry 5426 }


	iqhco31ValidAudioBackupPair4Ch1State OBJECT-TYPE
		SYNTAX		RollCallString
		MAX-ACCESS		read-only
		STATUS			current
		DESCRIPTION
				"TYPE: - Display
				 PAGE: - Backup- Video Backup- Backup Valid- Valid Audio
					Ch1 State  cmdID= 7030  format=   "
		::= { iqhco31CmdEntry 7030 }


	iqhco31ValidAudioBackupPair4Ch2State OBJECT-TYPE
		SYNTAX		RollCallString
		MAX-ACCESS		read-only
		STATUS			current
		DESCRIPTION
				"TYPE: - Display
				 PAGE: - Backup- Video Backup- Backup Valid- Valid Audio
					Ch2 State  cmdID= 7031  format=   "
		::= { iqhco31CmdEntry 7031 }


	iqhco31ValidAudioBackupPair4Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5461 "
		::= { iqhco31CmdEntry 5461 }


	iqhco31ValidAudioBackupPair4Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5427 "
		::= { iqhco31CmdEntry 5427 }


	iqhco31ValidAudioBackupPair4Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5428 "
		::= { iqhco31CmdEntry 5428 }


	iqhco31ValidAudioBackupPair5Decision OBJECT-TYPE
		SYNTAX		RollCallString
		MAX-ACCESS		read-only
		STATUS			current
		DESCRIPTION
				"TYPE: - Display
				 PAGE: - Backup- Video Backup- Backup Valid- Valid Audio
					Decision  cmdID= 5429  format=   "
		::= { iqhco31CmdEntry 5429 }


	iqhco31ValidAudioBackupPair5CurrentType OBJECT-TYPE
		SYNTAX		RollCallString
		MAX-ACCESS		read-only
		STATUS			current
		DESCRIPTION
				"TYPE: - Display
				 PAGE: - Backup- Video Backup- Backup Valid- Valid Audio
					Current Type  cmdID= 5430  format=   "
		::= { iqhco31CmdEntry 5430 }


	iqhco31ValidAudioBackupPair5 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5431  value= 0  
					DolbyE  cmdID= 5431  value= 1  
					Data  cmdID= 5431  value= 2  
					None  cmdID= 5431  value= 3  
					Any  cmdID= 5431  value= 4  
					Ignored  cmdID= 5431  value= 5  "
		::= { iqhco31CmdEntry 5431 }


	iqhco31ValidAudioBackupPair5Ch1State OBJECT-TYPE
		SYNTAX		RollCallString
		MAX-ACCESS		read-only
		STATUS			current
		DESCRIPTION
				"TYPE: - Display
				 PAGE: - Backup- Video Backup- Backup Valid- Valid Audio
					Ch1 State  cmdID= 7032  format=   "
		::= { iqhco31CmdEntry 7032 }


	iqhco31ValidAudioBackupPair5Ch2State OBJECT-TYPE
		SYNTAX		RollCallString
		MAX-ACCESS		read-only
		STATUS			current
		DESCRIPTION
				"TYPE: - Display
				 PAGE: - Backup- Video Backup- Backup Valid- Valid Audio
					Ch2 State  cmdID= 7033  format=   "
		::= { iqhco31CmdEntry 7033 }


	iqhco31ValidAudioBackupPair5Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5462 "
		::= { iqhco31CmdEntry 5462 }


	iqhco31ValidAudioBackupPair5Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5432 "
		::= { iqhco31CmdEntry 5432 }


	iqhco31ValidAudioBackupPair5Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5433 "
		::= { iqhco31CmdEntry 5433 }


	iqhco31ValidAudioBackupPair6Decision OBJECT-TYPE
		SYNTAX		RollCallString
		MAX-ACCESS		read-only
		STATUS			current
		DESCRIPTION
				"TYPE: - Display
				 PAGE: - Backup- Video Backup- Backup Valid- Valid Audio
					Decision  cmdID= 5434  format=   "
		::= { iqhco31CmdEntry 5434 }


	iqhco31ValidAudioBackupPair6CurrentType OBJECT-TYPE
		SYNTAX		RollCallString
		MAX-ACCESS		read-only
		STATUS			current
		DESCRIPTION
				"TYPE: - Display
				 PAGE: - Backup- Video Backup- Backup Valid- Valid Audio
					Current Type  cmdID= 5435  format=   "
		::= { iqhco31CmdEntry 5435 }


	iqhco31ValidAudioBackupPair6 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5436  value= 0  
					DolbyE  cmdID= 5436  value= 1  
					Data  cmdID= 5436  value= 2  
					None  cmdID= 5436  value= 3  
					Any  cmdID= 5436  value= 4  
					Ignored  cmdID= 5436  value= 5  "
		::= { iqhco31CmdEntry 5436 }


	iqhco31ValidAudioBackupPair6Ch1State OBJECT-TYPE
		SYNTAX		RollCallString
		MAX-ACCESS		read-only
		STATUS			current
		DESCRIPTION
				"TYPE: - Display
				 PAGE: - Backup- Video Backup- Backup Valid- Valid Audio
					Ch1 State  cmdID= 7034  format=   "
		::= { iqhco31CmdEntry 7034 }


	iqhco31ValidAudioBackupPair6Ch2State OBJECT-TYPE
		SYNTAX		RollCallString
		MAX-ACCESS		read-only
		STATUS			current
		DESCRIPTION
				"TYPE: - Display
				 PAGE: - Backup- Video Backup- Backup Valid- Valid Audio
					Ch2 State  cmdID= 7035  format=   "
		::= { iqhco31CmdEntry 7035 }


	iqhco31ValidAudioBackupPair6Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5463 "
		::= { iqhco31CmdEntry 5463 }


	iqhco31ValidAudioBackupPair6Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5437 "
		::= { iqhco31CmdEntry 5437 }


	iqhco31ValidAudioBackupPair6Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5438 "
		::= { iqhco31CmdEntry 5438 }


	iqhco31ValidAudioBackupPair7Decision OBJECT-TYPE
		SYNTAX		RollCallString
		MAX-ACCESS		read-only
		STATUS			current
		DESCRIPTION
				"TYPE: - Display
				 PAGE: - Backup- Video Backup- Backup Valid- Valid Audio
					Decision  cmdID= 5439  format=   "
		::= { iqhco31CmdEntry 5439 }


	iqhco31ValidAudioBackupPair7CurrentType OBJECT-TYPE
		SYNTAX		RollCallString
		MAX-ACCESS		read-only
		STATUS			current
		DESCRIPTION
				"TYPE: - Display
				 PAGE: - Backup- Video Backup- Backup Valid- Valid Audio
					Current Type  cmdID= 5440  format=   "
		::= { iqhco31CmdEntry 5440 }


	iqhco31ValidAudioBackupPair7 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5441  value= 0  
					DolbyE  cmdID= 5441  value= 1  
					Data  cmdID= 5441  value= 2  
					None  cmdID= 5441  value= 3  
					Any  cmdID= 5441  value= 4  
					Ignored  cmdID= 5441  value= 5  "
		::= { iqhco31CmdEntry 5441 }


	iqhco31ValidAudioBackupPair7Ch1State OBJECT-TYPE
		SYNTAX		RollCallString
		MAX-ACCESS		read-only
		STATUS			current
		DESCRIPTION
				"TYPE: - Display
				 PAGE: - Backup- Video Backup- Backup Valid- Valid Audio
					Ch1 State  cmdID= 7036  format=   "
		::= { iqhco31CmdEntry 7036 }


	iqhco31ValidAudioBackupPair7Ch2State OBJECT-TYPE
		SYNTAX		RollCallString
		MAX-ACCESS		read-only
		STATUS			current
		DESCRIPTION
				"TYPE: - Display
				 PAGE: - Backup- Video Backup- Backup Valid- Valid Audio
					Ch2 State  cmdID= 7037  format=   "
		::= { iqhco31CmdEntry 7037 }


	iqhco31ValidAudioBackupPair7Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5464 "
		::= { iqhco31CmdEntry 5464 }


	iqhco31ValidAudioBackupPair7Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5442 "
		::= { iqhco31CmdEntry 5442 }


	iqhco31ValidAudioBackupPair7Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5443 "
		::= { iqhco31CmdEntry 5443 }


	iqhco31ValidAudioBackupPair8Decision OBJECT-TYPE
		SYNTAX		RollCallString
		MAX-ACCESS		read-only
		STATUS			current
		DESCRIPTION
				"TYPE: - Display
				 PAGE: - Backup- Video Backup- Backup Valid- Valid Audio
					Decision  cmdID= 5444  format=   "
		::= { iqhco31CmdEntry 5444 }


	iqhco31ValidAudioBackupPair8CurrentType OBJECT-TYPE
		SYNTAX		RollCallString
		MAX-ACCESS		read-only
		STATUS			current
		DESCRIPTION
				"TYPE: - Display
				 PAGE: - Backup- Video Backup- Backup Valid- Valid Audio
					Current Type  cmdID= 5445  format=   "
		::= { iqhco31CmdEntry 5445 }


	iqhco31ValidAudioBackupPair8 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5446  value= 0  
					DolbyE  cmdID= 5446  value= 1  
					Data  cmdID= 5446  value= 2  
					None  cmdID= 5446  value= 3  
					Any  cmdID= 5446  value= 4  
					Ignored  cmdID= 5446  value= 5  "
		::= { iqhco31CmdEntry 5446 }


	iqhco31ValidAudioBackupPair8Ch1State OBJECT-TYPE
		SYNTAX		RollCallString
		MAX-ACCESS		read-only
		STATUS			current
		DESCRIPTION
				"TYPE: - Display
				 PAGE: - Backup- Video Backup- Backup Valid- Valid Audio
					Ch1 State  cmdID= 7038  format=   "
		::= { iqhco31CmdEntry 7038 }


	iqhco31ValidAudioBackupPair8Ch2State OBJECT-TYPE
		SYNTAX		RollCallString
		MAX-ACCESS		read-only
		STATUS			current
		DESCRIPTION
				"TYPE: - Display
				 PAGE: - Backup- Video Backup- Backup Valid- Valid Audio
					Ch2 State  cmdID= 7039  format=   "
		::= { iqhco31CmdEntry 7039 }


	iqhco31ValidAudioBackupPair8Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5465 "
		::= { iqhco31CmdEntry 5465 }


	iqhco31ValidAudioBackupPair8Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5447 "
		::= { iqhco31CmdEntry 5447 }


	iqhco31ValidAudioBackupPair8Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5448 "
		::= { iqhco31CmdEntry 5448 }


	iqhco31BackupValidValidAudioLowlevel OBJECT-TYPE
		SYNTAX		INTEGER
		MAX-ACCESS		read-write
		STATUS			current
		DESCRIPTION
				"TYPE: - Number
				 PAGE: - Backup- Video Backup- Backup Valid- Valid Audio
					Low-level  cmdID= 3075  min= -80  max= 0  step= 1  format= %1.0f dB  div_scale= 1 
					Min = -80 dB  Max = 0 dB  Step = 1 dB "
		::= { iqhco31CmdEntry 3075 }


	iqhco31BackupValidValidAudioOverloadLevel OBJECT-TYPE
		SYNTAX		INTEGER
		MAX-ACCESS		read-write
		STATUS			current
		DESCRIPTION
				"TYPE: - Number
				 PAGE: - Backup- Video Backup- Backup Valid- Valid Audio
					Overload Level  cmdID= 3078  min= -80  max= 0  step= 1  format= %1.0f dB  div_scale= 1 
					Min = -80 dB  Max = 0 dB  Step = 1 dB "
		::= { iqhco31CmdEntry 3078 }


	iqhco31BackupValidValidAudioTypeFailTimer OBJECT-TYPE
		SYNTAX		INTEGER
		MAX-ACCESS		read-write
		STATUS			current
		DESCRIPTION
				"TYPE: - Number
				 PAGE: - Backup- Video Backup- Backup Valid- Valid Audio
					Type Fail Timer  cmdID= 5570  min= 0  max= 10  step= 1  format= %1.0f sec  div_scale= 1 
					Min = 0 sec  Max = 10 sec  Step = 1 sec "
		::= { iqhco31CmdEntry 5570 }


	iqhco31BackupValidValidAudioTypeRecoverTimer OBJECT-TYPE
		SYNTAX		INTEGER
		MAX-ACCESS		read-write
		STATUS			current
		DESCRIPTION
				"TYPE: - Number
				 PAGE: - Backup- Video Backup- Backup Valid- Valid Audio
					Type Recover Timer  cmdID= 5571  min= 0  max= 10  step= 1  format= %1.0f sec  div_scale= 1 
					Min = 0 sec  Max = 10 sec  Step = 1 sec "
		::= { iqhco31CmdEntry 5571 }


	iqhco31BackupValidValidAudioMuteFailTimer OBJECT-TYPE
		SYNTAX		INTEGER
		MAX-ACCESS		read-write
		STATUS			current
		DESCRIPTION
				"TYPE: - Number
				 PAGE: - Backup- Video Backup- Backup Valid- Valid Audio
					Mute Fail Timer  cmdID= 5582  min= 0  max= 120  step= 1  format= %1.0f sec  div_scale= 1 
					Min = 0 sec  Max = 120 sec  Step = 1 sec "
		::= { iqhco31CmdEntry 5582 }


	iqhco31BackupValidValidAudioMuteRecoverTimer OBJECT-TYPE
		SYNTAX		INTEGER
		MAX-ACCESS		read-write
		STATUS			current
		DESCRIPTION
				"TYPE: - Number
				 PAGE: - Backup- Video Backup- Backup Valid- Valid Audio
					Mute Recover Timer  cmdID= 5583  min= 0  max= 120  step= 1  format= %1.0f sec  div_scale= 1 
					Min = 0 sec  Max = 120 sec  Step = 1 sec "
		::= { iqhco31CmdEntry 5583 }


	iqhco31BackupValidValidAudioLowFailTimer OBJECT-TYPE
		SYNTAX		INTEGER
		MAX-ACCESS		read-write
		STATUS			current
		DESCRIPTION
				"TYPE: - Number
				 PAGE: - Backup- Video Backup- Backup Valid- Valid Audio
					Low Fail Timer  cmdID= 5572  min= 0  max= 120  step= 1  format= %1.0f sec  div_scale= 1 
					Min = 0 sec  Max = 120 sec  Step = 1 sec "
		::= { iqhco31CmdEntry 5572 }


	iqhco31BackupValidValidAudioLowRecoverTimer OBJECT-TYPE
		SYNTAX		INTEGER
		MAX-ACCESS		read-write
		STATUS			current
		DESCRIPTION
				"TYPE: - Number
				 PAGE: - Backup- Video Backup- Backup Valid- Valid Audio
					Low Recover Timer  cmdID= 5573  min= 0  max= 120  step= 1  format= %1.0f sec  div_scale= 1 
					Min = 0 sec  Max = 120 sec  Step = 1 sec "
		::= { iqhco31CmdEntry 5573 }


	iqhco31BackupValidValidAudioOverFailTimer OBJECT-TYPE
		SYNTAX		INTEGER
		MAX-ACCESS		read-write
		STATUS			current
		DESCRIPTION
				"TYPE: - Number
				 PAGE: - Backup- Video Backup- Backup Valid- Valid Audio
					Over Fail Timer  cmdID= 5574  min= 0  max= 120  step= 1  format= %1.0f sec  div_scale= 1 
					Min = 0 sec  Max = 120 sec  Step = 1 sec "
		::= { iqhco31CmdEntry 5574 }


	iqhco31BackupValidValidAudioOverRecoverTimer OBJECT-TYPE
		SYNTAX		INTEGER
		MAX-ACCESS		read-write
		STATUS			current
		DESCRIPTION
				"TYPE: - Number
				 PAGE: - Backup- Video Backup- Backup Valid- Valid Audio
					Over Recover Timer  cmdID= 5575  min= 0  max= 120  step= 1  format= %1.0f sec  div_scale= 1 
					Min = 0 sec  Max = 120 sec  Step = 1 sec "
		::= { iqhco31CmdEntry 5575 }


	iqhco31BackupVideoBackupDefaultOutput OBJECT-TYPE
		SYNTAX		INTEGER {
							val-Black(1),
							val-Freeze(2),
							val-Pattern(3),
							val-Backup(0)
							}
		MAX-ACCESS		read-write
		STATUS			current
		DESCRIPTION
				"TYPE: - RadiobuttonList
				 PAGE: - Backup- Video Backup
					Default Output  cmdID= 2628 
					Black  value= 1  
					Freeze  value= 2  
					Pattern  value= 3  
					Backup  value= 0  "
		::= { iqhco31CmdEntry 2628 }


	iqhco31VideoBackupVideoProcampProcAmpEnable OBJECT-TYPE
		SYNTAX		INTEGER { disable(0), enable(1) }
		MAX-ACCESS		read-write
		STATUS			current
		DESCRIPTION
				"TYPE: - Checkbox
				 PAGE: - Backup- Video Backup
					ProcAmp Enable  cmdID= 2865 "
		::= { iqhco31CmdEntry 2865 }


	iqhco31VideoBackupVideoProcampBlackLevel OBJECT-TYPE
		SYNTAX		INTEGER
		MAX-ACCESS		read-write
		STATUS			current
		DESCRIPTION
				"TYPE: - Number
				 PAGE: - Backup- Video Backup
					Black Level  cmdID= 2712  min= -1000  max= 1000  step= 8  format= %3.1fmV  div_scale= 10 
					Min = -100.0mV  Max = 100.0mV  Step = 0.8mV "
		::= { iqhco31CmdEntry 2712 }


	iqhco31VideoBackupVideoProcampHueAdjust OBJECT-TYPE
		SYNTAX		INTEGER
		MAX-ACCESS		read-write
		STATUS			current
		DESCRIPTION
				"TYPE: - Number
				 PAGE: - Backup- Video Backup
					Hue Adjust  cmdID= 3630  min= -180  max= 180  step= 1  format= %1.0fdeg  div_scale= 1 
					Min = -180deg  Max = 180deg  Step = 1deg "
		::= { iqhco31CmdEntry 3630 }


	iqhco31VideoBackupVideoProcampMasterVideoGain OBJECT-TYPE
		SYNTAX		INTEGER
		MAX-ACCESS		read-write
		STATUS			current
		DESCRIPTION
				"TYPE: - Number
				 PAGE: - Backup- Video Backup
					Master Video Gain  cmdID= 3788  min= -60  max= 60  step= 1  format= %0.1fdB  div_scale= 10 
					Min = -6.0dB  Max = 6.0dB  Step = 0.1dB "
		::= { iqhco31CmdEntry 3788 }


	iqhco31VideoBackupVideoProcampYGain OBJECT-TYPE
		SYNTAX		INTEGER
		MAX-ACCESS		read-write
		STATUS			current
		DESCRIPTION
				"TYPE: - Number
				 PAGE: - Backup- Video Backup
					Y Gain  cmdID= 2711  min= -60  max= 60  step= 1  format= %0.1fdB  div_scale= 10 
					Min = -6.0dB  Max = 6.0dB  Step = 0.1dB "
		::= { iqhco31CmdEntry 2711 }


	iqhco31VideoBackupVideoProcampCbCrGain OBJECT-TYPE
		SYNTAX		INTEGER
		MAX-ACCESS		read-write
		STATUS			current
		DESCRIPTION
				"TYPE: - Number
				 PAGE: - Backup- Video Backup
					Cb/Cr Gain  cmdID= 2710  min= -60  max= 60  step= 1  format= %0.1fdB  div_scale= 10 
					Min = -6.0dB  Max = 6.0dB  Step = 0.1dB "
		::= { iqhco31CmdEntry 2710 }


	iqhco31VideoBackupVideoProcampYCTiming OBJECT-TYPE
		SYNTAX		INTEGER
		MAX-ACCESS		read-write
		STATUS			current
		DESCRIPTION
				"TYPE: - Number
				 PAGE: - Backup- Video Backup
					Y/C Timing  cmdID= 2925  min= -8  max= 8  step= 2  format= %1.0f pixels  div_scale= 1 
					Min = -8 pixels  Max = 8 pixels  Step = 2 pixels "
		::= { iqhco31CmdEntry 2925 }


	iqhco31VideoBackupVideoProcampPictureposition OBJECT-TYPE
		SYNTAX		INTEGER
		MAX-ACCESS		read-write
		STATUS			current
		DESCRIPTION
				"TYPE: - Number
				 PAGE: - Backup- Video Backup
					Picture position  cmdID= 2713  min= -8  max= 8  step= 2  format= %1.0f pixels  div_scale= 1 
					Min = -8 pixels  Max = 8 pixels  Step = 2 pixels "
		::= { iqhco31CmdEntry 2713 }


	iqhco31VideoBackupVideoProcampModalIndex OBJECT-TYPE
		SYNTAX		INTEGER
		MAX-ACCESS		read-write
		STATUS			current
		DESCRIPTION
				"TYPE: - Number
				 PAGE: - Backup- Video Backup
					Modal Index  cmdID= 5009  min= 0  max= 1  step= 1  format= %1.0f  div_scale= 1 
					Min = 0  Max = 1  Step = 1 "
		::= { iqhco31CmdEntry 5009 }


	iqhco31VideoBackupVideoProcampYCTimingnm OBJECT-TYPE
		SYNTAX		INTEGER
		MAX-ACCESS		read-write
		STATUS			current
		DESCRIPTION
				"TYPE: - Number
				 PAGE: - Backup- Video Backup
					Y/C Timing nm  cmdID= 5011  min= -16  max= 16  step= 2  format= %1.0f pixels  div_scale= 1 
					Min = -16 pixels  Max = 16 pixels  Step = 2 pixels "
		::= { iqhco31CmdEntry 5011 }


	iqhco31VideoBackupVideoProcampPicturepositionnm OBJECT-TYPE
		SYNTAX		INTEGER
		MAX-ACCESS		read-write
		STATUS			current
		DESCRIPTION
				"TYPE: - Number
				 PAGE: - Backup- Video Backup
					Picture position nm  cmdID= 5010  min= -16  max= 16  step= 2  format= %1.0f pixels  div_scale= 1 
					Min = -16 pixels  Max = 16 pixels  Step = 2 pixels "
		::= { iqhco31CmdEntry 5010 }


	iqhco31VideoBackupBlankingBlankVANC OBJECT-TYPE
		SYNTAX		INTEGER { disable(0), enable(1) }
		MAX-ACCESS		read-write
		STATUS			current
		DESCRIPTION
				"TYPE: - Checkbox
				 PAGE: - Backup- Video Backup
					Blank VANC  cmdID= 3950 "
		::= { iqhco31CmdEntry 3950 }


	iqhco31Blanking625BlankLinesLine233971 OBJECT-TYPE
		SYNTAX		INTEGER { disable(0), enable(1) }
		MAX-ACCESS		read-write
		STATUS			current
		DESCRIPTION
				"TYPE: - Checkbox
				 PAGE: - Backup- Video Backup
					Line 23  cmdID= 3971 "
		::= { iqhco31CmdEntry 3971 }


	iqhco31Blanking625BlankLinesLine3363972 OBJECT-TYPE
		SYNTAX		INTEGER { disable(0), enable(1) }
		MAX-ACCESS		read-write
		STATUS			current
		DESCRIPTION
				"TYPE: - Checkbox
				 PAGE: - Backup- Video Backup
					Line 336  cmdID= 3972 "
		::= { iqhco31CmdEntry 3972 }


	iqhco31Blanking525BlankLinesLine213973 OBJECT-TYPE
		SYNTAX		INTEGER { disable(0), enable(1) }
		MAX-ACCESS		read-write
		STATUS			current
		DESCRIPTION
				"TYPE: - Checkbox
				 PAGE: - Backup- Video Backup
					Line 21  cmdID= 3973 "
		::= { iqhco31CmdEntry 3973 }


	iqhco31Blanking525BlankLinesLine223975 OBJECT-TYPE
		SYNTAX		INTEGER { disable(0), enable(1) }
		MAX-ACCESS		read-write
		STATUS			current
		DESCRIPTION
				"TYPE: - Checkbox
				 PAGE: - Backup- Video Backup
					Line 22  cmdID= 3975 "
		::= { iqhco31CmdEntry 3975 }


	iqhco31Blanking525BlankLinesLine2833974 OBJECT-TYPE
		SYNTAX		INTEGER { disable(0), enable(1) }
		MAX-ACCESS		read-write
		STATUS			current
		DESCRIPTION
				"TYPE: - Checkbox
				 PAGE: - Backup- Video Backup
					Line 283  cmdID= 3974 "
		::= { iqhco31CmdEntry 3974 }


	iqhco31Blanking525BlankLinesLine2843976 OBJECT-TYPE
		SYNTAX		INTEGER { disable(0), enable(1) }
		MAX-ACCESS		read-write
		STATUS			current
		DESCRIPTION
				"TYPE: - Checkbox
				 PAGE: - Backup- Video Backup
					Line 284  cmdID= 3976 "
		::= { iqhco31CmdEntry 3976 }


	iqhco31VideoBackupBlankingBlankHANC OBJECT-TYPE
		SYNTAX		INTEGER { disable(0), enable(1) }
		MAX-ACCESS		read-write
		STATUS			current
		DESCRIPTION
				"TYPE: - Checkbox
				 PAGE: - Backup- Video Backup
					Blank HANC  cmdID= 3948 "
		::= { iqhco31CmdEntry 3948 }


	iqhco31VideoBackupCaption OBJECT-TYPE
		SYNTAX		INTEGER {
							val-Animated-Off(0),
							val-Animated-Slow(1),
							val-Animated-Medium(2),
							val-Animated-Fast(3)
							}
		MAX-ACCESS		read-write
		STATUS			current
		DESCRIPTION
				"TYPE: - Button
				 PAGE: - Backup- Video Backup
					Animated Off  cmdID= 1039  value= 0  
					Animated Slow  cmdID= 1039  value= 1  
					Animated Medium  cmdID= 1039  value= 2  
					Animated Fast  cmdID= 1039  value= 3  "
		::= { iqhco31CmdEntry 1039 }


	iqhco31VideoBackupCaptionEditCaption OBJECT-TYPE
		SYNTAX		RollCallString
		MAX-ACCESS		read-write
		STATUS			current
		DESCRIPTION
				"TYPE: - Editstring
				 PAGE: - Backup- Video Backup
					Edit Caption  cmdID= 1040  "
		::= { iqhco31CmdEntry 1040 }


	iqhco31BackupVideoBackupPattern OBJECT-TYPE
		SYNTAX		INTEGER {
							val-Black(1),
							val-Bars(2)
							}
		MAX-ACCESS		read-write
		STATUS			current
		DESCRIPTION
				"TYPE: - RadiobuttonList
				 PAGE: - Backup- Video Backup
					Pattern  cmdID= 2629 
					Black  value= 1  
					Bars  value= 2  "
		::= { iqhco31CmdEntry 2629 }


	iqhco31VideoBackupFreeze OBJECT-TYPE
		SYNTAX		INTEGER {
							val-Field(0),
							val-Frame(1)
							}
		MAX-ACCESS		read-write
		STATUS			current
		DESCRIPTION
				"TYPE: - Button
				 PAGE: - Backup- Video Backup
					Field  cmdID= 5025  value= 0  
					Frame  cmdID= 5025  value= 1  "
		::= { iqhco31CmdEntry 5025 }


	iqhco31VideoBackupFreezeManualFreeze OBJECT-TYPE
		SYNTAX		INTEGER { disable(0), enable(1) }
		MAX-ACCESS		read-write
		STATUS			current
		DESCRIPTION
				"TYPE: - Checkbox
				 PAGE: - Backup- Video Backup
					Manual Freeze  cmdID= 5024 "
		::= { iqhco31CmdEntry 5024 }


	iqhco31AudioBackupEmbeddersEnable5070 OBJECT-TYPE
		SYNTAX		INTEGER { disable(0), enable(1) }
		MAX-ACCESS		read-write
		STATUS			current
		DESCRIPTION
				"TYPE: - Checkbox
				 PAGE: - Backup- Audio Backup
					Enable  cmdID= 5070 "
		::= { iqhco31CmdEntry 5070 }


	iqhco31AudioBackupEmbeddersEnable5071 OBJECT-TYPE
		SYNTAX		INTEGER { disable(0), enable(1) }
		MAX-ACCESS		read-write
		STATUS			current
		DESCRIPTION
				"TYPE: - Checkbox
				 PAGE: - Backup- Audio Backup
					Enable  cmdID= 5071 "
		::= { iqhco31CmdEntry 5071 }


	iqhco31AudioBackupEmbeddersEnable5072 OBJECT-TYPE
		SYNTAX		INTEGER { disable(0), enable(1) }
		MAX-ACCESS		read-write
		STATUS			current
		DESCRIPTION
				"TYPE: - Checkbox
				 PAGE: - Backup- Audio Backup
					Enable  cmdID= 5072 "
		::= { iqhco31CmdEntry 5072 }


	iqhco31AudioBackupEmbeddersEnable5073 OBJECT-TYPE
		SYNTAX		INTEGER { disable(0), enable(1) }
		MAX-ACCESS		read-write
		STATUS			current
		DESCRIPTION
				"TYPE: - Checkbox
				 PAGE: - Backup- Audio Backup
					Enable  cmdID= 5073 "
		::= { iqhco31CmdEntry 5073 }


	iqhco31AudioDelayDelaysVideoDelay5089 OBJECT-TYPE
		SYNTAX		INTEGER { disable(0), enable(1) }
		MAX-ACCESS		read-write
		STATUS			current
		DESCRIPTION
				"TYPE: - Checkbox
				 PAGE: - Backup- Audio Backup
					Video Delay  cmdID= 5089 "
		::= { iqhco31CmdEntry 5089 }


	iqhco31AudioDelayDelaysManualDelay5090 OBJECT-TYPE
		SYNTAX		INTEGER { disable(0), enable(1) }
		MAX-ACCESS		read-write
		STATUS			current
		DESCRIPTION
				"TYPE: - Checkbox
				 PAGE: - Backup- Audio Backup
					Manual Delay  cmdID= 5090 "
		::= { iqhco31CmdEntry 5090 }


	iqhco31AudioDelayDelaysTrack14Delay5091 OBJECT-TYPE
		SYNTAX		INTEGER { disable(0), enable(1) }
		MAX-ACCESS		read-write
		STATUS			current
		DESCRIPTION
				"TYPE: - Checkbox
				 PAGE: - Backup- Audio Backup
					Track 14 Delay  cmdID= 5091 "
		::= { iqhco31CmdEntry 5091 }


	iqhco31AudioDelayDelaysTrack15Delay5092 OBJECT-TYPE
		SYNTAX		INTEGER { disable(0), enable(1) }
		MAX-ACCESS		read-write
		STATUS			current
		DESCRIPTION
				"TYPE: - Checkbox
				 PAGE: - Backup- Audio Backup
					Track 15 Delay  cmdID= 5092 "
		::= { iqhco31CmdEntry 5092 }


	iqhco31AudioDelayDelaysTrack16Delay5093 OBJECT-TYPE
		SYNTAX		INTEGER { disable(0), enable(1) }
		MAX-ACCESS		read-write
		STATUS			current
		DESCRIPTION
				"TYPE: - Checkbox
				 PAGE: - Backup- Audio Backup
					Track 16 Delay  cmdID= 5093 "
		::= { iqhco31CmdEntry 5093 }


	iqhco31AudioDelayDelaysTrack17Delay5094 OBJECT-TYPE
		SYNTAX		INTEGER { disable(0), enable(1) }
		MAX-ACCESS		read-write
		STATUS			current
		DESCRIPTION
				"TYPE: - Checkbox
				 PAGE: - Backup- Audio Backup
					Track 17 Delay  cmdID= 5094 "
		::= { iqhco31CmdEntry 5094 }


	iqhco31AudioDelayDelaysCoarseDelay5086 OBJECT-TYPE
		SYNTAX		INTEGER
		MAX-ACCESS		read-write
		STATUS			current
		DESCRIPTION
				"TYPE: - Number
				 PAGE: - Backup- Audio Backup
					Coarse Delay  cmdID= 5086  min= 0  max= 1750  step= 5  format= %5.3fs  div_scale= 1000 
					Min = 0.000s  Max = 1.750s  Step = 0.005s "
		::= { iqhco31CmdEntry 5086 }


	iqhco31AudioDelayDelaysFineDelay5088 OBJECT-TYPE
		SYNTAX		INTEGER
		MAX-ACCESS		read-write
		STATUS			current
		DESCRIPTION
				"TYPE: - Number
				 PAGE: - Backup- Audio Backup
					Fine Delay  cmdID= 5088  min= -2500  max= 2500  step= 5  format= %0.1fms  div_scale= 10 
					Min = -250.0ms  Max = 250.0ms  Step = 0.5ms "
		::= { iqhco31CmdEntry 5088 }


	iqhco31AudioDelayDelayStatusTotalDelay5095 OBJECT-TYPE
		SYNTAX		RollCallString
		MAX-ACCESS		read-only
		STATUS			current
		DESCRIPTION
				"TYPE: - Display
				 PAGE: - Backup- Audio Backup
					Total Delay  cmdID= 5095  format=   "
		::= { iqhco31CmdEntry 5095 }


	iqhco31AudioDelayDelayStatusVideoDelay5085 OBJECT-TYPE
		SYNTAX		RollCallString
		MAX-ACCESS		read-only
		STATUS			current
		DESCRIPTION
				"TYPE: - Display
				 PAGE: - Backup- Audio Backup
					Video Delay  cmdID= 5085  format=   "
		::= { iqhco31CmdEntry 5085 }


	iqhco31AudioDelayDelayStatusManualDelay5087 OBJECT-TYPE
		SYNTAX		RollCallString
		MAX-ACCESS		read-only
		STATUS			current
		DESCRIPTION
				"TYPE: - Display
				 PAGE: - Backup- Audio Backup
					Manual Delay  cmdID= 5087  format=   "
		::= { iqhco31CmdEntry 5087 }


	iqhco31RulesRulesVideoMasterCurrentOutput OBJECT-TYPE
		SYNTAX		RollCallString
		MAX-ACCESS		read-only
		STATUS			current
		DESCRIPTION
				"TYPE: - Display
				 PAGE: - Rules- Rules Video Master
					Current Output  cmdID= 6630  format=   "
		::= { iqhco31CmdEntry 6630 }


	iqhco31RulesRulesVideoMasterSwitchtoMaster OBJECT-TYPE
		SYNTAX		INTEGER { disable(0), enable(1) }
		MAX-ACCESS		read-write
		STATUS			current
		DESCRIPTION
				"TYPE: - Checkbox
				 PAGE: - Rules- Rules Video Master
					Switch to Master  cmdID= 5600 "
		::= { iqhco31CmdEntry 5600 }


	iqhco31RulesRulesVideoMasterActive OBJECT-TYPE
		SYNTAX		RollCallString
		MAX-ACCESS		read-only
		STATUS			current
		DESCRIPTION
				"TYPE: - Display
				 PAGE: - Rules- Rules Video Master
					Active  cmdID= 5601  format=   "
		::= { iqhco31CmdEntry 5601 }


	iqhco31RulesRulesVideoMaster5602 OBJECT-TYPE
		SYNTAX		INTEGER {
							val-or-OK-Master(1),
							val-and-OK-Master(2),
							val-Don-t-use-Master(5)
							}
		MAX-ACCESS		read-write
		STATUS			current
		DESCRIPTION
				"TYPE: - Button
				 PAGE: - Rules- Rules Video Master
					or:OK Master  cmdID= 5602  value= 1  
					and:OK Master  cmdID= 5602  value= 2  
					Don't use Master  cmdID= 5602  value= 5  "
		::= { iqhco31CmdEntry 5602 }


	iqhco31RulesRulesVideoMaster5603 OBJECT-TYPE
		SYNTAX		INTEGER {
							val-or-FAIL-Backup(3),
							val-Don-t-use-Backup(5)
							}
		MAX-ACCESS		read-write
		STATUS			current
		DESCRIPTION
				"TYPE: - Button
				 PAGE: - Rules- Rules Video Master
					or:FAIL Backup  cmdID= 5603  value= 3  
					Don't use Backup  cmdID= 5603  value= 5  "
		::= { iqhco31CmdEntry 5603 }


	iqhco31RulesRulesVideoMaster5604 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules Video Master
					or:GPI1 High  cmdID= 5604  value= 1  
					or:GPI1 Low  cmdID= 5604  value= 3  
					and:GPI1 High  cmdID= 5604  value= 2  
					and:GPI1 Low  cmdID= 5604  value= 4  
					Don't use GPI1  cmdID= 5604  value= 5  "
		::= { iqhco31CmdEntry 5604 }


	iqhco31RulesRulesVideoMaster5605 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules Video Master
					or:GPI2 High  cmdID= 5605  value= 1  
					or:GPI2 Low  cmdID= 5605  value= 3  
					and:GPI2 High  cmdID= 5605  value= 2  
					and:GPI2 Low  cmdID= 5605  value= 4  
					Don't use GPI2  cmdID= 5605  value= 5  "
		::= { iqhco31CmdEntry 5605 }


	iqhco31RulesRulesVideoMaster5606 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules Video Master
					or:GPI3 High  cmdID= 5606  value= 1  
					or:GPI3 Low  cmdID= 5606  value= 3  
					and:GPI3 High  cmdID= 5606  value= 2  
					and:GPI3 Low  cmdID= 5606  value= 4  
					Don't use GPI3  cmdID= 5606  value= 5  "
		::= { iqhco31CmdEntry 5606 }


	iqhco31RulesRulesVideoMaster5607 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules Video Master
					or:GPI4 High  cmdID= 5607  value= 1  
					or:GPI4 Low  cmdID= 5607  value= 3  
					and:GPI4 High  cmdID= 5607  value= 2  
					and:GPI4 Low  cmdID= 5607  value= 4  
					Don't use GPI4  cmdID= 5607  value= 5  "
		::= { iqhco31CmdEntry 5607 }


	iqhco31RulesRulesVideoMaster5608 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules Video Master
					or:RollTrack101=1  cmdID= 5608  value= 1  
					or:RollTrack101=0  cmdID= 5608  value= 3  
					and:RollTrack101=1  cmdID= 5608  value= 2  
					and:RollTrack101=0  cmdID= 5608  value= 4  
					Don't use 101  cmdID= 5608  value= 5  "
		::= { iqhco31CmdEntry 5608 }


	iqhco31RulesRulesVideoMaster5609 OBJECT-TYPE
		SYNTAX		INTEGER {
							val-or-RollTrack102-1(1),
							val-or-RollTrack102-0(3),
							val-and-RollTrack102-1(2),
							val-and-RollTrack102-0(4),
							val-Don-t-use-102(5)
							}
		MAX-ACCESS		read-write
		STATUS			current
		DESCRIPTION
				"TYPE: - Button
				 PAGE: - Rules- Rules Video Master
					or:RollTrack102=1  cmdID= 5609  value= 1  
					or:RollTrack102=0  cmdID= 5609  value= 3  
					and:RollTrack102=1  cmdID= 5609  value= 2  
					and:RollTrack102=0  cmdID= 5609  value= 4  
					Don't use 102  cmdID= 5609  value= 5  "
		::= { iqhco31CmdEntry 5609 }


	iqhco31RulesRulesVideoMaster5610 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules Video Master
					or:RollTrack103=1  cmdID= 5610  value= 1  
					or:RollTrack103=0  cmdID= 5610  value= 3  
					and:RollTrack103=1  cmdID= 5610  value= 2  
					and:RollTrack103=0  cmdID= 5610  value= 4  
					Don't use 103  cmdID= 5610  value= 5  "
		::= { iqhco31CmdEntry 5610 }


	iqhco31RulesRulesVideoMaster5611 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules Video Master
					or:RollTrack104=1  cmdID= 5611  value= 1  
					or:RollTrack104=0  cmdID= 5611  value= 3  
					and:RollTrack104=1  cmdID= 5611  value= 2  
					and:RollTrack104=0  cmdID= 5611  value= 4  
					Don't use 104  cmdID= 5611  value= 5  "
		::= { iqhco31CmdEntry 5611 }


	iqhco31RulesRulesVideoBackupSwitchtoBackup OBJECT-TYPE
		SYNTAX		INTEGER { disable(0), enable(1) }
		MAX-ACCESS		read-write
		STATUS			current
		DESCRIPTION
				"TYPE: - Checkbox
				 PAGE: - Rules- Rules Video Backup
					Switch to Backup  cmdID= 5620 "
		::= { iqhco31CmdEntry 5620 }


	iqhco31RulesRulesVideoBackupActive OBJECT-TYPE
		SYNTAX		RollCallString
		MAX-ACCESS		read-only
		STATUS			current
		DESCRIPTION
				"TYPE: - Display
				 PAGE: - Rules- Rules Video Backup
					Active  cmdID= 5621  format=   "
		::= { iqhco31CmdEntry 5621 }


	iqhco31RulesRulesVideoBackup5622 OBJECT-TYPE
		SYNTAX		INTEGER {
							val-or-FAIL-Master(3),
							val-Don-t-use-Master(5)
							}
		MAX-ACCESS		read-write
		STATUS			current
		DESCRIPTION
				"TYPE: - Button
				 PAGE: - Rules- Rules Video Backup
					or:FAIL Master  cmdID= 5622  value= 3  
					Don't use Master  cmdID= 5622  value= 5  "
		::= { iqhco31CmdEntry 5622 }


	iqhco31RulesRulesVideoBackup5623 OBJECT-TYPE
		SYNTAX		INTEGER {
							val-or-OK-Backup(1),
							val-and-OK-Backup(2),
							val-Don-t-use-Backup(5)
							}
		MAX-ACCESS		read-write
		STATUS			current
		DESCRIPTION
				"TYPE: - Button
				 PAGE: - Rules- Rules Video Backup
					or:OK Backup  cmdID= 5623  value= 1  
					and:OK Backup  cmdID= 5623  value= 2  
					Don't use Backup  cmdID= 5623  value= 5  "
		::= { iqhco31CmdEntry 5623 }


	iqhco31RulesRulesVideoBackup5624 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules Video Backup
					or:GPI1 High  cmdID= 5624  value= 1  
					or:GPI1 Low  cmdID= 5624  value= 3  
					and:GPI1 High  cmdID= 5624  value= 2  
					and:GPI1 Low  cmdID= 5624  value= 4  
					Don't use GPI1  cmdID= 5624  value= 5  "
		::= { iqhco31CmdEntry 5624 }


	iqhco31RulesRulesVideoBackup5625 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules Video Backup
					or:GPI2 High  cmdID= 5625  value= 1  
					or:GPI2 Low  cmdID= 5625  value= 3  
					and:GPI2 High  cmdID= 5625  value= 2  
					and:GPI2 Low  cmdID= 5625  value= 4  
					Don't use GPI2  cmdID= 5625  value= 5  "
		::= { iqhco31CmdEntry 5625 }


	iqhco31RulesRulesVideoBackup5626 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules Video Backup
					or:GPI3 High  cmdID= 5626  value= 1  
					or:GPI3 Low  cmdID= 5626  value= 3  
					and:GPI3 High  cmdID= 5626  value= 2  
					and:GPI3 Low  cmdID= 5626  value= 4  
					Don't use GPI3  cmdID= 5626  value= 5  "
		::= { iqhco31CmdEntry 5626 }


	iqhco31RulesRulesVideoBackup5627 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules Video Backup
					or:GPI4 High  cmdID= 5627  value= 1  
					or:GPI4 Low  cmdID= 5627  value= 3  
					and:GPI4 High  cmdID= 5627  value= 2  
					and:GPI4 Low  cmdID= 5627  value= 4  
					Don't use GPI4  cmdID= 5627  value= 5  "
		::= { iqhco31CmdEntry 5627 }


	iqhco31RulesRulesVideoBackup5628 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules Video Backup
					or:RollTrack101=1  cmdID= 5628  value= 1  
					or:RollTrack101=0  cmdID= 5628  value= 3  
					and:RollTrack101=1  cmdID= 5628  value= 2  
					and:RollTrack101=0  cmdID= 5628  value= 4  
					Don't use 101  cmdID= 5628  value= 5  "
		::= { iqhco31CmdEntry 5628 }


	iqhco31RulesRulesVideoBackup5629 OBJECT-TYPE
		SYNTAX		INTEGER {
							val-or-RollTrack102-1(1),
							val-or-RollTrack102-0(3),
							val-and-RollTrack102-1(2),
							val-and-RollTrack102-0(4),
							val-Don-t-use-102(5)
							}
		MAX-ACCESS		read-write
		STATUS			current
		DESCRIPTION
				"TYPE: - Button
				 PAGE: - Rules- Rules Video Backup
					or:RollTrack102=1  cmdID= 5629  value= 1  
					or:RollTrack102=0  cmdID= 5629  value= 3  
					and:RollTrack102=1  cmdID= 5629  value= 2  
					and:RollTrack102=0  cmdID= 5629  value= 4  
					Don't use 102  cmdID= 5629  value= 5  "
		::= { iqhco31CmdEntry 5629 }


	iqhco31RulesRulesVideoBackup5630 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules Video Backup
					or:RollTrack103=1  cmdID= 5630  value= 1  
					or:RollTrack103=0  cmdID= 5630  value= 3  
					and:RollTrack103=1  cmdID= 5630  value= 2  
					and:RollTrack103=0  cmdID= 5630  value= 4  
					Don't use 103  cmdID= 5630  value= 5  "
		::= { iqhco31CmdEntry 5630 }


	iqhco31RulesRulesVideoBackup5631 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules Video Backup
					or:RollTrack104=1  cmdID= 5631  value= 1  
					or:RollTrack104=0  cmdID= 5631  value= 3  
					and:RollTrack104=1  cmdID= 5631  value= 2  
					and:RollTrack104=0  cmdID= 5631  value= 4  
					Don't use 104  cmdID= 5631  value= 5  "
		::= { iqhco31CmdEntry 5631 }


	iqhco31GPIEnableGPIO1GPIO1State OBJECT-TYPE
		SYNTAX		RollCallString
		MAX-ACCESS		read-only
		STATUS			current
		DESCRIPTION
				"TYPE: - Display
				 PAGE: - Rules
					GPIO 1 State  cmdID= 6640  format=   "
		::= { iqhco31CmdEntry 6640 }


	iqhco31GPIEnableGPIO1 OBJECT-TYPE
		SYNTAX		INTEGER {
							val-GPIO-1-Input(1),
							val-GPIO-1-Output(0),
							val-GPIO-1-Unused(2)
							}
		MAX-ACCESS		read-write
		STATUS			current
		DESCRIPTION
				"TYPE: - Button
				 PAGE: - Rules
					GPIO 1 Input  cmdID= 6641  value= 1  
					GPIO 1 Output  cmdID= 6641  value= 0  
					GPIO 1 Unused  cmdID= 6641  value= 2  "
		::= { iqhco31CmdEntry 6641 }


	iqhco31GPIEnableGPIO1GPO1Invert OBJECT-TYPE
		SYNTAX		INTEGER { disable(0), enable(1) }
		MAX-ACCESS		read-write
		STATUS			current
		DESCRIPTION
				"TYPE: - Checkbox
				 PAGE: - Rules
					GPO 1 Invert  cmdID= 7071 "
		::= { iqhco31CmdEntry 7071 }


	iqhco31GPIEnableGPIO2GPIO2State OBJECT-TYPE
		SYNTAX		RollCallString
		MAX-ACCESS		read-only
		STATUS			current
		DESCRIPTION
				"TYPE: - Display
				 PAGE: - Rules
					GPIO 2 State  cmdID= 6642  format=   "
		::= { iqhco31CmdEntry 6642 }


	iqhco31GPIEnableGPIO2 OBJECT-TYPE
		SYNTAX		INTEGER {
							val-GPIO-2-Input(1),
							val-GPIO-2-Output(0),
							val-GPIO-2-Unused(2)
							}
		MAX-ACCESS		read-write
		STATUS			current
		DESCRIPTION
				"TYPE: - Button
				 PAGE: - Rules
					GPIO 2 Input  cmdID= 6643  value= 1  
					GPIO 2 Output  cmdID= 6643  value= 0  
					GPIO 2 Unused  cmdID= 6643  value= 2  "
		::= { iqhco31CmdEntry 6643 }


	iqhco31GPIEnableGPIO2GPO2Invert OBJECT-TYPE
		SYNTAX		INTEGER { disable(0), enable(1) }
		MAX-ACCESS		read-write
		STATUS			current
		DESCRIPTION
				"TYPE: - Checkbox
				 PAGE: - Rules
					GPO 2 Invert  cmdID= 7072 "
		::= { iqhco31CmdEntry 7072 }


	iqhco31GPIEnableGPIO3GPIO3State OBJECT-TYPE
		SYNTAX		RollCallString
		MAX-ACCESS		read-only
		STATUS			current
		DESCRIPTION
				"TYPE: - Display
				 PAGE: - Rules
					GPIO 3 State  cmdID= 6644  format=   "
		::= { iqhco31CmdEntry 6644 }


	iqhco31GPIEnableGPIO3 OBJECT-TYPE
		SYNTAX		INTEGER {
							val-GPIO-3-Input(1),
							val-GPIO-3-Output(0),
							val-GPIO-3-Unused(2)
							}
		MAX-ACCESS		read-write
		STATUS			current
		DESCRIPTION
				"TYPE: - Button
				 PAGE: - Rules
					GPIO 3 Input  cmdID= 6645  value= 1  
					GPIO 3 Output  cmdID= 6645  value= 0  
					GPIO 3 Unused  cmdID= 6645  value= 2  "
		::= { iqhco31CmdEntry 6645 }


	iqhco31GPIEnableGPIO3GPO3Invert OBJECT-TYPE
		SYNTAX		INTEGER { disable(0), enable(1) }
		MAX-ACCESS		read-write
		STATUS			current
		DESCRIPTION
				"TYPE: - Checkbox
				 PAGE: - Rules
					GPO 3 Invert  cmdID= 7073 "
		::= { iqhco31CmdEntry 7073 }


	iqhco31GPIEnableGPIO4GPIO4State OBJECT-TYPE
		SYNTAX		RollCallString
		MAX-ACCESS		read-only
		STATUS			current
		DESCRIPTION
				"TYPE: - Display
				 PAGE: - Rules
					GPIO 4 State  cmdID= 6646  format=   "
		::= { iqhco31CmdEntry 6646 }


	iqhco31GPIEnableGPIO4 OBJECT-TYPE
		SYNTAX		INTEGER {
							val-GPIO-4-Input(1),
							val-GPIO-4-Output(0),
							val-GPIO-4-Unused(2)
							}
		MAX-ACCESS		read-write
		STATUS			current
		DESCRIPTION
				"TYPE: - Button
				 PAGE: - Rules
					GPIO 4 Input  cmdID= 6647  value= 1  
					GPIO 4 Output  cmdID= 6647  value= 0  
					GPIO 4 Unused  cmdID= 6647  value= 2  "
		::= { iqhco31CmdEntry 6647 }


	iqhco31GPIEnableGPIO4GPO4Invert OBJECT-TYPE
		SYNTAX		INTEGER { disable(0), enable(1) }
		MAX-ACCESS		read-write
		STATUS			current
		DESCRIPTION
				"TYPE: - Checkbox
				 PAGE: - Rules
					GPO 4 Invert  cmdID= 7074 "
		::= { iqhco31CmdEntry 7074 }


	iqhco31RulesGPIEnableNoGPIsonRear OBJECT-TYPE
		SYNTAX		RollCallString
		MAX-ACCESS		read-only
		STATUS			current
		DESCRIPTION
				"TYPE: - Display
				 PAGE: - Rules
					No GPI's on Rear  cmdID= 7077  format=   "
		::= { iqhco31CmdEntry 7077 }


	iqhco31RulesRulesGPI1outActive OBJECT-TYPE
		SYNTAX		RollCallString
		MAX-ACCESS		read-only
		STATUS			current
		DESCRIPTION
				"TYPE: - Display
				 PAGE: - Rules- Rules GPI 1 out
					Active  cmdID= 5661  format=   "
		::= { iqhco31CmdEntry 5661 }


	iqhco31RulesRulesGPI1out5672 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules GPI 1 out
					or:Master Selected  cmdID= 5672  value= 1  
					or:Backup Selected  cmdID= 5672  value= 2  
					Don't Use  cmdID= 5672  value= 3  "
		::= { iqhco31CmdEntry 5672 }


	iqhco31RulesRulesGPI1out5662 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules GPI 1 out
					or:OK Master  cmdID= 5662  value= 1  
					or:FAIL Master  cmdID= 5662  value= 3  
					and:OK Master  cmdID= 5662  value= 2  
					and:FAIL Master  cmdID= 5662  value= 4  
					Don't use Master  cmdID= 5662  value= 5  "
		::= { iqhco31CmdEntry 5662 }


	iqhco31RulesRulesGPI1out5663 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules GPI 1 out
					or:OK Backup  cmdID= 5663  value= 1  
					or:FAIL Backup  cmdID= 5663  value= 3  
					and:OK Backup  cmdID= 5663  value= 2  
					and:FAIL Backup  cmdID= 5663  value= 4  
					Don't use Backup  cmdID= 5663  value= 5  "
		::= { iqhco31CmdEntry 5663 }


	iqhco31RulesRulesGPI1out5664 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules GPI 1 out
					or:GPI1 High  cmdID= 5664  value= 1  
					or:GPI1 Low  cmdID= 5664  value= 3  
					and:GPI1 High  cmdID= 5664  value= 2  
					and:GPI1 Low  cmdID= 5664  value= 4  
					Don't use GPI1  cmdID= 5664  value= 5  "
		::= { iqhco31CmdEntry 5664 }


	iqhco31RulesRulesGPI1out5665 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules GPI 1 out
					or:GPI2 High  cmdID= 5665  value= 1  
					or:GPI2 Low  cmdID= 5665  value= 3  
					and:GPI2 High  cmdID= 5665  value= 2  
					and:GPI2 Low  cmdID= 5665  value= 4  
					Don't use GPI2  cmdID= 5665  value= 5  "
		::= { iqhco31CmdEntry 5665 }


	iqhco31RulesRulesGPI1out5666 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules GPI 1 out
					or:GPI3 High  cmdID= 5666  value= 1  
					or:GPI3 Low  cmdID= 5666  value= 3  
					and:GPI3 High  cmdID= 5666  value= 2  
					and:GPI3 Low  cmdID= 5666  value= 4  
					Don't use GPI3  cmdID= 5666  value= 5  "
		::= { iqhco31CmdEntry 5666 }


	iqhco31RulesRulesGPI1out5667 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules GPI 1 out
					or:GPI4 High  cmdID= 5667  value= 1  
					or:GPI4 Low  cmdID= 5667  value= 3  
					and:GPI4 High  cmdID= 5667  value= 2  
					and:GPI4 Low  cmdID= 5667  value= 4  
					Don't use GPI4  cmdID= 5667  value= 5  "
		::= { iqhco31CmdEntry 5667 }


	iqhco31RulesRulesGPI1out5668 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules GPI 1 out
					or:RollTrack101=1  cmdID= 5668  value= 1  
					or:RollTrack101=0  cmdID= 5668  value= 3  
					and:RollTrack101=1  cmdID= 5668  value= 2  
					and:RollTrack101=0  cmdID= 5668  value= 4  
					Don't use 101  cmdID= 5668  value= 5  "
		::= { iqhco31CmdEntry 5668 }


	iqhco31RulesRulesGPI1out5669 OBJECT-TYPE
		SYNTAX		INTEGER {
							val-or-RollTrack102-1(1),
							val-or-RollTrack102-0(3),
							val-and-RollTrack102-1(2),
							val-and-RollTrack102-0(4),
							val-Don-t-use-102(5)
							}
		MAX-ACCESS		read-write
		STATUS			current
		DESCRIPTION
				"TYPE: - Button
				 PAGE: - Rules- Rules GPI 1 out
					or:RollTrack102=1  cmdID= 5669  value= 1  
					or:RollTrack102=0  cmdID= 5669  value= 3  
					and:RollTrack102=1  cmdID= 5669  value= 2  
					and:RollTrack102=0  cmdID= 5669  value= 4  
					Don't use 102  cmdID= 5669  value= 5  "
		::= { iqhco31CmdEntry 5669 }


	iqhco31RulesRulesGPI1out5670 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules GPI 1 out
					or:RollTrack103=1  cmdID= 5670  value= 1  
					or:RollTrack103=0  cmdID= 5670  value= 3  
					and:RollTrack103=1  cmdID= 5670  value= 2  
					and:RollTrack103=0  cmdID= 5670  value= 4  
					Don't use 103  cmdID= 5670  value= 5  "
		::= { iqhco31CmdEntry 5670 }


	iqhco31RulesRulesGPI1out OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules GPI 1 out
					or:RollTrack104=1  cmdID= 5671  value= 1  
					or:RollTrack104=0  cmdID= 5671  value= 3  
					and:RollTrack104=1  cmdID= 5671  value= 2  
					and:RollTrack104=0  cmdID= 5671  value= 4  
					Don't use 104  cmdID= 5671  value= 5  "
		::= { iqhco31CmdEntry 5671 }


	iqhco31RulesRulesGPI2outActive OBJECT-TYPE
		SYNTAX		RollCallString
		MAX-ACCESS		read-only
		STATUS			current
		DESCRIPTION
				"TYPE: - Display
				 PAGE: - Rules- Rules GPI 2 out
					Active  cmdID= 5681  format=   "
		::= { iqhco31CmdEntry 5681 }


	iqhco31RulesRulesGPI2out5692 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules GPI 2 out
					or:Master Selected  cmdID= 5692  value= 1  
					or:Backup Selected  cmdID= 5692  value= 2  
					Don't Use  cmdID= 5692  value= 3  "
		::= { iqhco31CmdEntry 5692 }


	iqhco31RulesRulesGPI2out5682 OBJECT-TYPE
		SYNTAX		INTEGER {
							val-or-OK-Master(1),
							val-or-FAIL-Master(3),
							val-and-OK-Master(2),
							val-and-FAIL-Master(4),
							val-Don-t-use(5)
							}
		MAX-ACCESS		read-write
		STATUS			current
		DESCRIPTION
				"TYPE: - Button
				 PAGE: - Rules- Rules GPI 2 out
					or:OK Master  cmdID= 5682  value= 1  
					or:FAIL Master  cmdID= 5682  value= 3  
					and:OK Master  cmdID= 5682  value= 2  
					and:FAIL Master  cmdID= 5682  value= 4  
					Don't use  cmdID= 5682  value= 5  "
		::= { iqhco31CmdEntry 5682 }


	iqhco31RulesRulesGPI2out5683 OBJECT-TYPE
		SYNTAX		INTEGER {
							val-or-OK-Backup(1),
							val-or-FAIL-Backup(3),
							val-and-OK-Backup(2),
							val-and-FAIL-Backup(4),
							val-Don-t-use(5)
							}
		MAX-ACCESS		read-write
		STATUS			current
		DESCRIPTION
				"TYPE: - Button
				 PAGE: - Rules- Rules GPI 2 out
					or:OK Backup  cmdID= 5683  value= 1  
					or:FAIL Backup  cmdID= 5683  value= 3  
					and:OK Backup  cmdID= 5683  value= 2  
					and:FAIL Backup  cmdID= 5683  value= 4  
					Don't use  cmdID= 5683  value= 5  "
		::= { iqhco31CmdEntry 5683 }


	iqhco31RulesRulesGPI2out5684 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules GPI 2 out
					or:GPI1 High  cmdID= 5684  value= 1  
					or:GPI1 Low  cmdID= 5684  value= 3  
					and:GPI1 High  cmdID= 5684  value= 2  
					and:GPI1 Low  cmdID= 5684  value= 4  
					Don't use GPI1  cmdID= 5684  value= 5  "
		::= { iqhco31CmdEntry 5684 }


	iqhco31RulesRulesGPI2out5685 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules GPI 2 out
					or:GPI2 High  cmdID= 5685  value= 1  
					or:GPI2 Low  cmdID= 5685  value= 3  
					and:GPI2 High  cmdID= 5685  value= 2  
					and:GPI2 Low  cmdID= 5685  value= 4  
					Don't use GPI2  cmdID= 5685  value= 5  "
		::= { iqhco31CmdEntry 5685 }


	iqhco31RulesRulesGPI2out5686 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules GPI 2 out
					or:GPI3 High  cmdID= 5686  value= 1  
					or:GPI3 Low  cmdID= 5686  value= 3  
					and:GPI3 High  cmdID= 5686  value= 2  
					and:GPI3 Low  cmdID= 5686  value= 4  
					Don't use GPI3  cmdID= 5686  value= 5  "
		::= { iqhco31CmdEntry 5686 }


	iqhco31RulesRulesGPI2out5687 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules GPI 2 out
					or:GPI4 High  cmdID= 5687  value= 1  
					or:GPI4 Low  cmdID= 5687  value= 3  
					and:GPI4 High  cmdID= 5687  value= 2  
					and:GPI4 Low  cmdID= 5687  value= 4  
					Don't use GPI4  cmdID= 5687  value= 5  "
		::= { iqhco31CmdEntry 5687 }


	iqhco31RulesRulesGPI2out5688 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules GPI 2 out
					or:RollTrack101=1  cmdID= 5688  value= 1  
					or:RollTrack101=0  cmdID= 5688  value= 3  
					and:RollTrack101=1  cmdID= 5688  value= 2  
					and:RollTrack101=0  cmdID= 5688  value= 4  
					Don't use 101  cmdID= 5688  value= 5  "
		::= { iqhco31CmdEntry 5688 }


	iqhco31RulesRulesGPI2out5689 OBJECT-TYPE
		SYNTAX		INTEGER {
							val-or-RollTrack102-1(1),
							val-or-RollTrack102-0(3),
							val-and-RollTrack102-1(2),
							val-and-RollTrack102-0(4),
							val-Don-t-use-102(5)
							}
		MAX-ACCESS		read-write
		STATUS			current
		DESCRIPTION
				"TYPE: - Button
				 PAGE: - Rules- Rules GPI 2 out
					or:RollTrack102=1  cmdID= 5689  value= 1  
					or:RollTrack102=0  cmdID= 5689  value= 3  
					and:RollTrack102=1  cmdID= 5689  value= 2  
					and:RollTrack102=0  cmdID= 5689  value= 4  
					Don't use 102  cmdID= 5689  value= 5  "
		::= { iqhco31CmdEntry 5689 }


	iqhco31RulesRulesGPI2out5690 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules GPI 2 out
					or:RollTrack103=1  cmdID= 5690  value= 1  
					or:RollTrack103=0  cmdID= 5690  value= 3  
					and:RollTrack103=1  cmdID= 5690  value= 2  
					and:RollTrack103=0  cmdID= 5690  value= 4  
					Don't use 103  cmdID= 5690  value= 5  "
		::= { iqhco31CmdEntry 5690 }


	iqhco31RulesRulesGPI2out OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules GPI 2 out
					or:RollTrack104=1  cmdID= 5691  value= 1  
					or:RollTrack104=0  cmdID= 5691  value= 3  
					and:RollTrack104=1  cmdID= 5691  value= 2  
					and:RollTrack104=0  cmdID= 5691  value= 4  
					Don't use 104  cmdID= 5691  value= 5  "
		::= { iqhco31CmdEntry 5691 }


	iqhco31RulesRulesGPI3outActive OBJECT-TYPE
		SYNTAX		RollCallString
		MAX-ACCESS		read-only
		STATUS			current
		DESCRIPTION
				"TYPE: - Display
				 PAGE: - Rules- Rules GPI 3 out
					Active  cmdID= 5701  format=   "
		::= { iqhco31CmdEntry 5701 }


	iqhco31RulesRulesGPI3out5712 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules GPI 3 out
					or:Master Selected  cmdID= 5712  value= 1  
					or:Backup Selected  cmdID= 5712  value= 2  
					Don't Use  cmdID= 5712  value= 3  "
		::= { iqhco31CmdEntry 5712 }


	iqhco31RulesRulesGPI3out5702 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules GPI 3 out
					or:OK Master  cmdID= 5702  value= 1  
					or:FAIL Master  cmdID= 5702  value= 3  
					and:OK Master  cmdID= 5702  value= 2  
					and:FAIL Master  cmdID= 5702  value= 4  
					Don't use Master  cmdID= 5702  value= 5  "
		::= { iqhco31CmdEntry 5702 }


	iqhco31RulesRulesGPI3out5703 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules GPI 3 out
					or:OK Backup  cmdID= 5703  value= 1  
					or:FAIL Backup  cmdID= 5703  value= 3  
					and:OK Backup  cmdID= 5703  value= 2  
					and:FAIL Backup  cmdID= 5703  value= 4  
					Don't use Backup  cmdID= 5703  value= 5  "
		::= { iqhco31CmdEntry 5703 }


	iqhco31RulesRulesGPI3out5704 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules GPI 3 out
					or:GPI1 High  cmdID= 5704  value= 1  
					or:GPI1 Low  cmdID= 5704  value= 3  
					and:GPI1 High  cmdID= 5704  value= 2  
					and:GPI1 Low  cmdID= 5704  value= 4  
					Don't use GPI1  cmdID= 5704  value= 5  "
		::= { iqhco31CmdEntry 5704 }


	iqhco31RulesRulesGPI3out5705 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules GPI 3 out
					or:GPI2 High  cmdID= 5705  value= 1  
					or:GPI2 Low  cmdID= 5705  value= 3  
					and:GPI2 High  cmdID= 5705  value= 2  
					and:GPI2 Low  cmdID= 5705  value= 4  
					Don't use GPI2  cmdID= 5705  value= 5  "
		::= { iqhco31CmdEntry 5705 }


	iqhco31RulesRulesGPI3out5706 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules GPI 3 out
					or:GPI3 High  cmdID= 5706  value= 1  
					or:GPI3 Low  cmdID= 5706  value= 3  
					and:GPI3 High  cmdID= 5706  value= 2  
					and:GPI3 Low  cmdID= 5706  value= 4  
					Don't use GPI3  cmdID= 5706  value= 5  "
		::= { iqhco31CmdEntry 5706 }


	iqhco31RulesRulesGPI3out5707 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules GPI 3 out
					or:GPI4 High  cmdID= 5707  value= 1  
					or:GPI4 Low  cmdID= 5707  value= 3  
					and:GPI4 High  cmdID= 5707  value= 2  
					and:GPI4 Low  cmdID= 5707  value= 4  
					Don't use GPI4  cmdID= 5707  value= 5  "
		::= { iqhco31CmdEntry 5707 }


	iqhco31RulesRulesGPI3out5708 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules GPI 3 out
					or:RollTrack101=1  cmdID= 5708  value= 1  
					or:RollTrack101=0  cmdID= 5708  value= 3  
					and:RollTrack101=1  cmdID= 5708  value= 2  
					and:RollTrack101=0  cmdID= 5708  value= 4  
					Don't use 101  cmdID= 5708  value= 5  "
		::= { iqhco31CmdEntry 5708 }


	iqhco31RulesRulesGPI3out5709 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules GPI 3 out
					or:RollTrack102=1  cmdID= 5709  value= 1  
					or:RollTrack102=0  cmdID= 5709  value= 3  
					and:RollTrack101=1  cmdID= 5709  value= 2  
					and:RollTrack102=0  cmdID= 5709  value= 4  
					Don't use 102  cmdID= 5709  value= 5  "
		::= { iqhco31CmdEntry 5709 }


	iqhco31RulesRulesGPI3out5710 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules GPI 3 out
					or:RollTrack103=1  cmdID= 5710  value= 1  
					or:RollTrack103=0  cmdID= 5710  value= 3  
					and:RollTrack103=1  cmdID= 5710  value= 2  
					and:RollTrack103=0  cmdID= 5710  value= 4  
					Don't use 103  cmdID= 5710  value= 5  "
		::= { iqhco31CmdEntry 5710 }


	iqhco31RulesRulesGPI3out OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules GPI 3 out
					or:RollTrack104=1  cmdID= 5711  value= 1  
					or:RollTrack104=0  cmdID= 5711  value= 3  
					and:RollTrack104=1  cmdID= 5711  value= 2  
					and:RollTrack104=0  cmdID= 5711  value= 4  
					Don't use 104  cmdID= 5711  value= 5  "
		::= { iqhco31CmdEntry 5711 }


	iqhco31RulesRulesGPI4outActive OBJECT-TYPE
		SYNTAX		RollCallString
		MAX-ACCESS		read-only
		STATUS			current
		DESCRIPTION
				"TYPE: - Display
				 PAGE: - Rules- Rules GPI 4 out
					Active  cmdID= 5721  format=   "
		::= { iqhco31CmdEntry 5721 }


	iqhco31RulesRulesGPI4out5732 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules GPI 4 out
					or:Master Selected  cmdID= 5732  value= 1  
					or:Backup Selected  cmdID= 5732  value= 2  
					Don't Use  cmdID= 5732  value= 3  "
		::= { iqhco31CmdEntry 5732 }


	iqhco31RulesRulesGPI4out5722 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules GPI 4 out
					or:OK Master  cmdID= 5722  value= 1  
					or:FAIL Master  cmdID= 5722  value= 3  
					and:OK Master  cmdID= 5722  value= 2  
					and:FAIL Master  cmdID= 5722  value= 4  
					Don't use Master  cmdID= 5722  value= 5  "
		::= { iqhco31CmdEntry 5722 }


	iqhco31RulesRulesGPI4out5723 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules GPI 4 out
					or:OK Backup  cmdID= 5723  value= 1  
					or:FAIL Backup  cmdID= 5723  value= 3  
					and:OK Backup  cmdID= 5723  value= 2  
					and:FAIL Backup  cmdID= 5723  value= 4  
					Don't use Backup  cmdID= 5723  value= 5  "
		::= { iqhco31CmdEntry 5723 }


	iqhco31RulesRulesGPI4out5724 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules GPI 4 out
					or:GPI1 High  cmdID= 5724  value= 1  
					or:GPI1 Low  cmdID= 5724  value= 3  
					and:GPI1 High  cmdID= 5724  value= 2  
					and:GPI1 Low  cmdID= 5724  value= 4  
					Don't use GPI1  cmdID= 5724  value= 5  "
		::= { iqhco31CmdEntry 5724 }


	iqhco31RulesRulesGPI4out5725 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules GPI 4 out
					or:GPI2 High  cmdID= 5725  value= 1  
					or:GPI2 Low  cmdID= 5725  value= 3  
					and:GPI2 High  cmdID= 5725  value= 2  
					and:GPI2 Low  cmdID= 5725  value= 4  
					Don't use GPI2  cmdID= 5725  value= 5  "
		::= { iqhco31CmdEntry 5725 }


	iqhco31RulesRulesGPI4out5726 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules GPI 4 out
					or:GPI3 High  cmdID= 5726  value= 1  
					or:GPI3 Low  cmdID= 5726  value= 3  
					and:GPI3 High  cmdID= 5726  value= 2  
					and:GPI3 Low  cmdID= 5726  value= 4  
					Don't use GPI3  cmdID= 5726  value= 5  "
		::= { iqhco31CmdEntry 5726 }


	iqhco31RulesRulesGPI4out5727 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules GPI 4 out
					or:GPI4 High  cmdID= 5727  value= 1  
					or:GPI4 Low  cmdID= 5727  value= 3  
					and:GPI4 High  cmdID= 5727  value= 2  
					and:GPI4 Low  cmdID= 5727  value= 4  
					Don't use GPI4  cmdID= 5727  value= 5  "
		::= { iqhco31CmdEntry 5727 }


	iqhco31RulesRulesGPI4out5728 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules GPI 4 out
					or:RollTrack101=1  cmdID= 5728  value= 1  
					or:RollTrack101=0  cmdID= 5728  value= 3  
					and:RollTrack101=1  cmdID= 5728  value= 2  
					and:RollTrack101=0  cmdID= 5728  value= 4  
					Don't use 101  cmdID= 5728  value= 5  "
		::= { iqhco31CmdEntry 5728 }


	iqhco31RulesRulesGPI4out5729 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules GPI 4 out
					or:RollTrack102=1  cmdID= 5729  value= 1  
					or:RollTrack102=0  cmdID= 5729  value= 3  
					and:RollTrack101=1  cmdID= 5729  value= 2  
					and:RollTrack102=0  cmdID= 5729  value= 4  
					Don't use 102  cmdID= 5729  value= 5  "
		::= { iqhco31CmdEntry 5729 }


	iqhco31RulesRulesGPI4out5730 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules GPI 4 out
					or:RollTrack103=1  cmdID= 5730  value= 1  
					or:RollTrack103=0  cmdID= 5730  value= 3  
					and:RollTrack103=1  cmdID= 5730  value= 2  
					and:RollTrack103=0  cmdID= 5730  value= 4  
					Don't use 103  cmdID= 5730  value= 5  "
		::= { iqhco31CmdEntry 5730 }


	iqhco31RulesRulesGPI4out OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules GPI 4 out
					or:RollTrack104=1  cmdID= 5731  value= 1  
					or:RollTrack104=0  cmdID= 5731  value= 3  
					and:RollTrack104=1  cmdID= 5731  value= 2  
					and:RollTrack104=0  cmdID= 5731  value= 4  
					Don't use 104  cmdID= 5731  value= 5  "
		::= { iqhco31CmdEntry 5731 }


	iqhco31RulesRollTrackEnableEnable6649 OBJECT-TYPE
		SYNTAX		INTEGER { disable(0), enable(1) }
		MAX-ACCESS		read-write
		STATUS			current
		DESCRIPTION
				"TYPE: - Checkbox
				 PAGE: - Rules
					Enable  cmdID= 6649 "
		::= { iqhco31CmdEntry 6649 }


	iqhco31RulesRollTrackEnableEnable6651 OBJECT-TYPE
		SYNTAX		INTEGER { disable(0), enable(1) }
		MAX-ACCESS		read-write
		STATUS			current
		DESCRIPTION
				"TYPE: - Checkbox
				 PAGE: - Rules
					Enable  cmdID= 6651 "
		::= { iqhco31CmdEntry 6651 }


	iqhco31RulesRollTrackEnableEnable6653 OBJECT-TYPE
		SYNTAX		INTEGER { disable(0), enable(1) }
		MAX-ACCESS		read-write
		STATUS			current
		DESCRIPTION
				"TYPE: - Checkbox
				 PAGE: - Rules
					Enable  cmdID= 6653 "
		::= { iqhco31CmdEntry 6653 }


	iqhco31RulesRollTrackEnableEnable6655 OBJECT-TYPE
		SYNTAX		INTEGER { disable(0), enable(1) }
		MAX-ACCESS		read-write
		STATUS			current
		DESCRIPTION
				"TYPE: - Checkbox
				 PAGE: - Rules
					Enable  cmdID= 6655 "
		::= { iqhco31CmdEntry 6655 }


	iqhco31RulesRollTrackEnableState6648 OBJECT-TYPE
		SYNTAX		RollCallString
		MAX-ACCESS		read-only
		STATUS			current
		DESCRIPTION
				"TYPE: - Display
				 PAGE: - Rules
					State  cmdID= 6648  format=   "
		::= { iqhco31CmdEntry 6648 }


	iqhco31RulesRollTrackEnableState6650 OBJECT-TYPE
		SYNTAX		RollCallString
		MAX-ACCESS		read-only
		STATUS			current
		DESCRIPTION
				"TYPE: - Display
				 PAGE: - Rules
					State  cmdID= 6650  format=   "
		::= { iqhco31CmdEntry 6650 }


	iqhco31RulesRollTrackEnableState6652 OBJECT-TYPE
		SYNTAX		RollCallString
		MAX-ACCESS		read-only
		STATUS			current
		DESCRIPTION
				"TYPE: - Display
				 PAGE: - Rules
					State  cmdID= 6652  format=   "
		::= { iqhco31CmdEntry 6652 }


	iqhco31RulesRollTrackEnableState6654 OBJECT-TYPE
		SYNTAX		RollCallString
		MAX-ACCESS		read-only
		STATUS			current
		DESCRIPTION
				"TYPE: - Display
				 PAGE: - Rules
					State  cmdID= 6654  format=   "
		::= { iqhco31CmdEntry 6654 }


	iqhco31RulesRulesRollTack101Active OBJECT-TYPE
		SYNTAX		RollCallString
		MAX-ACCESS		read-only
		STATUS			current
		DESCRIPTION
				"TYPE: - Display
				 PAGE: - Rules- Rules RollTack 101
					Active  cmdID= 5741  format=   "
		::= { iqhco31CmdEntry 5741 }


	iqhco31RulesRulesRollTack1015752 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules RollTack 101
					or:Master Selected  cmdID= 5752  value= 1  
					or:Backup Selected  cmdID= 5752  value= 2  
					Don't Use  cmdID= 5752  value= 3  "
		::= { iqhco31CmdEntry 5752 }


	iqhco31RulesRulesRollTack1015742 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules RollTack 101
					or:OK Master  cmdID= 5742  value= 1  
					or:FAIL Master  cmdID= 5742  value= 3  
					and:OK Master  cmdID= 5742  value= 2  
					and:FAIL Master  cmdID= 5742  value= 4  
					Don't use Master  cmdID= 5742  value= 5  "
		::= { iqhco31CmdEntry 5742 }


	iqhco31RulesRulesRollTack1015743 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules RollTack 101
					or:OK Backup  cmdID= 5743  value= 1  
					or:FAIL Backup  cmdID= 5743  value= 3  
					and:OK Backup  cmdID= 5743  value= 2  
					and:FAIL Backup  cmdID= 5743  value= 4  
					Don't use Backup  cmdID= 5743  value= 5  "
		::= { iqhco31CmdEntry 5743 }


	iqhco31RulesRulesRollTack1015744 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules RollTack 101
					or:GPI1 High  cmdID= 5744  value= 1  
					or:GPI1 Low  cmdID= 5744  value= 3  
					and:GPI1 High  cmdID= 5744  value= 2  
					and:GPI1 Low  cmdID= 5744  value= 4  
					Don't use GPI1  cmdID= 5744  value= 5  "
		::= { iqhco31CmdEntry 5744 }


	iqhco31RulesRulesRollTack1015745 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules RollTack 101
					or:GPI2 High  cmdID= 5745  value= 1  
					or:GPI2 Low  cmdID= 5745  value= 3  
					and:GPI2 High  cmdID= 5745  value= 2  
					and:GPI2 Low  cmdID= 5745  value= 4  
					Don't use GPI2  cmdID= 5745  value= 5  "
		::= { iqhco31CmdEntry 5745 }


	iqhco31RulesRulesRollTack1015746 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules RollTack 101
					or:GPI3 High  cmdID= 5746  value= 1  
					or:GPI3 Low  cmdID= 5746  value= 3  
					and:GPI3 High  cmdID= 5746  value= 2  
					and:GPI3 Low  cmdID= 5746  value= 4  
					Don't use GPI3  cmdID= 5746  value= 5  "
		::= { iqhco31CmdEntry 5746 }


	iqhco31RulesRulesRollTack1015747 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules RollTack 101
					or:GPI4 High  cmdID= 5747  value= 1  
					or:GPI4 Low  cmdID= 5747  value= 3  
					and:GPI4 High  cmdID= 5747  value= 2  
					and:GPI4 Low  cmdID= 5747  value= 4  
					Don't use GPI4  cmdID= 5747  value= 5  "
		::= { iqhco31CmdEntry 5747 }


	iqhco31RulesRulesRollTack1015748 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules RollTack 101
					or:RollTrack101=1  cmdID= 5748  value= 1  
					or:RollTrack101=0  cmdID= 5748  value= 3  
					and:RollTrack101=1  cmdID= 5748  value= 2  
					and:RollTrack101=0  cmdID= 5748  value= 4  
					Don't use 101  cmdID= 5748  value= 5  "
		::= { iqhco31CmdEntry 5748 }


	iqhco31RulesRulesRollTack1015749 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules RollTack 101
					or:RollTrack102=1  cmdID= 5749  value= 1  
					or:RollTrack102=0  cmdID= 5749  value= 3  
					and:RollTrack101=1  cmdID= 5749  value= 2  
					and:RollTrack102=0  cmdID= 5749  value= 4  
					Don't use 102  cmdID= 5749  value= 5  "
		::= { iqhco31CmdEntry 5749 }


	iqhco31RulesRulesRollTack1015750 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules RollTack 101
					or:RollTrack103=1  cmdID= 5750  value= 1  
					or:RollTrack103=0  cmdID= 5750  value= 3  
					and:RollTrack103=1  cmdID= 5750  value= 2  
					and:RollTrack103=0  cmdID= 5750  value= 4  
					Don't use 103  cmdID= 5750  value= 5  "
		::= { iqhco31CmdEntry 5750 }


	iqhco31RulesRulesRollTack101 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules RollTack 101
					or:RollTrack104=1  cmdID= 5751  value= 1  
					or:RollTrack104=0  cmdID= 5751  value= 3  
					and:RollTrack104=1  cmdID= 5751  value= 2  
					and:RollTrack104=0  cmdID= 5751  value= 4  
					Don't use 104  cmdID= 5751  value= 5  "
		::= { iqhco31CmdEntry 5751 }


	iqhco31RulesRulesRollTack102Active OBJECT-TYPE
		SYNTAX		RollCallString
		MAX-ACCESS		read-only
		STATUS			current
		DESCRIPTION
				"TYPE: - Display
				 PAGE: - Rules- Rules RollTack 102
					Active  cmdID= 5761  format=   "
		::= { iqhco31CmdEntry 5761 }


	iqhco31RulesRulesRollTack1025772 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules RollTack 102
					or:Master Selected  cmdID= 5772  value= 1  
					or:Backup Selected  cmdID= 5772  value= 2  
					Don't Use  cmdID= 5772  value= 3  "
		::= { iqhco31CmdEntry 5772 }


	iqhco31RulesRulesRollTack1025762 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules RollTack 102
					or:OK Master  cmdID= 5762  value= 1  
					or:FAIL Master  cmdID= 5762  value= 3  
					and:OK Master  cmdID= 5762  value= 2  
					and:FAIL Master  cmdID= 5762  value= 4  
					Don't use Master  cmdID= 5762  value= 5  "
		::= { iqhco31CmdEntry 5762 }


	iqhco31RulesRulesRollTack1025763 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules RollTack 102
					or:OK Backup  cmdID= 5763  value= 1  
					or:FAIL Backup  cmdID= 5763  value= 3  
					and:OK Backup  cmdID= 5763  value= 2  
					and:FAIL Backup  cmdID= 5763  value= 4  
					Don't use Backup  cmdID= 5763  value= 5  "
		::= { iqhco31CmdEntry 5763 }


	iqhco31RulesRulesRollTack1025764 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules RollTack 102
					or:GPI1 High  cmdID= 5764  value= 1  
					or:GPI1 Low  cmdID= 5764  value= 3  
					and:GPI1 High  cmdID= 5764  value= 2  
					and:GPI1 Low  cmdID= 5764  value= 4  
					Don't use GPI1  cmdID= 5764  value= 5  "
		::= { iqhco31CmdEntry 5764 }


	iqhco31RulesRulesRollTack1025765 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules RollTack 102
					or:GPI2 High  cmdID= 5765  value= 1  
					or:GPI2 Low  cmdID= 5765  value= 3  
					and:GPI2 High  cmdID= 5765  value= 2  
					and:GPI2 Low  cmdID= 5765  value= 4  
					Don't use GPI2  cmdID= 5765  value= 5  "
		::= { iqhco31CmdEntry 5765 }


	iqhco31RulesRulesRollTack1025766 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules RollTack 102
					or:GPI3 High  cmdID= 5766  value= 1  
					or:GPI3 Low  cmdID= 5766  value= 3  
					and:GPI3 High  cmdID= 5766  value= 2  
					and:GPI3 Low  cmdID= 5766  value= 4  
					Don't use GPI3  cmdID= 5766  value= 5  "
		::= { iqhco31CmdEntry 5766 }


	iqhco31RulesRulesRollTack1025767 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules RollTack 102
					or:GPI4 High  cmdID= 5767  value= 1  
					or:GPI4 Low  cmdID= 5767  value= 3  
					and:GPI4 High  cmdID= 5767  value= 2  
					and:GPI4 Low  cmdID= 5767  value= 4  
					Don't use GPI4  cmdID= 5767  value= 5  "
		::= { iqhco31CmdEntry 5767 }


	iqhco31RulesRulesRollTack1025768 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules RollTack 102
					or:RollTrack101=1  cmdID= 5768  value= 1  
					or:RollTrack101=0  cmdID= 5768  value= 3  
					and:RollTrack101=1  cmdID= 5768  value= 2  
					and:RollTrack101=0  cmdID= 5768  value= 4  
					Don't use 101  cmdID= 5768  value= 5  "
		::= { iqhco31CmdEntry 5768 }


	iqhco31RulesRulesRollTack1025769 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules RollTack 102
					or:RollTrack102=1  cmdID= 5769  value= 1  
					or:RollTrack102=0  cmdID= 5769  value= 3  
					and:RollTrack101=1  cmdID= 5769  value= 2  
					and:RollTrack102=0  cmdID= 5769  value= 4  
					Don't use 102  cmdID= 5769  value= 5  "
		::= { iqhco31CmdEntry 5769 }


	iqhco31RulesRulesRollTack1025770 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules RollTack 102
					or:RollTrack103=1  cmdID= 5770  value= 1  
					or:RollTrack103=0  cmdID= 5770  value= 3  
					and:RollTrack103=1  cmdID= 5770  value= 2  
					and:RollTrack103=0  cmdID= 5770  value= 4  
					Don't use 103  cmdID= 5770  value= 5  "
		::= { iqhco31CmdEntry 5770 }


	iqhco31RulesRulesRollTack102 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules RollTack 102
					or:RollTrack104=1  cmdID= 5771  value= 1  
					or:RollTrack104=0  cmdID= 5771  value= 3  
					and:RollTrack104=1  cmdID= 5771  value= 2  
					and:RollTrack104=0  cmdID= 5771  value= 4  
					Don't use 104  cmdID= 5771  value= 5  "
		::= { iqhco31CmdEntry 5771 }


	iqhco31RulesRulesRollTack103Active OBJECT-TYPE
		SYNTAX		RollCallString
		MAX-ACCESS		read-only
		STATUS			current
		DESCRIPTION
				"TYPE: - Display
				 PAGE: - Rules- Rules RollTack 103
					Active  cmdID= 5781  format=   "
		::= { iqhco31CmdEntry 5781 }


	iqhco31RulesRulesRollTack1035792 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules RollTack 103
					or:Master Selected  cmdID= 5792  value= 1  
					or:Backup Selected  cmdID= 5792  value= 2  
					Don't Use  cmdID= 5792  value= 3  "
		::= { iqhco31CmdEntry 5792 }


	iqhco31RulesRulesRollTack1035782 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules RollTack 103
					or:OK Master  cmdID= 5782  value= 1  
					or:FAIL Master  cmdID= 5782  value= 3  
					and:OK Master  cmdID= 5782  value= 2  
					and:FAIL Master  cmdID= 5782  value= 4  
					Don't use Master  cmdID= 5782  value= 5  "
		::= { iqhco31CmdEntry 5782 }


	iqhco31RulesRulesRollTack1035783 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules RollTack 103
					or:OK Backup  cmdID= 5783  value= 1  
					or:FAIL Backup  cmdID= 5783  value= 3  
					and:OK Backup  cmdID= 5783  value= 2  
					and:FAIL Backup  cmdID= 5783  value= 4  
					Don't use Backup  cmdID= 5783  value= 5  "
		::= { iqhco31CmdEntry 5783 }


	iqhco31RulesRulesRollTack1035784 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules RollTack 103
					or:GPI1 High  cmdID= 5784  value= 1  
					or:GPI1 Low  cmdID= 5784  value= 3  
					and:GPI1 High  cmdID= 5784  value= 2  
					and:GPI1 Low  cmdID= 5784  value= 4  
					Don't use GPI1  cmdID= 5784  value= 5  "
		::= { iqhco31CmdEntry 5784 }


	iqhco31RulesRulesRollTack1035785 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules RollTack 103
					or:GPI2 High  cmdID= 5785  value= 1  
					or:GPI2 Low  cmdID= 5785  value= 3  
					and:GPI2 High  cmdID= 5785  value= 2  
					and:GPI2 Low  cmdID= 5785  value= 4  
					Don't use GPI2  cmdID= 5785  value= 5  "
		::= { iqhco31CmdEntry 5785 }


	iqhco31RulesRulesRollTack1035786 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules RollTack 103
					or:GPI3 High  cmdID= 5786  value= 1  
					or:GPI3 Low  cmdID= 5786  value= 3  
					and:GPI3 High  cmdID= 5786  value= 2  
					and:GPI3 Low  cmdID= 5786  value= 4  
					Don't use GPI3  cmdID= 5786  value= 5  "
		::= { iqhco31CmdEntry 5786 }


	iqhco31RulesRulesRollTack1035787 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules RollTack 103
					or:GPI4 High  cmdID= 5787  value= 1  
					or:GPI4 Low  cmdID= 5787  value= 3  
					and:GPI4 High  cmdID= 5787  value= 2  
					and:GPI4 Low  cmdID= 5787  value= 4  
					Don't use GPI4  cmdID= 5787  value= 5  "
		::= { iqhco31CmdEntry 5787 }


	iqhco31RulesRulesRollTack1035788 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules RollTack 103
					or:RollTrack101=1  cmdID= 5788  value= 1  
					or:RollTrack101=0  cmdID= 5788  value= 3  
					and:RollTrack101=1  cmdID= 5788  value= 2  
					and:RollTrack101=0  cmdID= 5788  value= 4  
					Don't use 101  cmdID= 5788  value= 5  "
		::= { iqhco31CmdEntry 5788 }


	iqhco31RulesRulesRollTack1035789 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules RollTack 103
					or:RollTrack102=1  cmdID= 5789  value= 1  
					or:RollTrack102=0  cmdID= 5789  value= 3  
					and:RollTrack101=1  cmdID= 5789  value= 2  
					and:RollTrack102=0  cmdID= 5789  value= 4  
					Don't use 102  cmdID= 5789  value= 5  "
		::= { iqhco31CmdEntry 5789 }


	iqhco31RulesRulesRollTack1035790 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules RollTack 103
					or:RollTrack103=1  cmdID= 5790  value= 1  
					or:RollTrack103=0  cmdID= 5790  value= 3  
					and:RollTrack103=1  cmdID= 5790  value= 2  
					and:RollTrack103=0  cmdID= 5790  value= 4  
					Don't use 103  cmdID= 5790  value= 5  "
		::= { iqhco31CmdEntry 5790 }


	iqhco31RulesRulesRollTack103 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules RollTack 103
					or:RollTrack104=1  cmdID= 5791  value= 1  
					or:RollTrack104=0  cmdID= 5791  value= 3  
					and:RollTrack104=1  cmdID= 5791  value= 2  
					and:RollTrack104=0  cmdID= 5791  value= 4  
					Don't use 104  cmdID= 5791  value= 5  "
		::= { iqhco31CmdEntry 5791 }


	iqhco31RulesRulesRollTack104Active OBJECT-TYPE
		SYNTAX		RollCallString
		MAX-ACCESS		read-only
		STATUS			current
		DESCRIPTION
				"TYPE: - Display
				 PAGE: - Rules- Rules RollTack 104
					Active  cmdID= 5801  format=   "
		::= { iqhco31CmdEntry 5801 }


	iqhco31RulesRulesRollTack1045812 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules RollTack 104
					or:Master Selected  cmdID= 5812  value= 1  
					or:Backup Selected  cmdID= 5812  value= 2  
					Don't Use  cmdID= 5812  value= 3  "
		::= { iqhco31CmdEntry 5812 }


	iqhco31RulesRulesRollTack1045802 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules RollTack 104
					or:OK Master  cmdID= 5802  value= 1  
					or:FAIL Master  cmdID= 5802  value= 3  
					and:OK Master  cmdID= 5802  value= 2  
					and:FAIL Master  cmdID= 5802  value= 4  
					Don't use Master  cmdID= 5802  value= 5  "
		::= { iqhco31CmdEntry 5802 }


	iqhco31RulesRulesRollTack1045803 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules RollTack 104
					or:OK Backup  cmdID= 5803  value= 1  
					or:FAIL Backup  cmdID= 5803  value= 3  
					and:OK Backup  cmdID= 5803  value= 2  
					and:FAIL Backup  cmdID= 5803  value= 4  
					Don't use Backup  cmdID= 5803  value= 5  "
		::= { iqhco31CmdEntry 5803 }


	iqhco31RulesRulesRollTack1045804 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules RollTack 104
					or:GPI1 High  cmdID= 5804  value= 1  
					or:GPI1 Low  cmdID= 5804  value= 3  
					and:GPI1 High  cmdID= 5804  value= 2  
					and:GPI1 Low  cmdID= 5804  value= 4  
					Don't use GPI1  cmdID= 5804  value= 5  "
		::= { iqhco31CmdEntry 5804 }


	iqhco31RulesRulesRollTack1045805 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules RollTack 104
					or:GPI2 High  cmdID= 5805  value= 1  
					or:GPI2 Low  cmdID= 5805  value= 3  
					and:GPI2 High  cmdID= 5805  value= 2  
					and:GPI2 Low  cmdID= 5805  value= 4  
					Don't use GPI2  cmdID= 5805  value= 5  "
		::= { iqhco31CmdEntry 5805 }


	iqhco31RulesRulesRollTack1045806 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules RollTack 104
					or:GPI3 High  cmdID= 5806  value= 1  
					or:GPI3 Low  cmdID= 5806  value= 3  
					and:GPI3 High  cmdID= 5806  value= 2  
					and:GPI3 Low  cmdID= 5806  value= 4  
					Don't use GPI3  cmdID= 5806  value= 5  "
		::= { iqhco31CmdEntry 5806 }


	iqhco31RulesRulesRollTack1045807 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules RollTack 104
					or:GPI4 High  cmdID= 5807  value= 1  
					or:GPI4 Low  cmdID= 5807  value= 3  
					and:GPI4 High  cmdID= 5807  value= 2  
					and:GPI4 Low  cmdID= 5807  value= 4  
					Don't use GPI4  cmdID= 5807  value= 5  "
		::= { iqhco31CmdEntry 5807 }


	iqhco31RulesRulesRollTack1045808 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules RollTack 104
					or:RollTrack101=1  cmdID= 5808  value= 1  
					or:RollTrack101=0  cmdID= 5808  value= 3  
					and:RollTrack101=1  cmdID= 5808  value= 2  
					and:RollTrack101=0  cmdID= 5808  value= 4  
					Don't use 101  cmdID= 5808  value= 5  "
		::= { iqhco31CmdEntry 5808 }


	iqhco31RulesRulesRollTack1045809 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules RollTack 104
					or:RollTrack102=1  cmdID= 5809  value= 1  
					or:RollTrack102=0  cmdID= 5809  value= 3  
					and:RollTrack101=1  cmdID= 5809  value= 2  
					and:RollTrack102=0  cmdID= 5809  value= 4  
					Don't use 102  cmdID= 5809  value= 5  "
		::= { iqhco31CmdEntry 5809 }


	iqhco31RulesRulesRollTack1045810 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules RollTack 104
					or:RollTrack103=1  cmdID= 5810  value= 1  
					or:RollTrack103=0  cmdID= 5810  value= 3  
					and:RollTrack103=1  cmdID= 5810  value= 2  
					and:RollTrack103=0  cmdID= 5810  value= 4  
					Don't use 103  cmdID= 5810  value= 5  "
		::= { iqhco31CmdEntry 5810 }


	iqhco31RulesRulesRollTack104 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules RollTack 104
					or:RollTrack104=1  cmdID= 5811  value= 1  
					or:RollTrack104=0  cmdID= 5811  value= 3  
					and:RollTrack104=1  cmdID= 5811  value= 2  
					and:RollTrack104=0  cmdID= 5811  value= 4  
					Don't use 104  cmdID= 5811  value= 5  "
		::= { iqhco31CmdEntry 5811 }


	iqhco31RulesPresetsPriorityMaster6660 OBJECT-TYPE
		SYNTAX		INTEGER { noAction(0),val-Priority-Master(1) }
		MAX-ACCESS		read-write
		STATUS			current
		DESCRIPTION
				"TYPE: - Button
				 PAGE: - Rules
					Priority Master  cmdID= 6660  value= 1  "
		::= { iqhco31CmdEntry 6660 }


	iqhco31RulesPresetsPriorityBackup6661 OBJECT-TYPE
		SYNTAX		INTEGER { noAction(0),val-Priority-Backup(1) }
		MAX-ACCESS		read-write
		STATUS			current
		DESCRIPTION
				"TYPE: - Button
				 PAGE: - Rules
					Priority Backup  cmdID= 6661  value= 1  "
		::= { iqhco31CmdEntry 6661 }


	iqhco31RulesPresetsNoPriority6662 OBJECT-TYPE
		SYNTAX		INTEGER { noAction(0),val-No-Priority(1) }
		MAX-ACCESS		read-write
		STATUS			current
		DESCRIPTION
				"TYPE: - Button
				 PAGE: - Rules
					No Priority  cmdID= 6662  value= 1  "
		::= { iqhco31CmdEntry 6662 }


	iqhco31RulesPresetsPriorityMaster6663 OBJECT-TYPE
		SYNTAX		INTEGER { noAction(0),val-Priority-Master(1) }
		MAX-ACCESS		read-write
		STATUS			current
		DESCRIPTION
				"TYPE: - Button
				 PAGE: - Rules
					Priority Master.  cmdID= 6663  value= 1  "
		::= { iqhco31CmdEntry 6663 }


	iqhco31RulesPresetsPriorityBackup6664 OBJECT-TYPE
		SYNTAX		INTEGER { noAction(0),val-Priority-Backup(1) }
		MAX-ACCESS		read-write
		STATUS			current
		DESCRIPTION
				"TYPE: - Button
				 PAGE: - Rules
					Priority Backup.  cmdID= 6664  value= 1  "
		::= { iqhco31CmdEntry 6664 }


	iqhco31RulesPresetsNoPriority6665 OBJECT-TYPE
		SYNTAX		INTEGER { noAction(0),val-No-Priority(1) }
		MAX-ACCESS		read-write
		STATUS			current
		DESCRIPTION
				"TYPE: - Button
				 PAGE: - Rules
					No Priority.  cmdID= 6665  value= 1  "
		::= { iqhco31CmdEntry 6665 }


	iqhco31RulesPresetsPriorityMaster OBJECT-TYPE
		SYNTAX		INTEGER { noAction(0),val-Priority-Master(1) }
		MAX-ACCESS		read-write
		STATUS			current
		DESCRIPTION
				"TYPE: - Button
				 PAGE: - Rules
					Priority Master..  cmdID= 6666  value= 1  "
		::= { iqhco31CmdEntry 6666 }


	iqhco31RulesPresetsPriorityBackup OBJECT-TYPE
		SYNTAX		INTEGER { noAction(0),val-Priority-Backup(1) }
		MAX-ACCESS		read-write
		STATUS			current
		DESCRIPTION
				"TYPE: - Button
				 PAGE: - Rules
					Priority Backup..  cmdID= 6667  value= 1  "
		::= { iqhco31CmdEntry 6667 }


	iqhco31RulesPresetsNoPriority OBJECT-TYPE
		SYNTAX		INTEGER { noAction(0),val-No-Priority(1) }
		MAX-ACCESS		read-write
		STATUS			current
		DESCRIPTION
				"TYPE: - Button
				 PAGE: - Rules
					No Priority..  cmdID= 6668  value= 1  "
		::= { iqhco31CmdEntry 6668 }


	iqhco31OutputsMasterSelect OBJECT-TYPE
		SYNTAX		INTEGER {
							val-Rules(4),
							val-Master(0),
							val-Backup(1),
							val-Pattern(2),
							val-Caption(3)
							}
		MAX-ACCESS		read-write
		STATUS			current
		DESCRIPTION
				"TYPE: - RadiobuttonList
				 PAGE: - Outputs
					Master Select  cmdID= 6631 
					Rules  value= 4  
					Master  value= 0  
					Backup  value= 1  
					Pattern  value= 2  
					Caption  value= 3  "
		::= { iqhco31CmdEntry 6631 }


	iqhco31OutputsMonitorSelect OBJECT-TYPE
		SYNTAX		INTEGER {
							val-Follow-Main(5),
							val-Follow-InActive-Inp(6),
							val-Master(0),
							val-Backup(1),
							val-Pattern(2),
							val-Caption(7)
							}
		MAX-ACCESS		read-write
		STATUS			current
		DESCRIPTION
				"TYPE: - RadiobuttonList
				 PAGE: - Outputs
					Monitor Select  cmdID= 6632 
					Follow Main  value= 5  
					Follow InActive Inp  value= 6  
					Master  value= 0  
					Backup  value= 1  
					Pattern  value= 2  
					Caption  value= 7  "
		::= { iqhco31CmdEntry 6632 }


	iqhco31OutputsRulesSelection OBJECT-TYPE
		SYNTAX		INTEGER {
							val-Active-Master(1),
							val-Active-Backup(2)
							}
		MAX-ACCESS		read-write
		STATUS			current
		DESCRIPTION
				"TYPE: - RadiobuttonList
				 PAGE: - Outputs
					Rules Selection  cmdID= 6633 
					Active Master  value= 1  
					Active Backup  value= 2  "
		::= { iqhco31CmdEntry 6633 }


	iqhco31AESOut12AESOut1SourceLR OBJECT-TYPE
		SYNTAX		INTEGER {
							val-Disembed-1(0),
							val-Disembed-2(1),
							val-Disembed-3(2),
							val-Disembed-4(3),
							val-Disembed-5(4),
							val-Disembed-6(5),
							val-Disembed-7(6),
							val-Disembed-8(7),
							val-Tone(8),
							val-Silence(9)
							}
		MAX-ACCESS		read-write
		STATUS			current
		DESCRIPTION
				"TYPE: - RadiobuttonList
				 PAGE: - Outputs- AES Out 1-2- AES Out 1
					Source L+R  cmdID= 2951 
					Disembed 1  value= 0  
					Disembed 2  value= 1  
					Disembed 3  value= 2  
					Disembed 4  value= 3  
					Disembed 5  value= 4  
					Disembed 6  value= 5  
					Disembed 7  value= 6  
					Disembed 8  value= 7  
					Tone  value= 8  
					Silence  value= 9  "
		::= { iqhco31CmdEntry 2951 }


	iqhco31AESOut12AESOut2SourceLR OBJECT-TYPE
		SYNTAX		INTEGER {
							val-Disembed-1(0),
							val-Disembed-2(1),
							val-Disembed-3(2),
							val-Disembed-4(3),
							val-Disembed-5(4),
							val-Disembed-6(5),
							val-Disembed-7(6),
							val-Disembed-8(7),
							val-Tone(8),
							val-Silence(9)
							}
		MAX-ACCESS		read-write
		STATUS			current
		DESCRIPTION
				"TYPE: - RadiobuttonList
				 PAGE: - Outputs- AES Out 1-2- AES Out 2
					Source L+R  cmdID= 2952 
					Disembed 1  value= 0  
					Disembed 2  value= 1  
					Disembed 3  value= 2  
					Disembed 4  value= 3  
					Disembed 5  value= 4  
					Disembed 6  value= 5  
					Disembed 7  value= 6  
					Disembed 8  value= 7  
					Tone  value= 8  
					Silence  value= 9  "
		::= { iqhco31CmdEntry 2952 }


	iqhco31OutputsToneFrequency OBJECT-TYPE
		SYNTAX		INTEGER
		MAX-ACCESS		read-write
		STATUS			current
		DESCRIPTION
				"TYPE: - Number
				 PAGE: - Outputs
					Frequency  cmdID= 2487  min= 100  max= 10000  step= 100  format= %5.0fHz  div_scale= 1 
					Min =   100Hz  Max = 10000Hz  Step =   100Hz "
		::= { iqhco31CmdEntry 2487 }


	iqhco31OutputsToneChannelident OBJECT-TYPE
		SYNTAX		INTEGER { disable(0), enable(1) }
		MAX-ACCESS		read-write
		STATUS			current
		DESCRIPTION
				"TYPE: - Checkbox
				 PAGE: - Outputs
					Channel ident  cmdID= 5030 "
		::= { iqhco31CmdEntry 5030 }


	iqhco31CommonGenlock OBJECT-TYPE
		SYNTAX		INTEGER {
							val-Freerun(2),
							val-Lock-to-Reference(0)
							}
		MAX-ACCESS		read-write
		STATUS			current
		DESCRIPTION
				"TYPE: - Button
				 PAGE: - Common
					Freerun  cmdID= 3674  value= 2  
					Lock to Reference  cmdID= 3674  value= 0  "
		::= { iqhco31CmdEntry 3674 }


	iqhco31CommonGenlockFreerunFrequency OBJECT-TYPE
		SYNTAX		INTEGER
		MAX-ACCESS		read-write
		STATUS			current
		DESCRIPTION
				"TYPE: - Number
				 PAGE: - Common
					Freerun Frequency  cmdID= 2449  min= -200  max= 200  step= 1  format= %.0f  div_scale= 1 
					Min = -200  Max = 200  Step = 1 "
		::= { iqhco31CmdEntry 2449 }


	iqhco31CommonGenlockGenlockHPhase3790 OBJECT-TYPE
		SYNTAX		INTEGER
		MAX-ACCESS		read-write
		STATUS			current
		DESCRIPTION
				"TYPE: - Number
				 PAGE: - Common
					Genlock H Phase  cmdID= 3790  min= -1320  max= 1320  step= 1  format= %.0f pixels  div_scale= 1 
					Min = -1320 pixels  Max = 1320 pixels  Step = 1 pixels "
		::= { iqhco31CmdEntry 3790 }


	iqhco31CommonGenlockGenlockVPhase3791 OBJECT-TYPE
		SYNTAX		INTEGER
		MAX-ACCESS		read-write
		STATUS			current
		DESCRIPTION
				"TYPE: - Number
				 PAGE: - Common
					Genlock V Phase  cmdID= 3791  min= -562  max= 562  step= 1  format= %.0f lines  div_scale= 1 
					Min = -562 lines  Max = 562 lines  Step = 1 lines "
		::= { iqhco31CmdEntry 3791 }


	iqhco31CommonGenlockMasterFdelay OBJECT-TYPE
		SYNTAX		INTEGER
		MAX-ACCESS		read-write
		STATUS			current
		DESCRIPTION
				"TYPE: - Number
				 PAGE: - Common
					Master F delay  cmdID= 3796  min= 0  max= 3  step= 1  format= %.0f frames  div_scale= 1 
					Min = 0 frames  Max = 3 frames  Step = 1 frames "
		::= { iqhco31CmdEntry 3796 }


	iqhco31CommonGenlockBackupFdelay OBJECT-TYPE
		SYNTAX		INTEGER
		MAX-ACCESS		read-write
		STATUS			current
		DESCRIPTION
				"TYPE: - Number
				 PAGE: - Common
					Backup F delay  cmdID= 3799  min= 0  max= 3  step= 1  format= %.0f frames  div_scale= 1 
					Min = 0 frames  Max = 3 frames  Step = 1 frames "
		::= { iqhco31CmdEntry 3799 }


	iqhco31CommonGenlockGenlocksaveindex OBJECT-TYPE
		SYNTAX		INTEGER
		MAX-ACCESS		read-write
		STATUS			current
		DESCRIPTION
				"TYPE: - Number
				 PAGE: - Common
					Genlock save index  cmdID= 3991  min= 0  max= 10  step= 1  format= %.0f  div_scale= 1 
					Min = 0  Max = 10  Step = 1 "
		::= { iqhco31CmdEntry 3991 }


	iqhco31CommonGenlockGenlockHPhase3992 OBJECT-TYPE
		SYNTAX		INTEGER
		MAX-ACCESS		read-write
		STATUS			current
		DESCRIPTION
				"TYPE: - Number
				 PAGE: - Common
					Genlock H Phase  cmdID= 3992  min= -1320  max= 1320  step= 1  format= %.0f pixels  div_scale= 1 
					Min = -1320 pixels  Max = 1320 pixels  Step = 1 pixels "
		::= { iqhco31CmdEntry 3992 }


	iqhco31CommonGenlockGenlockVPhase3993 OBJECT-TYPE
		SYNTAX		INTEGER
		MAX-ACCESS		read-write
		STATUS			current
		DESCRIPTION
				"TYPE: - Number
				 PAGE: - Common
					Genlock V Phase  cmdID= 3993  min= -562  max= 562  step= 1  format= %.0f lines  div_scale= 1 
					Min = -562 lines  Max = 562 lines  Step = 1 lines "
		::= { iqhco31CmdEntry 3993 }


	iqhco31CommonGenlockReferenceSelect OBJECT-TYPE
		SYNTAX		INTEGER {
							val-Module-Reference(0),
							val-Chassis-Reference-A(1),
							val-Chassis-Reference-B(2)
							}
		MAX-ACCESS		read-write
		STATUS			current
		DESCRIPTION
				"TYPE: - RadiobuttonList
				 PAGE: - Common
					Reference Select  cmdID= 3792 
					Module Reference  value= 0  
					Chassis Reference A  value= 1  
					Chassis Reference B  value= 2  "
		::= { iqhco31CmdEntry 3792 }


	iqhco31CommonGenlockDefaultFormat OBJECT-TYPE
		SYNTAX		INTEGER {
							val-Last-Known-Good(1),
							val-625-25i(2),
							val-525-29i(3),
							val-720-50p(9),
							val-720-59p(10),
							val-1080-25i(17),
							val-1080-29i(18),
							val-1080-50p-A(22),
							val-1080-59p-A(23),
							val-1080-50p-B(25),
							val-1080-59p-B(26)
							}
		MAX-ACCESS		read-write
		STATUS			current
		DESCRIPTION
				"TYPE: - RadiobuttonList
				 PAGE: - Common
					Default Format  cmdID= 3793 
					Last Known Good  value= 1  
					625/25i  value= 2  
					525/29i  value= 3  
					720/50p  value= 9  
					720/59p  value= 10  
					1080/25i  value= 17  
					1080/29i  value= 18  
					1080/50p-A  value= 22  
					1080/59p-A  value= 23  
					1080/50p-B  value= 25  
					1080/59p-B  value= 26  "
		::= { iqhco31CmdEntry 3793 }


	iqhco31CommonMemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Common
					Sel Memory  cmdID= 37101 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqhco31CmdEntry 37101 }


	iqhco31CommonMemoriesSetMemName OBJECT-TYPE
		SYNTAX		RollCallString
		MAX-ACCESS		read-write
		STATUS			current
		DESCRIPTION
				"TYPE: - Editstring
				 PAGE: - Common
					SetMemName  cmdID= 37103  "
		::= { iqhco31CmdEntry 37103 }


	iqhco31CommonMemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Common
					Recall Memory  cmdID= 37100 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqhco31CmdEntry 37100 }


	iqhco31CommonMemoriesSaveMemory OBJECT-TYPE
		SYNTAX		INTEGER { noAction(0),val-Save-Memory(1) }
		MAX-ACCESS		read-write
		STATUS			current
		DESCRIPTION
				"TYPE: - Button
				 PAGE: - Common
					Save Memory  cmdID= 37102  value= 1  "
		::= { iqhco31CmdEntry 37102 }


	iqhco31CommonMemoriesLastUserMemory OBJECT-TYPE
		SYNTAX		RollCallString
		MAX-ACCESS		read-only
		STATUS			current
		DESCRIPTION
				"TYPE: - Display
				 PAGE: - Common
					Last User Memory  cmdID= 37104  format=   "
		::= { iqhco31CmdEntry 37104 }


	iqhco31CommonMemoriesClearMemory OBJECT-TYPE
		SYNTAX		INTEGER { noAction(0),val-Clear-Memory(1) }
		MAX-ACCESS		read-write
		STATUS			current
		DESCRIPTION
				"TYPE: - Button
				 PAGE: - Common
					Clear Memory  cmdID= 37105  value= 1  "
		::= { iqhco31CmdEntry 37105 }


	iqhco31MemoriesMemoryNamesMemory1Name OBJECT-TYPE
		SYNTAX		RollCallString
		MAX-ACCESS		read-only
		STATUS			current
		DESCRIPTION
				"TYPE: - Display
				 PAGE: - Common
					Memory 1 Name  cmdID= 37106  format=   "
		::= { iqhco31CmdEntry 37106 }


	iqhco31MemoriesMemoryNamesMemory2Name OBJECT-TYPE
		SYNTAX		RollCallString
		MAX-ACCESS		read-only
		STATUS			current
		DESCRIPTION
				"TYPE: - Display
				 PAGE: - Common
					Memory 2 Name  cmdID= 37107  format=   "
		::= { iqhco31CmdEntry 37107 }


	iqhco31MemoriesMemoryNamesMemory3Name OBJECT-TYPE
		SYNTAX		RollCallString
		MAX-ACCESS		read-only
		STATUS			current
		DESCRIPTION
				"TYPE: - Display
				 PAGE: - Common
					Memory 3 Name  cmdID= 37108  format=   "
		::= { iqhco31CmdEntry 37108 }


	iqhco31MemoriesMemoryNamesMemory4Name OBJECT-TYPE
		SYNTAX		RollCallString
		MAX-ACCESS		read-only
		STATUS			current
		DESCRIPTION
				"TYPE: - Display
				 PAGE: - Common
					Memory 4 Name  cmdID= 37109  format=   "
		::= { iqhco31CmdEntry 37109 }


	iqhco31MemoriesMemoryNamesMemory5Name OBJECT-TYPE
		SYNTAX		RollCallString
		MAX-ACCESS		read-only
		STATUS			current
		DESCRIPTION
				"TYPE: - Display
				 PAGE: - Common
					Memory 5 Name  cmdID= 37110  format=   "
		::= { iqhco31CmdEntry 37110 }


	iqhco31MemoriesMemoryNamesMemory6Name OBJECT-TYPE
		SYNTAX		RollCallString
		MAX-ACCESS		read-only
		STATUS			current
		DESCRIPTION
				"TYPE: - Display
				 PAGE: - Common
					Memory 6 Name  cmdID= 37111  format=   "
		::= { iqhco31CmdEntry 37111 }


	iqhco31MemoriesMemoryNamesMemory7Name OBJECT-TYPE
		SYNTAX		RollCallString
		MAX-ACCESS		read-only
		STATUS			current
		DESCRIPTION
				"TYPE: - Display
				 PAGE: - Common
					Memory 7 Name  cmdID= 37112  format=   "
		::= { iqhco31CmdEntry 37112 }


	iqhco31MemoriesMemoryNamesMemory8Name OBJECT-TYPE
		SYNTAX		RollCallString
		MAX-ACCESS		read-only
		STATUS			current
		DESCRIPTION
				"TYPE: - Display
				 PAGE: - Common
					Memory 8 Name  cmdID= 37113  format=   "
		::= { iqhco31CmdEntry 37113 }


	iqhco31MemoriesMemoryNamesMemory9Name OBJECT-TYPE
		SYNTAX		RollCallString
		MAX-ACCESS		read-only
		STATUS			current
		DESCRIPTION
				"TYPE: - Display
				 PAGE: - Common
					Memory 9 Name  cmdID= 37114  format=   "
		::= { iqhco31CmdEntry 37114 }


	iqhco31MemoriesMemoryNamesMemory10Name OBJECT-TYPE
		SYNTAX		RollCallString
		MAX-ACCESS		read-only
		STATUS			current
		DESCRIPTION
				"TYPE: - Display
				 PAGE: - Common
					Memory 10 Name  cmdID= 37115  format=   "
		::= { iqhco31CmdEntry 37115 }


	iqhco31MemoriesMemoryNamesMemory11Name OBJECT-TYPE
		SYNTAX		RollCallString
		MAX-ACCESS		read-only
		STATUS			current
		DESCRIPTION
				"TYPE: - Display
				 PAGE: - Common
					Memory 11 Name  cmdID= 37116  format=   "
		::= { iqhco31CmdEntry 37116 }


	iqhco31MemoriesMemoryNamesMemory12Name OBJECT-TYPE
		SYNTAX		RollCallString
		MAX-ACCESS		read-only
		STATUS			current
		DESCRIPTION
				"TYPE: - Display
				 PAGE: - Common
					Memory 12 Name  cmdID= 37117  format=   "
		::= { iqhco31CmdEntry 37117 }


	iqhco31MemoriesMemoryNamesMemory13Name OBJECT-TYPE
		SYNTAX		RollCallString
		MAX-ACCESS		read-only
		STATUS			current
		DESCRIPTION
				"TYPE: - Display
				 PAGE: - Common
					Memory 13 Name  cmdID= 37118  format=   "
		::= { iqhco31CmdEntry 37118 }


	iqhco31MemoriesMemoryNamesMemory14Name OBJECT-TYPE
		SYNTAX		RollCallString
		MAX-ACCESS		read-only
		STATUS			current
		DESCRIPTION
				"TYPE: - Display
				 PAGE: - Common
					Memory 14 Name  cmdID= 37119  format=   "
		::= { iqhco31CmdEntry 37119 }


	iqhco31MemoriesMemoryNamesMemory15Name OBJECT-TYPE
		SYNTAX		RollCallString
		MAX-ACCESS		read-only
		STATUS			current
		DESCRIPTION
				"TYPE: - Display
				 PAGE: - Common
					Memory 15 Name  cmdID= 37120  format=   "
		::= { iqhco31CmdEntry 37120 }


	iqhco31MemoriesMemoryNamesMemory16Name OBJECT-TYPE
		SYNTAX		RollCallString
		MAX-ACCESS		read-only
		STATUS			current
		DESCRIPTION
				"TYPE: - Display
				 PAGE: - Common
					Memory 16 Name  cmdID= 37121  format=   "
		::= { iqhco31CmdEntry 37121 }


	iqhco31LoggingLogMiscSlotStarten OBJECT-TYPE
		SYNTAX		INTEGER { disable(0), enable(1) }
		MAX-ACCESS		read-write
		STATUS			current
		DESCRIPTION
				"TYPE: - Checkbox
				 PAGE: - Common- Setup- Logging- Log Misc
					Slot Start_en  cmdID= 4976 "
		::= { iqhco31CmdEntry 4976 }


	iqhco31LoggingLogMiscSlotStart OBJECT-TYPE
		SYNTAX		RollCallString
		MAX-ACCESS		read-only
		STATUS			current
		DESCRIPTION
				"TYPE: - Display
				 PAGE: - Common- Setup- Logging- Log Misc
					Slot Start  cmdID= 4977  format=   "
		::= { iqhco31CmdEntry 4977 }


	iqhco31LoggingLogMiscSlotWidthen OBJECT-TYPE
		SYNTAX		INTEGER { disable(0), enable(1) }
		MAX-ACCESS		read-write
		STATUS			current
		DESCRIPTION
				"TYPE: - Checkbox
				 PAGE: - Common- Setup- Logging- Log Misc
					Slot Width_en  cmdID= 4978 "
		::= { iqhco31CmdEntry 4978 }


	iqhco31LoggingLogMiscSlotWidth OBJECT-TYPE
		SYNTAX		RollCallString
		MAX-ACCESS		read-only
		STATUS			current
		DESCRIPTION
				"TYPE: - Display
				 PAGE: - Common- Setup- Logging- Log Misc
					Slot Width  cmdID= 4979  format=   "
		::= { iqhco31CmdEntry 4979 }


	iqhco31LoggingLogMiscRearStatusen OBJECT-TYPE
		SYNTAX		INTEGER { disable(0), enable(1) }
		MAX-ACCESS		read-write
		STATUS			current
		DESCRIPTION
				"TYPE: - Checkbox
				 PAGE: - Common- Setup- Logging- Log Misc
					Rear Status_en  cmdID= 4980 "
		::= { iqhco31CmdEntry 4980 }


	iqhco31LoggingLogMiscRearStatus OBJECT-TYPE
		SYNTAX		RollCallString
		MAX-ACCESS		read-only
		STATUS			current
		DESCRIPTION
				"TYPE: - Display
				 PAGE: - Common- Setup- Logging- Log Misc
					Rear Status  cmdID= 4981  format=   "
		::= { iqhco31CmdEntry 4981 }


	iqhco31LoggingLogMiscRearIDen OBJECT-TYPE
		SYNTAX		INTEGER { disable(0), enable(1) }
		MAX-ACCESS		read-write
		STATUS			current
		DESCRIPTION
				"TYPE: - Checkbox
				 PAGE: - Common- Setup- Logging- Log Misc
					Rear ID_en  cmdID= 4982 "
		::= { iqhco31CmdEntry 4982 }


	iqhco31LoggingLogMiscRearID OBJECT-TYPE
		SYNTAX		RollCallString
		MAX-ACCESS		read-only
		STATUS			current
		DESCRIPTION
				"TYPE: - Display
				 PAGE: - Common- Setup- Logging- Log Misc
					Rear ID  cmdID= 4983  format=   "
		::= { iqhco31CmdEntry 4983 }


	iqhco31LoggingLogMiscFirmwareVersionen OBJECT-TYPE
		SYNTAX		INTEGER { disable(0), enable(1) }
		MAX-ACCESS		read-write
		STATUS			current
		DESCRIPTION
				"TYPE: - Checkbox
				 PAGE: - Common- Setup- Logging- Log Misc
					Firmware Version_en  cmdID= 4986 "
		::= { iqhco31CmdEntry 4986 }


	iqhco31LoggingLogMiscFirmwareVersion OBJECT-TYPE
		SYNTAX		RollCallString
		MAX-ACCESS		read-only
		STATUS			current
		DESCRIPTION
				"TYPE: - Display
				 PAGE: - Common- Setup- Logging- Log Misc
					Firmware Version  cmdID= 4987  format=   "
		::= { iqhco31CmdEntry 4987 }


	iqhco31LoggingLogMiscLicensedOptionsen OBJECT-TYPE
		SYNTAX		INTEGER { disable(0), enable(1) }
		MAX-ACCESS		read-write
		STATUS			current
		DESCRIPTION
				"TYPE: - Checkbox
				 PAGE: - Common- Setup- Logging- Log Misc
					Licensed Options_en  cmdID= 4988 "
		::= { iqhco31CmdEntry 4988 }


	iqhco31LoggingLogMiscLicensedOptions OBJECT-TYPE
		SYNTAX		RollCallString
		MAX-ACCESS		read-only
		STATUS			current
		DESCRIPTION
				"TYPE: - Display
				 PAGE: - Common- Setup- Logging- Log Misc
					Licensed Options  cmdID= 4989  format=   "
		::= { iqhco31CmdEntry 4989 }


	iqhco31LoggingLogMiscBuildNumberen OBJECT-TYPE
		SYNTAX		INTEGER { disable(0), enable(1) }
		MAX-ACCESS		read-write
		STATUS			current
		DESCRIPTION
				"TYPE: - Checkbox
				 PAGE: - Common- Setup- Logging- Log Misc
					Build Number_en  cmdID= 4992 "
		::= { iqhco31CmdEntry 4992 }


	iqhco31LoggingLogMiscBuildNumber OBJECT-TYPE
		SYNTAX		RollCallString
		MAX-ACCESS		read-only
		STATUS			current
		DESCRIPTION
				"TYPE: - Display
				 PAGE: - Common- Setup- Logging- Log Misc
					Build Number  cmdID= 4993  format=   "
		::= { iqhco31CmdEntry 4993 }


	iqhco31LoggingLogMiscOSVersionen OBJECT-TYPE
		SYNTAX		INTEGER { disable(0), enable(1) }
		MAX-ACCESS		read-write
		STATUS			current
		DESCRIPTION
				"TYPE: - Checkbox
				 PAGE: - Common- Setup- Logging- Log Misc
					OS Version_en  cmdID= 4994 "
		::= { iqhco31CmdEntry 4994 }


	iqhco31LoggingLogMiscOSVersion OBJECT-TYPE
		SYNTAX		RollCallString
		MAX-ACCESS		read-only
		STATUS			current
		DESCRIPTION
				"TYPE: - Display
				 PAGE: - Common- Setup- Logging- Log Misc
					OS Version  cmdID= 4995  format=   "
		::= { iqhco31CmdEntry 4995 }


	iqhco31LoggingLogMiscHardwareVersionen OBJECT-TYPE
		SYNTAX		INTEGER { disable(0), enable(1) }
		MAX-ACCESS		read-write
		STATUS			current
		DESCRIPTION
				"TYPE: - Checkbox
				 PAGE: - Common- Setup- Logging- Log Misc
					Hardware Version_en  cmdID= 4996 "
		::= { iqhco31CmdEntry 4996 }


	iqhco31LoggingLogMiscHardwareVersion OBJECT-TYPE
		SYNTAX		RollCallString
		MAX-ACCESS		read-only
		STATUS			current
		DESCRIPTION
				"TYPE: - Display
				 PAGE: - Common- Setup- Logging- Log Misc
					Hardware Version  cmdID= 4997  format=   "
		::= { iqhco31CmdEntry 4997 }


	iqhco31LoggingLogMiscUptimeen OBJECT-TYPE
		SYNTAX		INTEGER { disable(0), enable(1) }
		MAX-ACCESS		read-write
		STATUS			current
		DESCRIPTION
				"TYPE: - Checkbox
				 PAGE: - Common- Setup- Logging- Log Misc
					Uptime_en  cmdID= 4998 "
		::= { iqhco31CmdEntry 4998 }


	iqhco31LoggingLogMiscUptime OBJECT-TYPE
		SYNTAX		RollCallString
		MAX-ACCESS		read-only
		STATUS			current
		DESCRIPTION
				"TYPE: - Display
				 PAGE: - Common- Setup- Logging- Log Misc
					Uptime  cmdID= 4999  format=   "
		::= { iqhco31CmdEntry 4999 }


	iqhco31LoggingLogMiscSerialNumberen OBJECT-TYPE
		SYNTAX		INTEGER { disable(0), enable(1) }
		MAX-ACCESS		read-write
		STATUS			current
		DESCRIPTION
				"TYPE: - Checkbox
				 PAGE: - Common- Setup- Logging- Log Misc
					Serial Number_en  cmdID= 4990 "
		::= { iqhco31CmdEntry 4990 }


	iqhco31LoggingLogMiscSerialNumber OBJECT-TYPE
		SYNTAX		RollCallString
		MAX-ACCESS		read-only
		STATUS			current
		DESCRIPTION
				"TYPE: - Display
				 PAGE: - Common- Setup- Logging- Log Misc
					Serial Number  cmdID= 4991  format=   "
		::= { iqhco31CmdEntry 4991 }


	iqhco31LoggingLogVideoInput1Input1en OBJECT-TYPE
		SYNTAX		INTEGER { disable(0), enable(1) }
		MAX-ACCESS		read-write
		STATUS			current
		DESCRIPTION
				"TYPE: - Checkbox
				 PAGE: - Common- Setup- Logging- Log Video_Input_1
					Input1_en  cmdID= 4000 "
		::= { iqhco31CmdEntry 4000 }


	iqhco31LoggingLogVideoInput1Input1 OBJECT-TYPE
		SYNTAX		RollCallString
		MAX-ACCESS		read-only
		STATUS			current
		DESCRIPTION
				"TYPE: - Display
				 PAGE: - Common- Setup- Logging- Log Video_Input_1
					Input1  cmdID= 4001  format=   "
		::= { iqhco31CmdEntry 4001 }


	iqhco31LoggingLogVideoInput1Input1Standarden OBJECT-TYPE
		SYNTAX		INTEGER { disable(0), enable(1) }
		MAX-ACCESS		read-write
		STATUS			current
		DESCRIPTION
				"TYPE: - Checkbox
				 PAGE: - Common- Setup- Logging- Log Video_Input_1
					Input1 Standard_en  cmdID= 4004 "
		::= { iqhco31CmdEntry 4004 }


	iqhco31LoggingLogVideoInput1Input1Standard OBJECT-TYPE
		SYNTAX		RollCallString
		MAX-ACCESS		read-only
		STATUS			current
		DESCRIPTION
				"TYPE: - Display
				 PAGE: - Common- Setup- Logging- Log Video_Input_1
					Input1 Standard  cmdID= 4005  format=   "
		::= { iqhco31CmdEntry 4005 }


	iqhco31LoggingLogVideoInput1In1SDIERRSen OBJECT-TYPE
		SYNTAX		INTEGER { disable(0), enable(1) }
		MAX-ACCESS		read-write
		STATUS			current
		DESCRIPTION
				"TYPE: - Checkbox
				 PAGE: - Common- Setup- Logging- Log Video_Input_1
					In1 SDI ERRS_en  cmdID= 4012 "
		::= { iqhco31CmdEntry 4012 }


	iqhco31LoggingLogVideoInput1In1SDIERRS OBJECT-TYPE
		SYNTAX		RollCallString
		MAX-ACCESS		read-only
		STATUS			current
		DESCRIPTION
				"TYPE: - Display
				 PAGE: - Common- Setup- Logging- Log Video_Input_1
					In1 SDI ERRS  cmdID= 4013  format=   "
		::= { iqhco31CmdEntry 4013 }


	iqhco31LoggingLogVideoInput1In1SDIANCERRSen OBJECT-TYPE
		SYNTAX		INTEGER { disable(0), enable(1) }
		MAX-ACCESS		read-write
		STATUS			current
		DESCRIPTION
				"TYPE: - Checkbox
				 PAGE: - Common- Setup- Logging- Log Video_Input_1
					In1 SDI ANC ERRS_en  cmdID= 4020 "
		::= { iqhco31CmdEntry 4020 }


	iqhco31LoggingLogVideoInput1In1SDIANCERRS OBJECT-TYPE
		SYNTAX		RollCallString
		MAX-ACCESS		read-only
		STATUS			current
		DESCRIPTION
				"TYPE: - Display
				 PAGE: - Common- Setup- Logging- Log Video_Input_1
					In1 SDI ANC ERRS  cmdID= 4021  format=   "
		::= { iqhco31CmdEntry 4021 }


	iqhco31LoggingLogVideoInput1Input1Typeen OBJECT-TYPE
		SYNTAX		INTEGER { disable(0), enable(1) }
		MAX-ACCESS		read-write
		STATUS			current
		DESCRIPTION
				"TYPE: - Checkbox
				 PAGE: - Common- Setup- Logging- Log Video_Input_1
					Input1 Type_en  cmdID= 4024 "
		::= { iqhco31CmdEntry 4024 }


	iqhco31LoggingLogVideoInput1Input1Type OBJECT-TYPE
		SYNTAX		RollCallString
		MAX-ACCESS		read-only
		STATUS			current
		DESCRIPTION
				"TYPE: - Display
				 PAGE: - Common- Setup- Logging- Log Video_Input_1
					Input1 Type  cmdID= 4025  format=   "
		::= { iqhco31CmdEntry 4025 }


	iqhco31LoggingLogVideoInput1Input1Identen OBJECT-TYPE
		SYNTAX		INTEGER { disable(0), enable(1) }
		MAX-ACCESS		read-write
		STATUS			current
		DESCRIPTION
				"TYPE: - Checkbox
				 PAGE: - Common- Setup- Logging- Log Video_Input_1
					Input1 Ident_en  cmdID= 4028 "
		::= { iqhco31CmdEntry 4028 }


	iqhco31LoggingLogVideoInput1Input1Ident OBJECT-TYPE
		SYNTAX		RollCallString
		MAX-ACCESS		read-only
		STATUS			current
		DESCRIPTION
				"TYPE: - Display
				 PAGE: - Common- Setup- Logging- Log Video_Input_1
					Input1 Ident  cmdID= 4029  format=   "
		::= { iqhco31CmdEntry 4029 }


	iqhco31LoggingLogVideoInput1In1BlackERRSen OBJECT-TYPE
		SYNTAX		INTEGER { disable(0), enable(1) }
		MAX-ACCESS		read-write
		STATUS			current
		DESCRIPTION
				"TYPE: - Checkbox
				 PAGE: - Common- Setup- Logging- Log Video_Input_1
					In1 Black ERRS_en  cmdID= 4452 "
		::= { iqhco31CmdEntry 4452 }


	iqhco31LoggingLogVideoInput1In1BlackERRS OBJECT-TYPE
		SYNTAX		RollCallString
		MAX-ACCESS		read-only
		STATUS			current
		DESCRIPTION
				"TYPE: - Display
				 PAGE: - Common- Setup- Logging- Log Video_Input_1
					In1 Black ERRS  cmdID= 4453  format=   "
		::= { iqhco31CmdEntry 4453 }


	iqhco31LoggingLogVideoInput1In1FreezeERRSen OBJECT-TYPE
		SYNTAX		INTEGER { disable(0), enable(1) }
		MAX-ACCESS		read-write
		STATUS			current
		DESCRIPTION
				"TYPE: - Checkbox
				 PAGE: - Common- Setup- Logging- Log Video_Input_1
					In1 Freeze ERRS_en  cmdID= 4456 "
		::= { iqhco31CmdEntry 4456 }


	iqhco31LoggingLogVideoInput1In1FreezeERRS OBJECT-TYPE
		SYNTAX		RollCallString
		MAX-ACCESS		read-only
		STATUS			current
		DESCRIPTION
				"TYPE: - Display
				 PAGE: - Common- Setup- Logging- Log Video_Input_1
					In1 Freeze ERRS  cmdID= 4457  format=   "
		::= { iqhco31CmdEntry 4457 }


	iqhco31LoggingLogVideoInput2Input2en OBJECT-TYPE
		SYNTAX		INTEGER { disable(0), enable(1) }
		MAX-ACCESS		read-write
		STATUS			current
		DESCRIPTION
				"TYPE: - Checkbox
				 PAGE: - Common- Setup- Logging- Log Video_Input_2
					Input2_en  cmdID= 4002 "
		::= { iqhco31CmdEntry 4002 }


	iqhco31LoggingLogVideoInput2Input2 OBJECT-TYPE
		SYNTAX		RollCallString
		MAX-ACCESS		read-only
		STATUS			current
		DESCRIPTION
				"TYPE: - Display
				 PAGE: - Common- Setup- Logging- Log Video_Input_2
					Input2  cmdID= 4003  format=   "
		::= { iqhco31CmdEntry 4003 }


	iqhco31LoggingLogVideoInput2Input2Standarden OBJECT-TYPE
		SYNTAX		INTEGER { disable(0), enable(1) }
		MAX-ACCESS		read-write
		STATUS			current
		DESCRIPTION
				"TYPE: - Checkbox
				 PAGE: - Common- Setup- Logging- Log Video_Input_2
					Input2 Standard_en  cmdID= 4006 "
		::= { iqhco31CmdEntry 4006 }


	iqhco31LoggingLogVideoInput2Input2Standard OBJECT-TYPE
		SYNTAX		RollCallString
		MAX-ACCESS		read-only
		STATUS			current
		DESCRIPTION
				"TYPE: - Display
				 PAGE: - Common- Setup- Logging- Log Video_Input_2
					Input2 Standard  cmdID= 4007  format=   "
		::= { iqhco31CmdEntry 4007 }


	iqhco31LoggingLogVideoInput2In2SDIERRSen OBJECT-TYPE
		SYNTAX		INTEGER { disable(0), enable(1) }
		MAX-ACCESS		read-write
		STATUS			current
		DESCRIPTION
				"TYPE: - Checkbox
				 PAGE: - Common- Setup- Logging- Log Video_Input_2
					In2 SDI ERRS_en  cmdID= 4014 "
		::= { iqhco31CmdEntry 4014 }


	iqhco31LoggingLogVideoInput2In2SDIERRS OBJECT-TYPE
		SYNTAX		RollCallString
		MAX-ACCESS		read-only
		STATUS			current
		DESCRIPTION
				"TYPE: - Display
				 PAGE: - Common- Setup- Logging- Log Video_Input_2
					In2 SDI ERRS  cmdID= 4015  format=   "
		::= { iqhco31CmdEntry 4015 }


	iqhco31LoggingLogVideoInput2In2SDIANCERRSen OBJECT-TYPE
		SYNTAX		INTEGER { disable(0), enable(1) }
		MAX-ACCESS		read-write
		STATUS			current
		DESCRIPTION
				"TYPE: - Checkbox
				 PAGE: - Common- Setup- Logging- Log Video_Input_2
					In2 SDI ANC ERRS_en  cmdID= 4022 "
		::= { iqhco31CmdEntry 4022 }


	iqhco31LoggingLogVideoInput2In2SDIANCERRS OBJECT-TYPE
		SYNTAX		RollCallString
		MAX-ACCESS		read-only
		STATUS			current
		DESCRIPTION
				"TYPE: - Display
				 PAGE: - Common- Setup- Logging- Log Video_Input_2
					In2 SDI ANC ERRS  cmdID= 4023  format=   "
		::= { iqhco31CmdEntry 4023 }


	iqhco31LoggingLogVideoInput2Input2Typeen OBJECT-TYPE
		SYNTAX		INTEGER { disable(0), enable(1) }
		MAX-ACCESS		read-write
		STATUS			current
		DESCRIPTION
				"TYPE: - Checkbox
				 PAGE: - Common- Setup- Logging- Log Video_Input_2
					Input2 Type_en  cmdID= 4026 "
		::= { iqhco31CmdEntry 4026 }


	iqhco31LoggingLogVideoInput2Input2Type OBJECT-TYPE
		SYNTAX		RollCallString
		MAX-ACCESS		read-only
		STATUS			current
		DESCRIPTION
				"TYPE: - Display
				 PAGE: - Common- Setup- Logging- Log Video_Input_2
					Input2 Type  cmdID= 4027  format=   "
		::= { iqhco31CmdEntry 4027 }


	iqhco31LoggingLogVideoInput2Input2Identen OBJECT-TYPE
		SYNTAX		INTEGER { disable(0), enable(1) }
		MAX-ACCESS		read-write
		STATUS			current
		DESCRIPTION
				"TYPE: - Checkbox
				 PAGE: - Common- Setup- Logging- Log Video_Input_2
					Input2 Ident_en  cmdID= 4030 "
		::= { iqhco31CmdEntry 4030 }


	iqhco31LoggingLogVideoInput2Input2Ident OBJECT-TYPE
		SYNTAX		RollCallString
		MAX-ACCESS		read-only
		STATUS			current
		DESCRIPTION
				"TYPE: - Display
				 PAGE: - Common- Setup- Logging- Log Video_Input_2
					Input2 Ident  cmdID= 4031  format=   "
		::= { iqhco31CmdEntry 4031 }


	iqhco31LoggingLogVideoInput2In2BlackERRSen OBJECT-TYPE
		SYNTAX		INTEGER { disable(0), enable(1) }
		MAX-ACCESS		read-write
		STATUS			current
		DESCRIPTION
				"TYPE: - Checkbox
				 PAGE: - Common- Setup- Logging- Log Video_Input_2
					In2 Black ERRS_en  cmdID= 4454 "
		::= { iqhco31CmdEntry 4454 }


	iqhco31LoggingLogVideoInput2In2BlackERRS OBJECT-TYPE
		SYNTAX		RollCallString
		MAX-ACCESS		read-only
		STATUS			current
		DESCRIPTION
				"TYPE: - Display
				 PAGE: - Common- Setup- Logging- Log Video_Input_2
					In2 Black ERRS  cmdID= 4455  format=   "
		::= { iqhco31CmdEntry 4455 }


	iqhco31LoggingLogVideoInput2In2FreezeERRSen OBJECT-TYPE
		SYNTAX		INTEGER { disable(0), enable(1) }
		MAX-ACCESS		read-write
		STATUS			current
		DESCRIPTION
				"TYPE: - Checkbox
				 PAGE: - Common- Setup- Logging- Log Video_Input_2
					In2 Freeze ERRS_en  cmdID= 4458 "
		::= { iqhco31CmdEntry 4458 }


	iqhco31LoggingLogVideoInput2In2FreezeERRS OBJECT-TYPE
		SYNTAX		RollCallString
		MAX-ACCESS		read-only
		STATUS			current
		DESCRIPTION
				"TYPE: - Display
				 PAGE: - Common- Setup- Logging- Log Video_Input_2
					In2 Freeze ERRS  cmdID= 4459  format=   "
		::= { iqhco31CmdEntry 4459 }


	iqhco31LoggingLogReferenceRef1Stateen OBJECT-TYPE
		SYNTAX		INTEGER { disable(0), enable(1) }
		MAX-ACCESS		read-write
		STATUS			current
		DESCRIPTION
				"TYPE: - Checkbox
				 PAGE: - Common- Setup- Logging- Log Reference
					Ref1 State_en  cmdID= 4040 "
		::= { iqhco31CmdEntry 4040 }


	iqhco31LoggingLogReferenceRef1State OBJECT-TYPE
		SYNTAX		RollCallString
		MAX-ACCESS		read-only
		STATUS			current
		DESCRIPTION
				"TYPE: - Display
				 PAGE: - Common- Setup- Logging- Log Reference
					Ref1 State  cmdID= 4041  format=   "
		::= { iqhco31CmdEntry 4041 }


	iqhco31LoggingLogReferenceRef1Standarden OBJECT-TYPE
		SYNTAX		INTEGER { disable(0), enable(1) }
		MAX-ACCESS		read-write
		STATUS			current
		DESCRIPTION
				"TYPE: - Checkbox
				 PAGE: - Common- Setup- Logging- Log Reference
					Ref1 Standard_en  cmdID= 4044 "
		::= { iqhco31CmdEntry 4044 }


	iqhco31LoggingLogReferenceRef1Standard OBJECT-TYPE
		SYNTAX		RollCallString
		MAX-ACCESS		read-only
		STATUS			current
		DESCRIPTION
				"TYPE: - Display
				 PAGE: - Common- Setup- Logging- Log Reference
					Ref1 Standard  cmdID= 4045  format=   "
		::= { iqhco31CmdEntry 4045 }


	iqhco31LoggingLogReferenceRef1Typeen OBJECT-TYPE
		SYNTAX		INTEGER { disable(0), enable(1) }
		MAX-ACCESS		read-write
		STATUS			current
		DESCRIPTION
				"TYPE: - Checkbox
				 PAGE: - Common- Setup- Logging- Log Reference
					Ref1 Type_en  cmdID= 4048 "
		::= { iqhco31CmdEntry 4048 }


	iqhco31LoggingLogReferenceRef1Type OBJECT-TYPE
		SYNTAX		RollCallString
		MAX-ACCESS		read-only
		STATUS			current
		DESCRIPTION
				"TYPE: - Display
				 PAGE: - Common- Setup- Logging- Log Reference
					Ref1 Type  cmdID= 4049  format=   "
		::= { iqhco31CmdEntry 4049 }


	iqhco31LoggingLogReferenceGenlock1Stateen OBJECT-TYPE
		SYNTAX		INTEGER { disable(0), enable(1) }
		MAX-ACCESS		read-write
		STATUS			current
		DESCRIPTION
				"TYPE: - Checkbox
				 PAGE: - Common- Setup- Logging- Log Reference
					Genlock1 State_en  cmdID= 4052 "
		::= { iqhco31CmdEntry 4052 }


	iqhco31LoggingLogReferenceGenlock1State OBJECT-TYPE
		SYNTAX		RollCallString
		MAX-ACCESS		read-only
		STATUS			current
		DESCRIPTION
				"TYPE: - Display
				 PAGE: - Common- Setup- Logging- Log Reference
					Genlock1 State  cmdID= 4053  format=   "
		::= { iqhco31CmdEntry 4053 }


	iqhco31LoggingLogAudioInput1Input1Audio11en OBJECT-TYPE
		SYNTAX		INTEGER { disable(0), enable(1) }
		MAX-ACCESS		read-write
		STATUS			current
		DESCRIPTION
				"TYPE: - Checkbox
				 PAGE: - Common- Setup- Logging- Log Audio_Input_1
					Input1 Audio 1 1_en  cmdID= 4064 "
		::= { iqhco31CmdEntry 4064 }


	iqhco31LoggingLogAudioInput1Input1Audio11 OBJECT-TYPE
		SYNTAX		RollCallString
		MAX-ACCESS		read-only
		STATUS			current
		DESCRIPTION
				"TYPE: - Display
				 PAGE: - Common- Setup- Logging- Log Audio_Input_1
					Input1 Audio 1 1  cmdID= 4065  format=   "
		::= { iqhco31CmdEntry 4065 }


	iqhco31LoggingLogAudioInput1Input1Audio12en OBJECT-TYPE
		SYNTAX		INTEGER { disable(0), enable(1) }
		MAX-ACCESS		read-write
		STATUS			current
		DESCRIPTION
				"TYPE: - Checkbox
				 PAGE: - Common- Setup- Logging- Log Audio_Input_1
					Input1 Audio 1 2_en  cmdID= 4068 "
		::= { iqhco31CmdEntry 4068 }


	iqhco31LoggingLogAudioInput1Input1Audio12 OBJECT-TYPE
		SYNTAX		RollCallString
		MAX-ACCESS		read-only
		STATUS			current
		DESCRIPTION
				"TYPE: - Display
				 PAGE: - Common- Setup- Logging- Log Audio_Input_1
					Input1 Audio 1 2  cmdID= 4069  format=   "
		::= { iqhco31CmdEntry 4069 }


	iqhco31LoggingLogAudioInput1Input1Audio21en OBJECT-TYPE
		SYNTAX		INTEGER { disable(0), enable(1) }
		MAX-ACCESS		read-write
		STATUS			current
		DESCRIPTION
				"TYPE: - Checkbox
				 PAGE: - Common- Setup- Logging- Log Audio_Input_1
					Input1 Audio 2 1_en  cmdID= 4072 "
		::= { iqhco31CmdEntry 4072 }


	iqhco31LoggingLogAudioInput1Input1Audio21 OBJECT-TYPE
		SYNTAX		RollCallString
		MAX-ACCESS		read-only
		STATUS			current
		DESCRIPTION
				"TYPE: - Display
				 PAGE: - Common- Setup- Logging- Log Audio_Input_1
					Input1 Audio 2 1  cmdID= 4073  format=   "
		::= { iqhco31CmdEntry 4073 }


	iqhco31LoggingLogAudioInput1Input1Audio22en OBJECT-TYPE
		SYNTAX		INTEGER { disable(0), enable(1) }
		MAX-ACCESS		read-write
		STATUS			current
		DESCRIPTION
				"TYPE: - Checkbox
				 PAGE: - Common- Setup- Logging- Log Audio_Input_1
					Input1 Audio 2 2_en  cmdID= 4076 "
		::= { iqhco31CmdEntry 4076 }


	iqhco31LoggingLogAudioInput1Input1Audio22 OBJECT-TYPE
		SYNTAX		RollCallString
		MAX-ACCESS		read-only
		STATUS			current
		DESCRIPTION
				"TYPE: - Display
				 PAGE: - Common- Setup- Logging- Log Audio_Input_1
					Input1 Audio 2 2  cmdID= 4077  format=   "
		::= { iqhco31CmdEntry 4077 }


	iqhco31LoggingLogAudioInput1Input1Audio31en OBJECT-TYPE
		SYNTAX		INTEGER { disable(0), enable(1) }
		MAX-ACCESS		read-write
		STATUS			current
		DESCRIPTION
				"TYPE: - Checkbox
				 PAGE: - Common- Setup- Logging- Log Audio_Input_1
					Input1 Audio 3 1_en  cmdID= 4080 "
		::= { iqhco31CmdEntry 4080 }


	iqhco31LoggingLogAudioInput1Input1Audio31 OBJECT-TYPE
		SYNTAX		RollCallString
		MAX-ACCESS		read-only
		STATUS			current
		DESCRIPTION
				"TYPE: - Display
				 PAGE: - Common- Setup- Logging- Log Audio_Input_1
					Input1 Audio 3 1  cmdID= 4081  format=   "
		::= { iqhco31CmdEntry 4081 }


	iqhco31LoggingLogAudioInput1Input1Audio32en OBJECT-TYPE
		SYNTAX		INTEGER { disable(0), enable(1) }
		MAX-ACCESS		read-write
		STATUS			current
		DESCRIPTION
				"TYPE: - Checkbox
				 PAGE: - Common- Setup- Logging- Log Audio_Input_1
					Input1 Audio 3 2_en  cmdID= 4084 "
		::= { iqhco31CmdEntry 4084 }


	iqhco31LoggingLogAudioInput1Input1Audio32 OBJECT-TYPE
		SYNTAX		RollCallString
		MAX-ACCESS		read-only
		STATUS			current
		DESCRIPTION
				"TYPE: - Display
				 PAGE: - Common- Setup- Logging- Log Audio_Input_1
					Input1 Audio 3 2  cmdID= 4085  format=   "
		::= { iqhco31CmdEntry 4085 }


	iqhco31LoggingLogAudioInput1Input1Audio41en OBJECT-TYPE
		SYNTAX		INTEGER { disable(0), enable(1) }
		MAX-ACCESS		read-write
		STATUS			current
		DESCRIPTION
				"TYPE: - Checkbox
				 PAGE: - Common- Setup- Logging- Log Audio_Input_1
					Input1 Audio 4 1_en  cmdID= 4088 "
		::= { iqhco31CmdEntry 4088 }


	iqhco31LoggingLogAudioInput1Input1Audio41 OBJECT-TYPE
		SYNTAX		RollCallString
		MAX-ACCESS		read-only
		STATUS			current
		DESCRIPTION
				"TYPE: - Display
				 PAGE: - Common- Setup- Logging- Log Audio_Input_1
					Input1 Audio 4 1  cmdID= 4089  format=   "
		::= { iqhco31CmdEntry 4089 }


	iqhco31LoggingLogAudioInput1Input1Audio42en OBJECT-TYPE
		SYNTAX		INTEGER { disable(0), enable(1) }
		MAX-ACCESS		read-write
		STATUS			current
		DESCRIPTION
				"TYPE: - Checkbox
				 PAGE: - Common- Setup- Logging- Log Audio_Input_1
					Input1 Audio 4 2_en  cmdID= 4092 "
		::= { iqhco31CmdEntry 4092 }


	iqhco31LoggingLogAudioInput1Input1Audio42 OBJECT-TYPE
		SYNTAX		RollCallString
		MAX-ACCESS		read-only
		STATUS			current
		DESCRIPTION
				"TYPE: - Display
				 PAGE: - Common- Setup- Logging- Log Audio_Input_1
					Input1 Audio 4 2  cmdID= 4093  format=   "
		::= { iqhco31CmdEntry 4093 }


	iqhco31LoggingLogAudioInput1Input1Audio51en OBJECT-TYPE
		SYNTAX		INTEGER { disable(0), enable(1) }
		MAX-ACCESS		read-write
		STATUS			current
		DESCRIPTION
				"TYPE: - Checkbox
				 PAGE: - Common- Setup- Logging- Log Audio_Input_1
					Input1 Audio 5 1_en  cmdID= 4096 "
		::= { iqhco31CmdEntry 4096 }


	iqhco31LoggingLogAudioInput1Input1Audio51 OBJECT-TYPE
		SYNTAX		RollCallString
		MAX-ACCESS		read-only
		STATUS			current
		DESCRIPTION
				"TYPE: - Display
				 PAGE: - Common- Setup- Logging- Log Audio_Input_1
					Input1 Audio 5 1  cmdID= 4097  format=   "
		::= { iqhco31CmdEntry 4097 }


	iqhco31LoggingLogAudioInput1Input1Audio52en OBJECT-TYPE
		SYNTAX		INTEGER { disable(0), enable(1) }
		MAX-ACCESS		read-write
		STATUS			current
		DESCRIPTION
				"TYPE: - Checkbox
				 PAGE: - Common- Setup- Logging- Log Audio_Input_1
					Input1 Audio 5 2_en  cmdID= 4100 "
		::= { iqhco31CmdEntry 4100 }


	iqhco31LoggingLogAudioInput1Input1Audio52 OBJECT-TYPE
		SYNTAX		RollCallString
		MAX-ACCESS		read-only
		STATUS			current
		DESCRIPTION
				"TYPE: - Display
				 PAGE: - Common- Setup- Logging- Log Audio_Input_1
					Input1 Audio 5 2  cmdID= 4101  format=   "
		::= { iqhco31CmdEntry 4101 }


	iqhco31LoggingLogAudioInput1Input1Audio61en OBJECT-TYPE
		SYNTAX		INTEGER { disable(0), enable(1) }
		MAX-ACCESS		read-write
		STATUS			current
		DESCRIPTION
				"TYPE: - Checkbox
				 PAGE: - Common- Setup- Logging- Log Audio_Input_1
					Input1 Audio 6 1_en  cmdID= 4104 "
		::= { iqhco31CmdEntry 4104 }


	iqhco31LoggingLogAudioInput1Input1Audio61 OBJECT-TYPE
		SYNTAX		RollCallString
		MAX-ACCESS		read-only
		STATUS			current
		DESCRIPTION
				"TYPE: - Display
				 PAGE: - Common- Setup- Logging- Log Audio_Input_1
					Input1 Audio 6 1  cmdID= 4105  format=   "
		::= { iqhco31CmdEntry 4105 }


	iqhco31LoggingLogAudioInput1Input1Audio62en OBJECT-TYPE
		SYNTAX		INTEGER { disable(0), enable(1) }
		MAX-ACCESS		read-write
		STATUS			current
		DESCRIPTION
				"TYPE: - Checkbox
				 PAGE: - Common- Setup- Logging- Log Audio_Input_1
					Input1 Audio 6 2_en  cmdID= 4108 "
		::= { iqhco31CmdEntry 4108 }


	iqhco31LoggingLogAudioInput1Input1Audio62 OBJECT-TYPE
		SYNTAX		RollCallString
		MAX-ACCESS		read-only
		STATUS			current
		DESCRIPTION
				"TYPE: - Display
				 PAGE: - Common- Setup- Logging- Log Audio_Input_1
					Input1 Audio 6 2  cmdID= 4109  format=   "
		::= { iqhco31CmdEntry 4109 }


	iqhco31LoggingLogAudioInput1Input1Audio71en OBJECT-TYPE
		SYNTAX		INTEGER { disable(0), enable(1) }
		MAX-ACCESS		read-write
		STATUS			current
		DESCRIPTION
				"TYPE: - Checkbox
				 PAGE: - Common- Setup- Logging- Log Audio_Input_1
					Input1 Audio 7 1_en  cmdID= 4112 "
		::= { iqhco31CmdEntry 4112 }


	iqhco31LoggingLogAudioInput1Input1Audio71 OBJECT-TYPE
		SYNTAX		RollCallString
		MAX-ACCESS		read-only
		STATUS			current
		DESCRIPTION
				"TYPE: - Display
				 PAGE: - Common- Setup- Logging- Log Audio_Input_1
					Input1 Audio 7 1  cmdID= 4113  format=   "
		::= { iqhco31CmdEntry 4113 }


	iqhco31LoggingLogAudioInput1Input1Audio72en OBJECT-TYPE
		SYNTAX		INTEGER { disable(0), enable(1) }
		MAX-ACCESS		read-write
		STATUS			current
		DESCRIPTION
				"TYPE: - Checkbox
				 PAGE: - Common- Setup- Logging- Log Audio_Input_1
					Input1 Audio 7 2_en  cmdID= 4116 "
		::= { iqhco31CmdEntry 4116 }


	iqhco31LoggingLogAudioInput1Input1Audio72 OBJECT-TYPE
		SYNTAX		RollCallString
		MAX-ACCESS		read-only
		STATUS			current
		DESCRIPTION
				"TYPE: - Display
				 PAGE: - Common- Setup- Logging- Log Audio_Input_1
					Input1 Audio 7 2  cmdID= 4117  format=   "
		::= { iqhco31CmdEntry 4117 }


	iqhco31LoggingLogAudioInput1Input1Audio81en OBJECT-TYPE
		SYNTAX		INTEGER { disable(0), enable(1) }
		MAX-ACCESS		read-write
		STATUS			current
		DESCRIPTION
				"TYPE: - Checkbox
				 PAGE: - Common- Setup- Logging- Log Audio_Input_1
					Input1 Audio 8 1_en  cmdID= 4120 "
		::= { iqhco31CmdEntry 4120 }


	iqhco31LoggingLogAudioInput1Input1Audio81 OBJECT-TYPE
		SYNTAX		RollCallString
		MAX-ACCESS		read-only
		STATUS			current
		DESCRIPTION
				"TYPE: - Display
				 PAGE: - Common- Setup- Logging- Log Audio_Input_1
					Input1 Audio 8 1  cmdID= 4121  format=   "
		::= { iqhco31CmdEntry 4121 }


	iqhco31LoggingLogAudioInput1Input1Audio82en OBJECT-TYPE
		SYNTAX		INTEGER { disable(0), enable(1) }
		MAX-ACCESS		read-write
		STATUS			current
		DESCRIPTION
				"TYPE: - Checkbox
				 PAGE: - Common- Setup- Logging- Log Audio_Input_1
					Input1 Audio 8 2_en  cmdID= 4124 "
		::= { iqhco31CmdEntry 4124 }


	iqhco31LoggingLogAudioInput1Input1Audio82 OBJECT-TYPE
		SYNTAX		RollCallString
		MAX-ACCESS		read-only
		STATUS			current
		DESCRIPTION
				"TYPE: - Display
				 PAGE: - Common- Setup- Logging- Log Audio_Input_1
					Input1 Audio 8 2  cmdID= 4125  format=   "
		::= { iqhco31CmdEntry 4125 }


	iqhco31LoggingLogAudioInput2Input2Audio11en OBJECT-TYPE
		SYNTAX		INTEGER { disable(0), enable(1) }
		MAX-ACCESS		read-write
		STATUS			current
		DESCRIPTION
				"TYPE: - Checkbox
				 PAGE: - Common- Setup- Logging- Log Audio_Input_2
					Input2 Audio 1 1_en  cmdID= 4128 "
		::= { iqhco31CmdEntry 4128 }


	iqhco31LoggingLogAudioInput2Input2Audio11 OBJECT-TYPE
		SYNTAX		RollCallString
		MAX-ACCESS		read-only
		STATUS			current
		DESCRIPTION
				"TYPE: - Display
				 PAGE: - Common- Setup- Logging- Log Audio_Input_2
					Input2 Audio 1 1  cmdID= 4129  format=   "
		::= { iqhco31CmdEntry 4129 }


	iqhco31LoggingLogAudioInput2Input2Audio12en OBJECT-TYPE
		SYNTAX		INTEGER { disable(0), enable(1) }
		MAX-ACCESS		read-write
		STATUS			current
		DESCRIPTION
				"TYPE: - Checkbox
				 PAGE: - Common- Setup- Logging- Log Audio_Input_2
					Input2 Audio 1 2_en  cmdID= 4132 "
		::= { iqhco31CmdEntry 4132 }


	iqhco31LoggingLogAudioInput2Input2Audio12 OBJECT-TYPE
		SYNTAX		RollCallString
		MAX-ACCESS		read-only
		STATUS			current
		DESCRIPTION
				"TYPE: - Display
				 PAGE: - Common- Setup- Logging- Log Audio_Input_2
					Input2 Audio 1 2  cmdID= 4133  format=   "
		::= { iqhco31CmdEntry 4133 }


	iqhco31LoggingLogAudioInput2Input2Audio21en OBJECT-TYPE
		SYNTAX		INTEGER { disable(0), enable(1) }
		MAX-ACCESS		read-write
		STATUS			current
		DESCRIPTION
				"TYPE: - Checkbox
				 PAGE: - Common- Setup- Logging- Log Audio_Input_2
					Input2 Audio 2 1_en  cmdID= 4136 "
		::= { iqhco31CmdEntry 4136 }


	iqhco31LoggingLogAudioInput2Input2Audio21 OBJECT-TYPE
		SYNTAX		RollCallString
		MAX-ACCESS		read-only
		STATUS			current
		DESCRIPTION
				"TYPE: - Display
				 PAGE: - Common- Setup- Logging- Log Audio_Input_2
					Input2 Audio 2 1  cmdID= 4137  format=   "
		::= { iqhco31CmdEntry 4137 }


	iqhco31LoggingLogAudioInput2Input2Audio22en OBJECT-TYPE
		SYNTAX		INTEGER { disable(0), enable(1) }
		MAX-ACCESS		read-write
		STATUS			current
		DESCRIPTION
				"TYPE: - Checkbox
				 PAGE: - Common- Setup- Logging- Log Audio_Input_2
					Input2 Audio 2 2_en  cmdID= 4140 "
		::= { iqhco31CmdEntry 4140 }


	iqhco31LoggingLogAudioInput2Input2Audio22 OBJECT-TYPE
		SYNTAX		RollCallString
		MAX-ACCESS		read-only
		STATUS			current
		DESCRIPTION
				"TYPE: - Display
				 PAGE: - Common- Setup- Logging- Log Audio_Input_2
					Input2 Audio 2 2  cmdID= 4141  format=   "
		::= { iqhco31CmdEntry 4141 }


	iqhco31LoggingLogAudioInput2Input2Audio31en OBJECT-TYPE
		SYNTAX		INTEGER { disable(0), enable(1) }
		MAX-ACCESS		read-write
		STATUS			current
		DESCRIPTION
				"TYPE: - Checkbox
				 PAGE: - Common- Setup- Logging- Log Audio_Input_2
					Input2 Audio 3 1_en  cmdID= 4144 "
		::= { iqhco31CmdEntry 4144 }


	iqhco31LoggingLogAudioInput2Input2Audio31 OBJECT-TYPE
		SYNTAX		RollCallString
		MAX-ACCESS		read-only
		STATUS			current
		DESCRIPTION
				"TYPE: - Display
				 PAGE: - Common- Setup- Logging- Log Audio_Input_2
					Input2 Audio 3 1  cmdID= 4145  format=   "
		::= { iqhco31CmdEntry 4145 }


	iqhco31LoggingLogAudioInput2Input2Audio32en OBJECT-TYPE
		SYNTAX		INTEGER { disable(0), enable(1) }
		MAX-ACCESS		read-write
		STATUS			current
		DESCRIPTION
				"TYPE: - Checkbox
				 PAGE: - Common- Setup- Logging- Log Audio_Input_2
					Input2 Audio 3 2_en  cmdID= 4148 "
		::= { iqhco31CmdEntry 4148 }


	iqhco31LoggingLogAudioInput2Input2Audio32 OBJECT-TYPE
		SYNTAX		RollCallString
		MAX-ACCESS		read-only
		STATUS			current
		DESCRIPTION
				"TYPE: - Display
				 PAGE: - Common- Setup- Logging- Log Audio_Input_2
					Input2 Audio 3 2  cmdID= 4149  format=   "
		::= { iqhco31CmdEntry 4149 }


	iqhco31LoggingLogAudioInput2Input2Audio41en OBJECT-TYPE
		SYNTAX		INTEGER { disable(0), enable(1) }
		MAX-ACCESS		read-write
		STATUS			current
		DESCRIPTION
				"TYPE: - Checkbox
				 PAGE: - Common- Setup- Logging- Log Audio_Input_2
					Input2 Audio 4 1_en  cmdID= 4152 "
		::= { iqhco31CmdEntry 4152 }


	iqhco31LoggingLogAudioInput2Input2Audio41 OBJECT-TYPE
		SYNTAX		RollCallString
		MAX-ACCESS		read-only
		STATUS			current
		DESCRIPTION
				"TYPE: - Display
				 PAGE: - Common- Setup- Logging- Log Audio_Input_2
					Input2 Audio 4 1  cmdID= 4153  format=   "
		::= { iqhco31CmdEntry 4153 }


	iqhco31LoggingLogAudioInput2Input2Audio42en OBJECT-TYPE
		SYNTAX		INTEGER { disable(0), enable(1) }
		MAX-ACCESS		read-write
		STATUS			current
		DESCRIPTION
				"TYPE: - Checkbox
				 PAGE: - Common- Setup- Logging- Log Audio_Input_2
					Input2 Audio 4 2_en  cmdID= 4156 "
		::= { iqhco31CmdEntry 4156 }


	iqhco31LoggingLogAudioInput2Input2Audio42 OBJECT-TYPE
		SYNTAX		RollCallString
		MAX-ACCESS		read-only
		STATUS			current
		DESCRIPTION
				"TYPE: - Display
				 PAGE: - Common- Setup- Logging- Log Audio_Input_2
					Input2 Audio 4 2  cmdID= 4157  format=   "
		::= { iqhco31CmdEntry 4157 }


	iqhco31LoggingLogAudioInput2Input2Audio51en OBJECT-TYPE
		SYNTAX		INTEGER { disable(0), enable(1) }
		MAX-ACCESS		read-write
		STATUS			current
		DESCRIPTION
				"TYPE: - Checkbox
				 PAGE: - Common- Setup- Logging- Log Audio_Input_2
					Input2 Audio 5 1_en  cmdID= 4160 "
		::= { iqhco31CmdEntry 4160 }


	iqhco31LoggingLogAudioInput2Input2Audio51 OBJECT-TYPE
		SYNTAX		RollCallString
		MAX-ACCESS		read-only
		STATUS			current
		DESCRIPTION
				"TYPE: - Display
				 PAGE: - Common- Setup- Logging- Log Audio_Input_2
					Input2 Audio 5 1  cmdID= 4161  format=   "
		::= { iqhco31CmdEntry 4161 }


	iqhco31LoggingLogAudioInput2Input2Audio52en OBJECT-TYPE
		SYNTAX		INTEGER { disable(0), enable(1) }
		MAX-ACCESS		read-write
		STATUS			current
		DESCRIPTION
				"TYPE: - Checkbox
				 PAGE: - Common- Setup- Logging- Log Audio_Input_2
					Input2 Audio 5 2_en  cmdID= 4164 "
		::= { iqhco31CmdEntry 4164 }


	iqhco31LoggingLogAudioInput2Input2Audio52 OBJECT-TYPE
		SYNTAX		RollCallString
		MAX-ACCESS		read-only
		STATUS			current
		DESCRIPTION
				"TYPE: - Display
				 PAGE: - Common- Setup- Logging- Log Audio_Input_2
					Input2 Audio 5 2  cmdID= 4165  format=   "
		::= { iqhco31CmdEntry 4165 }


	iqhco31LoggingLogAudioInput2Input2Audio61en OBJECT-TYPE
		SYNTAX		INTEGER { disable(0), enable(1) }
		MAX-ACCESS		read-write
		STATUS			current
		DESCRIPTION
				"TYPE: - Checkbox
				 PAGE: - Common- Setup- Logging- Log Audio_Input_2
					Input2 Audio 6 1_en  cmdID= 4168 "
		::= { iqhco31CmdEntry 4168 }


	iqhco31LoggingLogAudioInput2Input2Audio61 OBJECT-TYPE
		SYNTAX		RollCallString
		MAX-ACCESS		read-only
		STATUS			current
		DESCRIPTION
				"TYPE: - Display
				 PAGE: - Common- Setup- Logging- Log Audio_Input_2
					Input2 Audio 6 1  cmdID= 4169  format=   "
		::= { iqhco31CmdEntry 4169 }


	iqhco31LoggingLogAudioInput2Input2Audio62en OBJECT-TYPE
		SYNTAX		INTEGER { disable(0), enable(1) }
		MAX-ACCESS		read-write
		STATUS			current
		DESCRIPTION
				"TYPE: - Checkbox
				 PAGE: - Common- Setup- Logging- Log Audio_Input_2
					Input2 Audio 6 2_en  cmdID= 4172 "
		::= { iqhco31CmdEntry 4172 }


	iqhco31LoggingLogAudioInput2Input2Audio62 OBJECT-TYPE
		SYNTAX		RollCallString
		MAX-ACCESS		read-only
		STATUS			current
		DESCRIPTION
				"TYPE: - Display
				 PAGE: - Common- Setup- Logging- Log Audio_Input_2
					Input2 Audio 6 2  cmdID= 4173  format=   "
		::= { iqhco31CmdEntry 4173 }


	iqhco31LoggingLogAudioInput2Input2Audio71en OBJECT-TYPE
		SYNTAX		INTEGER { disable(0), enable(1) }
		MAX-ACCESS		read-write
		STATUS			current
		DESCRIPTION
				"TYPE: - Checkbox
				 PAGE: - Common- Setup- Logging- Log Audio_Input_2
					Input2 Audio 7 1_en  cmdID= 4176 "
		::= { iqhco31CmdEntry 4176 }


	iqhco31LoggingLogAudioInput2Input2Audio71 OBJECT-TYPE
		SYNTAX		RollCallString
		MAX-ACCESS		read-only
		STATUS			current
		DESCRIPTION
				"TYPE: - Display
				 PAGE: - Common- Setup- Logging- Log Audio_Input_2
					Input2 Audio 7 1  cmdID= 4177  format=   "
		::= { iqhco31CmdEntry 4177 }


	iqhco31LoggingLogAudioInput2Input2Audio72en OBJECT-TYPE
		SYNTAX		INTEGER { disable(0), enable(1) }
		MAX-ACCESS		read-write
		STATUS			current
		DESCRIPTION
				"TYPE: - Checkbox
				 PAGE: - Common- Setup- Logging- Log Audio_Input_2
					Input2 Audio 7 2_en  cmdID= 4180 "
		::= { iqhco31CmdEntry 4180 }


	iqhco31LoggingLogAudioInput2Input2Audio72 OBJECT-TYPE
		SYNTAX		RollCallString
		MAX-ACCESS		read-only
		STATUS			current
		DESCRIPTION
				"TYPE: - Display
				 PAGE: - Common- Setup- Logging- Log Audio_Input_2
					Input2 Audio 7 2  cmdID= 4181  format=   "
		::= { iqhco31CmdEntry 4181 }


	iqhco31LoggingLogAudioInput2Input2Audio81en OBJECT-TYPE
		SYNTAX		INTEGER { disable(0), enable(1) }
		MAX-ACCESS		read-write
		STATUS			current
		DESCRIPTION
				"TYPE: - Checkbox
				 PAGE: - Common- Setup- Logging- Log Audio_Input_2
					Input2 Audio 8 1_en  cmdID= 4184 "
		::= { iqhco31CmdEntry 4184 }


	iqhco31LoggingLogAudioInput2Input2Audio81 OBJECT-TYPE
		SYNTAX		RollCallString
		MAX-ACCESS		read-only
		STATUS			current
		DESCRIPTION
				"TYPE: - Display
				 PAGE: - Common- Setup- Logging- Log Audio_Input_2
					Input2 Audio 8 1  cmdID= 4185  format=   "
		::= { iqhco31CmdEntry 4185 }


	iqhco31LoggingLogAudioInput2Input2Audio82en OBJECT-TYPE
		SYNTAX		INTEGER { disable(0), enable(1) }
		MAX-ACCESS		read-write
		STATUS			current
		DESCRIPTION
				"TYPE: - Checkbox
				 PAGE: - Common- Setup- Logging- Log Audio_Input_2
					Input2 Audio 8 2_en  cmdID= 4188 "
		::= { iqhco31CmdEntry 4188 }


	iqhco31LoggingLogAudioInput2Input2Audio82 OBJECT-TYPE
		SYNTAX		RollCallString
		MAX-ACCESS		read-only
		STATUS			current
		DESCRIPTION
				"TYPE: - Display
				 PAGE: - Common- Setup- Logging- Log Audio_Input_2
					Input2 Audio 8 2  cmdID= 4189  format=   "
		::= { iqhco31CmdEntry 4189 }


	iqhco31LoggingLogVideoOutputOutput1Typeen OBJECT-TYPE
		SYNTAX		INTEGER { disable(0), enable(1) }
		MAX-ACCESS		read-write
		STATUS			current
		DESCRIPTION
				"TYPE: - Checkbox
				 PAGE: - Common- Setup- Logging- Log Video_Output
					Output1 Type_en  cmdID= 4192 "
		::= { iqhco31CmdEntry 4192 }


	iqhco31LoggingLogVideoOutputOutput1Type OBJECT-TYPE
		SYNTAX		RollCallString
		MAX-ACCESS		read-only
		STATUS			current
		DESCRIPTION
				"TYPE: - Display
				 PAGE: - Common- Setup- Logging- Log Video_Output
					Output1 Type  cmdID= 4193  format=   "
		::= { iqhco31CmdEntry 4193 }


	iqhco31LoggingLogVideoOutputOutput1Stateen OBJECT-TYPE
		SYNTAX		INTEGER { disable(0), enable(1) }
		MAX-ACCESS		read-write
		STATUS			current
		DESCRIPTION
				"TYPE: - Checkbox
				 PAGE: - Common- Setup- Logging- Log Video_Output
					Output1 State_en  cmdID= 4196 "
		::= { iqhco31CmdEntry 4196 }


	iqhco31LoggingLogVideoOutputOutput1State OBJECT-TYPE
		SYNTAX		RollCallString
		MAX-ACCESS		read-only
		STATUS			current
		DESCRIPTION
				"TYPE: - Display
				 PAGE: - Common- Setup- Logging- Log Video_Output
					Output1 State  cmdID= 4197  format=   "
		::= { iqhco31CmdEntry 4197 }


	iqhco31LoggingLogVideoOutputOutput1Stden OBJECT-TYPE
		SYNTAX		INTEGER { disable(0), enable(1) }
		MAX-ACCESS		read-write
		STATUS			current
		DESCRIPTION
				"TYPE: - Checkbox
				 PAGE: - Common- Setup- Logging- Log Video_Output
					Output1 Std_en  cmdID= 4200 "
		::= { iqhco31CmdEntry 4200 }


	iqhco31LoggingLogVideoOutputOutput1Std OBJECT-TYPE
		SYNTAX		RollCallString
		MAX-ACCESS		read-only
		STATUS			current
		DESCRIPTION
				"TYPE: - Display
				 PAGE: - Common- Setup- Logging- Log Video_Output
					Output1 Std  cmdID= 4201  format=   "
		::= { iqhco31CmdEntry 4201 }


	iqhco31LoggingLogVideoOutputOutput1en OBJECT-TYPE
		SYNTAX		INTEGER { disable(0), enable(1) }
		MAX-ACCESS		read-write
		STATUS			current
		DESCRIPTION
				"TYPE: - Checkbox
				 PAGE: - Common- Setup- Logging- Log Video_Output
					Output1_en  cmdID= 4208 "
		::= { iqhco31CmdEntry 4208 }


	iqhco31LoggingLogVideoOutputOutput1 OBJECT-TYPE
		SYNTAX		RollCallString
		MAX-ACCESS		read-only
		STATUS			current
		DESCRIPTION
				"TYPE: - Display
				 PAGE: - Common- Setup- Logging- Log Video_Output
					Output1  cmdID= 4209  format=   "
		::= { iqhco31CmdEntry 4209 }


	iqhco31LoggingLogChangeoverMasterStateen OBJECT-TYPE
		SYNTAX		INTEGER { disable(0), enable(1) }
		MAX-ACCESS		read-write
		STATUS			current
		DESCRIPTION
				"TYPE: - Checkbox
				 PAGE: - Common- Setup- Logging- Log Changeover
					Master State_en  cmdID= 4032 "
		::= { iqhco31CmdEntry 4032 }


	iqhco31LoggingLogChangeoverMasterState OBJECT-TYPE
		SYNTAX		RollCallString
		MAX-ACCESS		read-only
		STATUS			current
		DESCRIPTION
				"TYPE: - Display
				 PAGE: - Common- Setup- Logging- Log Changeover
					Master State  cmdID= 4033  format=   "
		::= { iqhco31CmdEntry 4033 }


	iqhco31LoggingLogChangeoverBackupStateen OBJECT-TYPE
		SYNTAX		INTEGER { disable(0), enable(1) }
		MAX-ACCESS		read-write
		STATUS			current
		DESCRIPTION
				"TYPE: - Checkbox
				 PAGE: - Common- Setup- Logging- Log Changeover
					Backup State_en  cmdID= 4034 "
		::= { iqhco31CmdEntry 4034 }


	iqhco31LoggingLogChangeoverBackupState OBJECT-TYPE
		SYNTAX		RollCallString
		MAX-ACCESS		read-only
		STATUS			current
		DESCRIPTION
				"TYPE: - Display
				 PAGE: - Common- Setup- Logging- Log Changeover
					Backup State  cmdID= 4035  format=   "
		::= { iqhco31CmdEntry 4035 }


	iqhco31LoggingLogChangeoverRulesStateen OBJECT-TYPE
		SYNTAX		INTEGER { disable(0), enable(1) }
		MAX-ACCESS		read-write
		STATUS			current
		DESCRIPTION
				"TYPE: - Checkbox
				 PAGE: - Common- Setup- Logging- Log Changeover
					Rules State_en  cmdID= 4212 "
		::= { iqhco31CmdEntry 4212 }


	iqhco31LoggingLogChangeoverRulesState OBJECT-TYPE
		SYNTAX		RollCallString
		MAX-ACCESS		read-only
		STATUS			current
		DESCRIPTION
				"TYPE: - Display
				 PAGE: - Common- Setup- Logging- Log Changeover
					Rules State  cmdID= 4213  format=   "
		::= { iqhco31CmdEntry 4213 }


	iqhco31LoggingLogChangeoverGpi1Stateen OBJECT-TYPE
		SYNTAX		INTEGER { disable(0), enable(1) }
		MAX-ACCESS		read-write
		STATUS			current
		DESCRIPTION
				"TYPE: - Checkbox
				 PAGE: - Common- Setup- Logging- Log Changeover
					Gpi1 State_en  cmdID= 4404 "
		::= { iqhco31CmdEntry 4404 }


	iqhco31LoggingLogChangeoverGpi1State OBJECT-TYPE
		SYNTAX		RollCallString
		MAX-ACCESS		read-only
		STATUS			current
		DESCRIPTION
				"TYPE: - Display
				 PAGE: - Common- Setup- Logging- Log Changeover
					Gpi1 State  cmdID= 4405  format=   "
		::= { iqhco31CmdEntry 4405 }


	iqhco31LoggingLogChangeoverGpi2Stateen OBJECT-TYPE
		SYNTAX		INTEGER { disable(0), enable(1) }
		MAX-ACCESS		read-write
		STATUS			current
		DESCRIPTION
				"TYPE: - Checkbox
				 PAGE: - Common- Setup- Logging- Log Changeover
					Gpi2 State_en  cmdID= 4408 "
		::= { iqhco31CmdEntry 4408 }


	iqhco31LoggingLogChangeoverGpi2State OBJECT-TYPE
		SYNTAX		RollCallString
		MAX-ACCESS		read-only
		STATUS			current
		DESCRIPTION
				"TYPE: - Display
				 PAGE: - Common- Setup- Logging- Log Changeover
					Gpi2 State  cmdID= 4409  format=   "
		::= { iqhco31CmdEntry 4409 }


	iqhco31LoggingLogChangeoverGpi3Stateen OBJECT-TYPE
		SYNTAX		INTEGER { disable(0), enable(1) }
		MAX-ACCESS		read-write
		STATUS			current
		DESCRIPTION
				"TYPE: - Checkbox
				 PAGE: - Common- Setup- Logging- Log Changeover
					Gpi3 State_en  cmdID= 4412 "
		::= { iqhco31CmdEntry 4412 }


	iqhco31LoggingLogChangeoverGpi3State OBJECT-TYPE
		SYNTAX		RollCallString
		MAX-ACCESS		read-only
		STATUS			current
		DESCRIPTION
				"TYPE: - Display
				 PAGE: - Common- Setup- Logging- Log Changeover
					Gpi3 State  cmdID= 4413  format=   "
		::= { iqhco31CmdEntry 4413 }


	iqhco31LoggingLogChangeoverGpi4Stateen OBJECT-TYPE
		SYNTAX		INTEGER { disable(0), enable(1) }
		MAX-ACCESS		read-write
		STATUS			current
		DESCRIPTION
				"TYPE: - Checkbox
				 PAGE: - Common- Setup- Logging- Log Changeover
					Gpi4 State_en  cmdID= 4416 "
		::= { iqhco31CmdEntry 4416 }


	iqhco31LoggingLogChangeoverGpi4State OBJECT-TYPE
		SYNTAX		RollCallString
		MAX-ACCESS		read-only
		STATUS			current
		DESCRIPTION
				"TYPE: - Display
				 PAGE: - Common- Setup- Logging- Log Changeover
					Gpi4 State  cmdID= 4417  format=   "
		::= { iqhco31CmdEntry 4417 }


	iqhco31LoggingLogChangeoverRollCall101State4420 OBJECT-TYPE
		SYNTAX		INTEGER { disable(0), enable(1) }
		MAX-ACCESS		read-write
		STATUS			current
		DESCRIPTION
				"TYPE: - Checkbox
				 PAGE: - Common- Setup- Logging- Log Changeover
					RollCall 101 State_  cmdID= 4420 "
		::= { iqhco31CmdEntry 4420 }


	iqhco31LoggingLogChangeoverRollCall101State4421 OBJECT-TYPE
		SYNTAX		RollCallString
		MAX-ACCESS		read-only
		STATUS			current
		DESCRIPTION
				"TYPE: - Display
				 PAGE: - Common- Setup- Logging- Log Changeover
					RollCall 101 State  cmdID= 4421  format=   "
		::= { iqhco31CmdEntry 4421 }


	iqhco31LoggingLogChangeoverRollCall102State4424 OBJECT-TYPE
		SYNTAX		INTEGER { disable(0), enable(1) }
		MAX-ACCESS		read-write
		STATUS			current
		DESCRIPTION
				"TYPE: - Checkbox
				 PAGE: - Common- Setup- Logging- Log Changeover
					RollCall 102 State_  cmdID= 4424 "
		::= { iqhco31CmdEntry 4424 }


	iqhco31LoggingLogChangeoverRollCall102State4425 OBJECT-TYPE
		SYNTAX		RollCallString
		MAX-ACCESS		read-only
		STATUS			current
		DESCRIPTION
				"TYPE: - Display
				 PAGE: - Common- Setup- Logging- Log Changeover
					RollCall 102 State  cmdID= 4425  format=   "
		::= { iqhco31CmdEntry 4425 }


	iqhco31LoggingLogChangeoverRollCall103State4428 OBJECT-TYPE
		SYNTAX		INTEGER { disable(0), enable(1) }
		MAX-ACCESS		read-write
		STATUS			current
		DESCRIPTION
				"TYPE: - Checkbox
				 PAGE: - Common- Setup- Logging- Log Changeover
					RollCall 103 State_  cmdID= 4428 "
		::= { iqhco31CmdEntry 4428 }


	iqhco31LoggingLogChangeoverRollCall103State4429 OBJECT-TYPE
		SYNTAX		RollCallString
		MAX-ACCESS		read-only
		STATUS			current
		DESCRIPTION
				"TYPE: - Display
				 PAGE: - Common- Setup- Logging- Log Changeover
					RollCall 103 State  cmdID= 4429  format=   "
		::= { iqhco31CmdEntry 4429 }


	iqhco31LoggingLogChangeoverRollCall104State4432 OBJECT-TYPE
		SYNTAX		INTEGER { disable(0), enable(1) }
		MAX-ACCESS		read-write
		STATUS			current
		DESCRIPTION
				"TYPE: - Checkbox
				 PAGE: - Common- Setup- Logging- Log Changeover
					RollCall 104 State_  cmdID= 4432 "
		::= { iqhco31CmdEntry 4432 }


	iqhco31LoggingLogChangeoverRollCall104State4433 OBJECT-TYPE
		SYNTAX		RollCallString
		MAX-ACCESS		read-only
		STATUS			current
		DESCRIPTION
				"TYPE: - Display
				 PAGE: - Common- Setup- Logging- Log Changeover
					RollCall 104 State  cmdID= 4433  format=   "
		::= { iqhco31CmdEntry 4433 }


	iqhco31LoggingLogChangeoverRollTrkOut1State4436 OBJECT-TYPE
		SYNTAX		INTEGER { disable(0), enable(1) }
		MAX-ACCESS		read-write
		STATUS			current
		DESCRIPTION
				"TYPE: - Checkbox
				 PAGE: - Common- Setup- Logging- Log Changeover
					RollTrk Out1 State_  cmdID= 4436 "
		::= { iqhco31CmdEntry 4436 }


	iqhco31LoggingLogChangeoverRollTrkOut1State4437 OBJECT-TYPE
		SYNTAX		RollCallString
		MAX-ACCESS		read-only
		STATUS			current
		DESCRIPTION
				"TYPE: - Display
				 PAGE: - Common- Setup- Logging- Log Changeover
					RollTrk Out1 State  cmdID= 4437  format=   "
		::= { iqhco31CmdEntry 4437 }


	iqhco31LoggingLogChangeoverRollTrkOut2State4440 OBJECT-TYPE
		SYNTAX		INTEGER { disable(0), enable(1) }
		MAX-ACCESS		read-write
		STATUS			current
		DESCRIPTION
				"TYPE: - Checkbox
				 PAGE: - Common- Setup- Logging- Log Changeover
					RollTrk Out2 State_  cmdID= 4440 "
		::= { iqhco31CmdEntry 4440 }


	iqhco31LoggingLogChangeoverRollTrkOut2State4441 OBJECT-TYPE
		SYNTAX		RollCallString
		MAX-ACCESS		read-only
		STATUS			current
		DESCRIPTION
				"TYPE: - Display
				 PAGE: - Common- Setup- Logging- Log Changeover
					RollTrk Out2 State  cmdID= 4441  format=   "
		::= { iqhco31CmdEntry 4441 }


	iqhco31LoggingLogChangeoverRollTrkOut3State4444 OBJECT-TYPE
		SYNTAX		INTEGER { disable(0), enable(1) }
		MAX-ACCESS		read-write
		STATUS			current
		DESCRIPTION
				"TYPE: - Checkbox
				 PAGE: - Common- Setup- Logging- Log Changeover
					RollTrk Out3 State_  cmdID= 4444 "
		::= { iqhco31CmdEntry 4444 }


	iqhco31LoggingLogChangeoverRollTrkOut3State4445 OBJECT-TYPE
		SYNTAX		RollCallString
		MAX-ACCESS		read-only
		STATUS			current
		DESCRIPTION
				"TYPE: - Display
				 PAGE: - Common- Setup- Logging- Log Changeover
					RollTrk Out3 State  cmdID= 4445  format=   "
		::= { iqhco31CmdEntry 4445 }


	iqhco31LoggingLogChangeoverRollTrkOut4State4448 OBJECT-TYPE
		SYNTAX		INTEGER { disable(0), enable(1) }
		MAX-ACCESS		read-write
		STATUS			current
		DESCRIPTION
				"TYPE: - Checkbox
				 PAGE: - Common- Setup- Logging- Log Changeover
					RollTrk Out4 State_  cmdID= 4448 "
		::= { iqhco31CmdEntry 4448 }


	iqhco31LoggingLogChangeoverRollTrkOut4State4449 OBJECT-TYPE
		SYNTAX		RollCallString
		MAX-ACCESS		read-only
		STATUS			current
		DESCRIPTION
				"TYPE: - Display
				 PAGE: - Common- Setup- Logging- Log Changeover
					RollTrk Out4 State  cmdID= 4449  format=   "
		::= { iqhco31CmdEntry 4449 }


	iqhco31SetupRollTracksRollTrackIndex1495 OBJECT-TYPE
		SYNTAX		INTEGER
		MAX-ACCESS		read-write
		STATUS			current
		DESCRIPTION
				"TYPE: - Number
				 PAGE: - Common- Setup- RollTracks
					RollTrack Index  cmdID= 1495  min= 1  max= 70  step= 1  format= %.0f  div_scale= 1 
					Min = 1  Max = 70  Step = 1 "
		::= { iqhco31CmdEntry 1495 }


	iqhco31SetupRollTracksRollTrackSource1496 OBJECT-TYPE
		SYNTAX		INTEGER
		MAX-ACCESS		read-write
		STATUS			current
		DESCRIPTION
				"TYPE: - Number
				 PAGE: - Common- Setup- RollTracks
					RollTrack Source  cmdID= 1496  min= -1  max= 34  step= 1  format= %.0f  div_scale= 1 
					Min = -1  Max = 34  Step = 1 "
		::= { iqhco31CmdEntry 1496 }


	iqhco31SetupRollTracksRollTrackDisable OBJECT-TYPE
		SYNTAX		INTEGER { disable(0), enable(1) }
		MAX-ACCESS		read-write
		STATUS			current
		DESCRIPTION
				"TYPE: - Checkbox
				 PAGE: - Common- Setup- RollTracks
					RollTrack Disable  cmdID= 1513 "
		::= { iqhco31CmdEntry 1513 }


	iqhco31SetupRollTracksRollTrackAddress1497 OBJECT-TYPE
		SYNTAX		RollCallString
		MAX-ACCESS		read-write
		STATUS			current
		DESCRIPTION
				"TYPE: - Editstring
				 PAGE: - Common- Setup- RollTracks
					RollTrack Address  cmdID= 1497  "
		::= { iqhco31CmdEntry 1497 }


	iqhco31SetupRollTracksRollTrackCommand1498 OBJECT-TYPE
		SYNTAX		RollCallString
		MAX-ACCESS		read-write
		STATUS			current
		DESCRIPTION
				"TYPE: - Editstring
				 PAGE: - Common- Setup- RollTracks
					RollTrack Command  cmdID= 1498  "
		::= { iqhco31CmdEntry 1498 }


	iqhco31SetupRollTracksRollTrackSending OBJECT-TYPE
		SYNTAX		RollCallString
		MAX-ACCESS		read-only
		STATUS			current
		DESCRIPTION
				"TYPE: - Display
				 PAGE: - Common- Setup- RollTracks
					RollTrack Sending  cmdID= 1514  format=   "
		::= { iqhco31CmdEntry 1514 }


	iqhco31SetupRollTracksRollTrackStatus OBJECT-TYPE
		SYNTAX		RollCallString
		MAX-ACCESS		read-only
		STATUS			current
		DESCRIPTION
				"TYPE: - Display
				 PAGE: - Common- Setup- RollTracks
					RollTrack Status  cmdID= 1511  format=   "
		::= { iqhco31CmdEntry 1511 }


	iqhco31SetupRollTracksRollTrackIndex2870 OBJECT-TYPE
		SYNTAX		INTEGER
		MAX-ACCESS		read-write
		STATUS			current
		DESCRIPTION
				"TYPE: - Number
				 PAGE: - Common- Setup- RollTracks
					RollTrack Index  cmdID= 2870  min= 1  max= 70  step= 1  format= %.0f  div_scale= 1 
					Min = 1  Max = 70  Step = 1 "
		::= { iqhco31CmdEntry 2870 }


	iqhco31SetupRollTracksRollTrackSource2871 OBJECT-TYPE
		SYNTAX		INTEGER
		MAX-ACCESS		read-write
		STATUS			current
		DESCRIPTION
				"TYPE: - Number
				 PAGE: - Common- Setup- RollTracks
					RollTrack Source  cmdID= 2871  min= -1  max= 34  step= 1  format= %.0f  div_scale= 1 
					Min = -1  Max = 34  Step = 1 "
		::= { iqhco31CmdEntry 2871 }


	iqhco31SetupRollTracksRollTrackAddress2872 OBJECT-TYPE
		SYNTAX		RollCallString
		MAX-ACCESS		read-write
		STATUS			current
		DESCRIPTION
				"TYPE: - Editstring
				 PAGE: - Common- Setup- RollTracks
					RollTrack Address  cmdID= 2872  "
		::= { iqhco31CmdEntry 2872 }


	iqhco31SetupRollTracksRollTrackCommand2873 OBJECT-TYPE
		SYNTAX		RollCallString
		MAX-ACCESS		read-write
		STATUS			current
		DESCRIPTION
				"TYPE: - Editstring
				 PAGE: - Common- Setup- RollTracks
					RollTrack Command  cmdID= 2873  "
		::= { iqhco31CmdEntry 2873 }


	iqhco31CommonStatusStatusDisplay OBJECT-TYPE
		SYNTAX		INTEGER {
							val-Video-Status(0),
							val-Audio-Input-Status(1),
							val-Rules-Status(2),
							val-Reference-Status(3)
							}
		MAX-ACCESS		read-write
		STATUS			current
		DESCRIPTION
				"TYPE: - RadiobuttonList
				 PAGE: - Common
					Status Display  cmdID= 1915 
					Video Status  value= 0  
					Audio Input Status  value= 1  
					Rules Status  value= 2  
					Reference Status  value= 3  "
		::= { iqhco31CmdEntry 1915 }


	iqhco31CommonStatusProduct OBJECT-TYPE
		SYNTAX		RollCallString
		MAX-ACCESS		read-only
		STATUS			current
		DESCRIPTION
				"TYPE: - Display
				 PAGE: - Common
					Product  cmdID= 5000  format=   "
		::= { iqhco31CmdEntry 5000 }


	iqhco31CommonStatusSoftwareVersion OBJECT-TYPE
		SYNTAX		RollCallString
		MAX-ACCESS		read-only
		STATUS			current
		DESCRIPTION
				"TYPE: - Display
				 PAGE: - Common
					Software Version  cmdID= 2  format=   "
		::= { iqhco31CmdEntry 2 }


	iqhco31CommonStatusSerialNo OBJECT-TYPE
		SYNTAX		RollCallString
		MAX-ACCESS		read-only
		STATUS			current
		DESCRIPTION
				"TYPE: - Display
				 PAGE: - Common
					Serial No  cmdID= 1  format=   "
		::= { iqhco31CmdEntry 1 }


	iqhco31CommonStatusFactoryDefaults OBJECT-TYPE
		SYNTAX		INTEGER { noAction(0),val-Factory-Defaults(1) }
		MAX-ACCESS		read-write
		STATUS			current
		DESCRIPTION
				"TYPE: - Button
				 PAGE: - Common
					Factory Defaults  cmdID= 5020  value= 1  "
		::= { iqhco31CmdEntry 5020 }


	iqhco31CommonStatusDefaultSetting OBJECT-TYPE
		SYNTAX		INTEGER { noAction(0),val-Default-Setting(1) }
		MAX-ACCESS		read-write
		STATUS			current
		DESCRIPTION
				"TYPE: - Button
				 PAGE: - Common
					Default Setting  cmdID= 5021  value= 1  "
		::= { iqhco31CmdEntry 5021 }


	iqhco31CommonStatusRestart OBJECT-TYPE
		SYNTAX		INTEGER { noAction(0),val-Restart(1) }
		MAX-ACCESS		read-write
		STATUS			current
		DESCRIPTION
				"TYPE: - Button
				 PAGE: - Common
					Restart  cmdID= 4  value= 1  "
		::= { iqhco31CmdEntry 4 }


	iqhco31CommonStatusBuild OBJECT-TYPE
		SYNTAX		RollCallString
		MAX-ACCESS		read-only
		STATUS			current
		DESCRIPTION
				"TYPE: - Display
				 PAGE: - Common
					Build  cmdID= 5  format=   "
		::= { iqhco31CmdEntry 5 }


	iqhco31CommonStatusPCB OBJECT-TYPE
		SYNTAX		RollCallString
		MAX-ACCESS		read-only
		STATUS			current
		DESCRIPTION
				"TYPE: - Display
				 PAGE: - Common
					PCB  cmdID= 6  format=   "
		::= { iqhco31CmdEntry 6 }


	iqhco31CommonStatusKOSVersion OBJECT-TYPE
		SYNTAX		RollCallString
		MAX-ACCESS		read-only
		STATUS			current
		DESCRIPTION
				"TYPE: - Display
				 PAGE: - Common
					KOS Version  cmdID= 7  format=   "
		::= { iqhco31CmdEntry 7 }


	iqhco31CommonStatusFirmwareVersion OBJECT-TYPE
		SYNTAX		RollCallString
		MAX-ACCESS		read-only
		STATUS			current
		DESCRIPTION
				"TYPE: - Display
				 PAGE: - Common
					Firmware Version  cmdID= 5001  format=   "
		::= { iqhco31CmdEntry 5001 }


	iqhco31CommonStatusUpTime OBJECT-TYPE
		SYNTAX		RollCallString
		MAX-ACCESS		read-only
		STATUS			current
		DESCRIPTION
				"TYPE: - Display
				 PAGE: - Common
					Up Time  cmdID= 8  format=   "
		::= { iqhco31CmdEntry 8 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S12345678
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:06:00
--				: 
-- Comments		: 
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
-- Vary			: YES
--
-- Value(s)		: 18
--				: 
-- Comments		: 
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
-- Vary			: YES
--
-- Value(s)		: BACKUP
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				: 
-- Comments		: 
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				: 
-- Comments		: 
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
-- Vary			: YES
--
-- Value(s)		: 5
--				: 
-- Comments		: 
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
-- Vary			: YES
--
-- Value(s)		: 2
--				: 
-- Comments		: 
--
---------------------------------------------------------------------------------------------------
-- Header		: GPI_1_STATE
--
-- MIB ref		: swCardEventLogSlotXX       .11.71.80.73.95.49.95.83.84.65.84.69
-- absolute OID	: 1.3.6.1.4.1.7995.2.6.1.1.XX.11.71.80.73.95.49.95.83.84.65.84.69
-- Vary			: YES
--
-- Value(s)		: OK:Unused
--				: 
-- Comments		: 
--
---------------------------------------------------------------------------------------------------
-- Header		: GPI_2_STATE
--
-- MIB ref		: swCardEventLogSlotXX       .11.71.80.73.95.50.95.83.84.65.84.69
-- absolute OID	: 1.3.6.1.4.1.7995.2.6.1.1.XX.11.71.80.73.95.50.95.83.84.65.84.69
-- Vary			: YES
--
-- Value(s)		: OK:Unused
--				: 
-- Comments		: 
--
---------------------------------------------------------------------------------------------------
-- Header		: GPI_3_STATE
--
-- MIB ref		: swCardEventLogSlotXX       .11.71.80.73.95.51.95.83.84.65.84.69
-- absolute OID	: 1.3.6.1.4.1.7995.2.6.1.1.XX.11.71.80.73.95.51.95.83.84.65.84.69
-- Vary			: YES
--
-- Value(s)		: 
--				: 
-- Comments		: 
--
---------------------------------------------------------------------------------------------------
-- Header		: GPI_4_STATE
--
-- MIB ref		: swCardEventLogSlotXX       .11.71.80.73.95.52.95.83.84.65.84.69
-- absolute OID	: 1.3.6.1.4.1.7995.2.6.1.1.XX.11.71.80.73.95.52.95.83.84.65.84.69
-- Vary			: YES
--
-- Value(s)		: 
--				: 
-- Comments		: 
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
-- Vary			: YES
--
-- Value(s)		: OK
--				: 
-- Comments		: 
--
---------------------------------------------------------------------------------------------------
-- Header		: RULES_STATE
--
-- MIB ref		: swCardEventLogSlotXX       .11.82.85.76.69.83.95.83.84.65.84.69
-- absolute OID	: 1.3.6.1.4.1.7995.2.6.1.1.XX.11.82.85.76.69.83.95.83.84.65.84.69
-- Vary			: YES
--
-- Value(s)		: ACTIVE:BACKUP
--				: 
-- Comments		: 
--
---------------------------------------------------------------------------------------------------
-- Header		: BACKUP_STATE
--
-- MIB ref		: swCardEventLogSlotXX       .12.66.65.67.75.85.80.95.83.84.65.84.69
-- absolute OID	: 1.3.6.1.4.1.7995.2.6.1.1.XX.12.66.65.67.75.85.80.95.83.84.65.84.69
-- Vary			: YES
--
-- Value(s)		: FAIL
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 4713.4713.4713
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD/SD/3G SDI
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: HD/SD/3G SDI
--				: 
-- Comments		: 
--
---------------------------------------------------------------------------------------------------
-- Header		: MASTER_STATE
--
-- MIB ref		: swCardEventLogSlotXX       .12.77.65.83.84.69.82.95.83.84.65.84.69
-- absolute OID	: 1.3.6.1.4.1.7995.2.6.1.1.XX.12.77.65.83.84.69.82.95.83.84.65.84.69
-- Vary			: YES
--
-- Value(s)		: FAIL
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2014-11-13T15:05:11Z
--				: 
-- Comments		: 
--
---------------------------------------------------------------------------------------------------
-- Header		: CMD_101_STATE
--
-- MIB ref		: swCardEventLogSlotXX       .13.67.77.68.95.49.48.49.95.83.84.65.84.69
-- absolute OID	: 1.3.6.1.4.1.7995.2.6.1.1.XX.13.67.77.68.95.49.48.49.95.83.84.65.84.69
-- Vary			: YES
--
-- Value(s)		: OK:Unused
--				: 
-- Comments		: 
--
---------------------------------------------------------------------------------------------------
-- Header		: CMD_102_STATE
--
-- MIB ref		: swCardEventLogSlotXX       .13.67.77.68.95.49.48.50.95.83.84.65.84.69
-- absolute OID	: 1.3.6.1.4.1.7995.2.6.1.1.XX.13.67.77.68.95.49.48.50.95.83.84.65.84.69
-- Vary			: YES
--
-- Value(s)		: OK:Unused
--				: 
-- Comments		: 
--
---------------------------------------------------------------------------------------------------
-- Header		: CMD_103_STATE
--
-- MIB ref		: swCardEventLogSlotXX       .13.67.77.68.95.49.48.51.95.83.84.65.84.69
-- absolute OID	: 1.3.6.1.4.1.7995.2.6.1.1.XX.13.67.77.68.95.49.48.51.95.83.84.65.84.69
-- Vary			: YES
--
-- Value(s)		: OK:Unused
--				: 
-- Comments		: 
--
---------------------------------------------------------------------------------------------------
-- Header		: CMD_104_STATE
--
-- MIB ref		: swCardEventLogSlotXX       .13.67.77.68.95.49.48.52.95.83.84.65.84.69
-- absolute OID	: 1.3.6.1.4.1.7995.2.6.1.1.XX.13.67.77.68.95.49.48.52.95.83.84.65.84.69
-- Vary			: YES
--
-- Value(s)		: OK:Unused
--				: 
-- Comments		: 
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: YES
--
-- Value(s)		: SERIAL IN 1
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: 
-- Comments		: 
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
-- Vary			: YES
--
-- Value(s)		: SERIAL IN 2
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: FAIL:Lost
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: 3G / HD / SD SDI
--				: 
-- Comments		: 
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: FAIL:Black
--				: 
-- Comments		: 
--
---------------------------------------------------------------------------------------------------
-- Header		: GENLOCK_1_STATE
--
-- MIB ref		: swCardEventLogSlotXX       .15.71.69.78.76.79.67.75.95.49.95.83.84.65.84.69
-- absolute OID	: 1.3.6.1.4.1.7995.2.6.1.1.XX.15.71.69.78.76.79.67.75.95.49.95.83.84.65.84.69
-- Vary			: YES
--
-- Value(s)		: WARN:Freerun
--				: 
-- Comments		: 
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 4668
--				: 
-- Comments		: 
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: HDBASP2B
--				: 
-- Comments		: 
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: INFO:OK
--				: 
-- Comments		: 
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--				: 
-- Comments		: 
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
-- Vary			: YES
--
-- Value(s)		: INFO:OK
--				: 
-- Comments		: 
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: Unknown
--				: 
-- Comments		: 
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
-- Vary			: YES
--
-- Value(s)		: SDHD;3G
--				: 
-- Comments		: 
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
-- Vary			: YES
--
-- Value(s)		: WARN:Unknown
--				: 
-- Comments		: 
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: 625/25i
--				: 
-- Comments		: 
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
-- Vary			: YES
--
-- Value(s)		: FAIL:Lost
--				: 
-- Comments		: 
--
---------------------------------------------------------------------------------------------------
-- Header		: INPUT_1_BLACK_ERRS
--
-- MIB ref		: swCardEventLogSlotXX       .18.73.78.80.85.84.95.49.95.66.76.65.67.75.95.69.82.82.83
-- absolute OID	: 1.3.6.1.4.1.7995.2.6.1.1.XX.18.73.78.80.85.84.95.49.95.66.76.65.67.75.95.69.82.82.83
-- Vary			: YES
--
-- Value(s)		: OK
--				: 
-- Comments		: 
--
---------------------------------------------------------------------------------------------------
-- Header		: INPUT_2_BLACK_ERRS
--
-- MIB ref		: swCardEventLogSlotXX       .18.73.78.80.85.84.95.50.95.66.76.65.67.75.95.69.82.82.83
-- absolute OID	: 1.3.6.1.4.1.7995.2.6.1.1.XX.18.73.78.80.85.84.95.50.95.66.76.65.67.75.95.69.82.82.83
-- Vary			: YES
--
-- Value(s)		: OK
--				: 
-- Comments		: 
--
---------------------------------------------------------------------------------------------------
-- Header		: RTRACK_1_OUT_STATE
--
-- MIB ref		: swCardEventLogSlotXX       .18.82.84.82.65.67.75.95.49.95.79.85.84.95.83.84.65.84.69
-- absolute OID	: 1.3.6.1.4.1.7995.2.6.1.1.XX.18.82.84.82.65.67.75.95.49.95.79.85.84.95.83.84.65.84.69
-- Vary			: YES
--
-- Value(s)		: FALSE
--				: 
-- Comments		: 
--
---------------------------------------------------------------------------------------------------
-- Header		: RTRACK_2_OUT_STATE
--
-- MIB ref		: swCardEventLogSlotXX       .18.82.84.82.65.67.75.95.50.95.79.85.84.95.83.84.65.84.69
-- absolute OID	: 1.3.6.1.4.1.7995.2.6.1.1.XX.18.82.84.82.65.67.75.95.50.95.79.85.84.95.83.84.65.84.69
-- Vary			: YES
--
-- Value(s)		: FALSE
--				: 
-- Comments		: 
--
---------------------------------------------------------------------------------------------------
-- Header		: RTRACK_3_OUT_STATE
--
-- MIB ref		: swCardEventLogSlotXX       .18.82.84.82.65.67.75.95.51.95.79.85.84.95.83.84.65.84.69
-- absolute OID	: 1.3.6.1.4.1.7995.2.6.1.1.XX.18.82.84.82.65.67.75.95.51.95.79.85.84.95.83.84.65.84.69
-- Vary			: YES
--
-- Value(s)		: FALSE
--				: 
-- Comments		: 
--
---------------------------------------------------------------------------------------------------
-- Header		: RTRACK_4_OUT_STATE
--
-- MIB ref		: swCardEventLogSlotXX       .18.82.84.82.65.67.75.95.52.95.79.85.84.95.83.84.65.84.69
-- absolute OID	: 1.3.6.1.4.1.7995.2.6.1.1.XX.18.82.84.82.65.67.75.95.52.95.79.85.84.95.83.84.65.84.69
-- Vary			: YES
--
-- Value(s)		: FALSE
--				: 
-- Comments		: 
--
---------------------------------------------------------------------------------------------------
-- Header		: INPUT_1_FREEZE_ERRS
--
-- MIB ref		: swCardEventLogSlotXX       .19.73.78.80.85.84.95.49.95.70.82.69.69.90.69.95.69.82.82.83
-- absolute OID	: 1.3.6.1.4.1.7995.2.6.1.1.XX.19.73.78.80.85.84.95.49.95.70.82.69.69.90.69.95.69.82.82.83
-- Vary			: YES
--
-- Value(s)		: OK
--				: 
-- Comments		: 
--
---------------------------------------------------------------------------------------------------
-- Header		: INPUT_2_FREEZE_ERRS
--
-- MIB ref		: swCardEventLogSlotXX       .19.73.78.80.85.84.95.50.95.70.82.69.69.90.69.95.69.82.82.83
-- absolute OID	: 1.3.6.1.4.1.7995.2.6.1.1.XX.19.73.78.80.85.84.95.50.95.70.82.69.69.90.69.95.69.82.82.83
-- Vary			: YES
--
-- Value(s)		: OK
--				: 
-- Comments		: 
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: INFO:OK
--				: 
-- Comments		: 
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
-- Vary			: YES
--
-- Value(s)		: INFO:OK
--				: 
-- Comments		: 
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
-- Vary			: YES
--
-- Value(s)		: Unknown
--				: 
-- Comments		: 
--
---------------------------------------------------------------------------------------------------
-- Header		: INPUT_1_EMBEDDED_AUDIO_1_1_STATE
--
-- MIB ref		: swCardEventLogSlotXX       .32.73.78.80.85.84.95.49.95.69.77.66.69.68.68.69.68.95.65.85.68.73.79.95.49.95.49.95.83.84.65.84.69
-- absolute OID	: 1.3.6.1.4.1.7995.2.6.1.1.XX.32.73.78.80.85.84.95.49.95.69.77.66.69.68.68.69.68.95.65.85.68.73.79.95.49.95.49.95.83.84.65.84.69
-- Vary			: YES
--
-- Value(s)		: FAIL:Input Lost
--				: 
-- Comments		: 
--
---------------------------------------------------------------------------------------------------
-- Header		: INPUT_1_EMBEDDED_AUDIO_1_2_STATE
--
-- MIB ref		: swCardEventLogSlotXX       .32.73.78.80.85.84.95.49.95.69.77.66.69.68.68.69.68.95.65.85.68.73.79.95.49.95.50.95.83.84.65.84.69
-- absolute OID	: 1.3.6.1.4.1.7995.2.6.1.1.XX.32.73.78.80.85.84.95.49.95.69.77.66.69.68.68.69.68.95.65.85.68.73.79.95.49.95.50.95.83.84.65.84.69
-- Vary			: YES
--
-- Value(s)		: FAIL:Input Lost
--				: 
-- Comments		: 
--
---------------------------------------------------------------------------------------------------
-- Header		: INPUT_1_EMBEDDED_AUDIO_2_1_STATE
--
-- MIB ref		: swCardEventLogSlotXX       .32.73.78.80.85.84.95.49.95.69.77.66.69.68.68.69.68.95.65.85.68.73.79.95.50.95.49.95.83.84.65.84.69
-- absolute OID	: 1.3.6.1.4.1.7995.2.6.1.1.XX.32.73.78.80.85.84.95.49.95.69.77.66.69.68.68.69.68.95.65.85.68.73.79.95.50.95.49.95.83.84.65.84.69
-- Vary			: YES
--
-- Value(s)		: FAIL:Input Lost
--				: 
-- Comments		: 
--
---------------------------------------------------------------------------------------------------
-- Header		: INPUT_1_EMBEDDED_AUDIO_2_2_STATE
--
-- MIB ref		: swCardEventLogSlotXX       .32.73.78.80.85.84.95.49.95.69.77.66.69.68.68.69.68.95.65.85.68.73.79.95.50.95.50.95.83.84.65.84.69
-- absolute OID	: 1.3.6.1.4.1.7995.2.6.1.1.XX.32.73.78.80.85.84.95.49.95.69.77.66.69.68.68.69.68.95.65.85.68.73.79.95.50.95.50.95.83.84.65.84.69
-- Vary			: YES
--
-- Value(s)		: FAIL:Input Lost
--				: 
-- Comments		: 
--
---------------------------------------------------------------------------------------------------
-- Header		: INPUT_1_EMBEDDED_AUDIO_3_1_STATE
--
-- MIB ref		: swCardEventLogSlotXX       .32.73.78.80.85.84.95.49.95.69.77.66.69.68.68.69.68.95.65.85.68.73.79.95.51.95.49.95.83.84.65.84.69
-- absolute OID	: 1.3.6.1.4.1.7995.2.6.1.1.XX.32.73.78.80.85.84.95.49.95.69.77.66.69.68.68.69.68.95.65.85.68.73.79.95.51.95.49.95.83.84.65.84.69
-- Vary			: YES
--
-- Value(s)		: FAIL:Input Lost
--				: 
-- Comments		: 
--
---------------------------------------------------------------------------------------------------
-- Header		: INPUT_1_EMBEDDED_AUDIO_3_2_STATE
--
-- MIB ref		: swCardEventLogSlotXX       .32.73.78.80.85.84.95.49.95.69.77.66.69.68.68.69.68.95.65.85.68.73.79.95.51.95.50.95.83.84.65.84.69
-- absolute OID	: 1.3.6.1.4.1.7995.2.6.1.1.XX.32.73.78.80.85.84.95.49.95.69.77.66.69.68.68.69.68.95.65.85.68.73.79.95.51.95.50.95.83.84.65.84.69
-- Vary			: YES
--
-- Value(s)		: FAIL:Input Lost
--				: 
-- Comments		: 
--
---------------------------------------------------------------------------------------------------
-- Header		: INPUT_1_EMBEDDED_AUDIO_4_1_STATE
--
-- MIB ref		: swCardEventLogSlotXX       .32.73.78.80.85.84.95.49.95.69.77.66.69.68.68.69.68.95.65.85.68.73.79.95.52.95.49.95.83.84.65.84.69
-- absolute OID	: 1.3.6.1.4.1.7995.2.6.1.1.XX.32.73.78.80.85.84.95.49.95.69.77.66.69.68.68.69.68.95.65.85.68.73.79.95.52.95.49.95.83.84.65.84.69
-- Vary			: YES
--
-- Value(s)		: FAIL:Input Lost
--				: 
-- Comments		: 
--
---------------------------------------------------------------------------------------------------
-- Header		: INPUT_1_EMBEDDED_AUDIO_4_2_STATE
--
-- MIB ref		: swCardEventLogSlotXX       .32.73.78.80.85.84.95.49.95.69.77.66.69.68.68.69.68.95.65.85.68.73.79.95.52.95.50.95.83.84.65.84.69
-- absolute OID	: 1.3.6.1.4.1.7995.2.6.1.1.XX.32.73.78.80.85.84.95.49.95.69.77.66.69.68.68.69.68.95.65.85.68.73.79.95.52.95.50.95.83.84.65.84.69
-- Vary			: YES
--
-- Value(s)		: FAIL:Input Lost
--				: 
-- Comments		: 
--
---------------------------------------------------------------------------------------------------
-- Header		: INPUT_1_EMBEDDED_AUDIO_5_1_STATE
--
-- MIB ref		: swCardEventLogSlotXX       .32.73.78.80.85.84.95.49.95.69.77.66.69.68.68.69.68.95.65.85.68.73.79.95.53.95.49.95.83.84.65.84.69
-- absolute OID	: 1.3.6.1.4.1.7995.2.6.1.1.XX.32.73.78.80.85.84.95.49.95.69.77.66.69.68.68.69.68.95.65.85.68.73.79.95.53.95.49.95.83.84.65.84.69
-- Vary			: YES
--
-- Value(s)		: FAIL:Input Lost
--				: 
-- Comments		: 
--
---------------------------------------------------------------------------------------------------
-- Header		: INPUT_1_EMBEDDED_AUDIO_5_2_STATE
--
-- MIB ref		: swCardEventLogSlotXX       .32.73.78.80.85.84.95.49.95.69.77.66.69.68.68.69.68.95.65.85.68.73.79.95.53.95.50.95.83.84.65.84.69
-- absolute OID	: 1.3.6.1.4.1.7995.2.6.1.1.XX.32.73.78.80.85.84.95.49.95.69.77.66.69.68.68.69.68.95.65.85.68.73.79.95.53.95.50.95.83.84.65.84.69
-- Vary			: YES
--
-- Value(s)		: FAIL:Input Lost
--				: 
-- Comments		: 
--
---------------------------------------------------------------------------------------------------
-- Header		: INPUT_1_EMBEDDED_AUDIO_6_1_STATE
--
-- MIB ref		: swCardEventLogSlotXX       .32.73.78.80.85.84.95.49.95.69.77.66.69.68.68.69.68.95.65.85.68.73.79.95.54.95.49.95.83.84.65.84.69
-- absolute OID	: 1.3.6.1.4.1.7995.2.6.1.1.XX.32.73.78.80.85.84.95.49.95.69.77.66.69.68.68.69.68.95.65.85.68.73.79.95.54.95.49.95.83.84.65.84.69
-- Vary			: YES
--
-- Value(s)		: FAIL:Input Lost
--				: 
-- Comments		: 
--
---------------------------------------------------------------------------------------------------
-- Header		: INPUT_1_EMBEDDED_AUDIO_6_2_STATE
--
-- MIB ref		: swCardEventLogSlotXX       .32.73.78.80.85.84.95.49.95.69.77.66.69.68.68.69.68.95.65.85.68.73.79.95.54.95.50.95.83.84.65.84.69
-- absolute OID	: 1.3.6.1.4.1.7995.2.6.1.1.XX.32.73.78.80.85.84.95.49.95.69.77.66.69.68.68.69.68.95.65.85.68.73.79.95.54.95.50.95.83.84.65.84.69
-- Vary			: YES
--
-- Value(s)		: FAIL:Input Lost
--				: 
-- Comments		: 
--
---------------------------------------------------------------------------------------------------
-- Header		: INPUT_1_EMBEDDED_AUDIO_7_1_STATE
--
-- MIB ref		: swCardEventLogSlotXX       .32.73.78.80.85.84.95.49.95.69.77.66.69.68.68.69.68.95.65.85.68.73.79.95.55.95.49.95.83.84.65.84.69
-- absolute OID	: 1.3.6.1.4.1.7995.2.6.1.1.XX.32.73.78.80.85.84.95.49.95.69.77.66.69.68.68.69.68.95.65.85.68.73.79.95.55.95.49.95.83.84.65.84.69
-- Vary			: YES
--
-- Value(s)		: FAIL:Input Lost
--				: 
-- Comments		: 
--
---------------------------------------------------------------------------------------------------
-- Header		: INPUT_1_EMBEDDED_AUDIO_7_2_STATE
--
-- MIB ref		: swCardEventLogSlotXX       .32.73.78.80.85.84.95.49.95.69.77.66.69.68.68.69.68.95.65.85.68.73.79.95.55.95.50.95.83.84.65.84.69
-- absolute OID	: 1.3.6.1.4.1.7995.2.6.1.1.XX.32.73.78.80.85.84.95.49.95.69.77.66.69.68.68.69.68.95.65.85.68.73.79.95.55.95.50.95.83.84.65.84.69
-- Vary			: YES
--
-- Value(s)		: FAIL:Input Lost
--				: 
-- Comments		: 
--
---------------------------------------------------------------------------------------------------
-- Header		: INPUT_1_EMBEDDED_AUDIO_8_1_STATE
--
-- MIB ref		: swCardEventLogSlotXX       .32.73.78.80.85.84.95.49.95.69.77.66.69.68.68.69.68.95.65.85.68.73.79.95.56.95.49.95.83.84.65.84.69
-- absolute OID	: 1.3.6.1.4.1.7995.2.6.1.1.XX.32.73.78.80.85.84.95.49.95.69.77.66.69.68.68.69.68.95.65.85.68.73.79.95.56.95.49.95.83.84.65.84.69
-- Vary			: YES
--
-- Value(s)		: FAIL:Input Lost
--				: 
-- Comments		: 
--
---------------------------------------------------------------------------------------------------
-- Header		: INPUT_1_EMBEDDED_AUDIO_8_2_STATE
--
-- MIB ref		: swCardEventLogSlotXX       .32.73.78.80.85.84.95.49.95.69.77.66.69.68.68.69.68.95.65.85.68.73.79.95.56.95.50.95.83.84.65.84.69
-- absolute OID	: 1.3.6.1.4.1.7995.2.6.1.1.XX.32.73.78.80.85.84.95.49.95.69.77.66.69.68.68.69.68.95.65.85.68.73.79.95.56.95.50.95.83.84.65.84.69
-- Vary			: YES
--
-- Value(s)		: FAIL:Input Lost
--				: 
-- Comments		: 
--
---------------------------------------------------------------------------------------------------
-- Header		: INPUT_2_EMBEDDED_AUDIO_1_1_STATE
--
-- MIB ref		: swCardEventLogSlotXX       .32.73.78.80.85.84.95.50.95.69.77.66.69.68.68.69.68.95.65.85.68.73.79.95.49.95.49.95.83.84.65.84.69
-- absolute OID	: 1.3.6.1.4.1.7995.2.6.1.1.XX.32.73.78.80.85.84.95.50.95.69.77.66.69.68.68.69.68.95.65.85.68.73.79.95.49.95.49.95.83.84.65.84.69
-- Vary			: YES
--
-- Value(s)		: FAIL:Input Lost
--				: 
-- Comments		: 
--
---------------------------------------------------------------------------------------------------
-- Header		: INPUT_2_EMBEDDED_AUDIO_1_2_STATE
--
-- MIB ref		: swCardEventLogSlotXX       .32.73.78.80.85.84.95.50.95.69.77.66.69.68.68.69.68.95.65.85.68.73.79.95.49.95.50.95.83.84.65.84.69
-- absolute OID	: 1.3.6.1.4.1.7995.2.6.1.1.XX.32.73.78.80.85.84.95.50.95.69.77.66.69.68.68.69.68.95.65.85.68.73.79.95.49.95.50.95.83.84.65.84.69
-- Vary			: YES
--
-- Value(s)		: FAIL:Input Lost
--				: 
-- Comments		: 
--
---------------------------------------------------------------------------------------------------
-- Header		: INPUT_2_EMBEDDED_AUDIO_2_1_STATE
--
-- MIB ref		: swCardEventLogSlotXX       .32.73.78.80.85.84.95.50.95.69.77.66.69.68.68.69.68.95.65.85.68.73.79.95.50.95.49.95.83.84.65.84.69
-- absolute OID	: 1.3.6.1.4.1.7995.2.6.1.1.XX.32.73.78.80.85.84.95.50.95.69.77.66.69.68.68.69.68.95.65.85.68.73.79.95.50.95.49.95.83.84.65.84.69
-- Vary			: YES
--
-- Value(s)		: FAIL:Input Lost
--				: 
-- Comments		: 
--
---------------------------------------------------------------------------------------------------
-- Header		: INPUT_2_EMBEDDED_AUDIO_2_2_STATE
--
-- MIB ref		: swCardEventLogSlotXX       .32.73.78.80.85.84.95.50.95.69.77.66.69.68.68.69.68.95.65.85.68.73.79.95.50.95.50.95.83.84.65.84.69
-- absolute OID	: 1.3.6.1.4.1.7995.2.6.1.1.XX.32.73.78.80.85.84.95.50.95.69.77.66.69.68.68.69.68.95.65.85.68.73.79.95.50.95.50.95.83.84.65.84.69
-- Vary			: YES
--
-- Value(s)		: FAIL:Input Lost
--				: 
-- Comments		: 
--
---------------------------------------------------------------------------------------------------
-- Header		: INPUT_2_EMBEDDED_AUDIO_3_1_STATE
--
-- MIB ref		: swCardEventLogSlotXX       .32.73.78.80.85.84.95.50.95.69.77.66.69.68.68.69.68.95.65.85.68.73.79.95.51.95.49.95.83.84.65.84.69
-- absolute OID	: 1.3.6.1.4.1.7995.2.6.1.1.XX.32.73.78.80.85.84.95.50.95.69.77.66.69.68.68.69.68.95.65.85.68.73.79.95.51.95.49.95.83.84.65.84.69
-- Vary			: YES
--
-- Value(s)		: FAIL:Input Lost
--				: 
-- Comments		: 
--
---------------------------------------------------------------------------------------------------
-- Header		: INPUT_2_EMBEDDED_AUDIO_3_2_STATE
--
-- MIB ref		: swCardEventLogSlotXX       .32.73.78.80.85.84.95.50.95.69.77.66.69.68.68.69.68.95.65.85.68.73.79.95.51.95.50.95.83.84.65.84.69
-- absolute OID	: 1.3.6.1.4.1.7995.2.6.1.1.XX.32.73.78.80.85.84.95.50.95.69.77.66.69.68.68.69.68.95.65.85.68.73.79.95.51.95.50.95.83.84.65.84.69
-- Vary			: YES
--
-- Value(s)		: FAIL:Input Lost
--				: 
-- Comments		: 
--
---------------------------------------------------------------------------------------------------
-- Header		: INPUT_2_EMBEDDED_AUDIO_4_1_STATE
--
-- MIB ref		: swCardEventLogSlotXX       .32.73.78.80.85.84.95.50.95.69.77.66.69.68.68.69.68.95.65.85.68.73.79.95.52.95.49.95.83.84.65.84.69
-- absolute OID	: 1.3.6.1.4.1.7995.2.6.1.1.XX.32.73.78.80.85.84.95.50.95.69.77.66.69.68.68.69.68.95.65.85.68.73.79.95.52.95.49.95.83.84.65.84.69
-- Vary			: YES
--
-- Value(s)		: FAIL:Input Lost
--				: 
-- Comments		: 
--
---------------------------------------------------------------------------------------------------
-- Header		: INPUT_2_EMBEDDED_AUDIO_4_2_STATE
--
-- MIB ref		: swCardEventLogSlotXX       .32.73.78.80.85.84.95.50.95.69.77.66.69.68.68.69.68.95.65.85.68.73.79.95.52.95.50.95.83.84.65.84.69
-- absolute OID	: 1.3.6.1.4.1.7995.2.6.1.1.XX.32.73.78.80.85.84.95.50.95.69.77.66.69.68.68.69.68.95.65.85.68.73.79.95.52.95.50.95.83.84.65.84.69
-- Vary			: YES
--
-- Value(s)		: FAIL:Input Lost
--				: 
-- Comments		: 
--
---------------------------------------------------------------------------------------------------
-- Header		: INPUT_2_EMBEDDED_AUDIO_5_1_STATE
--
-- MIB ref		: swCardEventLogSlotXX       .32.73.78.80.85.84.95.50.95.69.77.66.69.68.68.69.68.95.65.85.68.73.79.95.53.95.49.95.83.84.65.84.69
-- absolute OID	: 1.3.6.1.4.1.7995.2.6.1.1.XX.32.73.78.80.85.84.95.50.95.69.77.66.69.68.68.69.68.95.65.85.68.73.79.95.53.95.49.95.83.84.65.84.69
-- Vary			: YES
--
-- Value(s)		: FAIL:Input Lost
--				: 
-- Comments		: 
--
---------------------------------------------------------------------------------------------------
-- Header		: INPUT_2_EMBEDDED_AUDIO_5_2_STATE
--
-- MIB ref		: swCardEventLogSlotXX       .32.73.78.80.85.84.95.50.95.69.77.66.69.68.68.69.68.95.65.85.68.73.79.95.53.95.50.95.83.84.65.84.69
-- absolute OID	: 1.3.6.1.4.1.7995.2.6.1.1.XX.32.73.78.80.85.84.95.50.95.69.77.66.69.68.68.69.68.95.65.85.68.73.79.95.53.95.50.95.83.84.65.84.69
-- Vary			: YES
--
-- Value(s)		: FAIL:Input Lost
--				: 
-- Comments		: 
--
---------------------------------------------------------------------------------------------------
-- Header		: INPUT_2_EMBEDDED_AUDIO_6_1_STATE
--
-- MIB ref		: swCardEventLogSlotXX       .32.73.78.80.85.84.95.50.95.69.77.66.69.68.68.69.68.95.65.85.68.73.79.95.54.95.49.95.83.84.65.84.69
-- absolute OID	: 1.3.6.1.4.1.7995.2.6.1.1.XX.32.73.78.80.85.84.95.50.95.69.77.66.69.68.68.69.68.95.65.85.68.73.79.95.54.95.49.95.83.84.65.84.69
-- Vary			: YES
--
-- Value(s)		: FAIL:Input Lost
--				: 
-- Comments		: 
--
---------------------------------------------------------------------------------------------------
-- Header		: INPUT_2_EMBEDDED_AUDIO_6_2_STATE
--
-- MIB ref		: swCardEventLogSlotXX       .32.73.78.80.85.84.95.50.95.69.77.66.69.68.68.69.68.95.65.85.68.73.79.95.54.95.50.95.83.84.65.84.69
-- absolute OID	: 1.3.6.1.4.1.7995.2.6.1.1.XX.32.73.78.80.85.84.95.50.95.69.77.66.69.68.68.69.68.95.65.85.68.73.79.95.54.95.50.95.83.84.65.84.69
-- Vary			: YES
--
-- Value(s)		: FAIL:Input Lost
--				: 
-- Comments		: 
--
---------------------------------------------------------------------------------------------------
-- Header		: INPUT_2_EMBEDDED_AUDIO_7_1_STATE
--
-- MIB ref		: swCardEventLogSlotXX       .32.73.78.80.85.84.95.50.95.69.77.66.69.68.68.69.68.95.65.85.68.73.79.95.55.95.49.95.83.84.65.84.69
-- absolute OID	: 1.3.6.1.4.1.7995.2.6.1.1.XX.32.73.78.80.85.84.95.50.95.69.77.66.69.68.68.69.68.95.65.85.68.73.79.95.55.95.49.95.83.84.65.84.69
-- Vary			: YES
--
-- Value(s)		: FAIL:Input Lost
--				: 
-- Comments		: 
--
---------------------------------------------------------------------------------------------------
-- Header		: INPUT_2_EMBEDDED_AUDIO_7_2_STATE
--
-- MIB ref		: swCardEventLogSlotXX       .32.73.78.80.85.84.95.50.95.69.77.66.69.68.68.69.68.95.65.85.68.73.79.95.55.95.50.95.83.84.65.84.69
-- absolute OID	: 1.3.6.1.4.1.7995.2.6.1.1.XX.32.73.78.80.85.84.95.50.95.69.77.66.69.68.68.69.68.95.65.85.68.73.79.95.55.95.50.95.83.84.65.84.69
-- Vary			: YES
--
-- Value(s)		: FAIL:Input Lost
--				: 
-- Comments		: 
--
---------------------------------------------------------------------------------------------------
-- Header		: INPUT_2_EMBEDDED_AUDIO_8_1_STATE
--
-- MIB ref		: swCardEventLogSlotXX       .32.73.78.80.85.84.95.50.95.69.77.66.69.68.68.69.68.95.65.85.68.73.79.95.56.95.49.95.83.84.65.84.69
-- absolute OID	: 1.3.6.1.4.1.7995.2.6.1.1.XX.32.73.78.80.85.84.95.50.95.69.77.66.69.68.68.69.68.95.65.85.68.73.79.95.56.95.49.95.83.84.65.84.69
-- Vary			: YES
--
-- Value(s)		: FAIL:Input Lost
--				: 
-- Comments		: 
--
---------------------------------------------------------------------------------------------------
-- Header		: INPUT_2_EMBEDDED_AUDIO_8_2_STATE
--
-- MIB ref		: swCardEventLogSlotXX       .32.73.78.80.85.84.95.50.95.69.77.66.69.68.68.69.68.95.65.85.68.73.79.95.56.95.50.95.83.84.65.84.69
-- absolute OID	: 1.3.6.1.4.1.7995.2.6.1.1.XX.32.73.78.80.85.84.95.50.95.69.77.66.69.68.68.69.68.95.65.85.68.73.79.95.56.95.50.95.83.84.65.84.69
-- Vary			: YES
--
-- Value(s)		: FAIL:Input Lost
--				: 
-- Comments		: 
--
---------------------------------------------------------------------------------------------------
