-- ************************************************************************************
--        Snell Card:IQDMX30
--        Module Id#:531
--       Command Set:17
--          Filename:SNELL-IQDMX30-CMD-MIB.mib
--            Author:n tye
--              Date:02/06/2015
--              Time:15:54
--
-- Copyright (c) 2010 Snell Ltd
-- All rights reserved.
--
-- ************************************************************************************

SNELL-IQDMX30-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDMX30,
    moduleIQDMX30MIB
        FROM SNELL-WILCOX-PRODUCT-REG;

 moduleIQDMX30CmdMi MODULE-IDENTITY
    LAST-UPDATED "1506021554Z"
    ORGANIZATION "Snell Ltd"
    CONTACT-INFO
        "Primary Author:n tye

         postal:    Southleigh Park House
                    Eastleigh Road
                    Havant, Hants
                    PO9 2PE
         phone:     +44 (0)23 92489000
         email:     snmp.support@snellgroup.com"
    DESCRIPTION
        "This file defines the Snell card, command set  translations."
    ::= { moduleIQDMX30MIB 1 }




--********************************************************************************
--*
--*  Snell Card:
--*  command set:
--*  list commands/menus:
--*
--******************************************************************************
	iqdmx30CmdTable OBJECT-TYPE
		SYNTAX			SEQUENCE OF Iqdmx30CmdEntry
		MAX-ACCESS		not-accessible
		STATUS			current
		DESCRIPTION
				"Note the instance of this table is relected in the command set Version"
		::= { moduleIQDMX30 1 }

	iqdmx30CmdEntry OBJECT-TYPE
		SYNTAX		Iqdmx30CmdEntry
		MAX-ACCESS		not-accessible
		STATUS			current
		DESCRIPTION
				"Entry in command table."
		INDEX	{ iqdmx30SlotIndex }
		::= { iqdmx30CmdTable 1 }

	Iqdmx30CmdEntry ::=
		SEQUENCE {
			iqdmx30SlotIndex
				Unsigned32,
			iqdmx30VideoVideoInputSelect
				INTEGER,
			iqdmx30VideoValidInputFormats62525i
				INTEGER,
			iqdmx30VideoValidInputFormats52529i
				INTEGER,
			iqdmx30VideoValidInputFormats72050p
				INTEGER,
			iqdmx30VideoValidInputFormats72059p
				INTEGER,
			iqdmx30VideoValidInputFormats108025i
				INTEGER,
			iqdmx30VideoValidInputFormats108029i
				INTEGER,
			iqdmx30VideoValidInputFormats108050pA
				INTEGER,
			iqdmx30VideoValidInputFormats108059pA
				INTEGER,
			iqdmx30VideoValidInputFormats108050pB
				INTEGER,
			iqdmx30VideoValidInputFormats108059pB
				INTEGER,
			iqdmx30VideoDefaultFormat
				INTEGER,
			iqdmx30VideoDefaultOutput
				INTEGER,
			iqdmx30VideoVideoProcampProcAmpEnable
				INTEGER,
			iqdmx30VideoVideoProcampBlackLevel
				INTEGER,
			iqdmx30VideoVideoProcampHueAdjust
				INTEGER,
			iqdmx30VideoVideoProcampMasterVideoGain
				INTEGER,
			iqdmx30VideoVideoProcampYGain
				INTEGER,
			iqdmx30VideoVideoProcampCbCrGain
				INTEGER,
			iqdmx30VideoVideoProcampYCTiming
				INTEGER,
			iqdmx30VideoVideoProcampPictureposition
				INTEGER,
			iqdmx30VideoVideoProcampModalIndex
				INTEGER,
			iqdmx30VideoVideoProcampYCTimingnm
				INTEGER,
			iqdmx30VideoVideoProcampPicturepositionnm
				INTEGER,
			iqdmx30VideoBlankingBlankVANC
				INTEGER,
			iqdmx30Blanking625BlankLinesLine23
				INTEGER,
			iqdmx30Blanking625BlankLinesLine336
				INTEGER,
			iqdmx30Blanking525BlankLinesLine21
				INTEGER,
			iqdmx30Blanking525BlankLinesLine22
				INTEGER,
			iqdmx30Blanking525BlankLinesLine283
				INTEGER,
			iqdmx30Blanking525BlankLinesLine284
				INTEGER,
			iqdmx30VideoBlankingBlankHANC
				INTEGER,
			iqdmx30VideoCaption
				INTEGER,
			iqdmx30VideoCaptionEditCaption
				RollCallString,
			iqdmx30VideoPattern
				INTEGER,
			iqdmx30VideoFreeze
				INTEGER,
			iqdmx30VideoFreezeManualFreeze
				INTEGER,
			iqdmx30AudioAudioInputSelect
				INTEGER,
			iqdmx30EmbeddersEmbedder1Enable
				INTEGER,
			iqdmx30EmbeddersEmbedder1SourceLNonPCM5034
				INTEGER,
			iqdmx30EmbeddersEmbedder1SourceR5035
				INTEGER,
			iqdmx30EmbeddersEmbedder1Mute3240
				INTEGER,
			iqdmx30EmbeddersEmbedder1MuteonVbit3272
				INTEGER,
			iqdmx30EmbeddersEmbedder1InvertL3160
				INTEGER,
			iqdmx30EmbeddersEmbedder1InvertR3161
				INTEGER,
			iqdmx30EmbeddersEmbedder1GainL3080
				INTEGER,
			iqdmx30EmbeddersEmbedder1GainR3081
				INTEGER,
			iqdmx30EmbeddersEmbedder1PairMode3930
				INTEGER,
			iqdmx30EmbeddersEmbedder1SourceLNonPCM5036
				INTEGER,
			iqdmx30EmbeddersEmbedder1SourceR5037
				INTEGER,
			iqdmx30EmbeddersEmbedder1Mute3241
				INTEGER,
			iqdmx30EmbeddersEmbedder1MuteonVbit3273
				INTEGER,
			iqdmx30EmbeddersEmbedder1InvertL3162
				INTEGER,
			iqdmx30EmbeddersEmbedder1InvertR3163
				INTEGER,
			iqdmx30EmbeddersEmbedder1GainL3082
				INTEGER,
			iqdmx30EmbeddersEmbedder1GainR3083
				INTEGER,
			iqdmx30EmbeddersEmbedder1PairMode3931
				INTEGER,
			iqdmx30EmbeddersEmbedder1NonModalIndex5338
				INTEGER,
			iqdmx30EmbeddersEmbedder1NonModalGain5339
				INTEGER,
			iqdmx30EmbeddersEmbedder1NonModalIndex5340
				INTEGER,
			iqdmx30EmbeddersEmbedder1NonModalGain5341
				INTEGER,
			iqdmx30EmbeddersEmbedder2Enable
				INTEGER,
			iqdmx30EmbeddersEmbedder2SourceLNonPCM5038
				INTEGER,
			iqdmx30EmbeddersEmbedder2SourceR5039
				INTEGER,
			iqdmx30EmbeddersEmbedder2Mute3242
				INTEGER,
			iqdmx30EmbeddersEmbedder2MuteonVbit3274
				INTEGER,
			iqdmx30EmbeddersEmbedder2InvertL3164
				INTEGER,
			iqdmx30EmbeddersEmbedder2InvertR3165
				INTEGER,
			iqdmx30EmbeddersEmbedder2GainL3084
				INTEGER,
			iqdmx30EmbeddersEmbedder2GainR3085
				INTEGER,
			iqdmx30EmbeddersEmbedder2PairMode3932
				INTEGER,
			iqdmx30EmbeddersEmbedder2SourceLNonPCM5040
				INTEGER,
			iqdmx30EmbeddersEmbedder2SourceR5041
				INTEGER,
			iqdmx30EmbeddersEmbedder2Mute3243
				INTEGER,
			iqdmx30EmbeddersEmbedder2MuteonVbit3275
				INTEGER,
			iqdmx30EmbeddersEmbedder2InvertL3166
				INTEGER,
			iqdmx30EmbeddersEmbedder2InvertR3167
				INTEGER,
			iqdmx30EmbeddersEmbedder2GainL3086
				INTEGER,
			iqdmx30EmbeddersEmbedder2GainR3087
				INTEGER,
			iqdmx30EmbeddersEmbedder2PairMode3933
				INTEGER,
			iqdmx30EmbeddersEmbedder3Enable
				INTEGER,
			iqdmx30EmbeddersEmbedder3SourceLNonPCM5042
				INTEGER,
			iqdmx30EmbeddersEmbedder3SourceR5043
				INTEGER,
			iqdmx30EmbeddersEmbedder3Mute3244
				INTEGER,
			iqdmx30EmbeddersEmbedder3MuteonVbit3276
				INTEGER,
			iqdmx30EmbeddersEmbedder3InvertL3168
				INTEGER,
			iqdmx30EmbeddersEmbedder3InvertR3169
				INTEGER,
			iqdmx30EmbeddersEmbedder3GainL3088
				INTEGER,
			iqdmx30EmbeddersEmbedder3GainR3089
				INTEGER,
			iqdmx30EmbeddersEmbedder3PairMode3934
				INTEGER,
			iqdmx30EmbeddersEmbedder3SourceLNonPCM5044
				INTEGER,
			iqdmx30EmbeddersEmbedder3SourceR5045
				INTEGER,
			iqdmx30EmbeddersEmbedder3Mute3245
				INTEGER,
			iqdmx30EmbeddersEmbedder3MuteonVbit3277
				INTEGER,
			iqdmx30EmbeddersEmbedder3InvertL3170
				INTEGER,
			iqdmx30EmbeddersEmbedder3InvertR3171
				INTEGER,
			iqdmx30EmbeddersEmbedder3GainL3090
				INTEGER,
			iqdmx30EmbeddersEmbedder3GainR3091
				INTEGER,
			iqdmx30EmbeddersEmbedder3PairMode3935
				INTEGER,
			iqdmx30EmbeddersEmbedder4Enable
				INTEGER,
			iqdmx30EmbeddersEmbedder4SourceLNonPCM5046
				INTEGER,
			iqdmx30EmbeddersEmbedder4SourceR5047
				INTEGER,
			iqdmx30EmbeddersEmbedder4Mute3246
				INTEGER,
			iqdmx30EmbeddersEmbedder4MuteonVbit3278
				INTEGER,
			iqdmx30EmbeddersEmbedder4InvertL3172
				INTEGER,
			iqdmx30EmbeddersEmbedder4InvertR3173
				INTEGER,
			iqdmx30EmbeddersEmbedder4GainL3092
				INTEGER,
			iqdmx30EmbeddersEmbedder4GainR3093
				INTEGER,
			iqdmx30EmbeddersEmbedder4PairMode3936
				INTEGER,
			iqdmx30EmbeddersEmbedder4SourceLNonPCM5048
				INTEGER,
			iqdmx30EmbeddersEmbedder4SourceR5049
				INTEGER,
			iqdmx30EmbeddersEmbedder4Mute3247
				INTEGER,
			iqdmx30EmbeddersEmbedder4MuteonVbit3279
				INTEGER,
			iqdmx30EmbeddersEmbedder4InvertL3174
				INTEGER,
			iqdmx30EmbeddersEmbedder4InvertR3175
				INTEGER,
			iqdmx30EmbeddersEmbedder4GainL3094
				INTEGER,
			iqdmx30EmbeddersEmbedder4GainR3095
				INTEGER,
			iqdmx30EmbeddersEmbedder4PairMode3937
				INTEGER,
			iqdmx30AESOutAESOut1SourceLNonPCM
				INTEGER,
			iqdmx30AESOutAESOut1SourceR
				INTEGER,
			iqdmx30AESOutAESOut1Mute
				INTEGER,
			iqdmx30AESOutAESOut1MuteonVbit
				INTEGER,
			iqdmx30AESOutAESOut1InvertL
				INTEGER,
			iqdmx30AESOutAESOut1InvertR
				INTEGER,
			iqdmx30AESOutAESOut1GainL
				INTEGER,
			iqdmx30AESOutAESOut1GainR
				INTEGER,
			iqdmx30AESOutAESOut1PairMode
				INTEGER,
			iqdmx30AESOutAESOut2SourceLNonPCM
				INTEGER,
			iqdmx30AESOutAESOut2SourceR
				INTEGER,
			iqdmx30AESOutAESOut2Mute
				INTEGER,
			iqdmx30AESOutAESOut2MuteonVbit
				INTEGER,
			iqdmx30AESOutAESOut2InvertL
				INTEGER,
			iqdmx30AESOutAESOut2InvertR
				INTEGER,
			iqdmx30AESOutAESOut2GainL
				INTEGER,
			iqdmx30AESOutAESOut2GainR
				INTEGER,
			iqdmx30AESOutAESOut2PairMode
				INTEGER,
			iqdmx30AESOutAESOut3SourceLNonPCM
				INTEGER,
			iqdmx30AESOutAESOut3SourceR
				INTEGER,
			iqdmx30AESOutAESOut3Mute
				INTEGER,
			iqdmx30AESOutAESOut3MuteonVbit
				INTEGER,
			iqdmx30AESOutAESOut3InvertL
				INTEGER,
			iqdmx30AESOutAESOut3InvertR
				INTEGER,
			iqdmx30AESOutAESOut3GainL
				INTEGER,
			iqdmx30AESOutAESOut3GainR
				INTEGER,
			iqdmx30AESOutAESOut3PairMode
				INTEGER,
			iqdmx30AESOutAESOut4SourceLNonPCM
				INTEGER,
			iqdmx30AESOutAESOut4SourceR
				INTEGER,
			iqdmx30AESOutAESOut4Mute
				INTEGER,
			iqdmx30AESOutAESOut4MuteonVbit
				INTEGER,
			iqdmx30AESOutAESOut4InvertL
				INTEGER,
			iqdmx30AESOutAESOut4InvertR
				INTEGER,
			iqdmx30AESOutAESOut4GainL
				INTEGER,
			iqdmx30AESOutAESOut4GainR
				INTEGER,
			iqdmx30AESOutAESOut4PairMode
				INTEGER,
			iqdmx30AESOutAESOut5SourceLNonPCM
				INTEGER,
			iqdmx30AESOutAESOut5SourceR
				INTEGER,
			iqdmx30AESOutAESOut5Mute
				INTEGER,
			iqdmx30AESOutAESOut5MuteonVbit
				INTEGER,
			iqdmx30AESOutAESOut5InvertL
				INTEGER,
			iqdmx30AESOutAESOut5InvertR
				INTEGER,
			iqdmx30AESOutAESOut5GainL
				INTEGER,
			iqdmx30AESOutAESOut5GainR
				INTEGER,
			iqdmx30AESOutAESOut5PairMode
				INTEGER,
			iqdmx30AESOutAESOut6SourceLNonPCM
				INTEGER,
			iqdmx30AESOutAESOut6SourceR
				INTEGER,
			iqdmx30AESOutAESOut6Mute
				INTEGER,
			iqdmx30AESOutAESOut6MuteonVbit
				INTEGER,
			iqdmx30AESOutAESOut6InvertL
				INTEGER,
			iqdmx30AESOutAESOut6InvertR
				INTEGER,
			iqdmx30AESOutAESOut6GainL
				INTEGER,
			iqdmx30AESOutAESOut6GainR
				INTEGER,
			iqdmx30AESOutAESOut6PairMode
				INTEGER,
			iqdmx30AESOutAESOut7SourceLNonPCM
				INTEGER,
			iqdmx30AESOutAESOut7SourceR
				INTEGER,
			iqdmx30AESOutAESOut7Mute
				INTEGER,
			iqdmx30AESOutAESOut7MuteonVbit
				INTEGER,
			iqdmx30AESOutAESOut7InvertL
				INTEGER,
			iqdmx30AESOutAESOut7InvertR
				INTEGER,
			iqdmx30AESOutAESOut7GainL
				INTEGER,
			iqdmx30AESOutAESOut7GainR
				INTEGER,
			iqdmx30AESOutAESOut7PairMode
				INTEGER,
			iqdmx30AESOutAESOut8SourceLNonPCM
				INTEGER,
			iqdmx30AESOutAESOut8SourceR
				INTEGER,
			iqdmx30AESOutAESOut8Mute
				INTEGER,
			iqdmx30AESOutAESOut8MuteonVbit
				INTEGER,
			iqdmx30AESOutAESOut8InvertL
				INTEGER,
			iqdmx30AESOutAESOut8InvertR
				INTEGER,
			iqdmx30AESOutAESOut8GainL
				INTEGER,
			iqdmx30AESOutAESOut8GainR
				INTEGER,
			iqdmx30AESOutAESOut8PairMode
				INTEGER,
			iqdmx30AudioDelayDelaysVideoDelay
				INTEGER,
			iqdmx30AudioDelayDelaysManualDelay
				INTEGER,
			iqdmx30AudioDelayDelaysCoarseDelay
				INTEGER,
			iqdmx30AudioDelayDelaysFineDelay
				INTEGER,
			iqdmx30AudioDelayDelayStatusTotalDelay
				RollCallString,
			iqdmx30AudioDelayDelayStatusVideoDelay
				RollCallString,
			iqdmx30AudioDelayDelayStatusManualDelay
				RollCallString,
			iqdmx30AudioDolbyEDolbyEAutoAlign
				INTEGER,
			iqdmx30AudioDolbyEUserDolbyELine
				INTEGER,
			iqdmx30AudioDolbyEDolbyEAutoLineNo
				INTEGER,
			iqdmx30AudioDolbyELineStandard
				INTEGER,
			iqdmx30AudioToneFrequency
				INTEGER,
			iqdmx30AudioToneChannelident
				INTEGER,
			iqdmx30AudioAudioMonitorSilenceLevel
				INTEGER,
			iqdmx30AudioAudioMonitorOverloadLevel
				INTEGER,
			iqdmx30AudioAudioMonitorWarningTimer
				INTEGER,
			iqdmx30VideoDelayFreerunFrequency
				INTEGER,
			iqdmx30VideoDelayVideoHdelay
				INTEGER,
			iqdmx30VideoDelayVideoVdelay
				INTEGER,
			iqdmx30VideoDelayVideoFdelay
				INTEGER,
			iqdmx30VideoDelayGenlocksaveindex
				INTEGER,
			iqdmx30VideoDelayVideoHdelaysave
				INTEGER,
			iqdmx30VideoDelayVideoVdelaysave
				INTEGER,
			iqdmx30StatusStatusDisplay
				INTEGER,
			iqdmx30StatusProduct
				RollCallString,
			iqdmx30StatusSoftwareVersion
				RollCallString,
			iqdmx30StatusSerialNo
				RollCallString,
			iqdmx30StatusFactoryDefaults
				INTEGER,
			iqdmx30StatusDefaultSetting
				INTEGER,
			iqdmx30StatusRestart
				INTEGER,
			iqdmx30StatusBuild
				RollCallString,
			iqdmx30StatusPCB
				RollCallString,
			iqdmx30StatusKOSVersion
				RollCallString,
			iqdmx30StatusFirmwareVersion
				RollCallString,
			iqdmx30StatusUpTime
				RollCallString,
			iqdmx30MemoriesSelMemory
				INTEGER,
			iqdmx30MemoriesSetMemName
				RollCallString,
			iqdmx30MemoriesRecallMemory
				INTEGER,
			iqdmx30MemoriesSaveMemory
				INTEGER,
			iqdmx30MemoriesLastUserMemory
				RollCallString,
			iqdmx30MemoriesClearMemory
				INTEGER,
			iqdmx30MemoriesMemoryNamesMemory1Name
				RollCallString,
			iqdmx30MemoriesMemoryNamesMemory2Name
				RollCallString,
			iqdmx30MemoriesMemoryNamesMemory3Name
				RollCallString,
			iqdmx30MemoriesMemoryNamesMemory4Name
				RollCallString,
			iqdmx30MemoriesMemoryNamesMemory5Name
				RollCallString,
			iqdmx30MemoriesMemoryNamesMemory6Name
				RollCallString,
			iqdmx30MemoriesMemoryNamesMemory7Name
				RollCallString,
			iqdmx30MemoriesMemoryNamesMemory8Name
				RollCallString,
			iqdmx30MemoriesMemoryNamesMemory9Name
				RollCallString,
			iqdmx30MemoriesMemoryNamesMemory10Name
				RollCallString,
			iqdmx30MemoriesMemoryNamesMemory11Name
				RollCallString,
			iqdmx30MemoriesMemoryNamesMemory12Name
				RollCallString,
			iqdmx30MemoriesMemoryNamesMemory13Name
				RollCallString,
			iqdmx30MemoriesMemoryNamesMemory14Name
				RollCallString,
			iqdmx30MemoriesMemoryNamesMemory15Name
				RollCallString,
			iqdmx30MemoriesMemoryNamesMemory16Name
				RollCallString,
			iqdmx30LoggingLogMiscSlotStarten
				INTEGER,
			iqdmx30LoggingLogMiscSlotStart
				RollCallString,
			iqdmx30LoggingLogMiscSlotWidthen
				INTEGER,
			iqdmx30LoggingLogMiscSlotWidth
				RollCallString,
			iqdmx30LoggingLogMiscRearStatusen
				INTEGER,
			iqdmx30LoggingLogMiscRearStatus
				RollCallString,
			iqdmx30LoggingLogMiscRearIDen
				INTEGER,
			iqdmx30LoggingLogMiscRearID
				RollCallString,
			iqdmx30LoggingLogMiscFirmwareVersionen
				INTEGER,
			iqdmx30LoggingLogMiscFirmwareVersion
				RollCallString,
			iqdmx30LoggingLogMiscLicensedOptionsen
				INTEGER,
			iqdmx30LoggingLogMiscLicensedOptions
				RollCallString,
			iqdmx30LoggingLogMiscBuildNumberen
				INTEGER,
			iqdmx30LoggingLogMiscBuildNumber
				RollCallString,
			iqdmx30LoggingLogMiscOSVersionen
				INTEGER,
			iqdmx30LoggingLogMiscOSVersion
				RollCallString,
			iqdmx30LoggingLogMiscHardwareVersionen
				INTEGER,
			iqdmx30LoggingLogMiscHardwareVersion
				RollCallString,
			iqdmx30LoggingLogMiscUptimeen
				INTEGER,
			iqdmx30LoggingLogMiscUptime
				RollCallString,
			iqdmx30LoggingLogMiscSerialNumberen
				INTEGER,
			iqdmx30LoggingLogMiscSerialNumber
				RollCallString,
			iqdmx30LoggingLogVideoInput1Input1en
				INTEGER,
			iqdmx30LoggingLogVideoInput1Input1
				RollCallString,
			iqdmx30LoggingLogVideoInput1Input1Standarden
				INTEGER,
			iqdmx30LoggingLogVideoInput1Input1Standard
				RollCallString,
			iqdmx30LoggingLogVideoInput1In1SDIERRSen
				INTEGER,
			iqdmx30LoggingLogVideoInput1In1SDIERRS
				RollCallString,
			iqdmx30LoggingLogVideoInput1In1SDIANCERRSen
				INTEGER,
			iqdmx30LoggingLogVideoInput1In1SDIANCERRS
				RollCallString,
			iqdmx30LoggingLogVideoInput1Input1Typeen
				INTEGER,
			iqdmx30LoggingLogVideoInput1Input1Type
				RollCallString,
			iqdmx30LoggingLogVideoInput1Input1Identen
				INTEGER,
			iqdmx30LoggingLogVideoInput1Input1Ident
				RollCallString,
			iqdmx30LoggingLogVideoInput2Input2en
				INTEGER,
			iqdmx30LoggingLogVideoInput2Input2
				RollCallString,
			iqdmx30LoggingLogVideoInput2Input2Standarden
				INTEGER,
			iqdmx30LoggingLogVideoInput2Input2Standard
				RollCallString,
			iqdmx30LoggingLogVideoInput2In2SDIERRSen
				INTEGER,
			iqdmx30LoggingLogVideoInput2In2SDIERRS
				RollCallString,
			iqdmx30LoggingLogVideoInput2In2SDIANCERRSen
				INTEGER,
			iqdmx30LoggingLogVideoInput2In2SDIANCERRS
				RollCallString,
			iqdmx30LoggingLogVideoInput2Input2Typeen
				INTEGER,
			iqdmx30LoggingLogVideoInput2Input2Type
				RollCallString,
			iqdmx30LoggingLogVideoInput2Input2Identen
				INTEGER,
			iqdmx30LoggingLogVideoInput2Input2Ident
				RollCallString,
			iqdmx30LoggingLogAudioInput1Input1Audio1en
				INTEGER,
			iqdmx30LoggingLogAudioInput1Input1Audio1
				RollCallString,
			iqdmx30LoggingLogAudioInput1Input1Audio2en
				INTEGER,
			iqdmx30LoggingLogAudioInput1Input1Audio2
				RollCallString,
			iqdmx30LoggingLogAudioInput1Input1Audio3en
				INTEGER,
			iqdmx30LoggingLogAudioInput1Input1Audio3
				RollCallString,
			iqdmx30LoggingLogAudioInput1Input1Audio4en
				INTEGER,
			iqdmx30LoggingLogAudioInput1Input1Audio4
				RollCallString,
			iqdmx30LoggingLogAudioInput1Input1Audio5en
				INTEGER,
			iqdmx30LoggingLogAudioInput1Input1Audio5
				RollCallString,
			iqdmx30LoggingLogAudioInput1Input1Audio6en
				INTEGER,
			iqdmx30LoggingLogAudioInput1Input1Audio6
				RollCallString,
			iqdmx30LoggingLogAudioInput1Input1Audio7en
				INTEGER,
			iqdmx30LoggingLogAudioInput1Input1Audio7
				RollCallString,
			iqdmx30LoggingLogAudioInput1Input1Audio8en
				INTEGER,
			iqdmx30LoggingLogAudioInput1Input1Audio8
				RollCallString,
			iqdmx30LoggingLogAudioInput2Input2Audio1en
				INTEGER,
			iqdmx30LoggingLogAudioInput2Input2Audio1
				RollCallString,
			iqdmx30LoggingLogAudioInput2Input2Audio2en
				INTEGER,
			iqdmx30LoggingLogAudioInput2Input2Audio2
				RollCallString,
			iqdmx30LoggingLogAudioInput2Input2Audio3en
				INTEGER,
			iqdmx30LoggingLogAudioInput2Input2Audio3
				RollCallString,
			iqdmx30LoggingLogAudioInput2Input2Audio4en
				INTEGER,
			iqdmx30LoggingLogAudioInput2Input2Audio4
				RollCallString,
			iqdmx30LoggingLogAudioInput2Input2Audio5en
				INTEGER,
			iqdmx30LoggingLogAudioInput2Input2Audio5
				RollCallString,
			iqdmx30LoggingLogAudioInput2Input2Audio6en
				INTEGER,
			iqdmx30LoggingLogAudioInput2Input2Audio6
				RollCallString,
			iqdmx30LoggingLogAudioInput2Input2Audio7en
				INTEGER,
			iqdmx30LoggingLogAudioInput2Input2Audio7
				RollCallString,
			iqdmx30LoggingLogAudioInput2Input2Audio8en
				INTEGER,
			iqdmx30LoggingLogAudioInput2Input2Audio8
				RollCallString,
			iqdmx30LoggingLogVideoOutputOutput1Typeen
				INTEGER,
			iqdmx30LoggingLogVideoOutputOutput1Type
				RollCallString,
			iqdmx30LoggingLogVideoOutputOutput1Stateen
				INTEGER,
			iqdmx30LoggingLogVideoOutputOutput1State
				RollCallString,
			iqdmx30LoggingLogVideoOutputOutput1Stden
				INTEGER,
			iqdmx30LoggingLogVideoOutputOutput1Std
				RollCallString,
			iqdmx30LoggingLogVideoOutputOutput1Captionen
				INTEGER,
			iqdmx30LoggingLogVideoOutputOutput1Caption
				RollCallString,
			iqdmx30LoggingLogVideoOutputOutput1en
				INTEGER,
			iqdmx30LoggingLogVideoOutputOutput1
				RollCallString,
			iqdmx30LoggingLogAudioOutputOutput1Embed11en
				INTEGER,
			iqdmx30LoggingLogAudioOutputOutput1Embed11
				RollCallString,
			iqdmx30LoggingLogAudioOutputOutput1Embed12en
				INTEGER,
			iqdmx30LoggingLogAudioOutputOutput1Embed12
				RollCallString,
			iqdmx30LoggingLogAudioOutputOutput1Embed21en
				INTEGER,
			iqdmx30LoggingLogAudioOutputOutput1Embed21
				RollCallString,
			iqdmx30LoggingLogAudioOutputOutput1Embed22en
				INTEGER,
			iqdmx30LoggingLogAudioOutputOutput1Embed22
				RollCallString,
			iqdmx30LoggingLogAudioOutputOutput1Embed31en
				INTEGER,
			iqdmx30LoggingLogAudioOutputOutput1Embed31
				RollCallString,
			iqdmx30LoggingLogAudioOutputOutput1Embed32en
				INTEGER,
			iqdmx30LoggingLogAudioOutputOutput1Embed32
				RollCallString,
			iqdmx30LoggingLogAudioOutputOutput1Embed41en
				INTEGER,
			iqdmx30LoggingLogAudioOutputOutput1Embed41
				RollCallString,
			iqdmx30LoggingLogAudioOutputOutput1Embed42en
				INTEGER,
			iqdmx30LoggingLogAudioOutputOutput1Embed42
				RollCallString,
			iqdmx30LoggingLogAudioOutputOutput1Embed51en
				INTEGER,
			iqdmx30LoggingLogAudioOutputOutput1Embed51
				RollCallString,
			iqdmx30LoggingLogAudioOutputOutput1Embed52en
				INTEGER,
			iqdmx30LoggingLogAudioOutputOutput1Embed52
				RollCallString,
			iqdmx30LoggingLogAudioOutputOutput1Embed61en
				INTEGER,
			iqdmx30LoggingLogAudioOutputOutput1Embed61
				RollCallString,
			iqdmx30LoggingLogAudioOutputOutput1Embed62en
				INTEGER,
			iqdmx30LoggingLogAudioOutputOutput1Embed62
				RollCallString,
			iqdmx30LoggingLogAudioOutputOutput1Embed71en
				INTEGER,
			iqdmx30LoggingLogAudioOutputOutput1Embed71
				RollCallString,
			iqdmx30LoggingLogAudioOutputOutput1Embed72en
				INTEGER,
			iqdmx30LoggingLogAudioOutputOutput1Embed72
				RollCallString,
			iqdmx30LoggingLogAudioOutputOutput1Embed81en
				INTEGER,
			iqdmx30LoggingLogAudioOutputOutput1Embed81
				RollCallString,
			iqdmx30LoggingLogAudioOutputOutput1Embed82en
				INTEGER,
			iqdmx30LoggingLogAudioOutputOutput1Embed82
				RollCallString,
			iqdmx30LoggingLogAudioOutputOutput1AES11en
				INTEGER,
			iqdmx30LoggingLogAudioOutputOutput1AES11
				RollCallString,
			iqdmx30LoggingLogAudioOutputOutput1AES12en
				INTEGER,
			iqdmx30LoggingLogAudioOutputOutput1AES12
				RollCallString,
			iqdmx30LoggingLogAudioOutputOutput1AES21en
				INTEGER,
			iqdmx30LoggingLogAudioOutputOutput1AES21
				RollCallString,
			iqdmx30LoggingLogAudioOutputOutput1AES22en
				INTEGER,
			iqdmx30LoggingLogAudioOutputOutput1AES22
				RollCallString,
			iqdmx30LoggingLogAudioOutputOutput1AES31en
				INTEGER,
			iqdmx30LoggingLogAudioOutputOutput1AES31
				RollCallString,
			iqdmx30LoggingLogAudioOutputOutput1AES32en
				INTEGER,
			iqdmx30LoggingLogAudioOutputOutput1AES32
				RollCallString,
			iqdmx30LoggingLogAudioOutputOutput1AES41en
				INTEGER,
			iqdmx30LoggingLogAudioOutputOutput1AES41
				RollCallString,
			iqdmx30LoggingLogAudioOutputOutput1AES42en
				INTEGER,
			iqdmx30LoggingLogAudioOutputOutput1AES42
				RollCallString,
			iqdmx30LoggingLogAudioOutputOutput1AES51en
				INTEGER,
			iqdmx30LoggingLogAudioOutputOutput1AES51
				RollCallString,
			iqdmx30LoggingLogAudioOutputOutput1AES52en
				INTEGER,
			iqdmx30LoggingLogAudioOutputOutput1AES52
				RollCallString,
			iqdmx30LoggingLogAudioOutputOutput1AES61en
				INTEGER,
			iqdmx30LoggingLogAudioOutputOutput1AES61
				RollCallString,
			iqdmx30LoggingLogAudioOutputOutput1AES62en
				INTEGER,
			iqdmx30LoggingLogAudioOutputOutput1AES62
				RollCallString,
			iqdmx30LoggingLogAudioOutputOutput1AES71en
				INTEGER,
			iqdmx30LoggingLogAudioOutputOutput1AES71
				RollCallString,
			iqdmx30LoggingLogAudioOutputOutput1AES72en
				INTEGER,
			iqdmx30LoggingLogAudioOutputOutput1AES72
				RollCallString,
			iqdmx30LoggingLogAudioOutputOutput1AES81en
				INTEGER,
			iqdmx30LoggingLogAudioOutputOutput1AES81
				RollCallString,
			iqdmx30LoggingLogAudioOutputOutput1AES82en
				INTEGER,
			iqdmx30LoggingLogAudioOutputOutput1AES82
				RollCallString,
			iqdmx30LoggingLogAudioOutputOutputEmbeden
				INTEGER,
			iqdmx30LoggingLogAudioOutputOutputEmbed
				RollCallString,
			iqdmx30SetupRollTracksRollTrackIndex1495
				INTEGER,
			iqdmx30SetupRollTracksRollTrackSource1496
				INTEGER,
			iqdmx30SetupRollTracksRollTrackDisable
				INTEGER,
			iqdmx30SetupRollTracksRollTrackAddress1497
				RollCallString,
			iqdmx30SetupRollTracksRollTrackCommand1498
				RollCallString,
			iqdmx30SetupRollTracksRollTrackSending
				RollCallString,
			iqdmx30SetupRollTracksRollTrackStatus
				RollCallString,
			iqdmx30SetupRollTracksRollTrackIndex2870
				INTEGER,
			iqdmx30SetupRollTracksRollTrackSource2871
				INTEGER,
			iqdmx30SetupRollTracksRollTrackAddress2872
				RollCallString,
			iqdmx30SetupRollTracksRollTrackCommand2873
				RollCallString
		}

	iqdmx30SlotIndex OBJECT-TYPE
		SYNTAX		Unsigned32
		MAX-ACCESS		not-accessible
		STATUS			current
		DESCRIPTION
				"The unique Index value for each slot.  Its value
					ranges between 1 and the value of slotNumber."
		::= { iqdmx30CmdEntry 0 }


	iqdmx30VideoVideoInputSelect OBJECT-TYPE
		SYNTAX		INTEGER {
							val-Input-1(0),
							val-Input-2(1)
							}
		MAX-ACCESS		read-write
		STATUS			current
		DESCRIPTION
				"TYPE: - RadiobuttonList
				 PAGE: - Video
					Video Input Select  cmdID= 2251 
					Input 1  value= 0  
					Input 2  value= 1  "
		::= { iqdmx30CmdEntry 2251 }


	iqdmx30VideoValidInputFormats62525i OBJECT-TYPE
		SYNTAX		INTEGER { disable(0), enable(1) }
		MAX-ACCESS		read-write
		STATUS			current
		DESCRIPTION
				"TYPE: - Checkbox
				 PAGE: - Video
					625/25i  cmdID= 3802 "
		::= { iqdmx30CmdEntry 3802 }


	iqdmx30VideoValidInputFormats52529i OBJECT-TYPE
		SYNTAX		INTEGER { disable(0), enable(1) }
		MAX-ACCESS		read-write
		STATUS			current
		DESCRIPTION
				"TYPE: - Checkbox
				 PAGE: - Video
					525/29i  cmdID= 3803 "
		::= { iqdmx30CmdEntry 3803 }


	iqdmx30VideoValidInputFormats72050p OBJECT-TYPE
		SYNTAX		INTEGER { disable(0), enable(1) }
		MAX-ACCESS		read-write
		STATUS			current
		DESCRIPTION
				"TYPE: - Checkbox
				 PAGE: - Video
					720/50p  cmdID= 3809 "
		::= { iqdmx30CmdEntry 3809 }


	iqdmx30VideoValidInputFormats72059p OBJECT-TYPE
		SYNTAX		INTEGER { disable(0), enable(1) }
		MAX-ACCESS		read-write
		STATUS			current
		DESCRIPTION
				"TYPE: - Checkbox
				 PAGE: - Video
					720/59p  cmdID= 3810 "
		::= { iqdmx30CmdEntry 3810 }


	iqdmx30VideoValidInputFormats108025i OBJECT-TYPE
		SYNTAX		INTEGER { disable(0), enable(1) }
		MAX-ACCESS		read-write
		STATUS			current
		DESCRIPTION
				"TYPE: - Checkbox
				 PAGE: - Video
					1080/25i  cmdID= 3817 "
		::= { iqdmx30CmdEntry 3817 }


	iqdmx30VideoValidInputFormats108029i OBJECT-TYPE
		SYNTAX		INTEGER { disable(0), enable(1) }
		MAX-ACCESS		read-write
		STATUS			current
		DESCRIPTION
				"TYPE: - Checkbox
				 PAGE: - Video
					1080/29i  cmdID= 3818 "
		::= { iqdmx30CmdEntry 3818 }


	iqdmx30VideoValidInputFormats108050pA OBJECT-TYPE
		SYNTAX		INTEGER { disable(0), enable(1) }
		MAX-ACCESS		read-write
		STATUS			current
		DESCRIPTION
				"TYPE: - Checkbox
				 PAGE: - Video
					1080/50p-A  cmdID= 3822 "
		::= { iqdmx30CmdEntry 3822 }


	iqdmx30VideoValidInputFormats108059pA OBJECT-TYPE
		SYNTAX		INTEGER { disable(0), enable(1) }
		MAX-ACCESS		read-write
		STATUS			current
		DESCRIPTION
				"TYPE: - Checkbox
				 PAGE: - Video
					1080/59p-A  cmdID= 3823 "
		::= { iqdmx30CmdEntry 3823 }


	iqdmx30VideoValidInputFormats108050pB OBJECT-TYPE
		SYNTAX		INTEGER { disable(0), enable(1) }
		MAX-ACCESS		read-write
		STATUS			current
		DESCRIPTION
				"TYPE: - Checkbox
				 PAGE: - Video
					1080/50p-B  cmdID= 3825 "
		::= { iqdmx30CmdEntry 3825 }


	iqdmx30VideoValidInputFormats108059pB OBJECT-TYPE
		SYNTAX		INTEGER { disable(0), enable(1) }
		MAX-ACCESS		read-write
		STATUS			current
		DESCRIPTION
				"TYPE: - Checkbox
				 PAGE: - Video
					1080/59p-B  cmdID= 3826 "
		::= { iqdmx30CmdEntry 3826 }


	iqdmx30VideoDefaultFormat OBJECT-TYPE
		SYNTAX		INTEGER {
							val-Last-Known-Good(1),
							val-625-25i(2),
							val-525-29i(3),
							val-720-50p(9),
							val-720-59p(10),
							val-1080-25i(17),
							val-1080-29i(18),
							val-1080-50p-A(22),
							val-1080-59p-A(23),
							val-1080-50p-B(25),
							val-1080-59p-B(26)
							}
		MAX-ACCESS		read-write
		STATUS			current
		DESCRIPTION
				"TYPE: - RadiobuttonList
				 PAGE: - Video
					Default Format  cmdID= 3793 
					Last Known Good  value= 1  
					625/25i  value= 2  
					525/29i  value= 3  
					720/50p  value= 9  
					720/59p  value= 10  
					1080/25i  value= 17  
					1080/29i  value= 18  
					1080/50p-A  value= 22  
					1080/59p-A  value= 23  
					1080/50p-B  value= 25  
					1080/59p-B  value= 26  "
		::= { iqdmx30CmdEntry 3793 }


	iqdmx30VideoDefaultOutput OBJECT-TYPE
		SYNTAX		INTEGER {
							val-Black(0),
							val-Freeze(1),
							val-Pattern(2)
							}
		MAX-ACCESS		read-write
		STATUS			current
		DESCRIPTION
				"TYPE: - RadiobuttonList
				 PAGE: - Video
					Default Output  cmdID= 2623 
					Black  value= 0  
					Freeze  value= 1  
					Pattern  value= 2  "
		::= { iqdmx30CmdEntry 2623 }


	iqdmx30VideoVideoProcampProcAmpEnable OBJECT-TYPE
		SYNTAX		INTEGER { disable(0), enable(1) }
		MAX-ACCESS		read-write
		STATUS			current
		DESCRIPTION
				"TYPE: - Checkbox
				 PAGE: - Video
					ProcAmp Enable  cmdID= 2864 "
		::= { iqdmx30CmdEntry 2864 }


	iqdmx30VideoVideoProcampBlackLevel OBJECT-TYPE
		SYNTAX		INTEGER
		MAX-ACCESS		read-write
		STATUS			current
		DESCRIPTION
				"TYPE: - Number
				 PAGE: - Video
					Black Level  cmdID= 2708  min= -1000  max= 1000  step= 8  format= %3.1fmV  div_scale= 10 
					Min = -100.0mV  Max = 100.0mV  Step = 0.8mV "
		::= { iqdmx30CmdEntry 2708 }


	iqdmx30VideoVideoProcampHueAdjust OBJECT-TYPE
		SYNTAX		INTEGER
		MAX-ACCESS		read-write
		STATUS			current
		DESCRIPTION
				"TYPE: - Number
				 PAGE: - Video
					Hue Adjust  cmdID= 3622  min= -180  max= 180  step= 1  format= %1.0fdeg  div_scale= 1 
					Min = -180deg  Max = 180deg  Step = 1deg "
		::= { iqdmx30CmdEntry 3622 }


	iqdmx30VideoVideoProcampMasterVideoGain OBJECT-TYPE
		SYNTAX		INTEGER
		MAX-ACCESS		read-write
		STATUS			current
		DESCRIPTION
				"TYPE: - Number
				 PAGE: - Video
					Master Video Gain  cmdID= 3780  min= -60  max= 60  step= 1  format= %0.1fdB  div_scale= 10 
					Min = -6.0dB  Max = 6.0dB  Step = 0.1dB "
		::= { iqdmx30CmdEntry 3780 }


	iqdmx30VideoVideoProcampYGain OBJECT-TYPE
		SYNTAX		INTEGER
		MAX-ACCESS		read-write
		STATUS			current
		DESCRIPTION
				"TYPE: - Number
				 PAGE: - Video
					Y Gain  cmdID= 2707  min= -60  max= 60  step= 1  format= %0.1fdB  div_scale= 10 
					Min = -6.0dB  Max = 6.0dB  Step = 0.1dB "
		::= { iqdmx30CmdEntry 2707 }


	iqdmx30VideoVideoProcampCbCrGain OBJECT-TYPE
		SYNTAX		INTEGER
		MAX-ACCESS		read-write
		STATUS			current
		DESCRIPTION
				"TYPE: - Number
				 PAGE: - Video
					Cb/Cr Gain  cmdID= 2706  min= -60  max= 60  step= 1  format= %0.1fdB  div_scale= 10 
					Min = -6.0dB  Max = 6.0dB  Step = 0.1dB "
		::= { iqdmx30CmdEntry 2706 }


	iqdmx30VideoVideoProcampYCTiming OBJECT-TYPE
		SYNTAX		INTEGER
		MAX-ACCESS		read-write
		STATUS			current
		DESCRIPTION
				"TYPE: - Number
				 PAGE: - Video
					Y/C Timing  cmdID= 2924  min= -8  max= 8  step= 2  format= %1.0f pixels  div_scale= 1 
					Min = -8 pixels  Max = 8 pixels  Step = 2 pixels "
		::= { iqdmx30CmdEntry 2924 }


	iqdmx30VideoVideoProcampPictureposition OBJECT-TYPE
		SYNTAX		INTEGER
		MAX-ACCESS		read-write
		STATUS			current
		DESCRIPTION
				"TYPE: - Number
				 PAGE: - Video
					Picture position  cmdID= 2709  min= -8  max= 8  step= 2  format= %1.0f pixels  div_scale= 1 
					Min = -8 pixels  Max = 8 pixels  Step = 2 pixels "
		::= { iqdmx30CmdEntry 2709 }


	iqdmx30VideoVideoProcampModalIndex OBJECT-TYPE
		SYNTAX		INTEGER
		MAX-ACCESS		read-write
		STATUS			current
		DESCRIPTION
				"TYPE: - Number
				 PAGE: - Video
					Modal Index  cmdID= 5006  min= 0  max= 1  step= 1  format= %1.0f  div_scale= 1 
					Min = 0  Max = 1  Step = 1 "
		::= { iqdmx30CmdEntry 5006 }


	iqdmx30VideoVideoProcampYCTimingnm OBJECT-TYPE
		SYNTAX		INTEGER
		MAX-ACCESS		read-write
		STATUS			current
		DESCRIPTION
				"TYPE: - Number
				 PAGE: - Video
					Y/C Timing nm  cmdID= 5008  min= -16  max= 16  step= 2  format= %1.0f pixels  div_scale= 1 
					Min = -16 pixels  Max = 16 pixels  Step = 2 pixels "
		::= { iqdmx30CmdEntry 5008 }


	iqdmx30VideoVideoProcampPicturepositionnm OBJECT-TYPE
		SYNTAX		INTEGER
		MAX-ACCESS		read-write
		STATUS			current
		DESCRIPTION
				"TYPE: - Number
				 PAGE: - Video
					Picture position nm  cmdID= 5007  min= -16  max= 16  step= 2  format= %1.0f pixels  div_scale= 1 
					Min = -16 pixels  Max = 16 pixels  Step = 2 pixels "
		::= { iqdmx30CmdEntry 5007 }


	iqdmx30VideoBlankingBlankVANC OBJECT-TYPE
		SYNTAX		INTEGER { disable(0), enable(1) }
		MAX-ACCESS		read-write
		STATUS			current
		DESCRIPTION
				"TYPE: - Checkbox
				 PAGE: - Video
					Blank VANC  cmdID= 3949 "
		::= { iqdmx30CmdEntry 3949 }


	iqdmx30Blanking625BlankLinesLine23 OBJECT-TYPE
		SYNTAX		INTEGER { disable(0), enable(1) }
		MAX-ACCESS		read-write
		STATUS			current
		DESCRIPTION
				"TYPE: - Checkbox
				 PAGE: - Video
					Line 23  cmdID= 3951 "
		::= { iqdmx30CmdEntry 3951 }


	iqdmx30Blanking625BlankLinesLine336 OBJECT-TYPE
		SYNTAX		INTEGER { disable(0), enable(1) }
		MAX-ACCESS		read-write
		STATUS			current
		DESCRIPTION
				"TYPE: - Checkbox
				 PAGE: - Video
					Line 336  cmdID= 3952 "
		::= { iqdmx30CmdEntry 3952 }


	iqdmx30Blanking525BlankLinesLine21 OBJECT-TYPE
		SYNTAX		INTEGER { disable(0), enable(1) }
		MAX-ACCESS		read-write
		STATUS			current
		DESCRIPTION
				"TYPE: - Checkbox
				 PAGE: - Video
					Line 21  cmdID= 3953 "
		::= { iqdmx30CmdEntry 3953 }


	iqdmx30Blanking525BlankLinesLine22 OBJECT-TYPE
		SYNTAX		INTEGER { disable(0), enable(1) }
		MAX-ACCESS		read-write
		STATUS			current
		DESCRIPTION
				"TYPE: - Checkbox
				 PAGE: - Video
					Line 22  cmdID= 3955 "
		::= { iqdmx30CmdEntry 3955 }


	iqdmx30Blanking525BlankLinesLine283 OBJECT-TYPE
		SYNTAX		INTEGER { disable(0), enable(1) }
		MAX-ACCESS		read-write
		STATUS			current
		DESCRIPTION
				"TYPE: - Checkbox
				 PAGE: - Video
					Line 283  cmdID= 3954 "
		::= { iqdmx30CmdEntry 3954 }


	iqdmx30Blanking525BlankLinesLine284 OBJECT-TYPE
		SYNTAX		INTEGER { disable(0), enable(1) }
		MAX-ACCESS		read-write
		STATUS			current
		DESCRIPTION
				"TYPE: - Checkbox
				 PAGE: - Video
					Line 284  cmdID= 3956 "
		::= { iqdmx30CmdEntry 3956 }


	iqdmx30VideoBlankingBlankHANC OBJECT-TYPE
		SYNTAX		INTEGER { disable(0), enable(1) }
		MAX-ACCESS		read-write
		STATUS			current
		DESCRIPTION
				"TYPE: - Checkbox
				 PAGE: - Video
					Blank HANC  cmdID= 3947 "
		::= { iqdmx30CmdEntry 3947 }


	iqdmx30VideoCaption OBJECT-TYPE
		SYNTAX		INTEGER {
							val-Off(0),
							val-On(1),
							val-Animated-Slow(2),
							val-Animated-Medium(3),
							val-Animated-Fast(4)
							}
		MAX-ACCESS		read-write
		STATUS			current
		DESCRIPTION
				"TYPE: - Button
				 PAGE: - Video
					Off  cmdID= 1037  value= 0  
					On  cmdID= 1037  value= 1  
					Animated Slow  cmdID= 1037  value= 2  
					Animated Medium  cmdID= 1037  value= 3  
					Animated Fast  cmdID= 1037  value= 4  "
		::= { iqdmx30CmdEntry 1037 }


	iqdmx30VideoCaptionEditCaption OBJECT-TYPE
		SYNTAX		RollCallString
		MAX-ACCESS		read-write
		STATUS			current
		DESCRIPTION
				"TYPE: - Editstring
				 PAGE: - Video
					Edit Caption  cmdID= 1041  "
		::= { iqdmx30CmdEntry 1041 }


	iqdmx30VideoPattern OBJECT-TYPE
		SYNTAX		INTEGER {
							val-Off(0),
							val-Black(1),
							val-Bars(2)
							}
		MAX-ACCESS		read-write
		STATUS			current
		DESCRIPTION
				"TYPE: - RadiobuttonList
				 PAGE: - Video
					Pattern  cmdID= 2624 
					Off  value= 0  
					Black  value= 1  
					Bars  value= 2  "
		::= { iqdmx30CmdEntry 2624 }


	iqdmx30VideoFreeze OBJECT-TYPE
		SYNTAX		INTEGER {
							val-Field(0),
							val-Frame(1)
							}
		MAX-ACCESS		read-write
		STATUS			current
		DESCRIPTION
				"TYPE: - Button
				 PAGE: - Video
					Field  cmdID= 5023  value= 0  
					Frame  cmdID= 5023  value= 1  "
		::= { iqdmx30CmdEntry 5023 }


	iqdmx30VideoFreezeManualFreeze OBJECT-TYPE
		SYNTAX		INTEGER { disable(0), enable(1) }
		MAX-ACCESS		read-write
		STATUS			current
		DESCRIPTION
				"TYPE: - Checkbox
				 PAGE: - Video
					Manual Freeze  cmdID= 5022 "
		::= { iqdmx30CmdEntry 5022 }


	iqdmx30AudioAudioInputSelect OBJECT-TYPE
		SYNTAX		INTEGER {
							val-Input-1(0),
							val-Input-2(1),
							val-Follow-Video(4)
							}
		MAX-ACCESS		read-write
		STATUS			current
		DESCRIPTION
				"TYPE: - RadiobuttonList
				 PAGE: - Audio
					Audio Input Select  cmdID= 2252 
					Input 1  value= 0  
					Input 2  value= 1  
					Follow Video  value= 4  "
		::= { iqdmx30CmdEntry 2252 }


	iqdmx30EmbeddersEmbedder1Enable OBJECT-TYPE
		SYNTAX		INTEGER { disable(0), enable(1) }
		MAX-ACCESS		read-write
		STATUS			current
		DESCRIPTION
				"TYPE: - Checkbox
				 PAGE: - Audio- Embedders- Embedder 1
					Enable  cmdID= 5066 "
		::= { iqdmx30CmdEntry 5066 }


	iqdmx30EmbeddersEmbedder1SourceLNonPCM5034 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 1
					Source L / Non-PCM  cmdID= 5034 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx30CmdEntry 5034 }


	iqdmx30EmbeddersEmbedder1SourceR5035 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 1
					Source R  cmdID= 5035 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx30CmdEntry 5035 }


	iqdmx30EmbeddersEmbedder1Mute3240 OBJECT-TYPE
		SYNTAX		INTEGER { disable(0), enable(1) }
		MAX-ACCESS		read-write
		STATUS			current
		DESCRIPTION
				"TYPE: - Checkbox
				 PAGE: - Audio- Embedders- Embedder 1
					Mute  cmdID= 3240 "
		::= { iqdmx30CmdEntry 3240 }


	iqdmx30EmbeddersEmbedder1MuteonVbit3272 OBJECT-TYPE
		SYNTAX		INTEGER { disable(0), enable(1) }
		MAX-ACCESS		read-write
		STATUS			current
		DESCRIPTION
				"TYPE: - Checkbox
				 PAGE: - Audio- Embedders- Embedder 1
					Mute on V bit  cmdID= 3272 "
		::= { iqdmx30CmdEntry 3272 }


	iqdmx30EmbeddersEmbedder1InvertL3160 OBJECT-TYPE
		SYNTAX		INTEGER { disable(0), enable(1) }
		MAX-ACCESS		read-write
		STATUS			current
		DESCRIPTION
				"TYPE: - Checkbox
				 PAGE: - Audio- Embedders- Embedder 1
					Invert L  cmdID= 3160 "
		::= { iqdmx30CmdEntry 3160 }


	iqdmx30EmbeddersEmbedder1InvertR3161 OBJECT-TYPE
		SYNTAX		INTEGER { disable(0), enable(1) }
		MAX-ACCESS		read-write
		STATUS			current
		DESCRIPTION
				"TYPE: - Checkbox
				 PAGE: - Audio- Embedders- Embedder 1
					Invert R  cmdID= 3161 "
		::= { iqdmx30CmdEntry 3161 }


	iqdmx30EmbeddersEmbedder1GainL3080 OBJECT-TYPE
		SYNTAX		INTEGER
		MAX-ACCESS		read-write
		STATUS			current
		DESCRIPTION
				"TYPE: - Number
				 PAGE: - Audio- Embedders- Embedder 1
					Gain L  cmdID= 3080  min= -720  max= 120  step= 1  format= %0.1fdB  div_scale= 10 
					Min = -72.0dB  Max = 12.0dB  Step = 0.1dB "
		::= { iqdmx30CmdEntry 3080 }


	iqdmx30EmbeddersEmbedder1GainR3081 OBJECT-TYPE
		SYNTAX		INTEGER
		MAX-ACCESS		read-write
		STATUS			current
		DESCRIPTION
				"TYPE: - Number
				 PAGE: - Audio- Embedders- Embedder 1
					Gain R  cmdID= 3081  min= -720  max= 120  step= 1  format= %0.1fdB  div_scale= 10 
					Min = -72.0dB  Max = 12.0dB  Step = 0.1dB "
		::= { iqdmx30CmdEntry 3081 }


	iqdmx30EmbeddersEmbedder1PairMode3930 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 1
					Pair Mode  cmdID= 3930 
					2 Channel PCM  value= 0  
					Stereo PCM  value= 1  
					Non-PCM  value= 2  "
		::= { iqdmx30CmdEntry 3930 }


	iqdmx30EmbeddersEmbedder1SourceLNonPCM5036 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 1
					Source L / Non-PCM  cmdID= 5036 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx30CmdEntry 5036 }


	iqdmx30EmbeddersEmbedder1SourceR5037 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 1
					Source R  cmdID= 5037 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx30CmdEntry 5037 }


	iqdmx30EmbeddersEmbedder1Mute3241 OBJECT-TYPE
		SYNTAX		INTEGER { disable(0), enable(1) }
		MAX-ACCESS		read-write
		STATUS			current
		DESCRIPTION
				"TYPE: - Checkbox
				 PAGE: - Audio- Embedders- Embedder 1
					Mute  cmdID= 3241 "
		::= { iqdmx30CmdEntry 3241 }


	iqdmx30EmbeddersEmbedder1MuteonVbit3273 OBJECT-TYPE
		SYNTAX		INTEGER { disable(0), enable(1) }
		MAX-ACCESS		read-write
		STATUS			current
		DESCRIPTION
				"TYPE: - Checkbox
				 PAGE: - Audio- Embedders- Embedder 1
					Mute on V bit  cmdID= 3273 "
		::= { iqdmx30CmdEntry 3273 }


	iqdmx30EmbeddersEmbedder1InvertL3162 OBJECT-TYPE
		SYNTAX		INTEGER { disable(0), enable(1) }
		MAX-ACCESS		read-write
		STATUS			current
		DESCRIPTION
				"TYPE: - Checkbox
				 PAGE: - Audio- Embedders- Embedder 1
					Invert L  cmdID= 3162 "
		::= { iqdmx30CmdEntry 3162 }


	iqdmx30EmbeddersEmbedder1InvertR3163 OBJECT-TYPE
		SYNTAX		INTEGER { disable(0), enable(1) }
		MAX-ACCESS		read-write
		STATUS			current
		DESCRIPTION
				"TYPE: - Checkbox
				 PAGE: - Audio- Embedders- Embedder 1
					Invert R  cmdID= 3163 "
		::= { iqdmx30CmdEntry 3163 }


	iqdmx30EmbeddersEmbedder1GainL3082 OBJECT-TYPE
		SYNTAX		INTEGER
		MAX-ACCESS		read-write
		STATUS			current
		DESCRIPTION
				"TYPE: - Number
				 PAGE: - Audio- Embedders- Embedder 1
					Gain L  cmdID= 3082  min= -720  max= 120  step= 1  format= %0.1fdB  div_scale= 10 
					Min = -72.0dB  Max = 12.0dB  Step = 0.1dB "
		::= { iqdmx30CmdEntry 3082 }


	iqdmx30EmbeddersEmbedder1GainR3083 OBJECT-TYPE
		SYNTAX		INTEGER
		MAX-ACCESS		read-write
		STATUS			current
		DESCRIPTION
				"TYPE: - Number
				 PAGE: - Audio- Embedders- Embedder 1
					Gain R  cmdID= 3083  min= -720  max= 120  step= 1  format= %0.1fdB  div_scale= 10 
					Min = -72.0dB  Max = 12.0dB  Step = 0.1dB "
		::= { iqdmx30CmdEntry 3083 }


	iqdmx30EmbeddersEmbedder1PairMode3931 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 1
					Pair Mode  cmdID= 3931 
					2 Channel PCM  value= 0  
					Stereo PCM  value= 1  
					Non-PCM  value= 2  "
		::= { iqdmx30CmdEntry 3931 }


	iqdmx30EmbeddersEmbedder1NonModalIndex5338 OBJECT-TYPE
		SYNTAX		INTEGER
		MAX-ACCESS		read-write
		STATUS			current
		DESCRIPTION
				"TYPE: - Number
				 PAGE: - Audio- Embedders- Embedder 1
					NonModal Index  cmdID= 5338  min= 0  max= 31  step= 1  format=   div_scale= 1 
					Min =   Max =   Step =  "
		::= { iqdmx30CmdEntry 5338 }


	iqdmx30EmbeddersEmbedder1NonModalGain5339 OBJECT-TYPE
		SYNTAX		INTEGER
		MAX-ACCESS		read-write
		STATUS			current
		DESCRIPTION
				"TYPE: - Number
				 PAGE: - Audio- Embedders- Embedder 1
					NonModal Gain  cmdID= 5339  min= -720  max= 120  step= 1  format=   div_scale= 10 
					Min =   Max =   Step =  "
		::= { iqdmx30CmdEntry 5339 }


	iqdmx30EmbeddersEmbedder1NonModalIndex5340 OBJECT-TYPE
		SYNTAX		INTEGER
		MAX-ACCESS		read-write
		STATUS			current
		DESCRIPTION
				"TYPE: - Number
				 PAGE: - Audio- Embedders- Embedder 1
					NonModal Index  cmdID= 5340  min= 0  max= 15  step= 1  format=   div_scale= 1 
					Min =   Max =   Step =  "
		::= { iqdmx30CmdEntry 5340 }


	iqdmx30EmbeddersEmbedder1NonModalGain5341 OBJECT-TYPE
		SYNTAX		INTEGER
		MAX-ACCESS		read-write
		STATUS			current
		DESCRIPTION
				"TYPE: - Number
				 PAGE: - Audio- Embedders- Embedder 1
					NonModal Gain  cmdID= 5341  min= -720  max= 120  step= 1  format=   div_scale= 10 
					Min =   Max =   Step =  "
		::= { iqdmx30CmdEntry 5341 }


	iqdmx30EmbeddersEmbedder2Enable OBJECT-TYPE
		SYNTAX		INTEGER { disable(0), enable(1) }
		MAX-ACCESS		read-write
		STATUS			current
		DESCRIPTION
				"TYPE: - Checkbox
				 PAGE: - Audio- Embedders- Embedder 2
					Enable  cmdID= 5067 "
		::= { iqdmx30CmdEntry 5067 }


	iqdmx30EmbeddersEmbedder2SourceLNonPCM5038 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 2
					Source L / Non-PCM  cmdID= 5038 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx30CmdEntry 5038 }


	iqdmx30EmbeddersEmbedder2SourceR5039 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 2
					Source R  cmdID= 5039 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx30CmdEntry 5039 }


	iqdmx30EmbeddersEmbedder2Mute3242 OBJECT-TYPE
		SYNTAX		INTEGER { disable(0), enable(1) }
		MAX-ACCESS		read-write
		STATUS			current
		DESCRIPTION
				"TYPE: - Checkbox
				 PAGE: - Audio- Embedders- Embedder 2
					Mute  cmdID= 3242 "
		::= { iqdmx30CmdEntry 3242 }


	iqdmx30EmbeddersEmbedder2MuteonVbit3274 OBJECT-TYPE
		SYNTAX		INTEGER { disable(0), enable(1) }
		MAX-ACCESS		read-write
		STATUS			current
		DESCRIPTION
				"TYPE: - Checkbox
				 PAGE: - Audio- Embedders- Embedder 2
					Mute on V bit  cmdID= 3274 "
		::= { iqdmx30CmdEntry 3274 }


	iqdmx30EmbeddersEmbedder2InvertL3164 OBJECT-TYPE
		SYNTAX		INTEGER { disable(0), enable(1) }
		MAX-ACCESS		read-write
		STATUS			current
		DESCRIPTION
				"TYPE: - Checkbox
				 PAGE: - Audio- Embedders- Embedder 2
					Invert L  cmdID= 3164 "
		::= { iqdmx30CmdEntry 3164 }


	iqdmx30EmbeddersEmbedder2InvertR3165 OBJECT-TYPE
		SYNTAX		INTEGER { disable(0), enable(1) }
		MAX-ACCESS		read-write
		STATUS			current
		DESCRIPTION
				"TYPE: - Checkbox
				 PAGE: - Audio- Embedders- Embedder 2
					Invert R  cmdID= 3165 "
		::= { iqdmx30CmdEntry 3165 }


	iqdmx30EmbeddersEmbedder2GainL3084 OBJECT-TYPE
		SYNTAX		INTEGER
		MAX-ACCESS		read-write
		STATUS			current
		DESCRIPTION
				"TYPE: - Number
				 PAGE: - Audio- Embedders- Embedder 2
					Gain L  cmdID= 3084  min= -720  max= 120  step= 1  format= %0.1fdB  div_scale= 10 
					Min = -72.0dB  Max = 12.0dB  Step = 0.1dB "
		::= { iqdmx30CmdEntry 3084 }


	iqdmx30EmbeddersEmbedder2GainR3085 OBJECT-TYPE
		SYNTAX		INTEGER
		MAX-ACCESS		read-write
		STATUS			current
		DESCRIPTION
				"TYPE: - Number
				 PAGE: - Audio- Embedders- Embedder 2
					Gain R  cmdID= 3085  min= -720  max= 120  step= 1  format= %0.1fdB  div_scale= 10 
					Min = -72.0dB  Max = 12.0dB  Step = 0.1dB "
		::= { iqdmx30CmdEntry 3085 }


	iqdmx30EmbeddersEmbedder2PairMode3932 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 2
					Pair Mode  cmdID= 3932 
					2 Channel PCM  value= 0  
					Stereo PCM  value= 1  
					Non-PCM  value= 2  "
		::= { iqdmx30CmdEntry 3932 }


	iqdmx30EmbeddersEmbedder2SourceLNonPCM5040 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 2
					Source L / Non-PCM  cmdID= 5040 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx30CmdEntry 5040 }


	iqdmx30EmbeddersEmbedder2SourceR5041 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 2
					Source R  cmdID= 5041 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx30CmdEntry 5041 }


	iqdmx30EmbeddersEmbedder2Mute3243 OBJECT-TYPE
		SYNTAX		INTEGER { disable(0), enable(1) }
		MAX-ACCESS		read-write
		STATUS			current
		DESCRIPTION
				"TYPE: - Checkbox
				 PAGE: - Audio- Embedders- Embedder 2
					Mute  cmdID= 3243 "
		::= { iqdmx30CmdEntry 3243 }


	iqdmx30EmbeddersEmbedder2MuteonVbit3275 OBJECT-TYPE
		SYNTAX		INTEGER { disable(0), enable(1) }
		MAX-ACCESS		read-write
		STATUS			current
		DESCRIPTION
				"TYPE: - Checkbox
				 PAGE: - Audio- Embedders- Embedder 2
					Mute on V bit  cmdID= 3275 "
		::= { iqdmx30CmdEntry 3275 }


	iqdmx30EmbeddersEmbedder2InvertL3166 OBJECT-TYPE
		SYNTAX		INTEGER { disable(0), enable(1) }
		MAX-ACCESS		read-write
		STATUS			current
		DESCRIPTION
				"TYPE: - Checkbox
				 PAGE: - Audio- Embedders- Embedder 2
					Invert L  cmdID= 3166 "
		::= { iqdmx30CmdEntry 3166 }


	iqdmx30EmbeddersEmbedder2InvertR3167 OBJECT-TYPE
		SYNTAX		INTEGER { disable(0), enable(1) }
		MAX-ACCESS		read-write
		STATUS			current
		DESCRIPTION
				"TYPE: - Checkbox
				 PAGE: - Audio- Embedders- Embedder 2
					Invert R  cmdID= 3167 "
		::= { iqdmx30CmdEntry 3167 }


	iqdmx30EmbeddersEmbedder2GainL3086 OBJECT-TYPE
		SYNTAX		INTEGER
		MAX-ACCESS		read-write
		STATUS			current
		DESCRIPTION
				"TYPE: - Number
				 PAGE: - Audio- Embedders- Embedder 2
					Gain L  cmdID= 3086  min= -720  max= 120  step= 1  format= %0.1fdB  div_scale= 10 
					Min = -72.0dB  Max = 12.0dB  Step = 0.1dB "
		::= { iqdmx30CmdEntry 3086 }


	iqdmx30EmbeddersEmbedder2GainR3087 OBJECT-TYPE
		SYNTAX		INTEGER
		MAX-ACCESS		read-write
		STATUS			current
		DESCRIPTION
				"TYPE: - Number
				 PAGE: - Audio- Embedders- Embedder 2
					Gain R  cmdID= 3087  min= -720  max= 120  step= 1  format= %0.1fdB  div_scale= 10 
					Min = -72.0dB  Max = 12.0dB  Step = 0.1dB "
		::= { iqdmx30CmdEntry 3087 }


	iqdmx30EmbeddersEmbedder2PairMode3933 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 2
					Pair Mode  cmdID= 3933 
					2 Channel PCM  value= 0  
					Stereo PCM  value= 1  
					Non-PCM  value= 2  "
		::= { iqdmx30CmdEntry 3933 }


	iqdmx30EmbeddersEmbedder3Enable OBJECT-TYPE
		SYNTAX		INTEGER { disable(0), enable(1) }
		MAX-ACCESS		read-write
		STATUS			current
		DESCRIPTION
				"TYPE: - Checkbox
				 PAGE: - Audio- Embedders- Embedder 3
					Enable  cmdID= 5068 "
		::= { iqdmx30CmdEntry 5068 }


	iqdmx30EmbeddersEmbedder3SourceLNonPCM5042 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 3
					Source L / Non-PCM  cmdID= 5042 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx30CmdEntry 5042 }


	iqdmx30EmbeddersEmbedder3SourceR5043 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 3
					Source R  cmdID= 5043 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx30CmdEntry 5043 }


	iqdmx30EmbeddersEmbedder3Mute3244 OBJECT-TYPE
		SYNTAX		INTEGER { disable(0), enable(1) }
		MAX-ACCESS		read-write
		STATUS			current
		DESCRIPTION
				"TYPE: - Checkbox
				 PAGE: - Audio- Embedders- Embedder 3
					Mute  cmdID= 3244 "
		::= { iqdmx30CmdEntry 3244 }


	iqdmx30EmbeddersEmbedder3MuteonVbit3276 OBJECT-TYPE
		SYNTAX		INTEGER { disable(0), enable(1) }
		MAX-ACCESS		read-write
		STATUS			current
		DESCRIPTION
				"TYPE: - Checkbox
				 PAGE: - Audio- Embedders- Embedder 3
					Mute on V bit  cmdID= 3276 "
		::= { iqdmx30CmdEntry 3276 }


	iqdmx30EmbeddersEmbedder3InvertL3168 OBJECT-TYPE
		SYNTAX		INTEGER { disable(0), enable(1) }
		MAX-ACCESS		read-write
		STATUS			current
		DESCRIPTION
				"TYPE: - Checkbox
				 PAGE: - Audio- Embedders- Embedder 3
					Invert L  cmdID= 3168 "
		::= { iqdmx30CmdEntry 3168 }


	iqdmx30EmbeddersEmbedder3InvertR3169 OBJECT-TYPE
		SYNTAX		INTEGER { disable(0), enable(1) }
		MAX-ACCESS		read-write
		STATUS			current
		DESCRIPTION
				"TYPE: - Checkbox
				 PAGE: - Audio- Embedders- Embedder 3
					Invert R  cmdID= 3169 "
		::= { iqdmx30CmdEntry 3169 }


	iqdmx30EmbeddersEmbedder3GainL3088 OBJECT-TYPE
		SYNTAX		INTEGER
		MAX-ACCESS		read-write
		STATUS			current
		DESCRIPTION
				"TYPE: - Number
				 PAGE: - Audio- Embedders- Embedder 3
					Gain L  cmdID= 3088  min= -720  max= 120  step= 1  format= %0.1fdB  div_scale= 10 
					Min = -72.0dB  Max = 12.0dB  Step = 0.1dB "
		::= { iqdmx30CmdEntry 3088 }


	iqdmx30EmbeddersEmbedder3GainR3089 OBJECT-TYPE
		SYNTAX		INTEGER
		MAX-ACCESS		read-write
		STATUS			current
		DESCRIPTION
				"TYPE: - Number
				 PAGE: - Audio- Embedders- Embedder 3
					Gain R  cmdID= 3089  min= -720  max= 120  step= 1  format= %0.1fdB  div_scale= 10 
					Min = -72.0dB  Max = 12.0dB  Step = 0.1dB "
		::= { iqdmx30CmdEntry 3089 }


	iqdmx30EmbeddersEmbedder3PairMode3934 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 3
					Pair Mode  cmdID= 3934 
					2 Channel PCM  value= 0  
					Stereo PCM  value= 1  
					Non-PCM  value= 2  "
		::= { iqdmx30CmdEntry 3934 }


	iqdmx30EmbeddersEmbedder3SourceLNonPCM5044 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 3
					Source L / Non-PCM  cmdID= 5044 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx30CmdEntry 5044 }


	iqdmx30EmbeddersEmbedder3SourceR5045 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 3
					Source R  cmdID= 5045 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx30CmdEntry 5045 }


	iqdmx30EmbeddersEmbedder3Mute3245 OBJECT-TYPE
		SYNTAX		INTEGER { disable(0), enable(1) }
		MAX-ACCESS		read-write
		STATUS			current
		DESCRIPTION
				"TYPE: - Checkbox
				 PAGE: - Audio- Embedders- Embedder 3
					Mute  cmdID= 3245 "
		::= { iqdmx30CmdEntry 3245 }


	iqdmx30EmbeddersEmbedder3MuteonVbit3277 OBJECT-TYPE
		SYNTAX		INTEGER { disable(0), enable(1) }
		MAX-ACCESS		read-write
		STATUS			current
		DESCRIPTION
				"TYPE: - Checkbox
				 PAGE: - Audio- Embedders- Embedder 3
					Mute on V bit  cmdID= 3277 "
		::= { iqdmx30CmdEntry 3277 }


	iqdmx30EmbeddersEmbedder3InvertL3170 OBJECT-TYPE
		SYNTAX		INTEGER { disable(0), enable(1) }
		MAX-ACCESS		read-write
		STATUS			current
		DESCRIPTION
				"TYPE: - Checkbox
				 PAGE: - Audio- Embedders- Embedder 3
					Invert L  cmdID= 3170 "
		::= { iqdmx30CmdEntry 3170 }


	iqdmx30EmbeddersEmbedder3InvertR3171 OBJECT-TYPE
		SYNTAX		INTEGER { disable(0), enable(1) }
		MAX-ACCESS		read-write
		STATUS			current
		DESCRIPTION
				"TYPE: - Checkbox
				 PAGE: - Audio- Embedders- Embedder 3
					Invert R  cmdID= 3171 "
		::= { iqdmx30CmdEntry 3171 }


	iqdmx30EmbeddersEmbedder3GainL3090 OBJECT-TYPE
		SYNTAX		INTEGER
		MAX-ACCESS		read-write
		STATUS			current
		DESCRIPTION
				"TYPE: - Number
				 PAGE: - Audio- Embedders- Embedder 3
					Gain L  cmdID= 3090  min= -720  max= 120  step= 1  format= %0.1fdB  div_scale= 10 
					Min = -72.0dB  Max = 12.0dB  Step = 0.1dB "
		::= { iqdmx30CmdEntry 3090 }


	iqdmx30EmbeddersEmbedder3GainR3091 OBJECT-TYPE
		SYNTAX		INTEGER
		MAX-ACCESS		read-write
		STATUS			current
		DESCRIPTION
				"TYPE: - Number
				 PAGE: - Audio- Embedders- Embedder 3
					Gain R  cmdID= 3091  min= -720  max= 120  step= 1  format= %0.1fdB  div_scale= 10 
					Min = -72.0dB  Max = 12.0dB  Step = 0.1dB "
		::= { iqdmx30CmdEntry 3091 }


	iqdmx30EmbeddersEmbedder3PairMode3935 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 3
					Pair Mode  cmdID= 3935 
					2 Channel PCM  value= 0  
					Stereo PCM  value= 1  
					Non-PCM  value= 2  "
		::= { iqdmx30CmdEntry 3935 }


	iqdmx30EmbeddersEmbedder4Enable OBJECT-TYPE
		SYNTAX		INTEGER { disable(0), enable(1) }
		MAX-ACCESS		read-write
		STATUS			current
		DESCRIPTION
				"TYPE: - Checkbox
				 PAGE: - Audio- Embedders- Embedder 4
					Enable  cmdID= 5069 "
		::= { iqdmx30CmdEntry 5069 }


	iqdmx30EmbeddersEmbedder4SourceLNonPCM5046 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 4
					Source L / Non-PCM  cmdID= 5046 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx30CmdEntry 5046 }


	iqdmx30EmbeddersEmbedder4SourceR5047 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 4
					Source R  cmdID= 5047 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx30CmdEntry 5047 }


	iqdmx30EmbeddersEmbedder4Mute3246 OBJECT-TYPE
		SYNTAX		INTEGER { disable(0), enable(1) }
		MAX-ACCESS		read-write
		STATUS			current
		DESCRIPTION
				"TYPE: - Checkbox
				 PAGE: - Audio- Embedders- Embedder 4
					Mute  cmdID= 3246 "
		::= { iqdmx30CmdEntry 3246 }


	iqdmx30EmbeddersEmbedder4MuteonVbit3278 OBJECT-TYPE
		SYNTAX		INTEGER { disable(0), enable(1) }
		MAX-ACCESS		read-write
		STATUS			current
		DESCRIPTION
				"TYPE: - Checkbox
				 PAGE: - Audio- Embedders- Embedder 4
					Mute on V bit  cmdID= 3278 "
		::= { iqdmx30CmdEntry 3278 }


	iqdmx30EmbeddersEmbedder4InvertL3172 OBJECT-TYPE
		SYNTAX		INTEGER { disable(0), enable(1) }
		MAX-ACCESS		read-write
		STATUS			current
		DESCRIPTION
				"TYPE: - Checkbox
				 PAGE: - Audio- Embedders- Embedder 4
					Invert L  cmdID= 3172 "
		::= { iqdmx30CmdEntry 3172 }


	iqdmx30EmbeddersEmbedder4InvertR3173 OBJECT-TYPE
		SYNTAX		INTEGER { disable(0), enable(1) }
		MAX-ACCESS		read-write
		STATUS			current
		DESCRIPTION
				"TYPE: - Checkbox
				 PAGE: - Audio- Embedders- Embedder 4
					Invert R  cmdID= 3173 "
		::= { iqdmx30CmdEntry 3173 }


	iqdmx30EmbeddersEmbedder4GainL3092 OBJECT-TYPE
		SYNTAX		INTEGER
		MAX-ACCESS		read-write
		STATUS			current
		DESCRIPTION
				"TYPE: - Number
				 PAGE: - Audio- Embedders- Embedder 4
					Gain L  cmdID= 3092  min= -720  max= 120  step= 1  format= %0.1fdB  div_scale= 10 
					Min = -72.0dB  Max = 12.0dB  Step = 0.1dB "
		::= { iqdmx30CmdEntry 3092 }


	iqdmx30EmbeddersEmbedder4GainR3093 OBJECT-TYPE
		SYNTAX		INTEGER
		MAX-ACCESS		read-write
		STATUS			current
		DESCRIPTION
				"TYPE: - Number
				 PAGE: - Audio- Embedders- Embedder 4
					Gain R  cmdID= 3093  min= -720  max= 120  step= 1  format= %0.1fdB  div_scale= 10 
					Min = -72.0dB  Max = 12.0dB  Step = 0.1dB "
		::= { iqdmx30CmdEntry 3093 }


	iqdmx30EmbeddersEmbedder4PairMode3936 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 4
					Pair Mode  cmdID= 3936 
					2 Channel PCM  value= 0  
					Stereo PCM  value= 1  
					Non-PCM  value= 2  "
		::= { iqdmx30CmdEntry 3936 }


	iqdmx30EmbeddersEmbedder4SourceLNonPCM5048 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 4
					Source L / Non-PCM  cmdID= 5048 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx30CmdEntry 5048 }


	iqdmx30EmbeddersEmbedder4SourceR5049 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 4
					Source R  cmdID= 5049 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx30CmdEntry 5049 }


	iqdmx30EmbeddersEmbedder4Mute3247 OBJECT-TYPE
		SYNTAX		INTEGER { disable(0), enable(1) }
		MAX-ACCESS		read-write
		STATUS			current
		DESCRIPTION
				"TYPE: - Checkbox
				 PAGE: - Audio- Embedders- Embedder 4
					Mute  cmdID= 3247 "
		::= { iqdmx30CmdEntry 3247 }


	iqdmx30EmbeddersEmbedder4MuteonVbit3279 OBJECT-TYPE
		SYNTAX		INTEGER { disable(0), enable(1) }
		MAX-ACCESS		read-write
		STATUS			current
		DESCRIPTION
				"TYPE: - Checkbox
				 PAGE: - Audio- Embedders- Embedder 4
					Mute on V bit  cmdID= 3279 "
		::= { iqdmx30CmdEntry 3279 }


	iqdmx30EmbeddersEmbedder4InvertL3174 OBJECT-TYPE
		SYNTAX		INTEGER { disable(0), enable(1) }
		MAX-ACCESS		read-write
		STATUS			current
		DESCRIPTION
				"TYPE: - Checkbox
				 PAGE: - Audio- Embedders- Embedder 4
					Invert L  cmdID= 3174 "
		::= { iqdmx30CmdEntry 3174 }


	iqdmx30EmbeddersEmbedder4InvertR3175 OBJECT-TYPE
		SYNTAX		INTEGER { disable(0), enable(1) }
		MAX-ACCESS		read-write
		STATUS			current
		DESCRIPTION
				"TYPE: - Checkbox
				 PAGE: - Audio- Embedders- Embedder 4
					Invert R  cmdID= 3175 "
		::= { iqdmx30CmdEntry 3175 }


	iqdmx30EmbeddersEmbedder4GainL3094 OBJECT-TYPE
		SYNTAX		INTEGER
		MAX-ACCESS		read-write
		STATUS			current
		DESCRIPTION
				"TYPE: - Number
				 PAGE: - Audio- Embedders- Embedder 4
					Gain L  cmdID= 3094  min= -720  max= 120  step= 1  format= %0.1fdB  div_scale= 10 
					Min = -72.0dB  Max = 12.0dB  Step = 0.1dB "
		::= { iqdmx30CmdEntry 3094 }


	iqdmx30EmbeddersEmbedder4GainR3095 OBJECT-TYPE
		SYNTAX		INTEGER
		MAX-ACCESS		read-write
		STATUS			current
		DESCRIPTION
				"TYPE: - Number
				 PAGE: - Audio- Embedders- Embedder 4
					Gain R  cmdID= 3095  min= -720  max= 120  step= 1  format= %0.1fdB  div_scale= 10 
					Min = -72.0dB  Max = 12.0dB  Step = 0.1dB "
		::= { iqdmx30CmdEntry 3095 }


	iqdmx30EmbeddersEmbedder4PairMode3937 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 4
					Pair Mode  cmdID= 3937 
					2 Channel PCM  value= 0  
					Stereo PCM  value= 1  
					Non-PCM  value= 2  "
		::= { iqdmx30CmdEntry 3937 }


	iqdmx30AESOutAESOut1SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Audio- AES Out- AES Out 1
					Source L / Non-PCM  cmdID= 5096 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx30CmdEntry 5096 }


	iqdmx30AESOutAESOut1SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Audio- AES Out- AES Out 1
					Source R  cmdID= 5097 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx30CmdEntry 5097 }


	iqdmx30AESOutAESOut1Mute OBJECT-TYPE
		SYNTAX		INTEGER { disable(0), enable(1) }
		MAX-ACCESS		read-write
		STATUS			current
		DESCRIPTION
				"TYPE: - Checkbox
				 PAGE: - Audio- AES Out- AES Out 1
					Mute  cmdID= 3256 "
		::= { iqdmx30CmdEntry 3256 }


	iqdmx30AESOutAESOut1MuteonVbit OBJECT-TYPE
		SYNTAX		INTEGER { disable(0), enable(1) }
		MAX-ACCESS		read-write
		STATUS			current
		DESCRIPTION
				"TYPE: - Checkbox
				 PAGE: - Audio- AES Out- AES Out 1
					Mute on V bit  cmdID= 3288 "
		::= { iqdmx30CmdEntry 3288 }


	iqdmx30AESOutAESOut1InvertL OBJECT-TYPE
		SYNTAX		INTEGER { disable(0), enable(1) }
		MAX-ACCESS		read-write
		STATUS			current
		DESCRIPTION
				"TYPE: - Checkbox
				 PAGE: - Audio- AES Out- AES Out 1
					Invert L  cmdID= 3192 "
		::= { iqdmx30CmdEntry 3192 }


	iqdmx30AESOutAESOut1InvertR OBJECT-TYPE
		SYNTAX		INTEGER { disable(0), enable(1) }
		MAX-ACCESS		read-write
		STATUS			current
		DESCRIPTION
				"TYPE: - Checkbox
				 PAGE: - Audio- AES Out- AES Out 1
					Invert R  cmdID= 3193 "
		::= { iqdmx30CmdEntry 3193 }


	iqdmx30AESOutAESOut1GainL OBJECT-TYPE
		SYNTAX		INTEGER
		MAX-ACCESS		read-write
		STATUS			current
		DESCRIPTION
				"TYPE: - Number
				 PAGE: - Audio- AES Out- AES Out 1
					Gain L  cmdID= 3112  min= -720  max= 120  step= 1  format= %0.1fdB  div_scale= 10 
					Min = -72.0dB  Max = 12.0dB  Step = 0.1dB "
		::= { iqdmx30CmdEntry 3112 }


	iqdmx30AESOutAESOut1GainR OBJECT-TYPE
		SYNTAX		INTEGER
		MAX-ACCESS		read-write
		STATUS			current
		DESCRIPTION
				"TYPE: - Number
				 PAGE: - Audio- AES Out- AES Out 1
					Gain R  cmdID= 3113  min= -720  max= 120  step= 1  format= %0.1fdB  div_scale= 10 
					Min = -72.0dB  Max = 12.0dB  Step = 0.1dB "
		::= { iqdmx30CmdEntry 3113 }


	iqdmx30AESOutAESOut1PairMode OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- AES Out- AES Out 1
					Pair Mode  cmdID= 5112 
					2 Channel PCM  value= 0  
					Stereo PCM  value= 1  
					Non-PCM  value= 2  "
		::= { iqdmx30CmdEntry 5112 }


	iqdmx30AESOutAESOut2SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Audio- AES Out- AES Out 2
					Source L / Non-PCM  cmdID= 5098 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx30CmdEntry 5098 }


	iqdmx30AESOutAESOut2SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Audio- AES Out- AES Out 2
					Source R  cmdID= 5099 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx30CmdEntry 5099 }


	iqdmx30AESOutAESOut2Mute OBJECT-TYPE
		SYNTAX		INTEGER { disable(0), enable(1) }
		MAX-ACCESS		read-write
		STATUS			current
		DESCRIPTION
				"TYPE: - Checkbox
				 PAGE: - Audio- AES Out- AES Out 2
					Mute  cmdID= 3257 "
		::= { iqdmx30CmdEntry 3257 }


	iqdmx30AESOutAESOut2MuteonVbit OBJECT-TYPE
		SYNTAX		INTEGER { disable(0), enable(1) }
		MAX-ACCESS		read-write
		STATUS			current
		DESCRIPTION
				"TYPE: - Checkbox
				 PAGE: - Audio- AES Out- AES Out 2
					Mute on V bit  cmdID= 3289 "
		::= { iqdmx30CmdEntry 3289 }


	iqdmx30AESOutAESOut2InvertL OBJECT-TYPE
		SYNTAX		INTEGER { disable(0), enable(1) }
		MAX-ACCESS		read-write
		STATUS			current
		DESCRIPTION
				"TYPE: - Checkbox
				 PAGE: - Audio- AES Out- AES Out 2
					Invert L  cmdID= 3194 "
		::= { iqdmx30CmdEntry 3194 }


	iqdmx30AESOutAESOut2InvertR OBJECT-TYPE
		SYNTAX		INTEGER { disable(0), enable(1) }
		MAX-ACCESS		read-write
		STATUS			current
		DESCRIPTION
				"TYPE: - Checkbox
				 PAGE: - Audio- AES Out- AES Out 2
					Invert R  cmdID= 3195 "
		::= { iqdmx30CmdEntry 3195 }


	iqdmx30AESOutAESOut2GainL OBJECT-TYPE
		SYNTAX		INTEGER
		MAX-ACCESS		read-write
		STATUS			current
		DESCRIPTION
				"TYPE: - Number
				 PAGE: - Audio- AES Out- AES Out 2
					Gain L  cmdID= 3114  min= -720  max= 120  step= 1  format= %0.1fdB  div_scale= 10 
					Min = -72.0dB  Max = 12.0dB  Step = 0.1dB "
		::= { iqdmx30CmdEntry 3114 }


	iqdmx30AESOutAESOut2GainR OBJECT-TYPE
		SYNTAX		INTEGER
		MAX-ACCESS		read-write
		STATUS			current
		DESCRIPTION
				"TYPE: - Number
				 PAGE: - Audio- AES Out- AES Out 2
					Gain R  cmdID= 3115  min= -720  max= 120  step= 1  format= %0.1fdB  div_scale= 10 
					Min = -72.0dB  Max = 12.0dB  Step = 0.1dB "
		::= { iqdmx30CmdEntry 3115 }


	iqdmx30AESOutAESOut2PairMode OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- AES Out- AES Out 2
					Pair Mode  cmdID= 5113 
					2 Channel PCM  value= 0  
					Stereo PCM  value= 1  
					Non-PCM  value= 2  "
		::= { iqdmx30CmdEntry 5113 }


	iqdmx30AESOutAESOut3SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Audio- AES Out- AES Out 3
					Source L / Non-PCM  cmdID= 5100 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx30CmdEntry 5100 }


	iqdmx30AESOutAESOut3SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Audio- AES Out- AES Out 3
					Source R  cmdID= 5101 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx30CmdEntry 5101 }


	iqdmx30AESOutAESOut3Mute OBJECT-TYPE
		SYNTAX		INTEGER { disable(0), enable(1) }
		MAX-ACCESS		read-write
		STATUS			current
		DESCRIPTION
				"TYPE: - Checkbox
				 PAGE: - Audio- AES Out- AES Out 3
					Mute  cmdID= 3258 "
		::= { iqdmx30CmdEntry 3258 }


	iqdmx30AESOutAESOut3MuteonVbit OBJECT-TYPE
		SYNTAX		INTEGER { disable(0), enable(1) }
		MAX-ACCESS		read-write
		STATUS			current
		DESCRIPTION
				"TYPE: - Checkbox
				 PAGE: - Audio- AES Out- AES Out 3
					Mute on V bit  cmdID= 3290 "
		::= { iqdmx30CmdEntry 3290 }


	iqdmx30AESOutAESOut3InvertL OBJECT-TYPE
		SYNTAX		INTEGER { disable(0), enable(1) }
		MAX-ACCESS		read-write
		STATUS			current
		DESCRIPTION
				"TYPE: - Checkbox
				 PAGE: - Audio- AES Out- AES Out 3
					Invert L  cmdID= 3196 "
		::= { iqdmx30CmdEntry 3196 }


	iqdmx30AESOutAESOut3InvertR OBJECT-TYPE
		SYNTAX		INTEGER { disable(0), enable(1) }
		MAX-ACCESS		read-write
		STATUS			current
		DESCRIPTION
				"TYPE: - Checkbox
				 PAGE: - Audio- AES Out- AES Out 3
					Invert R  cmdID= 3197 "
		::= { iqdmx30CmdEntry 3197 }


	iqdmx30AESOutAESOut3GainL OBJECT-TYPE
		SYNTAX		INTEGER
		MAX-ACCESS		read-write
		STATUS			current
		DESCRIPTION
				"TYPE: - Number
				 PAGE: - Audio- AES Out- AES Out 3
					Gain L  cmdID= 3116  min= -720  max= 120  step= 1  format= %0.1fdB  div_scale= 10 
					Min = -72.0dB  Max = 12.0dB  Step = 0.1dB "
		::= { iqdmx30CmdEntry 3116 }


	iqdmx30AESOutAESOut3GainR OBJECT-TYPE
		SYNTAX		INTEGER
		MAX-ACCESS		read-write
		STATUS			current
		DESCRIPTION
				"TYPE: - Number
				 PAGE: - Audio- AES Out- AES Out 3
					Gain R  cmdID= 3117  min= -720  max= 120  step= 1  format= %0.1fdB  div_scale= 10 
					Min = -72.0dB  Max = 12.0dB  Step = 0.1dB "
		::= { iqdmx30CmdEntry 3117 }


	iqdmx30AESOutAESOut3PairMode OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- AES Out- AES Out 3
					Pair Mode  cmdID= 5114 
					2 Channel PCM  value= 0  
					Stereo PCM  value= 1  
					Non-PCM  value= 2  "
		::= { iqdmx30CmdEntry 5114 }


	iqdmx30AESOutAESOut4SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Audio- AES Out- AES Out 4
					Source L / Non-PCM  cmdID= 5102 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx30CmdEntry 5102 }


	iqdmx30AESOutAESOut4SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Audio- AES Out- AES Out 4
					Source R  cmdID= 5103 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx30CmdEntry 5103 }


	iqdmx30AESOutAESOut4Mute OBJECT-TYPE
		SYNTAX		INTEGER { disable(0), enable(1) }
		MAX-ACCESS		read-write
		STATUS			current
		DESCRIPTION
				"TYPE: - Checkbox
				 PAGE: - Audio- AES Out- AES Out 4
					Mute  cmdID= 3259 "
		::= { iqdmx30CmdEntry 3259 }


	iqdmx30AESOutAESOut4MuteonVbit OBJECT-TYPE
		SYNTAX		INTEGER { disable(0), enable(1) }
		MAX-ACCESS		read-write
		STATUS			current
		DESCRIPTION
				"TYPE: - Checkbox
				 PAGE: - Audio- AES Out- AES Out 4
					Mute on V bit  cmdID= 3291 "
		::= { iqdmx30CmdEntry 3291 }


	iqdmx30AESOutAESOut4InvertL OBJECT-TYPE
		SYNTAX		INTEGER { disable(0), enable(1) }
		MAX-ACCESS		read-write
		STATUS			current
		DESCRIPTION
				"TYPE: - Checkbox
				 PAGE: - Audio- AES Out- AES Out 4
					Invert L  cmdID= 3198 "
		::= { iqdmx30CmdEntry 3198 }


	iqdmx30AESOutAESOut4InvertR OBJECT-TYPE
		SYNTAX		INTEGER { disable(0), enable(1) }
		MAX-ACCESS		read-write
		STATUS			current
		DESCRIPTION
				"TYPE: - Checkbox
				 PAGE: - Audio- AES Out- AES Out 4
					Invert R  cmdID= 3199 "
		::= { iqdmx30CmdEntry 3199 }


	iqdmx30AESOutAESOut4GainL OBJECT-TYPE
		SYNTAX		INTEGER
		MAX-ACCESS		read-write
		STATUS			current
		DESCRIPTION
				"TYPE: - Number
				 PAGE: - Audio- AES Out- AES Out 4
					Gain L  cmdID= 3118  min= -720  max= 120  step= 1  format= %0.1fdB  div_scale= 10 
					Min = -72.0dB  Max = 12.0dB  Step = 0.1dB "
		::= { iqdmx30CmdEntry 3118 }


	iqdmx30AESOutAESOut4GainR OBJECT-TYPE
		SYNTAX		INTEGER
		MAX-ACCESS		read-write
		STATUS			current
		DESCRIPTION
				"TYPE: - Number
				 PAGE: - Audio- AES Out- AES Out 4
					Gain R  cmdID= 3119  min= -720  max= 120  step= 1  format= %0.1fdB  div_scale= 10 
					Min = -72.0dB  Max = 12.0dB  Step = 0.1dB "
		::= { iqdmx30CmdEntry 3119 }


	iqdmx30AESOutAESOut4PairMode OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- AES Out- AES Out 4
					Pair Mode  cmdID= 5115 
					2 Channel PCM  value= 0  
					Stereo PCM  value= 1  
					Non-PCM  value= 2  "
		::= { iqdmx30CmdEntry 5115 }


	iqdmx30AESOutAESOut5SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Audio- AES Out- AES Out 5
					Source L / Non-PCM  cmdID= 5104 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx30CmdEntry 5104 }


	iqdmx30AESOutAESOut5SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Audio- AES Out- AES Out 5
					Source R  cmdID= 5105 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx30CmdEntry 5105 }


	iqdmx30AESOutAESOut5Mute OBJECT-TYPE
		SYNTAX		INTEGER { disable(0), enable(1) }
		MAX-ACCESS		read-write
		STATUS			current
		DESCRIPTION
				"TYPE: - Checkbox
				 PAGE: - Audio- AES Out- AES Out 5
					Mute  cmdID= 3260 "
		::= { iqdmx30CmdEntry 3260 }


	iqdmx30AESOutAESOut5MuteonVbit OBJECT-TYPE
		SYNTAX		INTEGER { disable(0), enable(1) }
		MAX-ACCESS		read-write
		STATUS			current
		DESCRIPTION
				"TYPE: - Checkbox
				 PAGE: - Audio- AES Out- AES Out 5
					Mute on V bit  cmdID= 3292 "
		::= { iqdmx30CmdEntry 3292 }


	iqdmx30AESOutAESOut5InvertL OBJECT-TYPE
		SYNTAX		INTEGER { disable(0), enable(1) }
		MAX-ACCESS		read-write
		STATUS			current
		DESCRIPTION
				"TYPE: - Checkbox
				 PAGE: - Audio- AES Out- AES Out 5
					Invert L  cmdID= 3200 "
		::= { iqdmx30CmdEntry 3200 }


	iqdmx30AESOutAESOut5InvertR OBJECT-TYPE
		SYNTAX		INTEGER { disable(0), enable(1) }
		MAX-ACCESS		read-write
		STATUS			current
		DESCRIPTION
				"TYPE: - Checkbox
				 PAGE: - Audio- AES Out- AES Out 5
					Invert R  cmdID= 3201 "
		::= { iqdmx30CmdEntry 3201 }


	iqdmx30AESOutAESOut5GainL OBJECT-TYPE
		SYNTAX		INTEGER
		MAX-ACCESS		read-write
		STATUS			current
		DESCRIPTION
				"TYPE: - Number
				 PAGE: - Audio- AES Out- AES Out 5
					Gain L  cmdID= 3120  min= -720  max= 120  step= 1  format= %0.1fdB  div_scale= 10 
					Min = -72.0dB  Max = 12.0dB  Step = 0.1dB "
		::= { iqdmx30CmdEntry 3120 }


	iqdmx30AESOutAESOut5GainR OBJECT-TYPE
		SYNTAX		INTEGER
		MAX-ACCESS		read-write
		STATUS			current
		DESCRIPTION
				"TYPE: - Number
				 PAGE: - Audio- AES Out- AES Out 5
					Gain R  cmdID= 3121  min= -720  max= 120  step= 1  format= %0.1fdB  div_scale= 10 
					Min = -72.0dB  Max = 12.0dB  Step = 0.1dB "
		::= { iqdmx30CmdEntry 3121 }


	iqdmx30AESOutAESOut5PairMode OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- AES Out- AES Out 5
					Pair Mode  cmdID= 5116 
					2 Channel PCM  value= 0  
					Stereo PCM  value= 1  
					Non-PCM  value= 2  "
		::= { iqdmx30CmdEntry 5116 }


	iqdmx30AESOutAESOut6SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Audio- AES Out- AES Out 6
					Source L / Non-PCM  cmdID= 5106 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx30CmdEntry 5106 }


	iqdmx30AESOutAESOut6SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Audio- AES Out- AES Out 6
					Source R  cmdID= 5107 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx30CmdEntry 5107 }


	iqdmx30AESOutAESOut6Mute OBJECT-TYPE
		SYNTAX		INTEGER { disable(0), enable(1) }
		MAX-ACCESS		read-write
		STATUS			current
		DESCRIPTION
				"TYPE: - Checkbox
				 PAGE: - Audio- AES Out- AES Out 6
					Mute  cmdID= 3261 "
		::= { iqdmx30CmdEntry 3261 }


	iqdmx30AESOutAESOut6MuteonVbit OBJECT-TYPE
		SYNTAX		INTEGER { disable(0), enable(1) }
		MAX-ACCESS		read-write
		STATUS			current
		DESCRIPTION
				"TYPE: - Checkbox
				 PAGE: - Audio- AES Out- AES Out 6
					Mute on V bit  cmdID= 3293 "
		::= { iqdmx30CmdEntry 3293 }


	iqdmx30AESOutAESOut6InvertL OBJECT-TYPE
		SYNTAX		INTEGER { disable(0), enable(1) }
		MAX-ACCESS		read-write
		STATUS			current
		DESCRIPTION
				"TYPE: - Checkbox
				 PAGE: - Audio- AES Out- AES Out 6
					Invert L  cmdID= 3202 "
		::= { iqdmx30CmdEntry 3202 }


	iqdmx30AESOutAESOut6InvertR OBJECT-TYPE
		SYNTAX		INTEGER { disable(0), enable(1) }
		MAX-ACCESS		read-write
		STATUS			current
		DESCRIPTION
				"TYPE: - Checkbox
				 PAGE: - Audio- AES Out- AES Out 6
					Invert R  cmdID= 3203 "
		::= { iqdmx30CmdEntry 3203 }


	iqdmx30AESOutAESOut6GainL OBJECT-TYPE
		SYNTAX		INTEGER
		MAX-ACCESS		read-write
		STATUS			current
		DESCRIPTION
				"TYPE: - Number
				 PAGE: - Audio- AES Out- AES Out 6
					Gain L  cmdID= 3122  min= -720  max= 120  step= 1  format= %0.1fdB  div_scale= 10 
					Min = -72.0dB  Max = 12.0dB  Step = 0.1dB "
		::= { iqdmx30CmdEntry 3122 }


	iqdmx30AESOutAESOut6GainR OBJECT-TYPE
		SYNTAX		INTEGER
		MAX-ACCESS		read-write
		STATUS			current
		DESCRIPTION
				"TYPE: - Number
				 PAGE: - Audio- AES Out- AES Out 6
					Gain R  cmdID= 3123  min= -720  max= 120  step= 1  format= %0.1fdB  div_scale= 10 
					Min = -72.0dB  Max = 12.0dB  Step = 0.1dB "
		::= { iqdmx30CmdEntry 3123 }


	iqdmx30AESOutAESOut6PairMode OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- AES Out- AES Out 6
					Pair Mode  cmdID= 5117 
					2 Channel PCM  value= 0  
					Stereo PCM  value= 1  
					Non-PCM  value= 2  "
		::= { iqdmx30CmdEntry 5117 }


	iqdmx30AESOutAESOut7SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Audio- AES Out- AES Out 7
					Source L / Non-PCM  cmdID= 5108 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx30CmdEntry 5108 }


	iqdmx30AESOutAESOut7SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Audio- AES Out- AES Out 7
					Source R  cmdID= 5109 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx30CmdEntry 5109 }


	iqdmx30AESOutAESOut7Mute OBJECT-TYPE
		SYNTAX		INTEGER { disable(0), enable(1) }
		MAX-ACCESS		read-write
		STATUS			current
		DESCRIPTION
				"TYPE: - Checkbox
				 PAGE: - Audio- AES Out- AES Out 7
					Mute  cmdID= 3262 "
		::= { iqdmx30CmdEntry 3262 }


	iqdmx30AESOutAESOut7MuteonVbit OBJECT-TYPE
		SYNTAX		INTEGER { disable(0), enable(1) }
		MAX-ACCESS		read-write
		STATUS			current
		DESCRIPTION
				"TYPE: - Checkbox
				 PAGE: - Audio- AES Out- AES Out 7
					Mute on V bit  cmdID= 3294 "
		::= { iqdmx30CmdEntry 3294 }


	iqdmx30AESOutAESOut7InvertL OBJECT-TYPE
		SYNTAX		INTEGER { disable(0), enable(1) }
		MAX-ACCESS		read-write
		STATUS			current
		DESCRIPTION
				"TYPE: - Checkbox
				 PAGE: - Audio- AES Out- AES Out 7
					Invert L  cmdID= 3204 "
		::= { iqdmx30CmdEntry 3204 }


	iqdmx30AESOutAESOut7InvertR OBJECT-TYPE
		SYNTAX		INTEGER { disable(0), enable(1) }
		MAX-ACCESS		read-write
		STATUS			current
		DESCRIPTION
				"TYPE: - Checkbox
				 PAGE: - Audio- AES Out- AES Out 7
					Invert R  cmdID= 3205 "
		::= { iqdmx30CmdEntry 3205 }


	iqdmx30AESOutAESOut7GainL OBJECT-TYPE
		SYNTAX		INTEGER
		MAX-ACCESS		read-write
		STATUS			current
		DESCRIPTION
				"TYPE: - Number
				 PAGE: - Audio- AES Out- AES Out 7
					Gain L  cmdID= 3124  min= -720  max= 120  step= 1  format= %0.1fdB  div_scale= 10 
					Min = -72.0dB  Max = 12.0dB  Step = 0.1dB "
		::= { iqdmx30CmdEntry 3124 }


	iqdmx30AESOutAESOut7GainR OBJECT-TYPE
		SYNTAX		INTEGER
		MAX-ACCESS		read-write
		STATUS			current
		DESCRIPTION
				"TYPE: - Number
				 PAGE: - Audio- AES Out- AES Out 7
					Gain R  cmdID= 3125  min= -720  max= 120  step= 1  format= %0.1fdB  div_scale= 10 
					Min = -72.0dB  Max = 12.0dB  Step = 0.1dB "
		::= { iqdmx30CmdEntry 3125 }


	iqdmx30AESOutAESOut7PairMode OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- AES Out- AES Out 7
					Pair Mode  cmdID= 5118 
					2 Channel PCM  value= 0  
					Stereo PCM  value= 1  
					Non-PCM  value= 2  "
		::= { iqdmx30CmdEntry 5118 }


	iqdmx30AESOutAESOut8SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Audio- AES Out- AES Out 8
					Source L / Non-PCM  cmdID= 5110 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx30CmdEntry 5110 }


	iqdmx30AESOutAESOut8SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Audio- AES Out- AES Out 8
					Source R  cmdID= 5111 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx30CmdEntry 5111 }


	iqdmx30AESOutAESOut8Mute OBJECT-TYPE
		SYNTAX		INTEGER { disable(0), enable(1) }
		MAX-ACCESS		read-write
		STATUS			current
		DESCRIPTION
				"TYPE: - Checkbox
				 PAGE: - Audio- AES Out- AES Out 8
					Mute  cmdID= 3263 "
		::= { iqdmx30CmdEntry 3263 }


	iqdmx30AESOutAESOut8MuteonVbit OBJECT-TYPE
		SYNTAX		INTEGER { disable(0), enable(1) }
		MAX-ACCESS		read-write
		STATUS			current
		DESCRIPTION
				"TYPE: - Checkbox
				 PAGE: - Audio- AES Out- AES Out 8
					Mute on V bit  cmdID= 3295 "
		::= { iqdmx30CmdEntry 3295 }


	iqdmx30AESOutAESOut8InvertL OBJECT-TYPE
		SYNTAX		INTEGER { disable(0), enable(1) }
		MAX-ACCESS		read-write
		STATUS			current
		DESCRIPTION
				"TYPE: - Checkbox
				 PAGE: - Audio- AES Out- AES Out 8
					Invert L  cmdID= 3206 "
		::= { iqdmx30CmdEntry 3206 }


	iqdmx30AESOutAESOut8InvertR OBJECT-TYPE
		SYNTAX		INTEGER { disable(0), enable(1) }
		MAX-ACCESS		read-write
		STATUS			current
		DESCRIPTION
				"TYPE: - Checkbox
				 PAGE: - Audio- AES Out- AES Out 8
					Invert R  cmdID= 3207 "
		::= { iqdmx30CmdEntry 3207 }


	iqdmx30AESOutAESOut8GainL OBJECT-TYPE
		SYNTAX		INTEGER
		MAX-ACCESS		read-write
		STATUS			current
		DESCRIPTION
				"TYPE: - Number
				 PAGE: - Audio- AES Out- AES Out 8
					Gain L  cmdID= 3126  min= -720  max= 120  step= 1  format= %0.1fdB  div_scale= 10 
					Min = -72.0dB  Max = 12.0dB  Step = 0.1dB "
		::= { iqdmx30CmdEntry 3126 }


	iqdmx30AESOutAESOut8GainR OBJECT-TYPE
		SYNTAX		INTEGER
		MAX-ACCESS		read-write
		STATUS			current
		DESCRIPTION
				"TYPE: - Number
				 PAGE: - Audio- AES Out- AES Out 8
					Gain R  cmdID= 3127  min= -720  max= 120  step= 1  format= %0.1fdB  div_scale= 10 
					Min = -72.0dB  Max = 12.0dB  Step = 0.1dB "
		::= { iqdmx30CmdEntry 3127 }


	iqdmx30AESOutAESOut8PairMode OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- AES Out- AES Out 8
					Pair Mode  cmdID= 5119 
					2 Channel PCM  value= 0  
					Stereo PCM  value= 1  
					Non-PCM  value= 2  "
		::= { iqdmx30CmdEntry 5119 }


	iqdmx30AudioDelayDelaysVideoDelay OBJECT-TYPE
		SYNTAX		INTEGER { disable(0), enable(1) }
		MAX-ACCESS		read-write
		STATUS			current
		DESCRIPTION
				"TYPE: - Checkbox
				 PAGE: - Audio
					Video Delay  cmdID= 5078 "
		::= { iqdmx30CmdEntry 5078 }


	iqdmx30AudioDelayDelaysManualDelay OBJECT-TYPE
		SYNTAX		INTEGER { disable(0), enable(1) }
		MAX-ACCESS		read-write
		STATUS			current
		DESCRIPTION
				"TYPE: - Checkbox
				 PAGE: - Audio
					Manual Delay  cmdID= 5079 "
		::= { iqdmx30CmdEntry 5079 }


	iqdmx30AudioDelayDelaysCoarseDelay OBJECT-TYPE
		SYNTAX		INTEGER
		MAX-ACCESS		read-write
		STATUS			current
		DESCRIPTION
				"TYPE: - Number
				 PAGE: - Audio
					Coarse Delay  cmdID= 5075  min= 0  max= 1750  step= 5  format= %5.3fs  div_scale= 1000 
					Min = 0.000s  Max = 1.750s  Step = 0.005s "
		::= { iqdmx30CmdEntry 5075 }


	iqdmx30AudioDelayDelaysFineDelay OBJECT-TYPE
		SYNTAX		INTEGER
		MAX-ACCESS		read-write
		STATUS			current
		DESCRIPTION
				"TYPE: - Number
				 PAGE: - Audio
					Fine Delay  cmdID= 5077  min= -2500  max= 2500  step= 5  format= %0.1fms  div_scale= 10 
					Min = -250.0ms  Max = 250.0ms  Step = 0.5ms "
		::= { iqdmx30CmdEntry 5077 }


	iqdmx30AudioDelayDelayStatusTotalDelay OBJECT-TYPE
		SYNTAX		RollCallString
		MAX-ACCESS		read-only
		STATUS			current
		DESCRIPTION
				"TYPE: - Display
				 PAGE: - Audio
					Total Delay  cmdID= 5084  format=   "
		::= { iqdmx30CmdEntry 5084 }


	iqdmx30AudioDelayDelayStatusVideoDelay OBJECT-TYPE
		SYNTAX		RollCallString
		MAX-ACCESS		read-only
		STATUS			current
		DESCRIPTION
				"TYPE: - Display
				 PAGE: - Audio
					Video Delay  cmdID= 5074  format=   "
		::= { iqdmx30CmdEntry 5074 }


	iqdmx30AudioDelayDelayStatusManualDelay OBJECT-TYPE
		SYNTAX		RollCallString
		MAX-ACCESS		read-only
		STATUS			current
		DESCRIPTION
				"TYPE: - Display
				 PAGE: - Audio
					Manual Delay  cmdID= 5076  format=   "
		::= { iqdmx30CmdEntry 5076 }


	iqdmx30AudioDolbyEDolbyEAutoAlign OBJECT-TYPE
		SYNTAX		INTEGER { disable(0), enable(1) }
		MAX-ACCESS		read-write
		STATUS			current
		DESCRIPTION
				"TYPE: - Checkbox
				 PAGE: - Audio
					DolbyE Auto Align  cmdID= 5032 "
		::= { iqdmx30CmdEntry 5032 }


	iqdmx30AudioDolbyEUserDolbyELine OBJECT-TYPE
		SYNTAX		INTEGER { disable(0), enable(1) }
		MAX-ACCESS		read-write
		STATUS			current
		DESCRIPTION
				"TYPE: - Checkbox
				 PAGE: - Audio
					User DolbyE Line  cmdID= 6701 "
		::= { iqdmx30CmdEntry 6701 }


	iqdmx30AudioDolbyEDolbyEAutoLineNo OBJECT-TYPE
		SYNTAX		INTEGER
		MAX-ACCESS		read-write
		STATUS			current
		DESCRIPTION
				"TYPE: - Number
				 PAGE: - Audio
					DolbyE Auto Line No  cmdID= 6703  min= 8  max= 22  step= 1  format= %0.0f  div_scale= 1 
					Min = 8  Max = 22  Step = 1 "
		::= { iqdmx30CmdEntry 6703 }


	iqdmx30AudioDolbyELineStandard OBJECT-TYPE
		SYNTAX		INTEGER
		MAX-ACCESS		read-write
		STATUS			current
		DESCRIPTION
				"TYPE: - Number
				 PAGE: - Audio
					Line Standard  cmdID= 6700  min= 0  max= 10  step= 1  format= %0.0f  div_scale= 1 
					Min = 0  Max = 10  Step = 1 "
		::= { iqdmx30CmdEntry 6700 }


	iqdmx30AudioToneFrequency OBJECT-TYPE
		SYNTAX		INTEGER
		MAX-ACCESS		read-write
		STATUS			current
		DESCRIPTION
				"TYPE: - Number
				 PAGE: - Audio
					Frequency  cmdID= 2487  min= 100  max= 10000  step= 100  format= %5.0fHz  div_scale= 1 
					Min =   100Hz  Max = 10000Hz  Step =   100Hz "
		::= { iqdmx30CmdEntry 2487 }


	iqdmx30AudioToneChannelident OBJECT-TYPE
		SYNTAX		INTEGER { disable(0), enable(1) }
		MAX-ACCESS		read-write
		STATUS			current
		DESCRIPTION
				"TYPE: - Checkbox
				 PAGE: - Audio
					Channel ident  cmdID= 5030 "
		::= { iqdmx30CmdEntry 5030 }


	iqdmx30AudioAudioMonitorSilenceLevel OBJECT-TYPE
		SYNTAX		INTEGER
		MAX-ACCESS		read-write
		STATUS			current
		DESCRIPTION
				"TYPE: - Number
				 PAGE: - Audio
					Silence Level  cmdID= 3061  min= -80  max= 0  step= 1  format= %1.0f dB  div_scale= 1 
					Min = -80 dB  Max = 0 dB  Step = 1 dB "
		::= { iqdmx30CmdEntry 3061 }


	iqdmx30AudioAudioMonitorOverloadLevel OBJECT-TYPE
		SYNTAX		INTEGER
		MAX-ACCESS		read-write
		STATUS			current
		DESCRIPTION
				"TYPE: - Number
				 PAGE: - Audio
					Overload Level  cmdID= 3064  min= -80  max= 0  step= 1  format= %1.0f dB  div_scale= 1 
					Min = -80 dB  Max = 0 dB  Step = 1 dB "
		::= { iqdmx30CmdEntry 3064 }


	iqdmx30AudioAudioMonitorWarningTimer OBJECT-TYPE
		SYNTAX		INTEGER
		MAX-ACCESS		read-write
		STATUS			current
		DESCRIPTION
				"TYPE: - Number
				 PAGE: - Audio
					Warning Timer  cmdID= 3065  min= 1  max= 20  step= 1  format= %1.0f sec  div_scale= 1 
					Min = 1 sec  Max = 20 sec  Step = 1 sec "
		::= { iqdmx30CmdEntry 3065 }


	iqdmx30VideoDelayFreerunFrequency OBJECT-TYPE
		SYNTAX		INTEGER
		MAX-ACCESS		read-write
		STATUS			current
		DESCRIPTION
				"TYPE: - Number
					Freerun Frequency  cmdID= 2449  min= -200  max= 200  step= 1  format= %.0f  div_scale= 1 
					Min = -200  Max = 200  Step = 1 "
		::= { iqdmx30CmdEntry 2449 }


	iqdmx30VideoDelayVideoHdelay OBJECT-TYPE
		SYNTAX		INTEGER
		MAX-ACCESS		read-write
		STATUS			current
		DESCRIPTION
				"TYPE: - Number
					Video H delay  cmdID= 3794  min= 0  max= 2640  step= 1  format= %.0f pixels  div_scale= 1 
					Min = 0 pixels  Max = 2640 pixels  Step = 1 pixels "
		::= { iqdmx30CmdEntry 3794 }


	iqdmx30VideoDelayVideoVdelay OBJECT-TYPE
		SYNTAX		INTEGER
		MAX-ACCESS		read-write
		STATUS			current
		DESCRIPTION
				"TYPE: - Number
					Video V delay  cmdID= 3795  min= 0  max= 1125  step= 1  format= %.0f lines  div_scale= 1 
					Min = 0 lines  Max = 1125 lines  Step = 1 lines "
		::= { iqdmx30CmdEntry 3795 }


	iqdmx30VideoDelayVideoFdelay OBJECT-TYPE
		SYNTAX		INTEGER
		MAX-ACCESS		read-write
		STATUS			current
		DESCRIPTION
				"TYPE: - Number
					Video F delay  cmdID= 3796  min= 0  max= 9  step= 1  format= %.0f frames  div_scale= 1 
					Min = 0 frames  Max = 9 frames  Step = 1 frames "
		::= { iqdmx30CmdEntry 3796 }


	iqdmx30VideoDelayGenlocksaveindex OBJECT-TYPE
		SYNTAX		INTEGER
		MAX-ACCESS		read-write
		STATUS			current
		DESCRIPTION
				"TYPE: - Number
					Genlock save index  cmdID= 3991  min= 0  max= 10  step= 1  format= %.0f  div_scale= 1 
					Min = 0  Max = 10  Step = 1 "
		::= { iqdmx30CmdEntry 3991 }


	iqdmx30VideoDelayVideoHdelaysave OBJECT-TYPE
		SYNTAX		INTEGER
		MAX-ACCESS		read-write
		STATUS			current
		DESCRIPTION
				"TYPE: - Number
					Video H delay save  cmdID= 3994  min= 0  max= 2640  step= 1  format= %.0f pixels  div_scale= 1 
					Min = 0 pixels  Max = 2640 pixels  Step = 1 pixels "
		::= { iqdmx30CmdEntry 3994 }


	iqdmx30VideoDelayVideoVdelaysave OBJECT-TYPE
		SYNTAX		INTEGER
		MAX-ACCESS		read-write
		STATUS			current
		DESCRIPTION
				"TYPE: - Number
					Video V delay save  cmdID= 3995  min= 0  max= 1125  step= 1  format= %.0f lines  div_scale= 1 
					Min = 0 lines  Max = 1125 lines  Step = 1 lines "
		::= { iqdmx30CmdEntry 3995 }


	iqdmx30StatusStatusDisplay OBJECT-TYPE
		SYNTAX		INTEGER {
							val-Video-Status(0),
							val-Audio-Input-Status(1)
							}
		MAX-ACCESS		read-write
		STATUS			current
		DESCRIPTION
				"TYPE: - RadiobuttonList
					Status Display  cmdID= 1915 
					Video Status  value= 0  
					Audio Input Status  value= 1  "
		::= { iqdmx30CmdEntry 1915 }


	iqdmx30StatusProduct OBJECT-TYPE
		SYNTAX		RollCallString
		MAX-ACCESS		read-only
		STATUS			current
		DESCRIPTION
				"TYPE: - Display
					Product  cmdID= 5000  format=   "
		::= { iqdmx30CmdEntry 5000 }


	iqdmx30StatusSoftwareVersion OBJECT-TYPE
		SYNTAX		RollCallString
		MAX-ACCESS		read-only
		STATUS			current
		DESCRIPTION
				"TYPE: - Display
					Software Version  cmdID= 2  format=   "
		::= { iqdmx30CmdEntry 2 }


	iqdmx30StatusSerialNo OBJECT-TYPE
		SYNTAX		RollCallString
		MAX-ACCESS		read-only
		STATUS			current
		DESCRIPTION
				"TYPE: - Display
					Serial No  cmdID= 1  format=   "
		::= { iqdmx30CmdEntry 1 }


	iqdmx30StatusFactoryDefaults OBJECT-TYPE
		SYNTAX		INTEGER { noAction(0),val-Factory-Defaults(1) }
		MAX-ACCESS		read-write
		STATUS			current
		DESCRIPTION
				"TYPE: - Button
					Factory Defaults  cmdID= 5020  value= 1  "
		::= { iqdmx30CmdEntry 5020 }


	iqdmx30StatusDefaultSetting OBJECT-TYPE
		SYNTAX		INTEGER { noAction(0),val-Default-Setting(1) }
		MAX-ACCESS		read-write
		STATUS			current
		DESCRIPTION
				"TYPE: - Button
					Default Setting  cmdID= 5021  value= 1  "
		::= { iqdmx30CmdEntry 5021 }


	iqdmx30StatusRestart OBJECT-TYPE
		SYNTAX		INTEGER { noAction(0),val-Restart(1) }
		MAX-ACCESS		read-write
		STATUS			current
		DESCRIPTION
				"TYPE: - Button
					Restart  cmdID= 4  value= 1  "
		::= { iqdmx30CmdEntry 4 }


	iqdmx30StatusBuild OBJECT-TYPE
		SYNTAX		RollCallString
		MAX-ACCESS		read-only
		STATUS			current
		DESCRIPTION
				"TYPE: - Display
					Build  cmdID= 5  format=   "
		::= { iqdmx30CmdEntry 5 }


	iqdmx30StatusPCB OBJECT-TYPE
		SYNTAX		RollCallString
		MAX-ACCESS		read-only
		STATUS			current
		DESCRIPTION
				"TYPE: - Display
					PCB  cmdID= 6  format=   "
		::= { iqdmx30CmdEntry 6 }


	iqdmx30StatusKOSVersion OBJECT-TYPE
		SYNTAX		RollCallString
		MAX-ACCESS		read-only
		STATUS			current
		DESCRIPTION
				"TYPE: - Display
					KOS Version  cmdID= 7  format=   "
		::= { iqdmx30CmdEntry 7 }


	iqdmx30StatusFirmwareVersion OBJECT-TYPE
		SYNTAX		RollCallString
		MAX-ACCESS		read-only
		STATUS			current
		DESCRIPTION
				"TYPE: - Display
					Firmware Version  cmdID= 5001  format=   "
		::= { iqdmx30CmdEntry 5001 }


	iqdmx30StatusUpTime OBJECT-TYPE
		SYNTAX		RollCallString
		MAX-ACCESS		read-only
		STATUS			current
		DESCRIPTION
				"TYPE: - Display
					Up Time  cmdID= 8  format=   "
		::= { iqdmx30CmdEntry 8 }


	iqdmx30MemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
					Sel Memory  cmdID= 37101 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqdmx30CmdEntry 37101 }


	iqdmx30MemoriesSetMemName OBJECT-TYPE
		SYNTAX		RollCallString
		MAX-ACCESS		read-write
		STATUS			current
		DESCRIPTION
				"TYPE: - Editstring
					SetMemName  cmdID= 37103  "
		::= { iqdmx30CmdEntry 37103 }


	iqdmx30MemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
					Recall Memory  cmdID= 37100 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqdmx30CmdEntry 37100 }


	iqdmx30MemoriesSaveMemory OBJECT-TYPE
		SYNTAX		INTEGER { noAction(0),val-Save-Memory(1) }
		MAX-ACCESS		read-write
		STATUS			current
		DESCRIPTION
				"TYPE: - Button
					Save Memory  cmdID= 37102  value= 1  "
		::= { iqdmx30CmdEntry 37102 }


	iqdmx30MemoriesLastUserMemory OBJECT-TYPE
		SYNTAX		RollCallString
		MAX-ACCESS		read-only
		STATUS			current
		DESCRIPTION
				"TYPE: - Display
					Last User Memory  cmdID= 37104  format=   "
		::= { iqdmx30CmdEntry 37104 }


	iqdmx30MemoriesClearMemory OBJECT-TYPE
		SYNTAX		INTEGER { noAction(0),val-Clear-Memory(1) }
		MAX-ACCESS		read-write
		STATUS			current
		DESCRIPTION
				"TYPE: - Button
					Clear Memory  cmdID= 37105  value= 1  "
		::= { iqdmx30CmdEntry 37105 }


	iqdmx30MemoriesMemoryNamesMemory1Name OBJECT-TYPE
		SYNTAX		RollCallString
		MAX-ACCESS		read-only
		STATUS			current
		DESCRIPTION
				"TYPE: - Display
					Memory 1 Name  cmdID= 37106  format=   "
		::= { iqdmx30CmdEntry 37106 }


	iqdmx30MemoriesMemoryNamesMemory2Name OBJECT-TYPE
		SYNTAX		RollCallString
		MAX-ACCESS		read-only
		STATUS			current
		DESCRIPTION
				"TYPE: - Display
					Memory 2 Name  cmdID= 37107  format=   "
		::= { iqdmx30CmdEntry 37107 }


	iqdmx30MemoriesMemoryNamesMemory3Name OBJECT-TYPE
		SYNTAX		RollCallString
		MAX-ACCESS		read-only
		STATUS			current
		DESCRIPTION
				"TYPE: - Display
					Memory 3 Name  cmdID= 37108  format=   "
		::= { iqdmx30CmdEntry 37108 }


	iqdmx30MemoriesMemoryNamesMemory4Name OBJECT-TYPE
		SYNTAX		RollCallString
		MAX-ACCESS		read-only
		STATUS			current
		DESCRIPTION
				"TYPE: - Display
					Memory 4 Name  cmdID= 37109  format=   "
		::= { iqdmx30CmdEntry 37109 }


	iqdmx30MemoriesMemoryNamesMemory5Name OBJECT-TYPE
		SYNTAX		RollCallString
		MAX-ACCESS		read-only
		STATUS			current
		DESCRIPTION
				"TYPE: - Display
					Memory 5 Name  cmdID= 37110  format=   "
		::= { iqdmx30CmdEntry 37110 }


	iqdmx30MemoriesMemoryNamesMemory6Name OBJECT-TYPE
		SYNTAX		RollCallString
		MAX-ACCESS		read-only
		STATUS			current
		DESCRIPTION
				"TYPE: - Display
					Memory 6 Name  cmdID= 37111  format=   "
		::= { iqdmx30CmdEntry 37111 }


	iqdmx30MemoriesMemoryNamesMemory7Name OBJECT-TYPE
		SYNTAX		RollCallString
		MAX-ACCESS		read-only
		STATUS			current
		DESCRIPTION
				"TYPE: - Display
					Memory 7 Name  cmdID= 37112  format=   "
		::= { iqdmx30CmdEntry 37112 }


	iqdmx30MemoriesMemoryNamesMemory8Name OBJECT-TYPE
		SYNTAX		RollCallString
		MAX-ACCESS		read-only
		STATUS			current
		DESCRIPTION
				"TYPE: - Display
					Memory 8 Name  cmdID= 37113  format=   "
		::= { iqdmx30CmdEntry 37113 }


	iqdmx30MemoriesMemoryNamesMemory9Name OBJECT-TYPE
		SYNTAX		RollCallString
		MAX-ACCESS		read-only
		STATUS			current
		DESCRIPTION
				"TYPE: - Display
					Memory 9 Name  cmdID= 37114  format=   "
		::= { iqdmx30CmdEntry 37114 }


	iqdmx30MemoriesMemoryNamesMemory10Name OBJECT-TYPE
		SYNTAX		RollCallString
		MAX-ACCESS		read-only
		STATUS			current
		DESCRIPTION
				"TYPE: - Display
					Memory 10 Name  cmdID= 37115  format=   "
		::= { iqdmx30CmdEntry 37115 }


	iqdmx30MemoriesMemoryNamesMemory11Name OBJECT-TYPE
		SYNTAX		RollCallString
		MAX-ACCESS		read-only
		STATUS			current
		DESCRIPTION
				"TYPE: - Display
					Memory 11 Name  cmdID= 37116  format=   "
		::= { iqdmx30CmdEntry 37116 }


	iqdmx30MemoriesMemoryNamesMemory12Name OBJECT-TYPE
		SYNTAX		RollCallString
		MAX-ACCESS		read-only
		STATUS			current
		DESCRIPTION
				"TYPE: - Display
					Memory 12 Name  cmdID= 37117  format=   "
		::= { iqdmx30CmdEntry 37117 }


	iqdmx30MemoriesMemoryNamesMemory13Name OBJECT-TYPE
		SYNTAX		RollCallString
		MAX-ACCESS		read-only
		STATUS			current
		DESCRIPTION
				"TYPE: - Display
					Memory 13 Name  cmdID= 37118  format=   "
		::= { iqdmx30CmdEntry 37118 }


	iqdmx30MemoriesMemoryNamesMemory14Name OBJECT-TYPE
		SYNTAX		RollCallString
		MAX-ACCESS		read-only
		STATUS			current
		DESCRIPTION
				"TYPE: - Display
					Memory 14 Name  cmdID= 37119  format=   "
		::= { iqdmx30CmdEntry 37119 }


	iqdmx30MemoriesMemoryNamesMemory15Name OBJECT-TYPE
		SYNTAX		RollCallString
		MAX-ACCESS		read-only
		STATUS			current
		DESCRIPTION
				"TYPE: - Display
					Memory 15 Name  cmdID= 37120  format=   "
		::= { iqdmx30CmdEntry 37120 }


	iqdmx30MemoriesMemoryNamesMemory16Name OBJECT-TYPE
		SYNTAX		RollCallString
		MAX-ACCESS		read-only
		STATUS			current
		DESCRIPTION
				"TYPE: - Display
					Memory 16 Name  cmdID= 37121  format=   "
		::= { iqdmx30CmdEntry 37121 }


	iqdmx30LoggingLogMiscSlotStarten OBJECT-TYPE
		SYNTAX		INTEGER { disable(0), enable(1) }
		MAX-ACCESS		read-write
		STATUS			current
		DESCRIPTION
				"TYPE: - Checkbox
				 PAGE: - Setup- Logging- Log Misc
					Slot Start_en  cmdID= 4976 "
		::= { iqdmx30CmdEntry 4976 }


	iqdmx30LoggingLogMiscSlotStart OBJECT-TYPE
		SYNTAX		RollCallString
		MAX-ACCESS		read-only
		STATUS			current
		DESCRIPTION
				"TYPE: - Display
				 PAGE: - Setup- Logging- Log Misc
					Slot Start  cmdID= 4977  format=   "
		::= { iqdmx30CmdEntry 4977 }


	iqdmx30LoggingLogMiscSlotWidthen OBJECT-TYPE
		SYNTAX		INTEGER { disable(0), enable(1) }
		MAX-ACCESS		read-write
		STATUS			current
		DESCRIPTION
				"TYPE: - Checkbox
				 PAGE: - Setup- Logging- Log Misc
					Slot Width_en  cmdID= 4978 "
		::= { iqdmx30CmdEntry 4978 }


	iqdmx30LoggingLogMiscSlotWidth OBJECT-TYPE
		SYNTAX		RollCallString
		MAX-ACCESS		read-only
		STATUS			current
		DESCRIPTION
				"TYPE: - Display
				 PAGE: - Setup- Logging- Log Misc
					Slot Width  cmdID= 4979  format=   "
		::= { iqdmx30CmdEntry 4979 }


	iqdmx30LoggingLogMiscRearStatusen OBJECT-TYPE
		SYNTAX		INTEGER { disable(0), enable(1) }
		MAX-ACCESS		read-write
		STATUS			current
		DESCRIPTION
				"TYPE: - Checkbox
				 PAGE: - Setup- Logging- Log Misc
					Rear Status_en  cmdID= 4980 "
		::= { iqdmx30CmdEntry 4980 }


	iqdmx30LoggingLogMiscRearStatus OBJECT-TYPE
		SYNTAX		RollCallString
		MAX-ACCESS		read-only
		STATUS			current
		DESCRIPTION
				"TYPE: - Display
				 PAGE: - Setup- Logging- Log Misc
					Rear Status  cmdID= 4981  format=   "
		::= { iqdmx30CmdEntry 4981 }


	iqdmx30LoggingLogMiscRearIDen OBJECT-TYPE
		SYNTAX		INTEGER { disable(0), enable(1) }
		MAX-ACCESS		read-write
		STATUS			current
		DESCRIPTION
				"TYPE: - Checkbox
				 PAGE: - Setup- Logging- Log Misc
					Rear ID_en  cmdID= 4982 "
		::= { iqdmx30CmdEntry 4982 }


	iqdmx30LoggingLogMiscRearID OBJECT-TYPE
		SYNTAX		RollCallString
		MAX-ACCESS		read-only
		STATUS			current
		DESCRIPTION
				"TYPE: - Display
				 PAGE: - Setup- Logging- Log Misc
					Rear ID  cmdID= 4983  format=   "
		::= { iqdmx30CmdEntry 4983 }


	iqdmx30LoggingLogMiscFirmwareVersionen OBJECT-TYPE
		SYNTAX		INTEGER { disable(0), enable(1) }
		MAX-ACCESS		read-write
		STATUS			current
		DESCRIPTION
				"TYPE: - Checkbox
				 PAGE: - Setup- Logging- Log Misc
					Firmware Version_en  cmdID= 4986 "
		::= { iqdmx30CmdEntry 4986 }


	iqdmx30LoggingLogMiscFirmwareVersion OBJECT-TYPE
		SYNTAX		RollCallString
		MAX-ACCESS		read-only
		STATUS			current
		DESCRIPTION
				"TYPE: - Display
				 PAGE: - Setup- Logging- Log Misc
					Firmware Version  cmdID= 4987  format=   "
		::= { iqdmx30CmdEntry 4987 }


	iqdmx30LoggingLogMiscLicensedOptionsen OBJECT-TYPE
		SYNTAX		INTEGER { disable(0), enable(1) }
		MAX-ACCESS		read-write
		STATUS			current
		DESCRIPTION
				"TYPE: - Checkbox
				 PAGE: - Setup- Logging- Log Misc
					Licensed Options_en  cmdID= 4988 "
		::= { iqdmx30CmdEntry 4988 }


	iqdmx30LoggingLogMiscLicensedOptions OBJECT-TYPE
		SYNTAX		RollCallString
		MAX-ACCESS		read-only
		STATUS			current
		DESCRIPTION
				"TYPE: - Display
				 PAGE: - Setup- Logging- Log Misc
					Licensed Options  cmdID= 4989  format=   "
		::= { iqdmx30CmdEntry 4989 }


	iqdmx30LoggingLogMiscBuildNumberen OBJECT-TYPE
		SYNTAX		INTEGER { disable(0), enable(1) }
		MAX-ACCESS		read-write
		STATUS			current
		DESCRIPTION
				"TYPE: - Checkbox
				 PAGE: - Setup- Logging- Log Misc
					Build Number_en  cmdID= 4992 "
		::= { iqdmx30CmdEntry 4992 }


	iqdmx30LoggingLogMiscBuildNumber OBJECT-TYPE
		SYNTAX		RollCallString
		MAX-ACCESS		read-only
		STATUS			current
		DESCRIPTION
				"TYPE: - Display
				 PAGE: - Setup- Logging- Log Misc
					Build Number  cmdID= 4993  format=   "
		::= { iqdmx30CmdEntry 4993 }


	iqdmx30LoggingLogMiscOSVersionen OBJECT-TYPE
		SYNTAX		INTEGER { disable(0), enable(1) }
		MAX-ACCESS		read-write
		STATUS			current
		DESCRIPTION
				"TYPE: - Checkbox
				 PAGE: - Setup- Logging- Log Misc
					OS Version_en  cmdID= 4994 "
		::= { iqdmx30CmdEntry 4994 }


	iqdmx30LoggingLogMiscOSVersion OBJECT-TYPE
		SYNTAX		RollCallString
		MAX-ACCESS		read-only
		STATUS			current
		DESCRIPTION
				"TYPE: - Display
				 PAGE: - Setup- Logging- Log Misc
					OS Version  cmdID= 4995  format=   "
		::= { iqdmx30CmdEntry 4995 }


	iqdmx30LoggingLogMiscHardwareVersionen OBJECT-TYPE
		SYNTAX		INTEGER { disable(0), enable(1) }
		MAX-ACCESS		read-write
		STATUS			current
		DESCRIPTION
				"TYPE: - Checkbox
				 PAGE: - Setup- Logging- Log Misc
					Hardware Version_en  cmdID= 4996 "
		::= { iqdmx30CmdEntry 4996 }


	iqdmx30LoggingLogMiscHardwareVersion OBJECT-TYPE
		SYNTAX		RollCallString
		MAX-ACCESS		read-only
		STATUS			current
		DESCRIPTION
				"TYPE: - Display
				 PAGE: - Setup- Logging- Log Misc
					Hardware Version  cmdID= 4997  format=   "
		::= { iqdmx30CmdEntry 4997 }


	iqdmx30LoggingLogMiscUptimeen OBJECT-TYPE
		SYNTAX		INTEGER { disable(0), enable(1) }
		MAX-ACCESS		read-write
		STATUS			current
		DESCRIPTION
				"TYPE: - Checkbox
				 PAGE: - Setup- Logging- Log Misc
					Uptime_en  cmdID= 4998 "
		::= { iqdmx30CmdEntry 4998 }


	iqdmx30LoggingLogMiscUptime OBJECT-TYPE
		SYNTAX		RollCallString
		MAX-ACCESS		read-only
		STATUS			current
		DESCRIPTION
				"TYPE: - Display
				 PAGE: - Setup- Logging- Log Misc
					Uptime  cmdID= 4999  format=   "
		::= { iqdmx30CmdEntry 4999 }


	iqdmx30LoggingLogMiscSerialNumberen OBJECT-TYPE
		SYNTAX		INTEGER { disable(0), enable(1) }
		MAX-ACCESS		read-write
		STATUS			current
		DESCRIPTION
				"TYPE: - Checkbox
				 PAGE: - Setup- Logging- Log Misc
					Serial Number_en  cmdID= 4990 "
		::= { iqdmx30CmdEntry 4990 }


	iqdmx30LoggingLogMiscSerialNumber OBJECT-TYPE
		SYNTAX		RollCallString
		MAX-ACCESS		read-only
		STATUS			current
		DESCRIPTION
				"TYPE: - Display
				 PAGE: - Setup- Logging- Log Misc
					Serial Number  cmdID= 4991  format=   "
		::= { iqdmx30CmdEntry 4991 }


	iqdmx30LoggingLogVideoInput1Input1en OBJECT-TYPE
		SYNTAX		INTEGER { disable(0), enable(1) }
		MAX-ACCESS		read-write
		STATUS			current
		DESCRIPTION
				"TYPE: - Checkbox
				 PAGE: - Setup- Logging- Log Video_Input_1
					Input1_en  cmdID= 4000 "
		::= { iqdmx30CmdEntry 4000 }


	iqdmx30LoggingLogVideoInput1Input1 OBJECT-TYPE
		SYNTAX		RollCallString
		MAX-ACCESS		read-only
		STATUS			current
		DESCRIPTION
				"TYPE: - Display
				 PAGE: - Setup- Logging- Log Video_Input_1
					Input1  cmdID= 4001  format=   "
		::= { iqdmx30CmdEntry 4001 }


	iqdmx30LoggingLogVideoInput1Input1Standarden OBJECT-TYPE
		SYNTAX		INTEGER { disable(0), enable(1) }
		MAX-ACCESS		read-write
		STATUS			current
		DESCRIPTION
				"TYPE: - Checkbox
				 PAGE: - Setup- Logging- Log Video_Input_1
					Input1 Standard_en  cmdID= 4004 "
		::= { iqdmx30CmdEntry 4004 }


	iqdmx30LoggingLogVideoInput1Input1Standard OBJECT-TYPE
		SYNTAX		RollCallString
		MAX-ACCESS		read-only
		STATUS			current
		DESCRIPTION
				"TYPE: - Display
				 PAGE: - Setup- Logging- Log Video_Input_1
					Input1 Standard  cmdID= 4005  format=   "
		::= { iqdmx30CmdEntry 4005 }


	iqdmx30LoggingLogVideoInput1In1SDIERRSen OBJECT-TYPE
		SYNTAX		INTEGER { disable(0), enable(1) }
		MAX-ACCESS		read-write
		STATUS			current
		DESCRIPTION
				"TYPE: - Checkbox
				 PAGE: - Setup- Logging- Log Video_Input_1
					In1 SDI ERRS_en  cmdID= 4012 "
		::= { iqdmx30CmdEntry 4012 }


	iqdmx30LoggingLogVideoInput1In1SDIERRS OBJECT-TYPE
		SYNTAX		RollCallString
		MAX-ACCESS		read-only
		STATUS			current
		DESCRIPTION
				"TYPE: - Display
				 PAGE: - Setup- Logging- Log Video_Input_1
					In1 SDI ERRS  cmdID= 4013  format=   "
		::= { iqdmx30CmdEntry 4013 }


	iqdmx30LoggingLogVideoInput1In1SDIANCERRSen OBJECT-TYPE
		SYNTAX		INTEGER { disable(0), enable(1) }
		MAX-ACCESS		read-write
		STATUS			current
		DESCRIPTION
				"TYPE: - Checkbox
				 PAGE: - Setup- Logging- Log Video_Input_1
					In1 SDI ANC ERRS_en  cmdID= 4020 "
		::= { iqdmx30CmdEntry 4020 }


	iqdmx30LoggingLogVideoInput1In1SDIANCERRS OBJECT-TYPE
		SYNTAX		RollCallString
		MAX-ACCESS		read-only
		STATUS			current
		DESCRIPTION
				"TYPE: - Display
				 PAGE: - Setup- Logging- Log Video_Input_1
					In1 SDI ANC ERRS  cmdID= 4021  format=   "
		::= { iqdmx30CmdEntry 4021 }


	iqdmx30LoggingLogVideoInput1Input1Typeen OBJECT-TYPE
		SYNTAX		INTEGER { disable(0), enable(1) }
		MAX-ACCESS		read-write
		STATUS			current
		DESCRIPTION
				"TYPE: - Checkbox
				 PAGE: - Setup- Logging- Log Video_Input_1
					Input1 Type_en  cmdID= 4024 "
		::= { iqdmx30CmdEntry 4024 }


	iqdmx30LoggingLogVideoInput1Input1Type OBJECT-TYPE
		SYNTAX		RollCallString
		MAX-ACCESS		read-only
		STATUS			current
		DESCRIPTION
				"TYPE: - Display
				 PAGE: - Setup- Logging- Log Video_Input_1
					Input1 Type  cmdID= 4025  format=   "
		::= { iqdmx30CmdEntry 4025 }


	iqdmx30LoggingLogVideoInput1Input1Identen OBJECT-TYPE
		SYNTAX		INTEGER { disable(0), enable(1) }
		MAX-ACCESS		read-write
		STATUS			current
		DESCRIPTION
				"TYPE: - Checkbox
				 PAGE: - Setup- Logging- Log Video_Input_1
					Input1 Ident_en  cmdID= 4028 "
		::= { iqdmx30CmdEntry 4028 }


	iqdmx30LoggingLogVideoInput1Input1Ident OBJECT-TYPE
		SYNTAX		RollCallString
		MAX-ACCESS		read-only
		STATUS			current
		DESCRIPTION
				"TYPE: - Display
				 PAGE: - Setup- Logging- Log Video_Input_1
					Input1 Ident  cmdID= 4029  format=   "
		::= { iqdmx30CmdEntry 4029 }


	iqdmx30LoggingLogVideoInput2Input2en OBJECT-TYPE
		SYNTAX		INTEGER { disable(0), enable(1) }
		MAX-ACCESS		read-write
		STATUS			current
		DESCRIPTION
				"TYPE: - Checkbox
				 PAGE: - Setup- Logging- Log Video_Input_2
					Input2_en  cmdID= 4002 "
		::= { iqdmx30CmdEntry 4002 }


	iqdmx30LoggingLogVideoInput2Input2 OBJECT-TYPE
		SYNTAX		RollCallString
		MAX-ACCESS		read-only
		STATUS			current
		DESCRIPTION
				"TYPE: - Display
				 PAGE: - Setup- Logging- Log Video_Input_2
					Input2  cmdID= 4003  format=   "
		::= { iqdmx30CmdEntry 4003 }


	iqdmx30LoggingLogVideoInput2Input2Standarden OBJECT-TYPE
		SYNTAX		INTEGER { disable(0), enable(1) }
		MAX-ACCESS		read-write
		STATUS			current
		DESCRIPTION
				"TYPE: - Checkbox
				 PAGE: - Setup- Logging- Log Video_Input_2
					Input2 Standard_en  cmdID= 4006 "
		::= { iqdmx30CmdEntry 4006 }


	iqdmx30LoggingLogVideoInput2Input2Standard OBJECT-TYPE
		SYNTAX		RollCallString
		MAX-ACCESS		read-only
		STATUS			current
		DESCRIPTION
				"TYPE: - Display
				 PAGE: - Setup- Logging- Log Video_Input_2
					Input2 Standard  cmdID= 4007  format=   "
		::= { iqdmx30CmdEntry 4007 }


	iqdmx30LoggingLogVideoInput2In2SDIERRSen OBJECT-TYPE
		SYNTAX		INTEGER { disable(0), enable(1) }
		MAX-ACCESS		read-write
		STATUS			current
		DESCRIPTION
				"TYPE: - Checkbox
				 PAGE: - Setup- Logging- Log Video_Input_2
					In2 SDI ERRS_en  cmdID= 4014 "
		::= { iqdmx30CmdEntry 4014 }


	iqdmx30LoggingLogVideoInput2In2SDIERRS OBJECT-TYPE
		SYNTAX		RollCallString
		MAX-ACCESS		read-only
		STATUS			current
		DESCRIPTION
				"TYPE: - Display
				 PAGE: - Setup- Logging- Log Video_Input_2
					In2 SDI ERRS  cmdID= 4015  format=   "
		::= { iqdmx30CmdEntry 4015 }


	iqdmx30LoggingLogVideoInput2In2SDIANCERRSen OBJECT-TYPE
		SYNTAX		INTEGER { disable(0), enable(1) }
		MAX-ACCESS		read-write
		STATUS			current
		DESCRIPTION
				"TYPE: - Checkbox
				 PAGE: - Setup- Logging- Log Video_Input_2
					In2 SDI ANC ERRS_en  cmdID= 4022 "
		::= { iqdmx30CmdEntry 4022 }


	iqdmx30LoggingLogVideoInput2In2SDIANCERRS OBJECT-TYPE
		SYNTAX		RollCallString
		MAX-ACCESS		read-only
		STATUS			current
		DESCRIPTION
				"TYPE: - Display
				 PAGE: - Setup- Logging- Log Video_Input_2
					In2 SDI ANC ERRS  cmdID= 4023  format=   "
		::= { iqdmx30CmdEntry 4023 }


	iqdmx30LoggingLogVideoInput2Input2Typeen OBJECT-TYPE
		SYNTAX		INTEGER { disable(0), enable(1) }
		MAX-ACCESS		read-write
		STATUS			current
		DESCRIPTION
				"TYPE: - Checkbox
				 PAGE: - Setup- Logging- Log Video_Input_2
					Input2 Type_en  cmdID= 4026 "
		::= { iqdmx30CmdEntry 4026 }


	iqdmx30LoggingLogVideoInput2Input2Type OBJECT-TYPE
		SYNTAX		RollCallString
		MAX-ACCESS		read-only
		STATUS			current
		DESCRIPTION
				"TYPE: - Display
				 PAGE: - Setup- Logging- Log Video_Input_2
					Input2 Type  cmdID= 4027  format=   "
		::= { iqdmx30CmdEntry 4027 }


	iqdmx30LoggingLogVideoInput2Input2Identen OBJECT-TYPE
		SYNTAX		INTEGER { disable(0), enable(1) }
		MAX-ACCESS		read-write
		STATUS			current
		DESCRIPTION
				"TYPE: - Checkbox
				 PAGE: - Setup- Logging- Log Video_Input_2
					Input2 Ident_en  cmdID= 4030 "
		::= { iqdmx30CmdEntry 4030 }


	iqdmx30LoggingLogVideoInput2Input2Ident OBJECT-TYPE
		SYNTAX		RollCallString
		MAX-ACCESS		read-only
		STATUS			current
		DESCRIPTION
				"TYPE: - Display
				 PAGE: - Setup- Logging- Log Video_Input_2
					Input2 Ident  cmdID= 4031  format=   "
		::= { iqdmx30CmdEntry 4031 }


	iqdmx30LoggingLogAudioInput1Input1Audio1en OBJECT-TYPE
		SYNTAX		INTEGER { disable(0), enable(1) }
		MAX-ACCESS		read-write
		STATUS			current
		DESCRIPTION
				"TYPE: - Checkbox
				 PAGE: - Setup- Logging- Log Audio_Input_1
					Input1 Audio 1_en  cmdID= 3852 "
		::= { iqdmx30CmdEntry 3852 }


	iqdmx30LoggingLogAudioInput1Input1Audio1 OBJECT-TYPE
		SYNTAX		RollCallString
		MAX-ACCESS		read-only
		STATUS			current
		DESCRIPTION
				"TYPE: - Display
				 PAGE: - Setup- Logging- Log Audio_Input_1
					Input1 Audio 1  cmdID= 3853  format=   "
		::= { iqdmx30CmdEntry 3853 }


	iqdmx30LoggingLogAudioInput1Input1Audio2en OBJECT-TYPE
		SYNTAX		INTEGER { disable(0), enable(1) }
		MAX-ACCESS		read-write
		STATUS			current
		DESCRIPTION
				"TYPE: - Checkbox
				 PAGE: - Setup- Logging- Log Audio_Input_1
					Input1 Audio 2_en  cmdID= 3854 "
		::= { iqdmx30CmdEntry 3854 }


	iqdmx30LoggingLogAudioInput1Input1Audio2 OBJECT-TYPE
		SYNTAX		RollCallString
		MAX-ACCESS		read-only
		STATUS			current
		DESCRIPTION
				"TYPE: - Display
				 PAGE: - Setup- Logging- Log Audio_Input_1
					Input1 Audio 2  cmdID= 3855  format=   "
		::= { iqdmx30CmdEntry 3855 }


	iqdmx30LoggingLogAudioInput1Input1Audio3en OBJECT-TYPE
		SYNTAX		INTEGER { disable(0), enable(1) }
		MAX-ACCESS		read-write
		STATUS			current
		DESCRIPTION
				"TYPE: - Checkbox
				 PAGE: - Setup- Logging- Log Audio_Input_1
					Input1 Audio 3_en  cmdID= 3856 "
		::= { iqdmx30CmdEntry 3856 }


	iqdmx30LoggingLogAudioInput1Input1Audio3 OBJECT-TYPE
		SYNTAX		RollCallString
		MAX-ACCESS		read-only
		STATUS			current
		DESCRIPTION
				"TYPE: - Display
				 PAGE: - Setup- Logging- Log Audio_Input_1
					Input1 Audio 3  cmdID= 3857  format=   "
		::= { iqdmx30CmdEntry 3857 }


	iqdmx30LoggingLogAudioInput1Input1Audio4en OBJECT-TYPE
		SYNTAX		INTEGER { disable(0), enable(1) }
		MAX-ACCESS		read-write
		STATUS			current
		DESCRIPTION
				"TYPE: - Checkbox
				 PAGE: - Setup- Logging- Log Audio_Input_1
					Input1 Audio 4_en  cmdID= 3858 "
		::= { iqdmx30CmdEntry 3858 }


	iqdmx30LoggingLogAudioInput1Input1Audio4 OBJECT-TYPE
		SYNTAX		RollCallString
		MAX-ACCESS		read-only
		STATUS			current
		DESCRIPTION
				"TYPE: - Display
				 PAGE: - Setup- Logging- Log Audio_Input_1
					Input1 Audio 4  cmdID= 3859  format=   "
		::= { iqdmx30CmdEntry 3859 }


	iqdmx30LoggingLogAudioInput1Input1Audio5en OBJECT-TYPE
		SYNTAX		INTEGER { disable(0), enable(1) }
		MAX-ACCESS		read-write
		STATUS			current
		DESCRIPTION
				"TYPE: - Checkbox
				 PAGE: - Setup- Logging- Log Audio_Input_1
					Input1 Audio 5_en  cmdID= 3860 "
		::= { iqdmx30CmdEntry 3860 }


	iqdmx30LoggingLogAudioInput1Input1Audio5 OBJECT-TYPE
		SYNTAX		RollCallString
		MAX-ACCESS		read-only
		STATUS			current
		DESCRIPTION
				"TYPE: - Display
				 PAGE: - Setup- Logging- Log Audio_Input_1
					Input1 Audio 5  cmdID= 3861  format=   "
		::= { iqdmx30CmdEntry 3861 }


	iqdmx30LoggingLogAudioInput1Input1Audio6en OBJECT-TYPE
		SYNTAX		INTEGER { disable(0), enable(1) }
		MAX-ACCESS		read-write
		STATUS			current
		DESCRIPTION
				"TYPE: - Checkbox
				 PAGE: - Setup- Logging- Log Audio_Input_1
					Input1 Audio 6_en  cmdID= 3862 "
		::= { iqdmx30CmdEntry 3862 }


	iqdmx30LoggingLogAudioInput1Input1Audio6 OBJECT-TYPE
		SYNTAX		RollCallString
		MAX-ACCESS		read-only
		STATUS			current
		DESCRIPTION
				"TYPE: - Display
				 PAGE: - Setup- Logging- Log Audio_Input_1
					Input1 Audio 6  cmdID= 3863  format=   "
		::= { iqdmx30CmdEntry 3863 }


	iqdmx30LoggingLogAudioInput1Input1Audio7en OBJECT-TYPE
		SYNTAX		INTEGER { disable(0), enable(1) }
		MAX-ACCESS		read-write
		STATUS			current
		DESCRIPTION
				"TYPE: - Checkbox
				 PAGE: - Setup- Logging- Log Audio_Input_1
					Input1 Audio 7_en  cmdID= 3864 "
		::= { iqdmx30CmdEntry 3864 }


	iqdmx30LoggingLogAudioInput1Input1Audio7 OBJECT-TYPE
		SYNTAX		RollCallString
		MAX-ACCESS		read-only
		STATUS			current
		DESCRIPTION
				"TYPE: - Display
				 PAGE: - Setup- Logging- Log Audio_Input_1
					Input1 Audio 7  cmdID= 3865  format=   "
		::= { iqdmx30CmdEntry 3865 }


	iqdmx30LoggingLogAudioInput1Input1Audio8en OBJECT-TYPE
		SYNTAX		INTEGER { disable(0), enable(1) }
		MAX-ACCESS		read-write
		STATUS			current
		DESCRIPTION
				"TYPE: - Checkbox
				 PAGE: - Setup- Logging- Log Audio_Input_1
					Input1 Audio 8_en  cmdID= 3866 "
		::= { iqdmx30CmdEntry 3866 }


	iqdmx30LoggingLogAudioInput1Input1Audio8 OBJECT-TYPE
		SYNTAX		RollCallString
		MAX-ACCESS		read-only
		STATUS			current
		DESCRIPTION
				"TYPE: - Display
				 PAGE: - Setup- Logging- Log Audio_Input_1
					Input1 Audio 8  cmdID= 3867  format=   "
		::= { iqdmx30CmdEntry 3867 }


	iqdmx30LoggingLogAudioInput2Input2Audio1en OBJECT-TYPE
		SYNTAX		INTEGER { disable(0), enable(1) }
		MAX-ACCESS		read-write
		STATUS			current
		DESCRIPTION
				"TYPE: - Checkbox
				 PAGE: - Setup- Logging- Log Audio_Input_2
					Input2 Audio 1_en  cmdID= 3868 "
		::= { iqdmx30CmdEntry 3868 }


	iqdmx30LoggingLogAudioInput2Input2Audio1 OBJECT-TYPE
		SYNTAX		RollCallString
		MAX-ACCESS		read-only
		STATUS			current
		DESCRIPTION
				"TYPE: - Display
				 PAGE: - Setup- Logging- Log Audio_Input_2
					Input2 Audio 1  cmdID= 3869  format=   "
		::= { iqdmx30CmdEntry 3869 }


	iqdmx30LoggingLogAudioInput2Input2Audio2en OBJECT-TYPE
		SYNTAX		INTEGER { disable(0), enable(1) }
		MAX-ACCESS		read-write
		STATUS			current
		DESCRIPTION
				"TYPE: - Checkbox
				 PAGE: - Setup- Logging- Log Audio_Input_2
					Input2 Audio 2_en  cmdID= 3870 "
		::= { iqdmx30CmdEntry 3870 }


	iqdmx30LoggingLogAudioInput2Input2Audio2 OBJECT-TYPE
		SYNTAX		RollCallString
		MAX-ACCESS		read-only
		STATUS			current
		DESCRIPTION
				"TYPE: - Display
				 PAGE: - Setup- Logging- Log Audio_Input_2
					Input2 Audio 2  cmdID= 3871  format=   "
		::= { iqdmx30CmdEntry 3871 }


	iqdmx30LoggingLogAudioInput2Input2Audio3en OBJECT-TYPE
		SYNTAX		INTEGER { disable(0), enable(1) }
		MAX-ACCESS		read-write
		STATUS			current
		DESCRIPTION
				"TYPE: - Checkbox
				 PAGE: - Setup- Logging- Log Audio_Input_2
					Input2 Audio 3_en  cmdID= 3872 "
		::= { iqdmx30CmdEntry 3872 }


	iqdmx30LoggingLogAudioInput2Input2Audio3 OBJECT-TYPE
		SYNTAX		RollCallString
		MAX-ACCESS		read-only
		STATUS			current
		DESCRIPTION
				"TYPE: - Display
				 PAGE: - Setup- Logging- Log Audio_Input_2
					Input2 Audio 3  cmdID= 3873  format=   "
		::= { iqdmx30CmdEntry 3873 }


	iqdmx30LoggingLogAudioInput2Input2Audio4en OBJECT-TYPE
		SYNTAX		INTEGER { disable(0), enable(1) }
		MAX-ACCESS		read-write
		STATUS			current
		DESCRIPTION
				"TYPE: - Checkbox
				 PAGE: - Setup- Logging- Log Audio_Input_2
					Input2 Audio 4_en  cmdID= 3874 "
		::= { iqdmx30CmdEntry 3874 }


	iqdmx30LoggingLogAudioInput2Input2Audio4 OBJECT-TYPE
		SYNTAX		RollCallString
		MAX-ACCESS		read-only
		STATUS			current
		DESCRIPTION
				"TYPE: - Display
				 PAGE: - Setup- Logging- Log Audio_Input_2
					Input2 Audio 4  cmdID= 3875  format=   "
		::= { iqdmx30CmdEntry 3875 }


	iqdmx30LoggingLogAudioInput2Input2Audio5en OBJECT-TYPE
		SYNTAX		INTEGER { disable(0), enable(1) }
		MAX-ACCESS		read-write
		STATUS			current
		DESCRIPTION
				"TYPE: - Checkbox
				 PAGE: - Setup- Logging- Log Audio_Input_2
					Input2 Audio 5_en  cmdID= 3876 "
		::= { iqdmx30CmdEntry 3876 }


	iqdmx30LoggingLogAudioInput2Input2Audio5 OBJECT-TYPE
		SYNTAX		RollCallString
		MAX-ACCESS		read-only
		STATUS			current
		DESCRIPTION
				"TYPE: - Display
				 PAGE: - Setup- Logging- Log Audio_Input_2
					Input2 Audio 5  cmdID= 3877  format=   "
		::= { iqdmx30CmdEntry 3877 }


	iqdmx30LoggingLogAudioInput2Input2Audio6en OBJECT-TYPE
		SYNTAX		INTEGER { disable(0), enable(1) }
		MAX-ACCESS		read-write
		STATUS			current
		DESCRIPTION
				"TYPE: - Checkbox
				 PAGE: - Setup- Logging- Log Audio_Input_2
					Input2 Audio 6_en  cmdID= 3878 "
		::= { iqdmx30CmdEntry 3878 }


	iqdmx30LoggingLogAudioInput2Input2Audio6 OBJECT-TYPE
		SYNTAX		RollCallString
		MAX-ACCESS		read-only
		STATUS			current
		DESCRIPTION
				"TYPE: - Display
				 PAGE: - Setup- Logging- Log Audio_Input_2
					Input2 Audio 6  cmdID= 3879  format=   "
		::= { iqdmx30CmdEntry 3879 }


	iqdmx30LoggingLogAudioInput2Input2Audio7en OBJECT-TYPE
		SYNTAX		INTEGER { disable(0), enable(1) }
		MAX-ACCESS		read-write
		STATUS			current
		DESCRIPTION
				"TYPE: - Checkbox
				 PAGE: - Setup- Logging- Log Audio_Input_2
					Input2 Audio 7_en  cmdID= 3880 "
		::= { iqdmx30CmdEntry 3880 }


	iqdmx30LoggingLogAudioInput2Input2Audio7 OBJECT-TYPE
		SYNTAX		RollCallString
		MAX-ACCESS		read-only
		STATUS			current
		DESCRIPTION
				"TYPE: - Display
				 PAGE: - Setup- Logging- Log Audio_Input_2
					Input2 Audio 7  cmdID= 3881  format=   "
		::= { iqdmx30CmdEntry 3881 }


	iqdmx30LoggingLogAudioInput2Input2Audio8en OBJECT-TYPE
		SYNTAX		INTEGER { disable(0), enable(1) }
		MAX-ACCESS		read-write
		STATUS			current
		DESCRIPTION
				"TYPE: - Checkbox
				 PAGE: - Setup- Logging- Log Audio_Input_2
					Input2 Audio 8_en  cmdID= 3882 "
		::= { iqdmx30CmdEntry 3882 }


	iqdmx30LoggingLogAudioInput2Input2Audio8 OBJECT-TYPE
		SYNTAX		RollCallString
		MAX-ACCESS		read-only
		STATUS			current
		DESCRIPTION
				"TYPE: - Display
				 PAGE: - Setup- Logging- Log Audio_Input_2
					Input2 Audio 8  cmdID= 3883  format=   "
		::= { iqdmx30CmdEntry 3883 }


	iqdmx30LoggingLogVideoOutputOutput1Typeen OBJECT-TYPE
		SYNTAX		INTEGER { disable(0), enable(1) }
		MAX-ACCESS		read-write
		STATUS			current
		DESCRIPTION
				"TYPE: - Checkbox
				 PAGE: - Setup- Logging- Log Video_Output
					Output1 Type_en  cmdID= 4192 "
		::= { iqdmx30CmdEntry 4192 }


	iqdmx30LoggingLogVideoOutputOutput1Type OBJECT-TYPE
		SYNTAX		RollCallString
		MAX-ACCESS		read-only
		STATUS			current
		DESCRIPTION
				"TYPE: - Display
				 PAGE: - Setup- Logging- Log Video_Output
					Output1 Type  cmdID= 4193  format=   "
		::= { iqdmx30CmdEntry 4193 }


	iqdmx30LoggingLogVideoOutputOutput1Stateen OBJECT-TYPE
		SYNTAX		INTEGER { disable(0), enable(1) }
		MAX-ACCESS		read-write
		STATUS			current
		DESCRIPTION
				"TYPE: - Checkbox
				 PAGE: - Setup- Logging- Log Video_Output
					Output1 State_en  cmdID= 4196 "
		::= { iqdmx30CmdEntry 4196 }


	iqdmx30LoggingLogVideoOutputOutput1State OBJECT-TYPE
		SYNTAX		RollCallString
		MAX-ACCESS		read-only
		STATUS			current
		DESCRIPTION
				"TYPE: - Display
				 PAGE: - Setup- Logging- Log Video_Output
					Output1 State  cmdID= 4197  format=   "
		::= { iqdmx30CmdEntry 4197 }


	iqdmx30LoggingLogVideoOutputOutput1Stden OBJECT-TYPE
		SYNTAX		INTEGER { disable(0), enable(1) }
		MAX-ACCESS		read-write
		STATUS			current
		DESCRIPTION
				"TYPE: - Checkbox
				 PAGE: - Setup- Logging- Log Video_Output
					Output1 Std_en  cmdID= 4200 "
		::= { iqdmx30CmdEntry 4200 }


	iqdmx30LoggingLogVideoOutputOutput1Std OBJECT-TYPE
		SYNTAX		RollCallString
		MAX-ACCESS		read-only
		STATUS			current
		DESCRIPTION
				"TYPE: - Display
				 PAGE: - Setup- Logging- Log Video_Output
					Output1 Std  cmdID= 4201  format=   "
		::= { iqdmx30CmdEntry 4201 }


	iqdmx30LoggingLogVideoOutputOutput1Captionen OBJECT-TYPE
		SYNTAX		INTEGER { disable(0), enable(1) }
		MAX-ACCESS		read-write
		STATUS			current
		DESCRIPTION
				"TYPE: - Checkbox
				 PAGE: - Setup- Logging- Log Video_Output
					Output1 Caption_en  cmdID= 4204 "
		::= { iqdmx30CmdEntry 4204 }


	iqdmx30LoggingLogVideoOutputOutput1Caption OBJECT-TYPE
		SYNTAX		RollCallString
		MAX-ACCESS		read-only
		STATUS			current
		DESCRIPTION
				"TYPE: - Display
				 PAGE: - Setup- Logging- Log Video_Output
					Output1 Caption  cmdID= 4205  format=   "
		::= { iqdmx30CmdEntry 4205 }


	iqdmx30LoggingLogVideoOutputOutput1en OBJECT-TYPE
		SYNTAX		INTEGER { disable(0), enable(1) }
		MAX-ACCESS		read-write
		STATUS			current
		DESCRIPTION
				"TYPE: - Checkbox
				 PAGE: - Setup- Logging- Log Video_Output
					Output1_en  cmdID= 4208 "
		::= { iqdmx30CmdEntry 4208 }


	iqdmx30LoggingLogVideoOutputOutput1 OBJECT-TYPE
		SYNTAX		RollCallString
		MAX-ACCESS		read-only
		STATUS			current
		DESCRIPTION
				"TYPE: - Display
				 PAGE: - Setup- Logging- Log Video_Output
					Output1  cmdID= 4209  format=   "
		::= { iqdmx30CmdEntry 4209 }


	iqdmx30LoggingLogAudioOutputOutput1Embed11en OBJECT-TYPE
		SYNTAX		INTEGER { disable(0), enable(1) }
		MAX-ACCESS		read-write
		STATUS			current
		DESCRIPTION
				"TYPE: - Checkbox
				 PAGE: - Setup- Logging- Log Audio_Output
					Output1 Embed1 1_en  cmdID= 4064 "
		::= { iqdmx30CmdEntry 4064 }


	iqdmx30LoggingLogAudioOutputOutput1Embed11 OBJECT-TYPE
		SYNTAX		RollCallString
		MAX-ACCESS		read-only
		STATUS			current
		DESCRIPTION
				"TYPE: - Display
				 PAGE: - Setup- Logging- Log Audio_Output
					Output1 Embed1 1  cmdID= 4065  format=   "
		::= { iqdmx30CmdEntry 4065 }


	iqdmx30LoggingLogAudioOutputOutput1Embed12en OBJECT-TYPE
		SYNTAX		INTEGER { disable(0), enable(1) }
		MAX-ACCESS		read-write
		STATUS			current
		DESCRIPTION
				"TYPE: - Checkbox
				 PAGE: - Setup- Logging- Log Audio_Output
					Output1 Embed1 2_en  cmdID= 4068 "
		::= { iqdmx30CmdEntry 4068 }


	iqdmx30LoggingLogAudioOutputOutput1Embed12 OBJECT-TYPE
		SYNTAX		RollCallString
		MAX-ACCESS		read-only
		STATUS			current
		DESCRIPTION
				"TYPE: - Display
				 PAGE: - Setup- Logging- Log Audio_Output
					Output1 Embed1 2  cmdID= 4069  format=   "
		::= { iqdmx30CmdEntry 4069 }


	iqdmx30LoggingLogAudioOutputOutput1Embed21en OBJECT-TYPE
		SYNTAX		INTEGER { disable(0), enable(1) }
		MAX-ACCESS		read-write
		STATUS			current
		DESCRIPTION
				"TYPE: - Checkbox
				 PAGE: - Setup- Logging- Log Audio_Output
					Output1 Embed2 1_en  cmdID= 4072 "
		::= { iqdmx30CmdEntry 4072 }


	iqdmx30LoggingLogAudioOutputOutput1Embed21 OBJECT-TYPE
		SYNTAX		RollCallString
		MAX-ACCESS		read-only
		STATUS			current
		DESCRIPTION
				"TYPE: - Display
				 PAGE: - Setup- Logging- Log Audio_Output
					Output1 Embed2 1  cmdID= 4073  format=   "
		::= { iqdmx30CmdEntry 4073 }


	iqdmx30LoggingLogAudioOutputOutput1Embed22en OBJECT-TYPE
		SYNTAX		INTEGER { disable(0), enable(1) }
		MAX-ACCESS		read-write
		STATUS			current
		DESCRIPTION
				"TYPE: - Checkbox
				 PAGE: - Setup- Logging- Log Audio_Output
					Output1 Embed2 2_en  cmdID= 4076 "
		::= { iqdmx30CmdEntry 4076 }


	iqdmx30LoggingLogAudioOutputOutput1Embed22 OBJECT-TYPE
		SYNTAX		RollCallString
		MAX-ACCESS		read-only
		STATUS			current
		DESCRIPTION
				"TYPE: - Display
				 PAGE: - Setup- Logging- Log Audio_Output
					Output1 Embed2 2  cmdID= 4077  format=   "
		::= { iqdmx30CmdEntry 4077 }


	iqdmx30LoggingLogAudioOutputOutput1Embed31en OBJECT-TYPE
		SYNTAX		INTEGER { disable(0), enable(1) }
		MAX-ACCESS		read-write
		STATUS			current
		DESCRIPTION
				"TYPE: - Checkbox
				 PAGE: - Setup- Logging- Log Audio_Output
					Output1 Embed3 1_en  cmdID= 4080 "
		::= { iqdmx30CmdEntry 4080 }


	iqdmx30LoggingLogAudioOutputOutput1Embed31 OBJECT-TYPE
		SYNTAX		RollCallString
		MAX-ACCESS		read-only
		STATUS			current
		DESCRIPTION
				"TYPE: - Display
				 PAGE: - Setup- Logging- Log Audio_Output
					Output1 Embed3 1  cmdID= 4081  format=   "
		::= { iqdmx30CmdEntry 4081 }


	iqdmx30LoggingLogAudioOutputOutput1Embed32en OBJECT-TYPE
		SYNTAX		INTEGER { disable(0), enable(1) }
		MAX-ACCESS		read-write
		STATUS			current
		DESCRIPTION
				"TYPE: - Checkbox
				 PAGE: - Setup- Logging- Log Audio_Output
					Output1 Embed3 2_en  cmdID= 4084 "
		::= { iqdmx30CmdEntry 4084 }


	iqdmx30LoggingLogAudioOutputOutput1Embed32 OBJECT-TYPE
		SYNTAX		RollCallString
		MAX-ACCESS		read-only
		STATUS			current
		DESCRIPTION
				"TYPE: - Display
				 PAGE: - Setup- Logging- Log Audio_Output
					Output1 Embed3 2  cmdID= 4085  format=   "
		::= { iqdmx30CmdEntry 4085 }


	iqdmx30LoggingLogAudioOutputOutput1Embed41en OBJECT-TYPE
		SYNTAX		INTEGER { disable(0), enable(1) }
		MAX-ACCESS		read-write
		STATUS			current
		DESCRIPTION
				"TYPE: - Checkbox
				 PAGE: - Setup- Logging- Log Audio_Output
					Output1 Embed4 1_en  cmdID= 4088 "
		::= { iqdmx30CmdEntry 4088 }


	iqdmx30LoggingLogAudioOutputOutput1Embed41 OBJECT-TYPE
		SYNTAX		RollCallString
		MAX-ACCESS		read-only
		STATUS			current
		DESCRIPTION
				"TYPE: - Display
				 PAGE: - Setup- Logging- Log Audio_Output
					Output1 Embed4 1  cmdID= 4089  format=   "
		::= { iqdmx30CmdEntry 4089 }


	iqdmx30LoggingLogAudioOutputOutput1Embed42en OBJECT-TYPE
		SYNTAX		INTEGER { disable(0), enable(1) }
		MAX-ACCESS		read-write
		STATUS			current
		DESCRIPTION
				"TYPE: - Checkbox
				 PAGE: - Setup- Logging- Log Audio_Output
					Output1 Embed4 2_en  cmdID= 4092 "
		::= { iqdmx30CmdEntry 4092 }


	iqdmx30LoggingLogAudioOutputOutput1Embed42 OBJECT-TYPE
		SYNTAX		RollCallString
		MAX-ACCESS		read-only
		STATUS			current
		DESCRIPTION
				"TYPE: - Display
				 PAGE: - Setup- Logging- Log Audio_Output
					Output1 Embed4 2  cmdID= 4093  format=   "
		::= { iqdmx30CmdEntry 4093 }


	iqdmx30LoggingLogAudioOutputOutput1Embed51en OBJECT-TYPE
		SYNTAX		INTEGER { disable(0), enable(1) }
		MAX-ACCESS		read-write
		STATUS			current
		DESCRIPTION
				"TYPE: - Checkbox
				 PAGE: - Setup- Logging- Log Audio_Output
					Output1 Embed5 1_en  cmdID= 4096 "
		::= { iqdmx30CmdEntry 4096 }


	iqdmx30LoggingLogAudioOutputOutput1Embed51 OBJECT-TYPE
		SYNTAX		RollCallString
		MAX-ACCESS		read-only
		STATUS			current
		DESCRIPTION
				"TYPE: - Display
				 PAGE: - Setup- Logging- Log Audio_Output
					Output1 Embed5 1  cmdID= 4097  format=   "
		::= { iqdmx30CmdEntry 4097 }


	iqdmx30LoggingLogAudioOutputOutput1Embed52en OBJECT-TYPE
		SYNTAX		INTEGER { disable(0), enable(1) }
		MAX-ACCESS		read-write
		STATUS			current
		DESCRIPTION
				"TYPE: - Checkbox
				 PAGE: - Setup- Logging- Log Audio_Output
					Output1 Embed5 2_en  cmdID= 4100 "
		::= { iqdmx30CmdEntry 4100 }


	iqdmx30LoggingLogAudioOutputOutput1Embed52 OBJECT-TYPE
		SYNTAX		RollCallString
		MAX-ACCESS		read-only
		STATUS			current
		DESCRIPTION
				"TYPE: - Display
				 PAGE: - Setup- Logging- Log Audio_Output
					Output1 Embed5 2  cmdID= 4101  format=   "
		::= { iqdmx30CmdEntry 4101 }


	iqdmx30LoggingLogAudioOutputOutput1Embed61en OBJECT-TYPE
		SYNTAX		INTEGER { disable(0), enable(1) }
		MAX-ACCESS		read-write
		STATUS			current
		DESCRIPTION
				"TYPE: - Checkbox
				 PAGE: - Setup- Logging- Log Audio_Output
					Output1 Embed6 1_en  cmdID= 4104 "
		::= { iqdmx30CmdEntry 4104 }


	iqdmx30LoggingLogAudioOutputOutput1Embed61 OBJECT-TYPE
		SYNTAX		RollCallString
		MAX-ACCESS		read-only
		STATUS			current
		DESCRIPTION
				"TYPE: - Display
				 PAGE: - Setup- Logging- Log Audio_Output
					Output1 Embed6 1  cmdID= 4105  format=   "
		::= { iqdmx30CmdEntry 4105 }


	iqdmx30LoggingLogAudioOutputOutput1Embed62en OBJECT-TYPE
		SYNTAX		INTEGER { disable(0), enable(1) }
		MAX-ACCESS		read-write
		STATUS			current
		DESCRIPTION
				"TYPE: - Checkbox
				 PAGE: - Setup- Logging- Log Audio_Output
					Output1 Embed6 2_en  cmdID= 4108 "
		::= { iqdmx30CmdEntry 4108 }


	iqdmx30LoggingLogAudioOutputOutput1Embed62 OBJECT-TYPE
		SYNTAX		RollCallString
		MAX-ACCESS		read-only
		STATUS			current
		DESCRIPTION
				"TYPE: - Display
				 PAGE: - Setup- Logging- Log Audio_Output
					Output1 Embed6 2  cmdID= 4109  format=   "
		::= { iqdmx30CmdEntry 4109 }


	iqdmx30LoggingLogAudioOutputOutput1Embed71en OBJECT-TYPE
		SYNTAX		INTEGER { disable(0), enable(1) }
		MAX-ACCESS		read-write
		STATUS			current
		DESCRIPTION
				"TYPE: - Checkbox
				 PAGE: - Setup- Logging- Log Audio_Output
					Output1 Embed7 1_en  cmdID= 4112 "
		::= { iqdmx30CmdEntry 4112 }


	iqdmx30LoggingLogAudioOutputOutput1Embed71 OBJECT-TYPE
		SYNTAX		RollCallString
		MAX-ACCESS		read-only
		STATUS			current
		DESCRIPTION
				"TYPE: - Display
				 PAGE: - Setup- Logging- Log Audio_Output
					Output1 Embed7 1  cmdID= 4113  format=   "
		::= { iqdmx30CmdEntry 4113 }


	iqdmx30LoggingLogAudioOutputOutput1Embed72en OBJECT-TYPE
		SYNTAX		INTEGER { disable(0), enable(1) }
		MAX-ACCESS		read-write
		STATUS			current
		DESCRIPTION
				"TYPE: - Checkbox
				 PAGE: - Setup- Logging- Log Audio_Output
					Output1 Embed7 2_en  cmdID= 4116 "
		::= { iqdmx30CmdEntry 4116 }


	iqdmx30LoggingLogAudioOutputOutput1Embed72 OBJECT-TYPE
		SYNTAX		RollCallString
		MAX-ACCESS		read-only
		STATUS			current
		DESCRIPTION
				"TYPE: - Display
				 PAGE: - Setup- Logging- Log Audio_Output
					Output1 Embed7 2  cmdID= 4117  format=   "
		::= { iqdmx30CmdEntry 4117 }


	iqdmx30LoggingLogAudioOutputOutput1Embed81en OBJECT-TYPE
		SYNTAX		INTEGER { disable(0), enable(1) }
		MAX-ACCESS		read-write
		STATUS			current
		DESCRIPTION
				"TYPE: - Checkbox
				 PAGE: - Setup- Logging- Log Audio_Output
					Output1 Embed8 1_en  cmdID= 4120 "
		::= { iqdmx30CmdEntry 4120 }


	iqdmx30LoggingLogAudioOutputOutput1Embed81 OBJECT-TYPE
		SYNTAX		RollCallString
		MAX-ACCESS		read-only
		STATUS			current
		DESCRIPTION
				"TYPE: - Display
				 PAGE: - Setup- Logging- Log Audio_Output
					Output1 Embed8 1  cmdID= 4121  format=   "
		::= { iqdmx30CmdEntry 4121 }


	iqdmx30LoggingLogAudioOutputOutput1Embed82en OBJECT-TYPE
		SYNTAX		INTEGER { disable(0), enable(1) }
		MAX-ACCESS		read-write
		STATUS			current
		DESCRIPTION
				"TYPE: - Checkbox
				 PAGE: - Setup- Logging- Log Audio_Output
					Output1 Embed8 2_en  cmdID= 4124 "
		::= { iqdmx30CmdEntry 4124 }


	iqdmx30LoggingLogAudioOutputOutput1Embed82 OBJECT-TYPE
		SYNTAX		RollCallString
		MAX-ACCESS		read-only
		STATUS			current
		DESCRIPTION
				"TYPE: - Display
				 PAGE: - Setup- Logging- Log Audio_Output
					Output1 Embed8 2  cmdID= 4125  format=   "
		::= { iqdmx30CmdEntry 4125 }


	iqdmx30LoggingLogAudioOutputOutput1AES11en OBJECT-TYPE
		SYNTAX		INTEGER { disable(0), enable(1) }
		MAX-ACCESS		read-write
		STATUS			current
		DESCRIPTION
				"TYPE: - Checkbox
				 PAGE: - Setup- Logging- Log Audio_Output
					Output1 AES1 1_en  cmdID= 4128 "
		::= { iqdmx30CmdEntry 4128 }


	iqdmx30LoggingLogAudioOutputOutput1AES11 OBJECT-TYPE
		SYNTAX		RollCallString
		MAX-ACCESS		read-only
		STATUS			current
		DESCRIPTION
				"TYPE: - Display
				 PAGE: - Setup- Logging- Log Audio_Output
					Output1 AES1 1  cmdID= 4129  format=   "
		::= { iqdmx30CmdEntry 4129 }


	iqdmx30LoggingLogAudioOutputOutput1AES12en OBJECT-TYPE
		SYNTAX		INTEGER { disable(0), enable(1) }
		MAX-ACCESS		read-write
		STATUS			current
		DESCRIPTION
				"TYPE: - Checkbox
				 PAGE: - Setup- Logging- Log Audio_Output
					Output1 AES1 2_en  cmdID= 4132 "
		::= { iqdmx30CmdEntry 4132 }


	iqdmx30LoggingLogAudioOutputOutput1AES12 OBJECT-TYPE
		SYNTAX		RollCallString
		MAX-ACCESS		read-only
		STATUS			current
		DESCRIPTION
				"TYPE: - Display
				 PAGE: - Setup- Logging- Log Audio_Output
					Output1 AES1 2  cmdID= 4133  format=   "
		::= { iqdmx30CmdEntry 4133 }


	iqdmx30LoggingLogAudioOutputOutput1AES21en OBJECT-TYPE
		SYNTAX		INTEGER { disable(0), enable(1) }
		MAX-ACCESS		read-write
		STATUS			current
		DESCRIPTION
				"TYPE: - Checkbox
				 PAGE: - Setup- Logging- Log Audio_Output
					Output1 AES2 1_en  cmdID= 4136 "
		::= { iqdmx30CmdEntry 4136 }


	iqdmx30LoggingLogAudioOutputOutput1AES21 OBJECT-TYPE
		SYNTAX		RollCallString
		MAX-ACCESS		read-only
		STATUS			current
		DESCRIPTION
				"TYPE: - Display
				 PAGE: - Setup- Logging- Log Audio_Output
					Output1 AES2 1  cmdID= 4137  format=   "
		::= { iqdmx30CmdEntry 4137 }


	iqdmx30LoggingLogAudioOutputOutput1AES22en OBJECT-TYPE
		SYNTAX		INTEGER { disable(0), enable(1) }
		MAX-ACCESS		read-write
		STATUS			current
		DESCRIPTION
				"TYPE: - Checkbox
				 PAGE: - Setup- Logging- Log Audio_Output
					Output1 AES2 2_en  cmdID= 4140 "
		::= { iqdmx30CmdEntry 4140 }


	iqdmx30LoggingLogAudioOutputOutput1AES22 OBJECT-TYPE
		SYNTAX		RollCallString
		MAX-ACCESS		read-only
		STATUS			current
		DESCRIPTION
				"TYPE: - Display
				 PAGE: - Setup- Logging- Log Audio_Output
					Output1 AES2 2  cmdID= 4141  format=   "
		::= { iqdmx30CmdEntry 4141 }


	iqdmx30LoggingLogAudioOutputOutput1AES31en OBJECT-TYPE
		SYNTAX		INTEGER { disable(0), enable(1) }
		MAX-ACCESS		read-write
		STATUS			current
		DESCRIPTION
				"TYPE: - Checkbox
				 PAGE: - Setup- Logging- Log Audio_Output
					Output1 AES3 1_en  cmdID= 4144 "
		::= { iqdmx30CmdEntry 4144 }


	iqdmx30LoggingLogAudioOutputOutput1AES31 OBJECT-TYPE
		SYNTAX		RollCallString
		MAX-ACCESS		read-only
		STATUS			current
		DESCRIPTION
				"TYPE: - Display
				 PAGE: - Setup- Logging- Log Audio_Output
					Output1 AES3 1  cmdID= 4145  format=   "
		::= { iqdmx30CmdEntry 4145 }


	iqdmx30LoggingLogAudioOutputOutput1AES32en OBJECT-TYPE
		SYNTAX		INTEGER { disable(0), enable(1) }
		MAX-ACCESS		read-write
		STATUS			current
		DESCRIPTION
				"TYPE: - Checkbox
				 PAGE: - Setup- Logging- Log Audio_Output
					Output1 AES3 2_en  cmdID= 4148 "
		::= { iqdmx30CmdEntry 4148 }


	iqdmx30LoggingLogAudioOutputOutput1AES32 OBJECT-TYPE
		SYNTAX		RollCallString
		MAX-ACCESS		read-only
		STATUS			current
		DESCRIPTION
				"TYPE: - Display
				 PAGE: - Setup- Logging- Log Audio_Output
					Output1 AES3 2  cmdID= 4149  format=   "
		::= { iqdmx30CmdEntry 4149 }


	iqdmx30LoggingLogAudioOutputOutput1AES41en OBJECT-TYPE
		SYNTAX		INTEGER { disable(0), enable(1) }
		MAX-ACCESS		read-write
		STATUS			current
		DESCRIPTION
				"TYPE: - Checkbox
				 PAGE: - Setup- Logging- Log Audio_Output
					Output1 AES4 1_en  cmdID= 4152 "
		::= { iqdmx30CmdEntry 4152 }


	iqdmx30LoggingLogAudioOutputOutput1AES41 OBJECT-TYPE
		SYNTAX		RollCallString
		MAX-ACCESS		read-only
		STATUS			current
		DESCRIPTION
				"TYPE: - Display
				 PAGE: - Setup- Logging- Log Audio_Output
					Output1 AES4 1  cmdID= 4153  format=   "
		::= { iqdmx30CmdEntry 4153 }


	iqdmx30LoggingLogAudioOutputOutput1AES42en OBJECT-TYPE
		SYNTAX		INTEGER { disable(0), enable(1) }
		MAX-ACCESS		read-write
		STATUS			current
		DESCRIPTION
				"TYPE: - Checkbox
				 PAGE: - Setup- Logging- Log Audio_Output
					Output1 AES4 2_en  cmdID= 4156 "
		::= { iqdmx30CmdEntry 4156 }


	iqdmx30LoggingLogAudioOutputOutput1AES42 OBJECT-TYPE
		SYNTAX		RollCallString
		MAX-ACCESS		read-only
		STATUS			current
		DESCRIPTION
				"TYPE: - Display
				 PAGE: - Setup- Logging- Log Audio_Output
					Output1 AES4 2  cmdID= 4157  format=   "
		::= { iqdmx30CmdEntry 4157 }


	iqdmx30LoggingLogAudioOutputOutput1AES51en OBJECT-TYPE
		SYNTAX		INTEGER { disable(0), enable(1) }
		MAX-ACCESS		read-write
		STATUS			current
		DESCRIPTION
				"TYPE: - Checkbox
				 PAGE: - Setup- Logging- Log Audio_Output
					Output1 AES5 1_en  cmdID= 4160 "
		::= { iqdmx30CmdEntry 4160 }


	iqdmx30LoggingLogAudioOutputOutput1AES51 OBJECT-TYPE
		SYNTAX		RollCallString
		MAX-ACCESS		read-only
		STATUS			current
		DESCRIPTION
				"TYPE: - Display
				 PAGE: - Setup- Logging- Log Audio_Output
					Output1 AES5 1  cmdID= 4161  format=   "
		::= { iqdmx30CmdEntry 4161 }


	iqdmx30LoggingLogAudioOutputOutput1AES52en OBJECT-TYPE
		SYNTAX		INTEGER { disable(0), enable(1) }
		MAX-ACCESS		read-write
		STATUS			current
		DESCRIPTION
				"TYPE: - Checkbox
				 PAGE: - Setup- Logging- Log Audio_Output
					Output1 AES5 2_en  cmdID= 4164 "
		::= { iqdmx30CmdEntry 4164 }


	iqdmx30LoggingLogAudioOutputOutput1AES52 OBJECT-TYPE
		SYNTAX		RollCallString
		MAX-ACCESS		read-only
		STATUS			current
		DESCRIPTION
				"TYPE: - Display
				 PAGE: - Setup- Logging- Log Audio_Output
					Output1 AES5 2  cmdID= 4165  format=   "
		::= { iqdmx30CmdEntry 4165 }


	iqdmx30LoggingLogAudioOutputOutput1AES61en OBJECT-TYPE
		SYNTAX		INTEGER { disable(0), enable(1) }
		MAX-ACCESS		read-write
		STATUS			current
		DESCRIPTION
				"TYPE: - Checkbox
				 PAGE: - Setup- Logging- Log Audio_Output
					Output1 AES6 1_en  cmdID= 4168 "
		::= { iqdmx30CmdEntry 4168 }


	iqdmx30LoggingLogAudioOutputOutput1AES61 OBJECT-TYPE
		SYNTAX		RollCallString
		MAX-ACCESS		read-only
		STATUS			current
		DESCRIPTION
				"TYPE: - Display
				 PAGE: - Setup- Logging- Log Audio_Output
					Output1 AES6 1  cmdID= 4169  format=   "
		::= { iqdmx30CmdEntry 4169 }


	iqdmx30LoggingLogAudioOutputOutput1AES62en OBJECT-TYPE
		SYNTAX		INTEGER { disable(0), enable(1) }
		MAX-ACCESS		read-write
		STATUS			current
		DESCRIPTION
				"TYPE: - Checkbox
				 PAGE: - Setup- Logging- Log Audio_Output
					Output1 AES6 2_en  cmdID= 4172 "
		::= { iqdmx30CmdEntry 4172 }


	iqdmx30LoggingLogAudioOutputOutput1AES62 OBJECT-TYPE
		SYNTAX		RollCallString
		MAX-ACCESS		read-only
		STATUS			current
		DESCRIPTION
				"TYPE: - Display
				 PAGE: - Setup- Logging- Log Audio_Output
					Output1 AES6 2  cmdID= 4173  format=   "
		::= { iqdmx30CmdEntry 4173 }


	iqdmx30LoggingLogAudioOutputOutput1AES71en OBJECT-TYPE
		SYNTAX		INTEGER { disable(0), enable(1) }
		MAX-ACCESS		read-write
		STATUS			current
		DESCRIPTION
				"TYPE: - Checkbox
				 PAGE: - Setup- Logging- Log Audio_Output
					Output1 AES7 1_en  cmdID= 4176 "
		::= { iqdmx30CmdEntry 4176 }


	iqdmx30LoggingLogAudioOutputOutput1AES71 OBJECT-TYPE
		SYNTAX		RollCallString
		MAX-ACCESS		read-only
		STATUS			current
		DESCRIPTION
				"TYPE: - Display
				 PAGE: - Setup- Logging- Log Audio_Output
					Output1 AES7 1  cmdID= 4177  format=   "
		::= { iqdmx30CmdEntry 4177 }


	iqdmx30LoggingLogAudioOutputOutput1AES72en OBJECT-TYPE
		SYNTAX		INTEGER { disable(0), enable(1) }
		MAX-ACCESS		read-write
		STATUS			current
		DESCRIPTION
				"TYPE: - Checkbox
				 PAGE: - Setup- Logging- Log Audio_Output
					Output1 AES7 2_en  cmdID= 4180 "
		::= { iqdmx30CmdEntry 4180 }


	iqdmx30LoggingLogAudioOutputOutput1AES72 OBJECT-TYPE
		SYNTAX		RollCallString
		MAX-ACCESS		read-only
		STATUS			current
		DESCRIPTION
				"TYPE: - Display
				 PAGE: - Setup- Logging- Log Audio_Output
					Output1 AES7 2  cmdID= 4181  format=   "
		::= { iqdmx30CmdEntry 4181 }


	iqdmx30LoggingLogAudioOutputOutput1AES81en OBJECT-TYPE
		SYNTAX		INTEGER { disable(0), enable(1) }
		MAX-ACCESS		read-write
		STATUS			current
		DESCRIPTION
				"TYPE: - Checkbox
				 PAGE: - Setup- Logging- Log Audio_Output
					Output1 AES8 1_en  cmdID= 4184 "
		::= { iqdmx30CmdEntry 4184 }


	iqdmx30LoggingLogAudioOutputOutput1AES81 OBJECT-TYPE
		SYNTAX		RollCallString
		MAX-ACCESS		read-only
		STATUS			current
		DESCRIPTION
				"TYPE: - Display
				 PAGE: - Setup- Logging- Log Audio_Output
					Output1 AES8 1  cmdID= 4185  format=   "
		::= { iqdmx30CmdEntry 4185 }


	iqdmx30LoggingLogAudioOutputOutput1AES82en OBJECT-TYPE
		SYNTAX		INTEGER { disable(0), enable(1) }
		MAX-ACCESS		read-write
		STATUS			current
		DESCRIPTION
				"TYPE: - Checkbox
				 PAGE: - Setup- Logging- Log Audio_Output
					Output1 AES8 2_en  cmdID= 4188 "
		::= { iqdmx30CmdEntry 4188 }


	iqdmx30LoggingLogAudioOutputOutput1AES82 OBJECT-TYPE
		SYNTAX		RollCallString
		MAX-ACCESS		read-only
		STATUS			current
		DESCRIPTION
				"TYPE: - Display
				 PAGE: - Setup- Logging- Log Audio_Output
					Output1 AES8 2  cmdID= 4189  format=   "
		::= { iqdmx30CmdEntry 4189 }


	iqdmx30LoggingLogAudioOutputOutputEmbeden OBJECT-TYPE
		SYNTAX		INTEGER { disable(0), enable(1) }
		MAX-ACCESS		read-write
		STATUS			current
		DESCRIPTION
				"TYPE: - Checkbox
				 PAGE: - Setup- Logging- Log Audio_Output
					Output Embed_en  cmdID= 4456 "
		::= { iqdmx30CmdEntry 4456 }


	iqdmx30LoggingLogAudioOutputOutputEmbed OBJECT-TYPE
		SYNTAX		RollCallString
		MAX-ACCESS		read-only
		STATUS			current
		DESCRIPTION
				"TYPE: - Display
				 PAGE: - Setup- Logging- Log Audio_Output
					Output Embed  cmdID= 4457  format=   "
		::= { iqdmx30CmdEntry 4457 }


	iqdmx30SetupRollTracksRollTrackIndex1495 OBJECT-TYPE
		SYNTAX		INTEGER
		MAX-ACCESS		read-write
		STATUS			current
		DESCRIPTION
				"TYPE: - Number
				 PAGE: - Setup- RollTracks
					RollTrack Index  cmdID= 1495  min= 1  max= 70  step= 1  format= %.0f  div_scale= 1 
					Min = 1  Max = 70  Step = 1 "
		::= { iqdmx30CmdEntry 1495 }


	iqdmx30SetupRollTracksRollTrackSource1496 OBJECT-TYPE
		SYNTAX		INTEGER
		MAX-ACCESS		read-write
		STATUS			current
		DESCRIPTION
				"TYPE: - Number
				 PAGE: - Setup- RollTracks
					RollTrack Source  cmdID= 1496  min= -1  max= 100  step= 1  format= %.0f  div_scale= 1 
					Min = -1  Max = 100  Step = 1 "
		::= { iqdmx30CmdEntry 1496 }


	iqdmx30SetupRollTracksRollTrackDisable OBJECT-TYPE
		SYNTAX		INTEGER { disable(0), enable(1) }
		MAX-ACCESS		read-write
		STATUS			current
		DESCRIPTION
				"TYPE: - Checkbox
				 PAGE: - Setup- RollTracks
					RollTrack Disable  cmdID= 1513 "
		::= { iqdmx30CmdEntry 1513 }


	iqdmx30SetupRollTracksRollTrackAddress1497 OBJECT-TYPE
		SYNTAX		RollCallString
		MAX-ACCESS		read-write
		STATUS			current
		DESCRIPTION
				"TYPE: - Editstring
				 PAGE: - Setup- RollTracks
					RollTrack Address  cmdID= 1497  "
		::= { iqdmx30CmdEntry 1497 }


	iqdmx30SetupRollTracksRollTrackCommand1498 OBJECT-TYPE
		SYNTAX		RollCallString
		MAX-ACCESS		read-write
		STATUS			current
		DESCRIPTION
				"TYPE: - Editstring
				 PAGE: - Setup- RollTracks
					RollTrack Command  cmdID= 1498  "
		::= { iqdmx30CmdEntry 1498 }


	iqdmx30SetupRollTracksRollTrackSending OBJECT-TYPE
		SYNTAX		RollCallString
		MAX-ACCESS		read-only
		STATUS			current
		DESCRIPTION
				"TYPE: - Display
				 PAGE: - Setup- RollTracks
					RollTrack Sending  cmdID= 1514  format=   "
		::= { iqdmx30CmdEntry 1514 }


	iqdmx30SetupRollTracksRollTrackStatus OBJECT-TYPE
		SYNTAX		RollCallString
		MAX-ACCESS		read-only
		STATUS			current
		DESCRIPTION
				"TYPE: - Display
				 PAGE: - Setup- RollTracks
					RollTrack Status  cmdID= 1511  format=   "
		::= { iqdmx30CmdEntry 1511 }


	iqdmx30SetupRollTracksRollTrackIndex2870 OBJECT-TYPE
		SYNTAX		INTEGER
		MAX-ACCESS		read-write
		STATUS			current
		DESCRIPTION
				"TYPE: - Number
				 PAGE: - Setup- RollTracks
					RollTrack Index  cmdID= 2870  min= 1  max= 70  step= 1  format= %.0f  div_scale= 1 
					Min = 1  Max = 70  Step = 1 "
		::= { iqdmx30CmdEntry 2870 }


	iqdmx30SetupRollTracksRollTrackSource2871 OBJECT-TYPE
		SYNTAX		INTEGER
		MAX-ACCESS		read-write
		STATUS			current
		DESCRIPTION
				"TYPE: - Number
				 PAGE: - Setup- RollTracks
					RollTrack Source  cmdID= 2871  min= -1  max= 100  step= 1  format= %.0f  div_scale= 1 
					Min = -1  Max = 100  Step = 1 "
		::= { iqdmx30CmdEntry 2871 }


	iqdmx30SetupRollTracksRollTrackAddress2872 OBJECT-TYPE
		SYNTAX		RollCallString
		MAX-ACCESS		read-write
		STATUS			current
		DESCRIPTION
				"TYPE: - Editstring
				 PAGE: - Setup- RollTracks
					RollTrack Address  cmdID= 2872  "
		::= { iqdmx30CmdEntry 2872 }


	iqdmx30SetupRollTracksRollTrackCommand2873 OBJECT-TYPE
		SYNTAX		RollCallString
		MAX-ACCESS		read-write
		STATUS			current
		DESCRIPTION
				"TYPE: - Editstring
				 PAGE: - Setup- RollTracks
					RollTrack Command  cmdID= 2873  "
		::= { iqdmx30CmdEntry 2873 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: unknown
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:03:00
--				: 
-- Comments		: 
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
-- Vary			: YES
--
-- Value(s)		: 85
--				: 
-- Comments		: 
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
-- Vary			: YES
--
-- Value(s)		: INPUT_1
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				: 
-- Comments		: 
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				: 
-- Comments		: 
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
-- Vary			: YES
--
-- Value(s)		: Unknown
--				: 
-- Comments		: 
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
-- Vary			: YES
--
-- Value(s)		: Unknown
--				: 
-- Comments		: 
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
-- Vary			: YES
--
-- Value(s)		: WARN:Type Mismatch
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 4677.4677.4677
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD/SD/3G SDI
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: HD/SD/3G SDI
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2015-06-02T15:47:29Z
--				: 
-- Comments		: 
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: YES
--
-- Value(s)		: SERIAL IN 1
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: 
-- Comments		: 
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
-- Vary			: YES
--
-- Value(s)		: SERIAL IN 2
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: FAIL:Lost
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: 3G / HD / SD SDI
--				: 
-- Comments		: 
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: WARN:Black
--				: 
-- Comments		: 
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 4674
--				: 
-- Comments		: 
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: unknown
--				: 
-- Comments		: 
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: 
-- Comments		: 
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--				: 
-- Comments		: 
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
-- Vary			: YES
--
-- Value(s)		: OK
--				: 
-- Comments		: 
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: Unknown
--				: 
-- Comments		: 
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
-- Vary			: YES
--
-- Value(s)		: FAIL:No File
--				: 
-- Comments		: 
--
---------------------------------------------------------------------------------------------------
-- Header		: OUTPUT_1_CAPTION
--
-- MIB ref		: swCardEventLogSlotXX       .16.79.85.84.80.85.84.95.49.95.67.65.80.84.73.79.78
-- absolute OID	: 1.3.6.1.4.1.7995.2.6.1.1.XX.16.79.85.84.80.85.84.95.49.95.67.65.80.84.73.79.78
-- Vary			: YES
--
-- Value(s)		: OK:Off
--				: 
-- Comments		: 
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: 1080/59p-A
--				: 
-- Comments		: 
--
---------------------------------------------------------------------------------------------------
-- Header		: AES_OUTPUT_1_1_STATE
--
-- MIB ref		: swCardEventLogSlotXX       .20.65.69.83.95.79.85.84.80.85.84.95.49.95.49.95.83.84.65.84.69
-- absolute OID	: 1.3.6.1.4.1.7995.2.6.1.1.XX.20.65.69.83.95.79.85.84.80.85.84.95.49.95.49.95.83.84.65.84.69
-- Vary			: YES
--
-- Value(s)		: WARN:Silent PCM
--				: 
-- Comments		: 
--
---------------------------------------------------------------------------------------------------
-- Header		: AES_OUTPUT_1_2_STATE
--
-- MIB ref		: swCardEventLogSlotXX       .20.65.69.83.95.79.85.84.80.85.84.95.49.95.50.95.83.84.65.84.69
-- absolute OID	: 1.3.6.1.4.1.7995.2.6.1.1.XX.20.65.69.83.95.79.85.84.80.85.84.95.49.95.50.95.83.84.65.84.69
-- Vary			: YES
--
-- Value(s)		: WARN:Silent PCM
--				: 
-- Comments		: 
--
---------------------------------------------------------------------------------------------------
-- Header		: AES_OUTPUT_2_1_STATE
--
-- MIB ref		: swCardEventLogSlotXX       .20.65.69.83.95.79.85.84.80.85.84.95.50.95.49.95.83.84.65.84.69
-- absolute OID	: 1.3.6.1.4.1.7995.2.6.1.1.XX.20.65.69.83.95.79.85.84.80.85.84.95.50.95.49.95.83.84.65.84.69
-- Vary			: YES
--
-- Value(s)		: WARN:Silent PCM
--				: 
-- Comments		: 
--
---------------------------------------------------------------------------------------------------
-- Header		: AES_OUTPUT_2_2_STATE
--
-- MIB ref		: swCardEventLogSlotXX       .20.65.69.83.95.79.85.84.80.85.84.95.50.95.50.95.83.84.65.84.69
-- absolute OID	: 1.3.6.1.4.1.7995.2.6.1.1.XX.20.65.69.83.95.79.85.84.80.85.84.95.50.95.50.95.83.84.65.84.69
-- Vary			: YES
--
-- Value(s)		: WARN:Silent PCM
--				: 
-- Comments		: 
--
---------------------------------------------------------------------------------------------------
-- Header		: AES_OUTPUT_3_1_STATE
--
-- MIB ref		: swCardEventLogSlotXX       .20.65.69.83.95.79.85.84.80.85.84.95.51.95.49.95.83.84.65.84.69
-- absolute OID	: 1.3.6.1.4.1.7995.2.6.1.1.XX.20.65.69.83.95.79.85.84.80.85.84.95.51.95.49.95.83.84.65.84.69
-- Vary			: YES
--
-- Value(s)		: WARN:Silent PCM
--				: 
-- Comments		: 
--
---------------------------------------------------------------------------------------------------
-- Header		: AES_OUTPUT_3_2_STATE
--
-- MIB ref		: swCardEventLogSlotXX       .20.65.69.83.95.79.85.84.80.85.84.95.51.95.50.95.83.84.65.84.69
-- absolute OID	: 1.3.6.1.4.1.7995.2.6.1.1.XX.20.65.69.83.95.79.85.84.80.85.84.95.51.95.50.95.83.84.65.84.69
-- Vary			: YES
--
-- Value(s)		: WARN:Silent PCM
--				: 
-- Comments		: 
--
---------------------------------------------------------------------------------------------------
-- Header		: AES_OUTPUT_4_1_STATE
--
-- MIB ref		: swCardEventLogSlotXX       .20.65.69.83.95.79.85.84.80.85.84.95.52.95.49.95.83.84.65.84.69
-- absolute OID	: 1.3.6.1.4.1.7995.2.6.1.1.XX.20.65.69.83.95.79.85.84.80.85.84.95.52.95.49.95.83.84.65.84.69
-- Vary			: YES
--
-- Value(s)		: WARN:Silent PCM
--				: 
-- Comments		: 
--
---------------------------------------------------------------------------------------------------
-- Header		: AES_OUTPUT_4_2_STATE
--
-- MIB ref		: swCardEventLogSlotXX       .20.65.69.83.95.79.85.84.80.85.84.95.52.95.50.95.83.84.65.84.69
-- absolute OID	: 1.3.6.1.4.1.7995.2.6.1.1.XX.20.65.69.83.95.79.85.84.80.85.84.95.52.95.50.95.83.84.65.84.69
-- Vary			: YES
--
-- Value(s)		: WARN:Silent PCM
--				: 
-- Comments		: 
--
---------------------------------------------------------------------------------------------------
-- Header		: AES_OUTPUT_5_1_STATE
--
-- MIB ref		: swCardEventLogSlotXX       .20.65.69.83.95.79.85.84.80.85.84.95.53.95.49.95.83.84.65.84.69
-- absolute OID	: 1.3.6.1.4.1.7995.2.6.1.1.XX.20.65.69.83.95.79.85.84.80.85.84.95.53.95.49.95.83.84.65.84.69
-- Vary			: YES
--
-- Value(s)		: WARN:Silent PCM
--				: 
-- Comments		: 
--
---------------------------------------------------------------------------------------------------
-- Header		: AES_OUTPUT_5_2_STATE
--
-- MIB ref		: swCardEventLogSlotXX       .20.65.69.83.95.79.85.84.80.85.84.95.53.95.50.95.83.84.65.84.69
-- absolute OID	: 1.3.6.1.4.1.7995.2.6.1.1.XX.20.65.69.83.95.79.85.84.80.85.84.95.53.95.50.95.83.84.65.84.69
-- Vary			: YES
--
-- Value(s)		: WARN:Silent PCM
--				: 
-- Comments		: 
--
---------------------------------------------------------------------------------------------------
-- Header		: AES_OUTPUT_6_1_STATE
--
-- MIB ref		: swCardEventLogSlotXX       .20.65.69.83.95.79.85.84.80.85.84.95.54.95.49.95.83.84.65.84.69
-- absolute OID	: 1.3.6.1.4.1.7995.2.6.1.1.XX.20.65.69.83.95.79.85.84.80.85.84.95.54.95.49.95.83.84.65.84.69
-- Vary			: YES
--
-- Value(s)		: WARN:Silent PCM
--				: 
-- Comments		: 
--
---------------------------------------------------------------------------------------------------
-- Header		: AES_OUTPUT_6_2_STATE
--
-- MIB ref		: swCardEventLogSlotXX       .20.65.69.83.95.79.85.84.80.85.84.95.54.95.50.95.83.84.65.84.69
-- absolute OID	: 1.3.6.1.4.1.7995.2.6.1.1.XX.20.65.69.83.95.79.85.84.80.85.84.95.54.95.50.95.83.84.65.84.69
-- Vary			: YES
--
-- Value(s)		: WARN:Silent PCM
--				: 
-- Comments		: 
--
---------------------------------------------------------------------------------------------------
-- Header		: AES_OUTPUT_7_1_STATE
--
-- MIB ref		: swCardEventLogSlotXX       .20.65.69.83.95.79.85.84.80.85.84.95.55.95.49.95.83.84.65.84.69
-- absolute OID	: 1.3.6.1.4.1.7995.2.6.1.1.XX.20.65.69.83.95.79.85.84.80.85.84.95.55.95.49.95.83.84.65.84.69
-- Vary			: YES
--
-- Value(s)		: WARN:Silent PCM
--				: 
-- Comments		: 
--
---------------------------------------------------------------------------------------------------
-- Header		: AES_OUTPUT_7_2_STATE
--
-- MIB ref		: swCardEventLogSlotXX       .20.65.69.83.95.79.85.84.80.85.84.95.55.95.50.95.83.84.65.84.69
-- absolute OID	: 1.3.6.1.4.1.7995.2.6.1.1.XX.20.65.69.83.95.79.85.84.80.85.84.95.55.95.50.95.83.84.65.84.69
-- Vary			: YES
--
-- Value(s)		: WARN:Silent PCM
--				: 
-- Comments		: 
--
---------------------------------------------------------------------------------------------------
-- Header		: AES_OUTPUT_8_1_STATE
--
-- MIB ref		: swCardEventLogSlotXX       .20.65.69.83.95.79.85.84.80.85.84.95.56.95.49.95.83.84.65.84.69
-- absolute OID	: 1.3.6.1.4.1.7995.2.6.1.1.XX.20.65.69.83.95.79.85.84.80.85.84.95.56.95.49.95.83.84.65.84.69
-- Vary			: YES
--
-- Value(s)		: WARN:Silent PCM
--				: 
-- Comments		: 
--
---------------------------------------------------------------------------------------------------
-- Header		: AES_OUTPUT_8_2_STATE
--
-- MIB ref		: swCardEventLogSlotXX       .20.65.69.83.95.79.85.84.80.85.84.95.56.95.50.95.83.84.65.84.69
-- absolute OID	: 1.3.6.1.4.1.7995.2.6.1.1.XX.20.65.69.83.95.79.85.84.80.85.84.95.56.95.50.95.83.84.65.84.69
-- Vary			: YES
--
-- Value(s)		: WARN:Silent PCM
--				: 
-- Comments		: 
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: 
-- Comments		: 
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
-- Vary			: YES
--
-- Value(s)		: OK
--				: 
-- Comments		: 
--
---------------------------------------------------------------------------------------------------
-- Header		: OUTPUT_1_EMBED_AUDIO
--
-- MIB ref		: swCardEventLogSlotXX       .20.79.85.84.80.85.84.95.49.95.69.77.66.69.68.95.65.85.68.73.79
-- absolute OID	: 1.3.6.1.4.1.7995.2.6.1.1.XX.20.79.85.84.80.85.84.95.49.95.69.77.66.69.68.95.65.85.68.73.79
-- Vary			: YES
--
-- Value(s)		: INPUT_1
--				: 
-- Comments		: 
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: WARN:No Input
--				: 
-- Comments		: 
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: WARN:No Input
--				: 
-- Comments		: 
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: WARN:No Input
--				: 
-- Comments		: 
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: WARN:No Input
--				: 
-- Comments		: 
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: WARN:No Input
--				: 
-- Comments		: 
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: WARN:No Input
--				: 
-- Comments		: 
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: WARN:No Input
--				: 
-- Comments		: 
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: WARN:No Input
--				: 
-- Comments		: 
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
-- Vary			: YES
--
-- Value(s)		: WARN:Unknown
--				: 
-- Comments		: 
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
-- Vary			: YES
--
-- Value(s)		: WARN:Unknown
--				: 
-- Comments		: 
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
-- Vary			: YES
--
-- Value(s)		: WARN:Unknown
--				: 
-- Comments		: 
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
-- Vary			: YES
--
-- Value(s)		: WARN:Unknown
--				: 
-- Comments		: 
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
-- Vary			: YES
--
-- Value(s)		: WARN:Unknown
--				: 
-- Comments		: 
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
-- Vary			: YES
--
-- Value(s)		: WARN:Unknown
--				: 
-- Comments		: 
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
-- Vary			: YES
--
-- Value(s)		: WARN:Unknown
--				: 
-- Comments		: 
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
-- Vary			: YES
--
-- Value(s)		: WARN:Unknown
--				: 
-- Comments		: 
--
---------------------------------------------------------------------------------------------------
-- Header		: OUTPUT_1_EMBED_AUDIO_1_1_STATE
--
-- MIB ref		: swCardEventLogSlotXX       .30.79.85.84.80.85.84.95.49.95.69.77.66.69.68.95.65.85.68.73.79.95.49.95.49.95.83.84.65.84.69
-- absolute OID	: 1.3.6.1.4.1.7995.2.6.1.1.XX.30.79.85.84.80.85.84.95.49.95.69.77.66.69.68.95.65.85.68.73.79.95.49.95.49.95.83.84.65.84.69
-- Vary			: YES
--
-- Value(s)		: WARN:Silent PCM
--				: 
-- Comments		: 
--
---------------------------------------------------------------------------------------------------
-- Header		: OUTPUT_1_EMBED_AUDIO_1_2_STATE
--
-- MIB ref		: swCardEventLogSlotXX       .30.79.85.84.80.85.84.95.49.95.69.77.66.69.68.95.65.85.68.73.79.95.49.95.50.95.83.84.65.84.69
-- absolute OID	: 1.3.6.1.4.1.7995.2.6.1.1.XX.30.79.85.84.80.85.84.95.49.95.69.77.66.69.68.95.65.85.68.73.79.95.49.95.50.95.83.84.65.84.69
-- Vary			: YES
--
-- Value(s)		: WARN:Silent PCM
--				: 
-- Comments		: 
--
---------------------------------------------------------------------------------------------------
-- Header		: OUTPUT_1_EMBED_AUDIO_2_1_STATE
--
-- MIB ref		: swCardEventLogSlotXX       .30.79.85.84.80.85.84.95.49.95.69.77.66.69.68.95.65.85.68.73.79.95.50.95.49.95.83.84.65.84.69
-- absolute OID	: 1.3.6.1.4.1.7995.2.6.1.1.XX.30.79.85.84.80.85.84.95.49.95.69.77.66.69.68.95.65.85.68.73.79.95.50.95.49.95.83.84.65.84.69
-- Vary			: YES
--
-- Value(s)		: WARN:Silent PCM
--				: 
-- Comments		: 
--
---------------------------------------------------------------------------------------------------
-- Header		: OUTPUT_1_EMBED_AUDIO_2_2_STATE
--
-- MIB ref		: swCardEventLogSlotXX       .30.79.85.84.80.85.84.95.49.95.69.77.66.69.68.95.65.85.68.73.79.95.50.95.50.95.83.84.65.84.69
-- absolute OID	: 1.3.6.1.4.1.7995.2.6.1.1.XX.30.79.85.84.80.85.84.95.49.95.69.77.66.69.68.95.65.85.68.73.79.95.50.95.50.95.83.84.65.84.69
-- Vary			: YES
--
-- Value(s)		: WARN:Silent PCM
--				: 
-- Comments		: 
--
---------------------------------------------------------------------------------------------------
-- Header		: OUTPUT_1_EMBED_AUDIO_3_1_STATE
--
-- MIB ref		: swCardEventLogSlotXX       .30.79.85.84.80.85.84.95.49.95.69.77.66.69.68.95.65.85.68.73.79.95.51.95.49.95.83.84.65.84.69
-- absolute OID	: 1.3.6.1.4.1.7995.2.6.1.1.XX.30.79.85.84.80.85.84.95.49.95.69.77.66.69.68.95.65.85.68.73.79.95.51.95.49.95.83.84.65.84.69
-- Vary			: YES
--
-- Value(s)		: WARN:Silent PCM
--				: 
-- Comments		: 
--
---------------------------------------------------------------------------------------------------
-- Header		: OUTPUT_1_EMBED_AUDIO_3_2_STATE
--
-- MIB ref		: swCardEventLogSlotXX       .30.79.85.84.80.85.84.95.49.95.69.77.66.69.68.95.65.85.68.73.79.95.51.95.50.95.83.84.65.84.69
-- absolute OID	: 1.3.6.1.4.1.7995.2.6.1.1.XX.30.79.85.84.80.85.84.95.49.95.69.77.66.69.68.95.65.85.68.73.79.95.51.95.50.95.83.84.65.84.69
-- Vary			: YES
--
-- Value(s)		: WARN:Silent PCM
--				: 
-- Comments		: 
--
---------------------------------------------------------------------------------------------------
-- Header		: OUTPUT_1_EMBED_AUDIO_4_1_STATE
--
-- MIB ref		: swCardEventLogSlotXX       .30.79.85.84.80.85.84.95.49.95.69.77.66.69.68.95.65.85.68.73.79.95.52.95.49.95.83.84.65.84.69
-- absolute OID	: 1.3.6.1.4.1.7995.2.6.1.1.XX.30.79.85.84.80.85.84.95.49.95.69.77.66.69.68.95.65.85.68.73.79.95.52.95.49.95.83.84.65.84.69
-- Vary			: YES
--
-- Value(s)		: WARN:Silent PCM
--				: 
-- Comments		: 
--
---------------------------------------------------------------------------------------------------
-- Header		: OUTPUT_1_EMBED_AUDIO_4_2_STATE
--
-- MIB ref		: swCardEventLogSlotXX       .30.79.85.84.80.85.84.95.49.95.69.77.66.69.68.95.65.85.68.73.79.95.52.95.50.95.83.84.65.84.69
-- absolute OID	: 1.3.6.1.4.1.7995.2.6.1.1.XX.30.79.85.84.80.85.84.95.49.95.69.77.66.69.68.95.65.85.68.73.79.95.52.95.50.95.83.84.65.84.69
-- Vary			: YES
--
-- Value(s)		: WARN:Silent PCM
--				: 
-- Comments		: 
--
---------------------------------------------------------------------------------------------------
-- Header		: OUTPUT_1_EMBED_AUDIO_5_1_STATE
--
-- MIB ref		: swCardEventLogSlotXX       .30.79.85.84.80.85.84.95.49.95.69.77.66.69.68.95.65.85.68.73.79.95.53.95.49.95.83.84.65.84.69
-- absolute OID	: 1.3.6.1.4.1.7995.2.6.1.1.XX.30.79.85.84.80.85.84.95.49.95.69.77.66.69.68.95.65.85.68.73.79.95.53.95.49.95.83.84.65.84.69
-- Vary			: YES
--
-- Value(s)		: WARN:Silent PCM
--				: 
-- Comments		: 
--
---------------------------------------------------------------------------------------------------
-- Header		: OUTPUT_1_EMBED_AUDIO_5_2_STATE
--
-- MIB ref		: swCardEventLogSlotXX       .30.79.85.84.80.85.84.95.49.95.69.77.66.69.68.95.65.85.68.73.79.95.53.95.50.95.83.84.65.84.69
-- absolute OID	: 1.3.6.1.4.1.7995.2.6.1.1.XX.30.79.85.84.80.85.84.95.49.95.69.77.66.69.68.95.65.85.68.73.79.95.53.95.50.95.83.84.65.84.69
-- Vary			: YES
--
-- Value(s)		: WARN:Silent PCM
--				: 
-- Comments		: 
--
---------------------------------------------------------------------------------------------------
-- Header		: OUTPUT_1_EMBED_AUDIO_6_1_STATE
--
-- MIB ref		: swCardEventLogSlotXX       .30.79.85.84.80.85.84.95.49.95.69.77.66.69.68.95.65.85.68.73.79.95.54.95.49.95.83.84.65.84.69
-- absolute OID	: 1.3.6.1.4.1.7995.2.6.1.1.XX.30.79.85.84.80.85.84.95.49.95.69.77.66.69.68.95.65.85.68.73.79.95.54.95.49.95.83.84.65.84.69
-- Vary			: YES
--
-- Value(s)		: WARN:Silent PCM
--				: 
-- Comments		: 
--
---------------------------------------------------------------------------------------------------
-- Header		: OUTPUT_1_EMBED_AUDIO_6_2_STATE
--
-- MIB ref		: swCardEventLogSlotXX       .30.79.85.84.80.85.84.95.49.95.69.77.66.69.68.95.65.85.68.73.79.95.54.95.50.95.83.84.65.84.69
-- absolute OID	: 1.3.6.1.4.1.7995.2.6.1.1.XX.30.79.85.84.80.85.84.95.49.95.69.77.66.69.68.95.65.85.68.73.79.95.54.95.50.95.83.84.65.84.69
-- Vary			: YES
--
-- Value(s)		: WARN:Silent PCM
--				: 
-- Comments		: 
--
---------------------------------------------------------------------------------------------------
-- Header		: OUTPUT_1_EMBED_AUDIO_7_1_STATE
--
-- MIB ref		: swCardEventLogSlotXX       .30.79.85.84.80.85.84.95.49.95.69.77.66.69.68.95.65.85.68.73.79.95.55.95.49.95.83.84.65.84.69
-- absolute OID	: 1.3.6.1.4.1.7995.2.6.1.1.XX.30.79.85.84.80.85.84.95.49.95.69.77.66.69.68.95.65.85.68.73.79.95.55.95.49.95.83.84.65.84.69
-- Vary			: YES
--
-- Value(s)		: WARN:Silent PCM
--				: 
-- Comments		: 
--
---------------------------------------------------------------------------------------------------
-- Header		: OUTPUT_1_EMBED_AUDIO_7_2_STATE
--
-- MIB ref		: swCardEventLogSlotXX       .30.79.85.84.80.85.84.95.49.95.69.77.66.69.68.95.65.85.68.73.79.95.55.95.50.95.83.84.65.84.69
-- absolute OID	: 1.3.6.1.4.1.7995.2.6.1.1.XX.30.79.85.84.80.85.84.95.49.95.69.77.66.69.68.95.65.85.68.73.79.95.55.95.50.95.83.84.65.84.69
-- Vary			: YES
--
-- Value(s)		: WARN:Silent PCM
--				: 
-- Comments		: 
--
---------------------------------------------------------------------------------------------------
-- Header		: OUTPUT_1_EMBED_AUDIO_8_1_STATE
--
-- MIB ref		: swCardEventLogSlotXX       .30.79.85.84.80.85.84.95.49.95.69.77.66.69.68.95.65.85.68.73.79.95.56.95.49.95.83.84.65.84.69
-- absolute OID	: 1.3.6.1.4.1.7995.2.6.1.1.XX.30.79.85.84.80.85.84.95.49.95.69.77.66.69.68.95.65.85.68.73.79.95.56.95.49.95.83.84.65.84.69
-- Vary			: YES
--
-- Value(s)		: WARN:Silent PCM
--				: 
-- Comments		: 
--
---------------------------------------------------------------------------------------------------
-- Header		: OUTPUT_1_EMBED_AUDIO_8_2_STATE
--
-- MIB ref		: swCardEventLogSlotXX       .30.79.85.84.80.85.84.95.49.95.69.77.66.69.68.95.65.85.68.73.79.95.56.95.50.95.83.84.65.84.69
-- absolute OID	: 1.3.6.1.4.1.7995.2.6.1.1.XX.30.79.85.84.80.85.84.95.49.95.69.77.66.69.68.95.65.85.68.73.79.95.56.95.50.95.83.84.65.84.69
-- Vary			: YES
--
-- Value(s)		: WARN:Silent PCM
--				: 
-- Comments		: 
--
---------------------------------------------------------------------------------------------------
