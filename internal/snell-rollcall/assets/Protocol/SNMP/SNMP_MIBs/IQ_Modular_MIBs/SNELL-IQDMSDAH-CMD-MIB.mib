-- ************************************************************************************
-- Snell&Wilcox Card:IQDMSDAH
--        Module Id#:236
--       Command Set:10
--          Filename:SNELL-IQDMSDAH-CMD-MIB.mib
--            Author:Jonathan Riches
--              Date:30/06/2005
--              Time:09:00
--
-- Copyright (c) 2005 Snell & Wilcox Ltd
-- All rights reserved.
--
-- ************************************************************************************

SNELL-IQDMSDAH-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDMSDAH,
    moduleIQDMSDAHMIB
        FROM SNELL-WILCOX-PRODUCT-REG;

 moduleIQDMSDAHCmdMi MODULE-IDENTITY
    LAST-UPDATED "0506300900Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDMSDAHMIB 1 }




--********************************************************************************
--*
--*  Snell Wilcox Card:
--*  command set:
--*  list commands/menus:
--*
--******************************************************************************
	iqdmsdahCmdTable OBJECT-TYPE
		SYNTAX			SEQUENCE OF IqdmsdahCmdEntry
		MAX-ACCESS		not-accessible
		STATUS			current
		DESCRIPTION
				"Note the instance of this table is relected in the command set Version"
		::= { moduleIQDMSDAH 1 }

	iqdmsdahCmdEntry OBJECT-TYPE
		SYNTAX		IqdmsdahCmdEntry
		MAX-ACCESS		not-accessible
		STATUS			current
		DESCRIPTION
				"Entry in command table."
		INDEX	{ iqdmsdahSlotIndex }
		::= { iqdmsdahCmdTable 1 }

	IqdmsdahCmdEntry ::=
		SEQUENCE {
			iqdmsdahSlotIndex
				Unsigned32,
			iqdmsdahStandard
				INTEGER,
			iqdmsdahMode
				INTEGER,
			iqdmsdahGenlockMode
				INTEGER,
			iqdmsdahGenlockHPhase
				INTEGER,
			iqdmsdahGenlockVPhase
				INTEGER,
			iqdmsdahFreeze
				INTEGER,
			iqdmsdahProcAmpVideoGain
				INTEGER,
			iqdmsdahProcAmpBlackLevel
				INTEGER,
			iqdmsdahProcAmpChromaGain
				INTEGER,
			iqdmsdahProcAmpNTSCHue
				INTEGER,
			iqdmsdahProcAmpYCDelay
				INTEGER,
			iqdmsdahProcAmpPicturePosition
				INTEGER,
			iqdmsdahMemoryReadMemory
				INTEGER,
			iqdmsdahMemorySaveMemory
				INTEGER,
			iqdmsdahMemoryNameUserMemoryMemory1Name
				RollCallString,
			iqdmsdahMemoryNameUserMemoryMemory2Name
				RollCallString,
			iqdmsdahMemoryNameUserMemoryMemory3Name
				RollCallString,
			iqdmsdahMemoryNameUserMemoryMemory4Name
				RollCallString,
			iqdmsdahMemoryNameUserMemoryPresetAllNames
				INTEGER,
			iqdmsdahMemoryClearUserMemory
				INTEGER,
			iqdmsdahSetupVITSVITSPass
				INTEGER,
			iqdmsdahSetupVITSPassLine283
				INTEGER,
			iqdmsdahSetupVITSPassLine21
				INTEGER,
			iqdmsdahSetupVITSPassLine23
				INTEGER,
			iqdmsdahSetupPedestalStrip
				INTEGER,
			iqdmsdahSetupBlanking
				INTEGER,
			iqdmsdahSetupBlankingVariableBlanking
				INTEGER,
			iqdmsdahSetupVHSPeaking
				INTEGER,
			iqdmsdahSetupPatternPatternOn
				INTEGER,
			iqdmsdahSetupPatternSelectPattern
				INTEGER,
			iqdmsdahSetupDefaultOutputAutoFreeze
				INTEGER,
			iqdmsdahSetupDefaultOutputDefaultPattern
				INTEGER,
			iqdmsdahSetupCaptionEditCaption
				RollCallString,
			iqdmsdahSetupCaptionInsertCaption
				INTEGER,
			iqdmsdahSetupEDHEnable
				INTEGER,
			iqdmsdahSetupRollTrackUnit1
				RollCallString,
			iqdmsdahSetupRollTrackUnit2
				RollCallString,
			iqdmsdahSetupRollTrackUnit3
				RollCallString,
			iqdmsdahSetupRollTrackUnit4
				RollCallString,
			iqdmsdahSetupRollTrackUnit5
				RollCallString,
			iqdmsdahSetupRollTrackUnit6
				RollCallString,
			iqdmsdahSetupRollTrackUnit7
				RollCallString,
			iqdmsdahSetupRollTrackUnit8
				RollCallString,
			iqdmsdahSetupRollTrackMessages
				INTEGER,
			iqdmsdahSetupLoggingInpStdChange
				INTEGER,
			iqdmsdahSetupLoggingReferenceLoss
				INTEGER,
			iqdmsdahSetupPresetUnit
				INTEGER,
			iqdmsdahSetupSoftwareVersion
				RollCallString,
			iqdmsdahSetupSerialNo
				RollCallString
		}

	iqdmsdahSlotIndex OBJECT-TYPE
		SYNTAX		Unsigned32
		MAX-ACCESS		not-accessible
		STATUS			current
		DESCRIPTION
				"The unique Index value for each slot.  Its value
					ranges between 1 and the value of slotNumber."
		::= { iqdmsdahCmdEntry 0 }


	iqdmsdahStandard OBJECT-TYPE
		SYNTAX		INTEGER {
							val_PAL(2),
							val_NTSC(1),
							val_PAL_N(4),
							val_PAL_M(3),
							val_SECAM(6),
							val_NTSC_4_43(5)
							}
		MAX-ACCESS		read-write
		STATUS			current
		DESCRIPTION
				"TYPE: - RadiobuttonList
					Standard  cmdID= 10 
					PAL  value= 2  
					NTSC  value= 1  
					PAL-N  value= 4  
					PAL-M  value= 3  
					SECAM  value= 6  
					NTSC-4.43  value= 5  "
		::= { iqdmsdahCmdEntry 10 }


	iqdmsdahMode OBJECT-TYPE
		SYNTAX		INTEGER {
							val_Field_Comb_Crystal(0),
							val_Line_Comb_Crystal(1),
							val_Simple_VHS(5),
							val_Pass_Through(6)
							}
		MAX-ACCESS		read-write
		STATUS			current
		DESCRIPTION
				"TYPE: - RadiobuttonList
					Mode  cmdID= 11 
					Field_Comb/Crystal  value= 0  
					Line_Comb/Crystal  value= 1  
					Simple/VHS  value= 5  
					Pass_Through  value= 6  "
		::= { iqdmsdahCmdEntry 11 }


	iqdmsdahGenlockMode OBJECT-TYPE
		SYNTAX		INTEGER {
							val_Genlock(0),
							val_Minimum_Delay(1),
							val_Free_Run(2)
							}
		MAX-ACCESS		read-write
		STATUS			current
		DESCRIPTION
				"TYPE: - RadiobuttonList
					Mode  cmdID= 43 
					Genlock  value= 0  
					Minimum_Delay  value= 1  
					Free_Run  value= 2  "
		::= { iqdmsdahCmdEntry 43 }


	iqdmsdahGenlockHPhase OBJECT-TYPE
		SYNTAX		INTEGER
		MAX-ACCESS		read-write
		STATUS			current
		DESCRIPTION
				"TYPE: - Number
					H_Phase  cmdID= 45  min= -31968  max= 31968  step= 37  format= %4.0fns  div_scale= 1 
					Min = -31968ns  Max = 31968ns  Step =   37ns "
		::= { iqdmsdahCmdEntry 45 }


	iqdmsdahGenlockVPhase OBJECT-TYPE
		SYNTAX		INTEGER
		MAX-ACCESS		read-write
		STATUS			current
		DESCRIPTION
				"TYPE: - Number
					V_Phase  cmdID= 44  min= -7  max= 7  step= 1  format= %4.0f Lines  div_scale= 1 
					Min =   -7 Lines  Max =    7 Lines  Step =    1 Lines "
		::= { iqdmsdahCmdEntry 44 }


	iqdmsdahFreeze OBJECT-TYPE
		SYNTAX		INTEGER { disable(0), enable(1) }
		MAX-ACCESS		read-write
		STATUS			current
		DESCRIPTION
				"TYPE: - Checkbox
					Freeze  cmdID= 46 "
		::= { iqdmsdahCmdEntry 46 }


	iqdmsdahProcAmpVideoGain OBJECT-TYPE
		SYNTAX		INTEGER
		MAX-ACCESS		read-write
		STATUS			current
		DESCRIPTION
				"TYPE: - Number
					Video_Gain  cmdID= 5  min= -30  max= 60  step= 1  format= %1.1f dB  div_scale= 10 
					Min = -3.0 dB  Max = 6.0 dB  Step = 0.1 dB "
		::= { iqdmsdahCmdEntry 5 }


	iqdmsdahProcAmpBlackLevel OBJECT-TYPE
		SYNTAX		INTEGER
		MAX-ACCESS		read-write
		STATUS			current
		DESCRIPTION
				"TYPE: - Number
					Black_Level  cmdID= 6  min= -75  max= 75  step= 1  format= %1.0f  div_scale= 1 
					Min = -75  Max = 75  Step = 1 "
		::= { iqdmsdahCmdEntry 6 }


	iqdmsdahProcAmpChromaGain OBJECT-TYPE
		SYNTAX		INTEGER
		MAX-ACCESS		read-write
		STATUS			current
		DESCRIPTION
				"TYPE: - Number
					Chroma_Gain  cmdID= 7  min= -30  max= 30  step= 1  format= %1.1f dB  div_scale= 10 
					Min = -3.0 dB  Max = 3.0 dB  Step = 0.1 dB "
		::= { iqdmsdahCmdEntry 7 }


	iqdmsdahProcAmpNTSCHue OBJECT-TYPE
		SYNTAX		INTEGER
		MAX-ACCESS		read-write
		STATUS			current
		DESCRIPTION
				"TYPE: - Number
					NTSC_Hue  cmdID= 8  min= -30  max= 30  step= 1  format= %1.0f Deg  div_scale= 1 
					Min = -30 Deg  Max = 30 Deg  Step = 1 Deg "
		::= { iqdmsdahCmdEntry 8 }


	iqdmsdahProcAmpYCDelay OBJECT-TYPE
		SYNTAX		INTEGER
		MAX-ACCESS		read-write
		STATUS			current
		DESCRIPTION
				"TYPE: - Number
					YC_Delay  cmdID= 9  min= -222  max= 148  step= 74  format= %4.0fns  div_scale= 1 
					Min = -222ns  Max =  148ns  Step =   74ns "
		::= { iqdmsdahCmdEntry 9 }


	iqdmsdahProcAmpPicturePosition OBJECT-TYPE
		SYNTAX		INTEGER
		MAX-ACCESS		read-write
		STATUS			current
		DESCRIPTION
				"TYPE: - Number
					Picture_Position  cmdID= 42  min= -2220  max= 2220  step= 148  format= %1.0f ns  div_scale= 1 
					Min = -2220 ns  Max = 2220 ns  Step = 148 ns "
		::= { iqdmsdahCmdEntry 42 }


	iqdmsdahMemoryReadMemory OBJECT-TYPE
		SYNTAX		INTEGER {
							val_Memory_1(0),
							val_Memory_2(1),
							val_Memory_3(2),
							val_Memory_4(3)
							}
		MAX-ACCESS		read-write
		STATUS			current
		DESCRIPTION
				"TYPE: - RadiobuttonList
					Read_Memory  cmdID= 18 
					Memory__1  value= 0  
					Memory__2  value= 1  
					Memory__3  value= 2  
					Memory__4  value= 3  "
		::= { iqdmsdahCmdEntry 18 }


	iqdmsdahMemorySaveMemory OBJECT-TYPE
		SYNTAX		INTEGER {
							val_Memory_1(0),
							val_Memory_2(1),
							val_Memory_3(2),
							val_Memory_4(3)
							}
		MAX-ACCESS		read-write
		STATUS			current
		DESCRIPTION
				"TYPE: - RadiobuttonList
					Save_Memory  cmdID= 19 
					Memory__1  value= 0  
					Memory__2  value= 1  
					Memory__3  value= 2  
					Memory__4  value= 3  "
		::= { iqdmsdahCmdEntry 19 }


	iqdmsdahMemoryNameUserMemoryMemory1Name OBJECT-TYPE
		SYNTAX		RollCallString
		MAX-ACCESS		read-write
		STATUS			current
		DESCRIPTION
				"TYPE: - Editstring
					Memory_1_Name  cmdID= 20  "
		::= { iqdmsdahCmdEntry 20 }


	iqdmsdahMemoryNameUserMemoryMemory2Name OBJECT-TYPE
		SYNTAX		RollCallString
		MAX-ACCESS		read-write
		STATUS			current
		DESCRIPTION
				"TYPE: - Editstring
					Memory_2_Name  cmdID= 21  "
		::= { iqdmsdahCmdEntry 21 }


	iqdmsdahMemoryNameUserMemoryMemory3Name OBJECT-TYPE
		SYNTAX		RollCallString
		MAX-ACCESS		read-write
		STATUS			current
		DESCRIPTION
				"TYPE: - Editstring
					Memory_3_Name  cmdID= 22  "
		::= { iqdmsdahCmdEntry 22 }


	iqdmsdahMemoryNameUserMemoryMemory4Name OBJECT-TYPE
		SYNTAX		RollCallString
		MAX-ACCESS		read-write
		STATUS			current
		DESCRIPTION
				"TYPE: - Editstring
					Memory_4_Name  cmdID= 23  "
		::= { iqdmsdahCmdEntry 23 }


	iqdmsdahMemoryNameUserMemoryPresetAllNames OBJECT-TYPE
		SYNTAX		INTEGER { noAction(0),val_Preset_All_Names(1) }
		MAX-ACCESS		read-write
		STATUS			current
		DESCRIPTION
				"TYPE: - Button
					Preset_All_Names  cmdID= 25  value= 1  "
		::= { iqdmsdahCmdEntry 25 }


	iqdmsdahMemoryClearUserMemory OBJECT-TYPE
		SYNTAX		INTEGER {
							val_Memory_1(0),
							val_Memory_2(1),
							val_Memory_3(2),
							val_Memory_4(3)
							}
		MAX-ACCESS		read-write
		STATUS			current
		DESCRIPTION
				"TYPE: - RadiobuttonList
					Clear_User_Memory  cmdID= 24 
					Memory_1  value= 0  
					Memory_2  value= 1  
					Memory_3  value= 2  
					Memory_4  value= 3  "
		::= { iqdmsdahCmdEntry 24 }


	iqdmsdahSetupVITSVITSPass OBJECT-TYPE
		SYNTAX		INTEGER { disable(0), enable(1) }
		MAX-ACCESS		read-write
		STATUS			current
		DESCRIPTION
				"TYPE: - Checkbox
					VITS_Pass  cmdID= 38 "
		::= { iqdmsdahCmdEntry 38 }


	iqdmsdahSetupVITSPassLine283 OBJECT-TYPE
		SYNTAX		INTEGER { disable(0), enable(1) }
		MAX-ACCESS		read-write
		STATUS			current
		DESCRIPTION
				"TYPE: - Checkbox
					Pass_Line_283  cmdID= 39 "
		::= { iqdmsdahCmdEntry 39 }


	iqdmsdahSetupVITSPassLine21 OBJECT-TYPE
		SYNTAX		INTEGER { disable(0), enable(1) }
		MAX-ACCESS		read-write
		STATUS			current
		DESCRIPTION
				"TYPE: - Checkbox
					Pass_Line_21  cmdID= 40 "
		::= { iqdmsdahCmdEntry 40 }


	iqdmsdahSetupVITSPassLine23 OBJECT-TYPE
		SYNTAX		INTEGER { disable(0), enable(1) }
		MAX-ACCESS		read-write
		STATUS			current
		DESCRIPTION
				"TYPE: - Checkbox
					Pass_Line_23  cmdID= 41 "
		::= { iqdmsdahCmdEntry 41 }


	iqdmsdahSetupPedestalStrip OBJECT-TYPE
		SYNTAX		INTEGER { disable(0), enable(1) }
		MAX-ACCESS		read-write
		STATUS			current
		DESCRIPTION
				"TYPE: - Checkbox
					Pedestal_Strip  cmdID= 17 "
		::= { iqdmsdahCmdEntry 17 }


	iqdmsdahSetupBlanking OBJECT-TYPE
		SYNTAX		INTEGER {
							val_Digital(0),
							val_Analogue(1)
							}
		MAX-ACCESS		read-write
		STATUS			current
		DESCRIPTION
				"TYPE: - Button
					Digital  cmdID= 36  value= 0  
					Analogue  cmdID= 36  value= 1  "
		::= { iqdmsdahCmdEntry 36 }


	iqdmsdahSetupBlankingVariableBlanking OBJECT-TYPE
		SYNTAX		INTEGER
		MAX-ACCESS		read-write
		STATUS			current
		DESCRIPTION
				"TYPE: - Number
					Variable_Blanking  cmdID= 37  min= -1184  max= 1184  step= 74  format= %4.0fns  div_scale= 1 
					Min = -1184ns  Max = 1184ns  Step =   74ns "
		::= { iqdmsdahCmdEntry 37 }


	iqdmsdahSetupVHSPeaking OBJECT-TYPE
		SYNTAX		INTEGER { disable(0), enable(1) }
		MAX-ACCESS		read-write
		STATUS			current
		DESCRIPTION
				"TYPE: - Checkbox
					VHS_Peaking  cmdID= 56 "
		::= { iqdmsdahCmdEntry 56 }


	iqdmsdahSetupPatternPatternOn OBJECT-TYPE
		SYNTAX		INTEGER { disable(0), enable(1) }
		MAX-ACCESS		read-write
		STATUS			current
		DESCRIPTION
				"TYPE: - Checkbox
					Pattern_On  cmdID= 13 "
		::= { iqdmsdahCmdEntry 13 }


	iqdmsdahSetupPatternSelectPattern OBJECT-TYPE
		SYNTAX		INTEGER
		MAX-ACCESS		read-write
		STATUS			current
		DESCRIPTION
				"TYPE: - Number
					Select_Pattern  cmdID= 12  min= 0  max= 3  step= 1  format= %f  div_scale= 1 
					Min = 0.000000  Max = 3.000000  Step = 1.000000 "
		::= { iqdmsdahCmdEntry 12 }


	iqdmsdahSetupDefaultOutputAutoFreeze OBJECT-TYPE
		SYNTAX		INTEGER { disable(0), enable(1) }
		MAX-ACCESS		read-write
		STATUS			current
		DESCRIPTION
				"TYPE: - Checkbox
					Auto_Freeze  cmdID= 58 "
		::= { iqdmsdahCmdEntry 58 }


	iqdmsdahSetupDefaultOutputDefaultPattern OBJECT-TYPE
		SYNTAX		INTEGER
		MAX-ACCESS		read-write
		STATUS			current
		DESCRIPTION
				"TYPE: - Number
					Default_Pattern  cmdID= 14  min= 0  max= 3  step= 1  format= %f  div_scale= 1 
					Min = 0.000000  Max = 3.000000  Step = 1.000000 "
		::= { iqdmsdahCmdEntry 14 }


	iqdmsdahSetupCaptionEditCaption OBJECT-TYPE
		SYNTAX		RollCallString
		MAX-ACCESS		read-write
		STATUS			current
		DESCRIPTION
				"TYPE: - Editstring
					Edit_Caption  cmdID= 16  "
		::= { iqdmsdahCmdEntry 16 }


	iqdmsdahSetupCaptionInsertCaption OBJECT-TYPE
		SYNTAX		INTEGER { disable(0), enable(1) }
		MAX-ACCESS		read-write
		STATUS			current
		DESCRIPTION
				"TYPE: - Checkbox
					Insert_Caption  cmdID= 15 "
		::= { iqdmsdahCmdEntry 15 }


	iqdmsdahSetupEDHEnable OBJECT-TYPE
		SYNTAX		INTEGER { disable(0), enable(1) }
		MAX-ACCESS		read-write
		STATUS			current
		DESCRIPTION
				"TYPE: - Checkbox
					EDH_Enable  cmdID= 27 "
		::= { iqdmsdahCmdEntry 27 }


	iqdmsdahSetupRollTrackUnit1 OBJECT-TYPE
		SYNTAX		RollCallString
		MAX-ACCESS		read-write
		STATUS			current
		DESCRIPTION
				"TYPE: - Editstring
					Unit_1  cmdID= 48  "
		::= { iqdmsdahCmdEntry 48 }


	iqdmsdahSetupRollTrackUnit2 OBJECT-TYPE
		SYNTAX		RollCallString
		MAX-ACCESS		read-write
		STATUS			current
		DESCRIPTION
				"TYPE: - Editstring
					Unit_2  cmdID= 49  "
		::= { iqdmsdahCmdEntry 49 }


	iqdmsdahSetupRollTrackUnit3 OBJECT-TYPE
		SYNTAX		RollCallString
		MAX-ACCESS		read-write
		STATUS			current
		DESCRIPTION
				"TYPE: - Editstring
					Unit_3  cmdID= 50  "
		::= { iqdmsdahCmdEntry 50 }


	iqdmsdahSetupRollTrackUnit4 OBJECT-TYPE
		SYNTAX		RollCallString
		MAX-ACCESS		read-write
		STATUS			current
		DESCRIPTION
				"TYPE: - Editstring
					Unit_4  cmdID= 51  "
		::= { iqdmsdahCmdEntry 51 }


	iqdmsdahSetupRollTrackUnit5 OBJECT-TYPE
		SYNTAX		RollCallString
		MAX-ACCESS		read-write
		STATUS			current
		DESCRIPTION
				"TYPE: - Editstring
					Unit_5  cmdID= 52  "
		::= { iqdmsdahCmdEntry 52 }


	iqdmsdahSetupRollTrackUnit6 OBJECT-TYPE
		SYNTAX		RollCallString
		MAX-ACCESS		read-write
		STATUS			current
		DESCRIPTION
				"TYPE: - Editstring
					Unit_6  cmdID= 53  "
		::= { iqdmsdahCmdEntry 53 }


	iqdmsdahSetupRollTrackUnit7 OBJECT-TYPE
		SYNTAX		RollCallString
		MAX-ACCESS		read-write
		STATUS			current
		DESCRIPTION
				"TYPE: - Editstring
					Unit_7  cmdID= 54  "
		::= { iqdmsdahCmdEntry 54 }


	iqdmsdahSetupRollTrackUnit8 OBJECT-TYPE
		SYNTAX		RollCallString
		MAX-ACCESS		read-write
		STATUS			current
		DESCRIPTION
				"TYPE: - Editstring
					Unit_8  cmdID= 55  "
		::= { iqdmsdahCmdEntry 55 }


	iqdmsdahSetupRollTrackMessages OBJECT-TYPE
		SYNTAX		INTEGER { disable(0), enable(1) }
		MAX-ACCESS		read-write
		STATUS			current
		DESCRIPTION
				"TYPE: - Checkbox
					RollTrack_Messages  cmdID= 61 "
		::= { iqdmsdahCmdEntry 61 }


	iqdmsdahSetupLoggingInpStdChange OBJECT-TYPE
		SYNTAX		INTEGER { disable(0), enable(1) }
		MAX-ACCESS		read-write
		STATUS			current
		DESCRIPTION
				"TYPE: - Checkbox
					Inp/Std_Change  cmdID= 26 "
		::= { iqdmsdahCmdEntry 26 }


	iqdmsdahSetupLoggingReferenceLoss OBJECT-TYPE
		SYNTAX		INTEGER { disable(0), enable(1) }
		MAX-ACCESS		read-write
		STATUS			current
		DESCRIPTION
				"TYPE: - Checkbox
					Reference_Loss  cmdID= 47 "
		::= { iqdmsdahCmdEntry 47 }


	iqdmsdahSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqdmsdahCmdEntry 3 }


	iqdmsdahSetupSoftwareVersion OBJECT-TYPE
		SYNTAX		RollCallString
		MAX-ACCESS		read-only
		STATUS			current
		DESCRIPTION
				"TYPE: - Display
					Software_Version  cmdID= 2  format=   "
		::= { iqdmsdahCmdEntry 2 }


	iqdmsdahSetupSerialNo OBJECT-TYPE
		SYNTAX		RollCallString
		MAX-ACCESS		read-only
		STATUS			current
		DESCRIPTION
				"TYPE: - Display
					Serial_No  cmdID= 1  format=   "
		::= { iqdmsdahCmdEntry 1 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: UNKNOWN
--				: AUTO
--				: NTSC
--				: PAL
--				: PAL-M
--				: PAL-N
--				: NTSC-443
--				: SECAM
--				: MONO
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: ERROR
--				: OK
-- Comments		: 
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: N/A
--				: LOST
--				: OK
-- Comments		: 
--
---------------------------------------------------------------------------------------------------
