-- Generated file, do not edit
--
-- (c) 2005 Snell and Wilcox Ltd, all rights reserved.
-- Format: MIBv2
-- Product: Alchemist HD
-- ProductID: 471
-- CommandSet: 9
-- Software: V9.0.0
-- CreatedBy: mibgen
-- CreationDate: Thu Apr 30 11:10:29 2009

SNELL-AlchemistHd-CMD DEFINITIONS ::= BEGIN

IMPORTS
	OBJECT-TYPE, NOTIFICATION-TYPE, MODULE-IDENTITY, OBJECT-IDENTITY,
	Counter32, Gauge32, IpAddress, Unsigned32, Integer32
		FROM SNMPv2-SMI

	OBJECT-GROUP, MODULE-COMPLIANCE, AGENT-CAPABILITIES
		FROM SNMPv2-CONF

	RollCallString
		FROM SNELL-WILCOX-TC

	conversionAlchemistHd, conversionAlchemistHdMib
		FROM SNELL-WILCOX-PRODUCT-REG;

conversionAlchemistHdMi MODULE-IDENTITY
	LAST-UPDATED "200904301110Z"
	ORGANIZATION "Snell & Wilcox Ltd"
	CONTACT-INFO
		"Primary Author: Generated by mibgen

		post:	Southleigh Park House
			Eastleigh Road
			Havant, Hants
			PO9 2PE
		phone:	+44 (0)23 92489000
		email:	snmp.support@snellwilcox.com"
	DESCRIPTION "Command logging and trap interface for Alchemist HD"

	REVISION "200904301110Z"
	DESCRIPTION	"Sole revision, this file generated on each release"
		::= { conversionAlchemistHdMib 1 }

-- ********************************
-- Notifications

	alchemistHdNoteEntries OBJECT IDENTIFIER ::= { conversionAlchemistHd 0 }

	input1Standard NOTIFICATION-TYPE
		OBJECTS		{ logInpStdStat }
		STATUS		current
		DESCRIPTION	"
			style='ReadOnly string'
			path='/System/Debug/status/status1/input_status'
		"
		::= { alchemistHdNoteEntries 6000 }

	output1Standard NOTIFICATION-TYPE
		OBJECTS		{ logOutAStdStat }
		STATUS		current
		DESCRIPTION	"
			style='ReadOnly string'
			path='/System/Debug/status/status1/output_a_status'
		"
		::= { alchemistHdNoteEntries 6001 }

	extRef NOTIFICATION-TYPE
		OBJECTS		{ logRefStdStat }
		STATUS		current
		DESCRIPTION	"
			style='ReadOnly string'
			path='/System/Debug/status/status1/reference_status'
		"
		::= { alchemistHdNoteEntries 6002 }

	systemStatus NOTIFICATION-TYPE
		OBJECTS		{ logStatusStat }
		STATUS		current
		DESCRIPTION	"
			style='ReadOnly numeric'
			path='/System/Debug/status/status1/status_string'
		"
		::= { alchemistHdNoteEntries 6006 }

	output2Standard NOTIFICATION-TYPE
		OBJECTS		{ logOutBStdStat }
		STATUS		current
		DESCRIPTION	"
			style='ReadOnly string'
			path='/System/Debug/status/status1/output_b_status'
		"
		::= { alchemistHdNoteEntries 6011 }

	input NOTIFICATION-TYPE
		OBJECTS		{ logInpLossStat }
		STATUS		current
		DESCRIPTION	"
			style='Radiobutton list'
			preset='ok'
			path='/System/Debug/status/input_state'
		"
		::= { alchemistHdNoteEntries 6665 }



-- ********************************
-- Control

	alchemistHdCtrlEntries OBJECT IDENTIFIER ::= { conversionAlchemistHd 1 }

	panelcalibrate OBJECT-TYPE
		SYNTAX		INTEGER { ready(0), trigger(1) }
		MAX-ACCESS	read-write
		STATUS		current
		DESCRIPTION	"
			style='Event button'
			path='/System 2/Panel Controls/Calibrate'
		"
		::= { alchemistHdCtrlEntries 21 }

	panelclean OBJECT-TYPE
		SYNTAX		INTEGER { ready(0), trigger(1) }
		MAX-ACCESS	read-write
		STATUS		current
		DESCRIPTION	"
			style='Event button'
			path='/System 2/Panel Controls/Clean'
		"
		::= { alchemistHdCtrlEntries 22 }

	paneldim OBJECT-TYPE
		SYNTAX		INTEGER { enable(0), disable(1) }
		MAX-ACCESS	read-write
		STATUS		current
		DESCRIPTION	"
			style='Checkbox'
			path='/System 2/Panel Controls/Dim'
		"
		::= { alchemistHdCtrlEntries 23 }

	paneltimeout OBJECT-TYPE
		SYNTAX		Integer32 (0..30)
		MAX-ACCESS	read-write
		STATUS		current
		DESCRIPTION	"
			style='Numeric control'
			range='0..30'
			preset='5'
			path='/System 2/Panel Controls/Timeout'
		"
		::= { alchemistHdCtrlEntries 24 }

	panelbrightness OBJECT-TYPE
		SYNTAX		Integer32 (0..100)
		MAX-ACCESS	read-write
		STATUS		current
		DESCRIPTION	"
			style='Numeric control'
			range='0..100'
			preset='3'
			path='/System 2/Panel Controls/Brightness'
		"
		::= { alchemistHdCtrlEntries 25 }

	memoryRecall OBJECT-TYPE
		SYNTAX		INTEGER {
					auto(0),
					v525i59(19),
					v1080i50(8),
					v1080i59(7),
					v1080i60(6),
					v625i50(20),
					v720p50(30),
					v720p59(17),
					v720p60(16)
				}
		MAX-ACCESS	read-write
		STATUS		current
		DESCRIPTION	"
			style='Radiobutton list'
			path='/System/Debug/Demo/MR'
		"
		::= { alchemistHdCtrlEntries 31 }

	fittedOptions OBJECT-TYPE
		SYNTAX		Integer32 (0..255)
		MAX-ACCESS	read-only
		STATUS		current
		DESCRIPTION	"
			style='ReadOnly numeric'
			range='0..255'
			path='/System/Debug/status/status1/Fitted Options'
		"
		::= { alchemistHdCtrlEntries 814 }

	audDelay OBJECT-TYPE
		SYNTAX		Integer32
		MAX-ACCESS	read-only
		STATUS		current
		DESCRIPTION	"
			style='ReadOnly numeric'
			path='/System/Debug/status/status2/Audio delay'
		"
		::= { alchemistHdCtrlEntries 2310 }

	referenceTimingHorizA OBJECT-TYPE
		SYNTAX		Integer32 (-2640..2640)
		MAX-ACCESS	read-only
		STATUS		current
		DESCRIPTION	"
			style='ReadOnly numeric'
			range='-2640..2640'
			path='/System/Debug/status/status2/Horizontal timing A'
		"
		::= { alchemistHdCtrlEntries 2430 }

	referenceTimingVertA OBJECT-TYPE
		SYNTAX		Integer32 (-1249..1249)
		MAX-ACCESS	read-only
		STATUS		current
		DESCRIPTION	"
			style='ReadOnly numeric'
			range='-1249..1249'
			path='/System/Debug/status/status2/Vertical timing A'
		"
		::= { alchemistHdCtrlEntries 2431 }

	referenceTimingHorizB OBJECT-TYPE
		SYNTAX		Integer32 (-2640..2640)
		MAX-ACCESS	read-only
		STATUS		current
		DESCRIPTION	"
			style='ReadOnly numeric'
			range='-2640..2640'
			path='/System/Debug/status/status2/Horizontal timing B'
		"
		::= { alchemistHdCtrlEntries 2433 }

	referenceTimingVertB OBJECT-TYPE
		SYNTAX		Integer32 (-1249..1249)
		MAX-ACCESS	read-only
		STATUS		current
		DESCRIPTION	"
			style='ReadOnly numeric'
			range='-1249..1249'
			path='/System/Debug/status/status2/Vertical timing B'
		"
		::= { alchemistHdCtrlEntries 2434 }

	referenceTimingHorizInp OBJECT-TYPE
		SYNTAX		Integer32 (-2640..2640)
		MAX-ACCESS	read-only
		STATUS		current
		DESCRIPTION	"
			style='ReadOnly numeric'
			range='-2640..2640'
			path='/System/Debug/status/status2/Horizontal timing'
		"
		::= { alchemistHdCtrlEntries 2435 }

	referenceTimingVertInp OBJECT-TYPE
		SYNTAX		Integer32 (-1249..1249)
		MAX-ACCESS	read-only
		STATUS		current
		DESCRIPTION	"
			style='ReadOnly numeric'
			range='-1249..1249'
			path='/System/Debug/status/status2/Vertical timing'
		"
		::= { alchemistHdCtrlEntries 2436 }

	aliasSuppressionHorizA OBJECT-TYPE
		SYNTAX		Integer32 (-50..50)
		MAX-ACCESS	read-write
		STATUS		current
		DESCRIPTION	"
			style='Numeric control'
			range='-50..50'
			path='/Enhancements/Alias Suppression/Horizontal a'
		"
		::= { alchemistHdCtrlEntries 4197 }

	aliasSuppressionHorizB OBJECT-TYPE
		SYNTAX		Integer32 (-50..50)
		MAX-ACCESS	read-write
		STATUS		current
		DESCRIPTION	"
			style='Numeric control'
			range='-50..50'
			path='/Enhancements/Alias Suppression/Horizontal b'
		"
		::= { alchemistHdCtrlEntries 4198 }

	aliasSuppressionVertA OBJECT-TYPE
		SYNTAX		Integer32 (-50..50)
		MAX-ACCESS	read-write
		STATUS		current
		DESCRIPTION	"
			style='Numeric control'
			range='-50..50'
			path='/Enhancements/Alias Suppression/Vertical a'
		"
		::= { alchemistHdCtrlEntries 4297 }

	aliasSuppressionVertB OBJECT-TYPE
		SYNTAX		Integer32 (-50..50)
		MAX-ACCESS	read-write
		STATUS		current
		DESCRIPTION	"
			style='Numeric control'
			range='-50..50'
			path='/Enhancements/Alias Suppression/Vertical b'
		"
		::= { alchemistHdCtrlEntries 4298 }

	aliasSuppressionHoriz OBJECT-TYPE
		SYNTAX		Integer32 (-50..50)
		MAX-ACCESS	read-write
		STATUS		current
		DESCRIPTION	"
			style='Numeric control'
			range='-50..50'
			path='/Enhancements/Alias Suppression/Horizontal'
		"
		::= { alchemistHdCtrlEntries 4496 }

	aliasSuppressionVert OBJECT-TYPE
		SYNTAX		Integer32 (-50..50)
		MAX-ACCESS	read-write
		STATUS		current
		DESCRIPTION	"
			style='Numeric control'
			range='-50..50'
			path='/Enhancements/Alias Suppression/Vertical'
		"
		::= { alchemistHdCtrlEntries 4497 }

	inpBlankValInputBlankLeft OBJECT-TYPE
		SYNTAX		Integer32 (1..1920)
		MAX-ACCESS	read-write
		STATUS		current
		DESCRIPTION	"
			style='Numeric control'
			range='1..1920'
			preset='1'
			path='/Input/Blanking/Left'
		"
		::= { alchemistHdCtrlEntries 5010 }

	inpBlankValInputBlankRight OBJECT-TYPE
		SYNTAX		Integer32 (1..1920)
		MAX-ACCESS	read-write
		STATUS		current
		DESCRIPTION	"
			style='Numeric control'
			range='1..1920'
			preset='720'
			path='/Input/Blanking/Right'
		"
		::= { alchemistHdCtrlEntries 5011 }

	inpBlankValInputBlankTop OBJECT-TYPE
		SYNTAX		Integer32 (1..1080)
		MAX-ACCESS	read-write
		STATUS		current
		DESCRIPTION	"
			style='Numeric control'
			range='1..1080'
			preset='1'
			path='/Input/Blanking/Top'
		"
		::= { alchemistHdCtrlEntries 5012 }

	inpBlankValInputBlankBottom OBJECT-TYPE
		SYNTAX		Integer32 (1..1080)
		MAX-ACCESS	read-write
		STATUS		current
		DESCRIPTION	"
			style='Numeric control'
			range='1..1080'
			preset='576'
			path='/Input/Blanking/Bottom'
		"
		::= { alchemistHdCtrlEntries 5013 }

	loss OBJECT-TYPE
		SYNTAX		INTEGER {
					input(0),
					freeze(1),
					black(2)
				}
		MAX-ACCESS	read-write
		STATUS		current
		DESCRIPTION	"
			style='Radiobutton list'
			preset='input'
			path='/Input/On loss'
		"
		::= { alchemistHdCtrlEntries 5020 }

	source OBJECT-TYPE
		SYNTAX		INTEGER {
					sdiA(0),
					sdiB(1)
				}
		MAX-ACCESS	read-write
		STATUS		current
		DESCRIPTION	"
			style='Radiobutton list'
			preset='sdiA'
			path='/Input/Source'
		"
		::= { alchemistHdCtrlEntries 5030 }

	matrixA OBJECT-TYPE
		SYNTAX		INTEGER {
					auto(0),
					rec601(1),
					smpte240(3),
					bt709(4)
				}
		MAX-ACCESS	read-write
		STATUS		current
		DESCRIPTION	"
			style='Radiobutton list'
			preset='auto'
			path='/output/Output A/Colorimetry'
		"
		::= { alchemistHdCtrlEntries 5050 }

	matrixB OBJECT-TYPE
		SYNTAX		INTEGER {
					auto(0),
					rec601(1),
					smpte240(3),
					bt709(4)
				}
		MAX-ACCESS	read-write
		STATUS		current
		DESCRIPTION	"
			style='Radiobutton list'
			preset='auto'
			path='/output/Output B/Colorimetry'
		"
		::= { alchemistHdCtrlEntries 5051 }

	inputMatrix OBJECT-TYPE
		SYNTAX		INTEGER {
					auto(0),
					rec601(1),
					smpte240(3),
					bt709(4)
				}
		MAX-ACCESS	read-write
		STATUS		current
		DESCRIPTION	"
			style='Radiobutton list'
			preset='auto'
			path='/Input/Colorimetry'
		"
		::= { alchemistHdCtrlEntries 5052 }

	stdOutB OBJECT-TYPE
		SYNTAX		INTEGER {
					v525i59(19),
					v720p59(17),
					v1080i59(7),
					v625i50(20),
					v720p50(30),
					v1080i50(8),
					v625psf2398(28),
					v1080psf2398(24),
					v625psf24(27),
					v1080psf24(23),
					v625psf25(1020),
					v1080psf25(36),
					v525psf2998(1019),
					v1080psf2998(35),
					v1080psf30(34),
					v625i4795(1028),
					v1080i4795(1024),
					v625i48(1027),
					v1080i48(1023),
					v720p60(16),
					v1080i60(6),
					v720p23(41),
					v720p24(40),
					v720p25(39),
					v720p29(38),
					v720p30(37)
				}
		MAX-ACCESS	read-write
		STATUS		current
		DESCRIPTION	"
			style='Radiobutton list'
			preset='v625i50'
			path='/output/Output B/Output Standard'
		"
		::= { alchemistHdCtrlEntries 5101 }

	outABlankValOutputABlankLeft OBJECT-TYPE
		SYNTAX		Integer32 (1..1920)
		MAX-ACCESS	read-write
		STATUS		current
		DESCRIPTION	"
			style='Numeric control'
			range='1..1920'
			preset='1'
			path='/output/Output A/Blanking/Left'
		"
		::= { alchemistHdCtrlEntries 5110 }

	outABlankValOutputABlankRight OBJECT-TYPE
		SYNTAX		Integer32 (1..1920)
		MAX-ACCESS	read-write
		STATUS		current
		DESCRIPTION	"
			style='Numeric control'
			range='1..1920'
			preset='720'
			path='/output/Output A/Blanking/Right'
		"
		::= { alchemistHdCtrlEntries 5111 }

	outABlankValOutputABlankTop OBJECT-TYPE
		SYNTAX		Integer32 (1..1080)
		MAX-ACCESS	read-write
		STATUS		current
		DESCRIPTION	"
			style='Numeric control'
			range='1..1080'
			preset='1'
			path='/output/Output A/Blanking/Top'
		"
		::= { alchemistHdCtrlEntries 5112 }

	outABlankValOutputABlankBottom OBJECT-TYPE
		SYNTAX		Integer32 (1..1080)
		MAX-ACCESS	read-write
		STATUS		current
		DESCRIPTION	"
			style='Numeric control'
			range='1..1080'
			preset='576'
			path='/output/Output A/Blanking/Bottom'
		"
		::= { alchemistHdCtrlEntries 5113 }

	outBBlankValOutputBBlankLeft OBJECT-TYPE
		SYNTAX		Integer32 (1..1920)
		MAX-ACCESS	read-write
		STATUS		current
		DESCRIPTION	"
			style='Numeric control'
			range='1..1920'
			preset='1'
			path='/output/Output B/Blanking/Left'
		"
		::= { alchemistHdCtrlEntries 5114 }

	outBBlankValOutputBBlankRight OBJECT-TYPE
		SYNTAX		Integer32 (1..1920)
		MAX-ACCESS	read-write
		STATUS		current
		DESCRIPTION	"
			style='Numeric control'
			range='1..1920'
			preset='720'
			path='/output/Output B/Blanking/Right'
		"
		::= { alchemistHdCtrlEntries 5115 }

	outBBlankValOutputBBlankTop OBJECT-TYPE
		SYNTAX		Integer32 (1..1080)
		MAX-ACCESS	read-write
		STATUS		current
		DESCRIPTION	"
			style='Numeric control'
			range='1..1080'
			preset='1'
			path='/output/Output B/Blanking/Top'
		"
		::= { alchemistHdCtrlEntries 5116 }

	outBBlankValOutputBBlankBottom OBJECT-TYPE
		SYNTAX		Integer32 (1..1080)
		MAX-ACCESS	read-write
		STATUS		current
		DESCRIPTION	"
			style='Numeric control'
			range='1..1080'
			preset='576'
			path='/output/Output B/Blanking/Bottom'
		"
		::= { alchemistHdCtrlEntries 5117 }

	borderAEnable OBJECT-TYPE
		SYNTAX		INTEGER { enable(0), disable(1) }
		MAX-ACCESS	read-write
		STATUS		current
		DESCRIPTION	"
			style='Checkbox'
			path='/output/Output A/Border/Enable'
		"
		::= { alchemistHdCtrlEntries 5120 }

	borderAR OBJECT-TYPE
		SYNTAX		Integer32 (64..940)
		MAX-ACCESS	read-write
		STATUS		current
		DESCRIPTION	"
			style='Numeric control'
			range='64..940'
			preset='64'
			path='/output/Output A/Border/Red'
		"
		::= { alchemistHdCtrlEntries 5121 }

	borderAG OBJECT-TYPE
		SYNTAX		Integer32 (64..940)
		MAX-ACCESS	read-write
		STATUS		current
		DESCRIPTION	"
			style='Numeric control'
			range='64..940'
			preset='64'
			path='/output/Output A/Border/Green'
		"
		::= { alchemistHdCtrlEntries 5122 }

	borderAB OBJECT-TYPE
		SYNTAX		Integer32 (64..940)
		MAX-ACCESS	read-write
		STATUS		current
		DESCRIPTION	"
			style='Numeric control'
			range='64..940'
			preset='64'
			path='/output/Output A/Border/Blue'
		"
		::= { alchemistHdCtrlEntries 5123 }

	borderBEnable OBJECT-TYPE
		SYNTAX		INTEGER { enable(0), disable(1) }
		MAX-ACCESS	read-write
		STATUS		current
		DESCRIPTION	"
			style='Checkbox'
			path='/output/Output B/Border/Enable'
		"
		::= { alchemistHdCtrlEntries 5124 }

	borderBR OBJECT-TYPE
		SYNTAX		Integer32 (64..940)
		MAX-ACCESS	read-write
		STATUS		current
		DESCRIPTION	"
			style='Numeric control'
			range='64..940'
			preset='64'
			path='/output/Output B/Border/Red'
		"
		::= { alchemistHdCtrlEntries 5125 }

	borderBG OBJECT-TYPE
		SYNTAX		Integer32 (64..940)
		MAX-ACCESS	read-write
		STATUS		current
		DESCRIPTION	"
			style='Numeric control'
			range='64..940'
			preset='64'
			path='/output/Output B/Border/Green'
		"
		::= { alchemistHdCtrlEntries 5126 }

	borderBB OBJECT-TYPE
		SYNTAX		Integer32 (64..940)
		MAX-ACCESS	read-write
		STATUS		current
		DESCRIPTION	"
			style='Numeric control'
			range='64..940'
			preset='64'
			path='/output/Output B/Border/Blue'
		"
		::= { alchemistHdCtrlEntries 5127 }

	procBlack OBJECT-TYPE
		SYNTAX		Integer32 (-101..101)
		MAX-ACCESS	read-write
		STATUS		current
		DESCRIPTION	"
			style='Numeric control'
			range='-101.0..101.0'
			path='/Proc Amp/Gain/Black Level'
		"
		::= { alchemistHdCtrlEntries 5150 }

	procGainY OBJECT-TYPE
		SYNTAX		Integer32 (-60..60)
		MAX-ACCESS	read-write
		STATUS		current
		DESCRIPTION	"
			style='Numeric control'
			range='-6.00dB..6.00dB'
			stepsize='0.10dB'
			path='/Proc Amp/Gain/Luma Gain'
		"
		::= { alchemistHdCtrlEntries 5160 }

	procGainC OBJECT-TYPE
		SYNTAX		Integer32 (-60..60)
		MAX-ACCESS	read-write
		STATUS		current
		DESCRIPTION	"
			style='Numeric control'
			range='-6.00dB..6.00dB'
			stepsize='0.10dB'
			path='/Proc Amp/Gain/Chroma Gain'
		"
		::= { alchemistHdCtrlEntries 5161 }

	procEnhanceVertA OBJECT-TYPE
		SYNTAX		Integer32 (0..100)
		MAX-ACCESS	read-write
		STATUS		current
		DESCRIPTION	"
			style='Numeric control'
			range='0%..100%'
			path='/Enhancements/Enhance/Vertical a'
		"
		::= { alchemistHdCtrlEntries 5172 }

	procEnhanceVert OBJECT-TYPE
		SYNTAX		Integer32 (0..100)
		MAX-ACCESS	read-write
		STATUS		current
		DESCRIPTION	"
			style='Numeric control'
			range='0..100'
			path='/Enhancements/Enhance/Vertical'
		"
		::= { alchemistHdCtrlEntries 5173 }

	procEnhanceHoriz OBJECT-TYPE
		SYNTAX		Integer32 (0..100)
		MAX-ACCESS	read-write
		STATUS		current
		DESCRIPTION	"
			style='Numeric control'
			range='0..100'
			path='/Enhancements/Enhance/Horizontal'
		"
		::= { alchemistHdCtrlEntries 5174 }

	procEnhanceHorizA OBJECT-TYPE
		SYNTAX		Integer32 (0..100)
		MAX-ACCESS	read-write
		STATUS		current
		DESCRIPTION	"
			style='Numeric control'
			range='0%..100%'
			path='/Enhancements/Enhance/Horizontal a'
		"
		::= { alchemistHdCtrlEntries 5175 }

	gamutA OBJECT-TYPE
		SYNTAX		INTEGER {
					off(0),
					v721mv(1),
					v700mv(2),
					v735mv(3)
				}
		MAX-ACCESS	read-write
		STATUS		current
		DESCRIPTION	"
			style='Radiobutton list'
			preset='off'
			path='/utils/Legaliser/Gamut Legaliser A'
		"
		::= { alchemistHdCtrlEntries 5183 }

	gamutB OBJECT-TYPE
		SYNTAX		INTEGER {
					off(0),
					v721mv(1),
					v700mv(2),
					v735mv(3)
				}
		MAX-ACCESS	read-write
		STATUS		current
		DESCRIPTION	"
			style='Radiobutton list'
			preset='off'
			path='/utils/Legaliser/Gamut Legaliser B'
		"
		::= { alchemistHdCtrlEntries 5184 }

	phcEnable OBJECT-TYPE
		SYNTAX		INTEGER {
					off(0),
					on(1)
				}
		MAX-ACCESS	read-write
		STATUS		current
		DESCRIPTION	"
			style='Radiobutton list'
			preset='on'
			path='/Convert/Ph.C'
		"
		::= { alchemistHdCtrlEntries 5190 }

	apertureA OBJECT-TYPE
		SYNTAX		INTEGER {
					sharp(0),
					normal(1),
					antiAlias(2)
				}
		MAX-ACCESS	read-write
		STATUS		current
		DESCRIPTION	"
			style='Radiobutton list'
			preset='normal'
			path='/Convert/Aperture A'
		"
		::= { alchemistHdCtrlEntries 5191 }

	cleanCut OBJECT-TYPE
		SYNTAX		INTEGER {
					off(0),
					on(1)
				}
		MAX-ACCESS	read-write
		STATUS		current
		DESCRIPTION	"
			style='Radiobutton list'
			preset='on'
			path='/Convert/Clean Cut'
		"
		::= { alchemistHdCtrlEntries 5192 }

	cleanCutType OBJECT-TYPE
		SYNTAX		INTEGER {
					anyField(0),
					field1Only(1),
					field2Only(2)
				}
		MAX-ACCESS	read-write
		STATUS		current
		DESCRIPTION	"
			style='Radiobutton list'
			preset='anyField'
			path='/Convert/Clean Cut Type'
		"
		::= { alchemistHdCtrlEntries 5193 }

	apertureB OBJECT-TYPE
		SYNTAX		INTEGER {
					sharp(0),
					normal(1),
					antiAlias(2)
				}
		MAX-ACCESS	read-write
		STATUS		current
		DESCRIPTION	"
			style='Radiobutton list'
			preset='normal'
			path='/Convert/Aperture B'
		"
		::= { alchemistHdCtrlEntries 5194 }

	activeAreaKey1ValAaKey1Left OBJECT-TYPE
		SYNTAX		Integer32 (1..720)
		MAX-ACCESS	read-write
		STATUS		current
		DESCRIPTION	"
			style='Numeric control'
			range='1..720'
			preset='1'
			path='/Convert/Ph.C Area/Active Area 1/Left'
		"
		::= { alchemistHdCtrlEntries 5200 }

	activeAreaKey1ValAaKey1Right OBJECT-TYPE
		SYNTAX		Integer32 (1..720)
		MAX-ACCESS	read-write
		STATUS		current
		DESCRIPTION	"
			style='Numeric control'
			range='1..720'
			preset='720'
			path='/Convert/Ph.C Area/Active Area 1/Right'
		"
		::= { alchemistHdCtrlEntries 5201 }

	activeAreaKey1ValAaKey1Top OBJECT-TYPE
		SYNTAX		Integer32 (1..576)
		MAX-ACCESS	read-write
		STATUS		current
		DESCRIPTION	"
			style='Numeric control'
			range='1..576'
			preset='1'
			path='/Convert/Ph.C Area/Active Area 1/Top'
		"
		::= { alchemistHdCtrlEntries 5202 }

	activeAreaKey1ValAaKey1Bottom OBJECT-TYPE
		SYNTAX		Integer32 (1..576)
		MAX-ACCESS	read-write
		STATUS		current
		DESCRIPTION	"
			style='Numeric control'
			range='1..576'
			preset='576'
			path='/Convert/Ph.C Area/Active Area 1/Bottom'
		"
		::= { alchemistHdCtrlEntries 5203 }

	activeAreaKey1Enable OBJECT-TYPE
		SYNTAX		INTEGER { enable(0), disable(1) }
		MAX-ACCESS	read-write
		STATUS		current
		DESCRIPTION	"
			style='Checkbox'
			path='/Convert/Ph.C Area/Active Area 1/Enable'
		"
		::= { alchemistHdCtrlEntries 5204 }

	activeAreaKey1Active OBJECT-TYPE
		SYNTAX		INTEGER { enable(0), disable(1) }
		MAX-ACCESS	read-write
		STATUS		current
		DESCRIPTION	"
			style='Checkbox'
			path='/Convert/Ph.C Area/Active Area 1/Active'
		"
		::= { alchemistHdCtrlEntries 5205 }

	activeAreaKey2ValAaKey2Left OBJECT-TYPE
		SYNTAX		Integer32 (1..720)
		MAX-ACCESS	read-write
		STATUS		current
		DESCRIPTION	"
			style='Numeric control'
			range='1..720'
			preset='1'
			path='/Convert/Ph.C Area/Active Area 2/Left'
		"
		::= { alchemistHdCtrlEntries 5206 }

	activeAreaKey2ValAaKey2Right OBJECT-TYPE
		SYNTAX		Integer32 (1..720)
		MAX-ACCESS	read-write
		STATUS		current
		DESCRIPTION	"
			style='Numeric control'
			range='1..720'
			preset='720'
			path='/Convert/Ph.C Area/Active Area 2/Right'
		"
		::= { alchemistHdCtrlEntries 5207 }

	activeAreaKey2ValAaKey2Top OBJECT-TYPE
		SYNTAX		Integer32 (1..576)
		MAX-ACCESS	read-write
		STATUS		current
		DESCRIPTION	"
			style='Numeric control'
			range='1..576'
			preset='1'
			path='/Convert/Ph.C Area/Active Area 2/Top'
		"
		::= { alchemistHdCtrlEntries 5208 }

	activeAreaKey2ValAaKey2Bottom OBJECT-TYPE
		SYNTAX		Integer32 (1..576)
		MAX-ACCESS	read-write
		STATUS		current
		DESCRIPTION	"
			style='Numeric control'
			range='1..576'
			preset='576'
			path='/Convert/Ph.C Area/Active Area 2/Bottom'
		"
		::= { alchemistHdCtrlEntries 5209 }

	activeAreaKey2Enable OBJECT-TYPE
		SYNTAX		INTEGER { enable(0), disable(1) }
		MAX-ACCESS	read-write
		STATUS		current
		DESCRIPTION	"
			style='Checkbox'
			path='/Convert/Ph.C Area/Active Area 2/Enable'
		"
		::= { alchemistHdCtrlEntries 5210 }

	activeAreaKey2Active OBJECT-TYPE
		SYNTAX		INTEGER { enable(0), disable(1) }
		MAX-ACCESS	read-write
		STATUS		current
		DESCRIPTION	"
			style='Checkbox'
			path='/Convert/Ph.C Area/Active Area 2/Active'
		"
		::= { alchemistHdCtrlEntries 5211 }

	activeAreaKey3ValAaKey3Left OBJECT-TYPE
		SYNTAX		Integer32 (1..720)
		MAX-ACCESS	read-write
		STATUS		current
		DESCRIPTION	"
			style='Numeric control'
			range='1..720'
			preset='1'
			path='/Convert/Ph.C Area/Active Area 3/Left'
		"
		::= { alchemistHdCtrlEntries 5212 }

	activeAreaKey3ValAaKey3Right OBJECT-TYPE
		SYNTAX		Integer32 (1..720)
		MAX-ACCESS	read-write
		STATUS		current
		DESCRIPTION	"
			style='Numeric control'
			range='1..720'
			preset='720'
			path='/Convert/Ph.C Area/Active Area 3/Right'
		"
		::= { alchemistHdCtrlEntries 5213 }

	activeAreaKey3ValAaKey3Top OBJECT-TYPE
		SYNTAX		Integer32 (1..576)
		MAX-ACCESS	read-write
		STATUS		current
		DESCRIPTION	"
			style='Numeric control'
			range='1..576'
			preset='1'
			path='/Convert/Ph.C Area/Active Area 3/Top'
		"
		::= { alchemistHdCtrlEntries 5214 }

	activeAreaKey3ValAaKey3Bottom OBJECT-TYPE
		SYNTAX		Integer32 (1..576)
		MAX-ACCESS	read-write
		STATUS		current
		DESCRIPTION	"
			style='Numeric control'
			range='1..576'
			preset='576'
			path='/Convert/Ph.C Area/Active Area 3/Bottom'
		"
		::= { alchemistHdCtrlEntries 5215 }

	activeAreaKey3Enable OBJECT-TYPE
		SYNTAX		INTEGER { enable(0), disable(1) }
		MAX-ACCESS	read-write
		STATUS		current
		DESCRIPTION	"
			style='Checkbox'
			path='/Convert/Ph.C Area/Active Area 3/Enable'
		"
		::= { alchemistHdCtrlEntries 5216 }

	activeAreaKey3Active OBJECT-TYPE
		SYNTAX		INTEGER { enable(0), disable(1) }
		MAX-ACCESS	read-write
		STATUS		current
		DESCRIPTION	"
			style='Checkbox'
			path='/Convert/Ph.C Area/Active Area 3/Active'
		"
		::= { alchemistHdCtrlEntries 5217 }

	activeAreaKey4ValAaKey4Left OBJECT-TYPE
		SYNTAX		Integer32 (1..720)
		MAX-ACCESS	read-write
		STATUS		current
		DESCRIPTION	"
			style='Numeric control'
			range='1..720'
			preset='1'
			path='/Convert/Ph.C Area/Active Area 4/Left'
		"
		::= { alchemistHdCtrlEntries 5218 }

	activeAreaKey4ValAaKey4Right OBJECT-TYPE
		SYNTAX		Integer32 (1..720)
		MAX-ACCESS	read-write
		STATUS		current
		DESCRIPTION	"
			style='Numeric control'
			range='1..720'
			preset='720'
			path='/Convert/Ph.C Area/Active Area 4/Right'
		"
		::= { alchemistHdCtrlEntries 5219 }

	activeAreaKey4ValAaKey4Top OBJECT-TYPE
		SYNTAX		Integer32 (1..576)
		MAX-ACCESS	read-write
		STATUS		current
		DESCRIPTION	"
			style='Numeric control'
			range='1..576'
			preset='1'
			path='/Convert/Ph.C Area/Active Area 4/Top'
		"
		::= { alchemistHdCtrlEntries 5220 }

	activeAreaKey4ValAaKey4Bottom OBJECT-TYPE
		SYNTAX		Integer32 (1..576)
		MAX-ACCESS	read-write
		STATUS		current
		DESCRIPTION	"
			style='Numeric control'
			range='1..576'
			preset='576'
			path='/Convert/Ph.C Area/Active Area 4/Bottom'
		"
		::= { alchemistHdCtrlEntries 5221 }

	activeAreaKey4Enable OBJECT-TYPE
		SYNTAX		INTEGER { enable(0), disable(1) }
		MAX-ACCESS	read-write
		STATUS		current
		DESCRIPTION	"
			style='Checkbox'
			path='/Convert/Ph.C Area/Active Area 4/Enable'
		"
		::= { alchemistHdCtrlEntries 5222 }

	activeAreaKey4Active OBJECT-TYPE
		SYNTAX		INTEGER { enable(0), disable(1) }
		MAX-ACCESS	read-write
		STATUS		current
		DESCRIPTION	"
			style='Checkbox'
			path='/Convert/Ph.C Area/Active Area 4/Active'
		"
		::= { alchemistHdCtrlEntries 5223 }

	activeAreaKey5ValAaKey5Left OBJECT-TYPE
		SYNTAX		Integer32 (1..720)
		MAX-ACCESS	read-write
		STATUS		current
		DESCRIPTION	"
			style='Numeric control'
			range='1..720'
			preset='1'
			path='/Convert/Ph.C Area/Active Area 5/Left'
		"
		::= { alchemistHdCtrlEntries 5224 }

	activeAreaKey5ValAaKey5Right OBJECT-TYPE
		SYNTAX		Integer32 (1..720)
		MAX-ACCESS	read-write
		STATUS		current
		DESCRIPTION	"
			style='Numeric control'
			range='1..720'
			preset='720'
			path='/Convert/Ph.C Area/Active Area 5/Right'
		"
		::= { alchemistHdCtrlEntries 5225 }

	activeAreaKey5ValAaKey5Top OBJECT-TYPE
		SYNTAX		Integer32 (1..576)
		MAX-ACCESS	read-write
		STATUS		current
		DESCRIPTION	"
			style='Numeric control'
			range='1..576'
			preset='1'
			path='/Convert/Ph.C Area/Active Area 5/Top'
		"
		::= { alchemistHdCtrlEntries 5226 }

	activeAreaKey5ValAaKey5Bottom OBJECT-TYPE
		SYNTAX		Integer32 (1..576)
		MAX-ACCESS	read-write
		STATUS		current
		DESCRIPTION	"
			style='Numeric control'
			range='1..576'
			preset='576'
			path='/Convert/Ph.C Area/Active Area 5/Bottom'
		"
		::= { alchemistHdCtrlEntries 5227 }

	activeAreaKey5Enable OBJECT-TYPE
		SYNTAX		INTEGER { enable(0), disable(1) }
		MAX-ACCESS	read-write
		STATUS		current
		DESCRIPTION	"
			style='Checkbox'
			path='/Convert/Ph.C Area/Active Area 5/Enable'
		"
		::= { alchemistHdCtrlEntries 5228 }

	activeAreaKey5Active OBJECT-TYPE
		SYNTAX		INTEGER { enable(0), disable(1) }
		MAX-ACCESS	read-write
		STATUS		current
		DESCRIPTION	"
			style='Checkbox'
			path='/Convert/Ph.C Area/Active Area 5/Active'
		"
		::= { alchemistHdCtrlEntries 5229 }

	activeAreaBgndActive OBJECT-TYPE
		SYNTAX		INTEGER { enable(0), disable(1) }
		MAX-ACCESS	read-write
		STATUS		current
		DESCRIPTION	"
			style='Checkbox'
			range='0..1'
			path='/Convert/Ph.C Area/Active Area Control/Bgnd Active'
		"
		::= { alchemistHdCtrlEntries 5230 }

	activeAreaOverlayKeys OBJECT-TYPE
		SYNTAX		INTEGER { enable(0), disable(1) }
		MAX-ACCESS	read-write
		STATUS		current
		DESCRIPTION	"
			style='Checkbox'
			range='0..1'
			path='/Convert/Ph.C Area/Active Area Control/Overlay Keys'
		"
		::= { alchemistHdCtrlEntries 5231 }

	activeAreaOverlayPhc OBJECT-TYPE
		SYNTAX		INTEGER { enable(0), disable(1) }
		MAX-ACCESS	read-write
		STATUS		current
		DESCRIPTION	"
			style='Checkbox'
			range='0..1'
			path='/Convert/Ph.C Area/Active Area Control/Overlay Ph.C'
		"
		::= { alchemistHdCtrlEntries 5232 }

	activeAreaSettings OBJECT-TYPE
		SYNTAX		Integer32
		MAX-ACCESS	read-write
		STATUS		current
		DESCRIPTION	"
			style='Numeric control'
			path='/System/Debug/status/status1/Settings'
		"
		::= { alchemistHdCtrlEntries 5233 }

	activeAreaResetall OBJECT-TYPE
		SYNTAX		INTEGER { ready(0), trigger(1) }
		MAX-ACCESS	read-write
		STATUS		current
		DESCRIPTION	"
			style='Event button'
			path='/Convert/Ph.C Area/Active Area Control/Reset All'
		"
		::= { alchemistHdCtrlEntries 5234 }

	procEnhanceVertB OBJECT-TYPE
		SYNTAX		Integer32 (0..100)
		MAX-ACCESS	read-write
		STATUS		current
		DESCRIPTION	"
			style='Numeric control'
			range='0%..100%'
			path='/Enhancements/Enhance/Vertical b'
		"
		::= { alchemistHdCtrlEntries 5272 }

	procEnhanceHorizB OBJECT-TYPE
		SYNTAX		Integer32 (0..100)
		MAX-ACCESS	read-write
		STATUS		current
		DESCRIPTION	"
			style='Numeric control'
			range='0%..100%'
			path='/Enhancements/Enhance/Horizontal b'
		"
		::= { alchemistHdCtrlEntries 5275 }

	inputAspect OBJECT-TYPE
		SYNTAX		INTEGER {
					v4x3(1),
					v14x9lb(2),
					v16x9lb(3),
					anamorphic(4),
					none(5)
				}
		MAX-ACCESS	read-write
		STATUS		current
		DESCRIPTION	"
			style='Radiobutton list'
			preset='v4x3'
			path='/display/Input/Aspect'
		"
		::= { alchemistHdCtrlEntries 5317 }

	aspectControlA OBJECT-TYPE
		SYNTAX		INTEGER {
					v16x9(1),
					v4x3fh(2),
					v14x9fh(3),
					v4x3fw(4),
					v14x9fw(5),
					none(6)
				}
		MAX-ACCESS	read-write
		STATUS		current
		DESCRIPTION	"
			style='Radiobutton list'
			preset='v16x9'
			path='/display/Chan A/Channel A'
		"
		::= { alchemistHdCtrlEntries 5318 }

	aspectControlB OBJECT-TYPE
		SYNTAX		INTEGER {
					v16x9(1),
					v4x3fh(2),
					v14x9fh(3),
					v4x3fw(4),
					v14x9fw(5),
					none(6)
				}
		MAX-ACCESS	read-write
		STATUS		current
		DESCRIPTION	"
			style='Radiobutton list'
			preset='v16x9'
			path='/display/Chan B/Channel B'
		"
		::= { alchemistHdCtrlEntries 5319 }

	displaySizeA OBJECT-TYPE
		SYNTAX		Integer32 (4000..20000)
		MAX-ACCESS	read-write
		STATUS		current
		DESCRIPTION	"
			style='Numeric control'
			range='40.00%..200.00%'
			stepsize='0.00%'
			preset='100.00%'
			path='/display/Chan A/Size'
		"
		::= { alchemistHdCtrlEntries 5320 }

	displayAspA OBJECT-TYPE
		SYNTAX		Integer32 (4000..20000)
		MAX-ACCESS	read-write
		STATUS		current
		DESCRIPTION	"
			style='Numeric control'
			range='40.00%..200.00%'
			stepsize='0.00%'
			preset='100.00%'
			path='/display/Chan A/Asp'
		"
		::= { alchemistHdCtrlEntries 5321 }

	displayPanA OBJECT-TYPE
		SYNTAX		Integer32 (-3750..3750)
		MAX-ACCESS	read-write
		STATUS		current
		DESCRIPTION	"
			style='Numeric control'
			range='-75.00%..75.00%'
			stepsize='0.00%'
			path='/display/Chan A/Pan'
		"
		::= { alchemistHdCtrlEntries 5322 }

	displayPosA OBJECT-TYPE
		SYNTAX		Integer32 (-3750..3750)
		MAX-ACCESS	read-write
		STATUS		current
		DESCRIPTION	"
			style='Numeric control'
			range='-75.00%..75.00%'
			stepsize='0.00%'
			path='/display/Chan A/Tilt'
		"
		::= { alchemistHdCtrlEntries 5323 }

	displaySizeB OBJECT-TYPE
		SYNTAX		Integer32 (4000..20000)
		MAX-ACCESS	read-write
		STATUS		current
		DESCRIPTION	"
			style='Numeric control'
			range='40.00%..200.00%'
			stepsize='0.00%'
			preset='100.00%'
			path='/display/Chan B/Size'
		"
		::= { alchemistHdCtrlEntries 5324 }

	displayAspB OBJECT-TYPE
		SYNTAX		Integer32 (4000..20000)
		MAX-ACCESS	read-write
		STATUS		current
		DESCRIPTION	"
			style='Numeric control'
			range='40.00%..200.00%'
			stepsize='0.00%'
			preset='100.00%'
			path='/display/Chan B/Asp'
		"
		::= { alchemistHdCtrlEntries 5325 }

	displayPanB OBJECT-TYPE
		SYNTAX		Integer32 (-3750..3750)
		MAX-ACCESS	read-write
		STATUS		current
		DESCRIPTION	"
			style='Numeric control'
			range='-75.00%..75.00%'
			stepsize='0.00%'
			path='/display/Chan B/Pan'
		"
		::= { alchemistHdCtrlEntries 5326 }

	displayPosB OBJECT-TYPE
		SYNTAX		Integer32 (-3750..3750)
		MAX-ACCESS	read-write
		STATUS		current
		DESCRIPTION	"
			style='Numeric control'
			range='-75.00%..75.00%'
			stepsize='0.00%'
			path='/display/Chan B/Tilt'
		"
		::= { alchemistHdCtrlEntries 5327 }

	aspectControlBLock OBJECT-TYPE
		SYNTAX		INTEGER { enable(0), disable(1) }
		MAX-ACCESS	read-write
		STATUS		current
		DESCRIPTION	"
			style='Checkbox'
			path='/display/Chan B/Lock to A'
		"
		::= { alchemistHdCtrlEntries 5328 }

	slewEnable OBJECT-TYPE
		SYNTAX		INTEGER {
					off(0),
					on(1)
				}
		MAX-ACCESS	read-write
		STATUS		current
		DESCRIPTION	"
			style='Radiobutton list'
			preset='on'
			path='/display/Transition/Slew'
		"
		::= { alchemistHdCtrlEntries 5329 }

	slewProfile OBJECT-TYPE
		SYNTAX		INTEGER {
					vSlowOut(2),
					vLinear(0),
					vStdSCurve(4),
					vSCurve(3),
					vSlowIn(1)
				}
		MAX-ACCESS	read-write
		STATUS		current
		DESCRIPTION	"
			style='Radiobutton list'
			preset='vStdSCurve'
			path='/display/Transition/Profile'
		"
		::= { alchemistHdCtrlEntries 5330 }

	slewDurationMode OBJECT-TYPE
		SYNTAX		INTEGER {
					absolute(0),
					proportional(1)
				}
		MAX-ACCESS	read-write
		STATUS		current
		DESCRIPTION	"
			style='Radiobutton list'
			preset='proportional'
			path='/display/Transition/Slew Duration Mode'
		"
		::= { alchemistHdCtrlEntries 5331 }

	slewDurationUnit OBJECT-TYPE
		SYNTAX		INTEGER {
					fields(0),
					seconds(1)
				}
		MAX-ACCESS	read-write
		STATUS		current
		DESCRIPTION	"
			style='Radiobutton list'
			preset='fields'
			path='/display/Transition/Slew Duration Unit'
		"
		::= { alchemistHdCtrlEntries 5332 }

	slewDuration OBJECT-TYPE
		SYNTAX		Integer32 (20..20000)
		MAX-ACCESS	read-write
		STATUS		current
		DESCRIPTION	"
			style='Numeric control'
			range='0.00Sec..20.00Sec'
			stepsize='0.00Sec'
			preset='1.00Sec'
			path='/display/Transition/Slew Duration'
		"
		::= { alchemistHdCtrlEntries 5333 }

	slewUpdate OBJECT-TYPE
		SYNTAX		INTEGER {
					anyField(0),
					field1Only(1),
					field2Only(2)
				}
		MAX-ACCESS	read-write
		STATUS		current
		DESCRIPTION	"
			style='Radiobutton list'
			preset='anyField'
			path='/display/Transition/Transition Update'
		"
		::= { alchemistHdCtrlEntries 5334 }

	slewDurationFields OBJECT-TYPE
		SYNTAX		Integer32 (2..1000)
		MAX-ACCESS	read-write
		STATUS		current
		DESCRIPTION	"
			style='Numeric control'
			range='2Flds..1000Flds'
			preset='50Flds'
			path='/display/Transition/Slew Duration'
		"
		::= { alchemistHdCtrlEntries 5335 }

	displayControlModeA OBJECT-TYPE
		SYNTAX		INTEGER {
					manual(0),
					forced(1),
					autoFormat(2)
				}
		MAX-ACCESS	read-write
		STATUS		current
		DESCRIPTION	"
			style='Radiobutton list'
			preset='manual'
			path='/display/Control/Output A Mode'
		"
		::= { alchemistHdCtrlEntries 5350 }

	displayControlModeB OBJECT-TYPE
		SYNTAX		INTEGER {
					manual(0),
					forced(1),
					autoFormat(2)
				}
		MAX-ACCESS	read-write
		STATUS		current
		DESCRIPTION	"
			style='Radiobutton list'
			preset='manual'
			path='/display/Control/Output B Mode'
		"
		::= { alchemistHdCtrlEntries 5351 }

	dispSizeEntry OBJECT-TYPE
		SYNTAX		Integer32 (4000..20000)
		MAX-ACCESS	read-write
		STATUS		current
		DESCRIPTION	"
			style='Numeric control'
			range='40.00%..200.00%'
			stepsize='0.00%'
			preset='100.00%'
			path='/display/Control/Dispaly Memory Setup/Size'
		"
		::= { alchemistHdCtrlEntries 5353 }

	dispAspEntry OBJECT-TYPE
		SYNTAX		Integer32 (4000..20000)
		MAX-ACCESS	read-write
		STATUS		current
		DESCRIPTION	"
			style='Numeric control'
			range='40.00%..200.00%'
			stepsize='0.00%'
			preset='100.00%'
			path='/display/Control/Dispaly Memory Setup/Asp'
		"
		::= { alchemistHdCtrlEntries 5354 }

	dispPanEntry OBJECT-TYPE
		SYNTAX		Integer32 (-3750..3750)
		MAX-ACCESS	read-write
		STATUS		current
		DESCRIPTION	"
			style='Numeric control'
			range='-75.00%..75.00%'
			stepsize='0.00%'
			path='/display/Control/Dispaly Memory Setup/Pan'
		"
		::= { alchemistHdCtrlEntries 5355 }

	dispPosEntry OBJECT-TYPE
		SYNTAX		Integer32 (-3750..3750)
		MAX-ACCESS	read-write
		STATUS		current
		DESCRIPTION	"
			style='Numeric control'
			range='-75.00%..75.00%'
			stepsize='0.00%'
			path='/display/Control/Dispaly Memory Setup/Tilt'
		"
		::= { alchemistHdCtrlEntries 5356 }

	dispEntryPreset OBJECT-TYPE
		SYNTAX		INTEGER { ready(0), trigger(1) }
		MAX-ACCESS	read-write
		STATUS		current
		DESCRIPTION	"
			style='Event button'
			path='/display/Control/Dispaly Memory Setup/Preset'
		"
		::= { alchemistHdCtrlEntries 5357 }

	dispEntryCurrent OBJECT-TYPE
		SYNTAX		INTEGER { ready(0), trigger(1) }
		MAX-ACCESS	read-write
		STATUS		current
		DESCRIPTION	"
			style='Event button'
			path='/display/Control/Dispaly Memory Setup/Current'
		"
		::= { alchemistHdCtrlEntries 5358 }

	dispEntryAccept OBJECT-TYPE
		SYNTAX		INTEGER { ready(0), trigger(1) }
		MAX-ACCESS	read-write
		STATUS		current
		DESCRIPTION	"
			style='Event button'
			path='/display/Control/Dispaly Memory Setup/Accept Changes'
		"
		::= { alchemistHdCtrlEntries 5359 }

	dispEntryPreview OBJECT-TYPE
		SYNTAX		INTEGER { enable(0), disable(1) }
		MAX-ACCESS	read-write
		STATUS		current
		DESCRIPTION	"
			style='Checkbox'
			range='0..1'
			path='/display/Control/Dispaly Memory Setup/Preview'
		"
		::= { alchemistHdCtrlEntries 5360 }

	dispMemSetupSel OBJECT-TYPE
		SYNTAX		INTEGER {
					sdToSd(1),
					sdToHd(2),
					hdToSd(3),
					hdToHd(4)
				}
		MAX-ACCESS	read-write
		STATUS		current
		DESCRIPTION	"
			style='Radiobutton list'
			path='/display/Control/Dispaly Memory Setup/Memory Select'
		"
		::= { alchemistHdCtrlEntries 5361 }

	dispMemSetupGrp OBJECT-TYPE
		SYNTAX		INTEGER {
					format(0),
					group0(1),
					group1(2),
					group2(3),
					group3(4)
				}
		MAX-ACCESS	read-write
		STATUS		current
		DESCRIPTION	"
			style='Radiobutton list'
			preset='format'
			path='/display/Control/Dispaly Memory Setup/Memory Group Select'
		"
		::= { alchemistHdCtrlEntries 5362 }

	dispEntryAfdCode OBJECT-TYPE
		SYNTAX		INTEGER {
					v00000(0),
					v00011(1),
					v00102(2),
					v00113(3),
					v01004(4),
					v01015(5),
					v01106(6),
					v01117(7),
					v10008(8),
					v10019(9),
					v101010(10),
					v101111(11),
					v110012(12),
					v110113(13),
					v111014(14),
					v111115(15)
				}
		MAX-ACCESS	read-write
		STATUS		current
		DESCRIPTION	"
			style='Radiobutton list'
			preset='v00000'
			path='/display/Control/Dispaly Memory Setup/AFD Code'
		"
		::= { alchemistHdCtrlEntries 5363 }

	dispEntryDefault OBJECT-TYPE
		SYNTAX		INTEGER { ready(0), trigger(1) }
		MAX-ACCESS	read-write
		STATUS		current
		DESCRIPTION	"
			style='Event button'
			path='/display/Control/Dispaly Memory Setup/Default'
		"
		::= { alchemistHdCtrlEntries 5364 }

	dispEntryCodedFrame4X3 OBJECT-TYPE
		SYNTAX		INTEGER { enable(0), disable(1) }
		MAX-ACCESS	read-write
		STATUS		current
		DESCRIPTION	"
			style='Checkbox'
			range='0..1'
			path='/display/Control/Dispaly Memory Setup/4:3'
		"
		::= { alchemistHdCtrlEntries 5365 }

	dispEntryCodedFrame16X9 OBJECT-TYPE
		SYNTAX		INTEGER { enable(0), disable(1) }
		MAX-ACCESS	read-write
		STATUS		current
		DESCRIPTION	"
			style='Checkbox'
			range='0..1'
			path='/display/Control/Dispaly Memory Setup/16:9'
		"
		::= { alchemistHdCtrlEntries 5366 }

	dispForcedMemSelA OBJECT-TYPE
		SYNTAX		INTEGER {
					sdToSd(1),
					sdToHd(2),
					hdToSd(3),
					hdToHd(4)
				}
		MAX-ACCESS	read-write
		STATUS		current
		DESCRIPTION	"
			style='Radiobutton list'
			path='/display/Control/Dispaly Memory Setup/Output A Forced Mem'
		"
		::= { alchemistHdCtrlEntries 5367 }

	dispForcedMemSelB OBJECT-TYPE
		SYNTAX		INTEGER {
					sdToSd(1),
					sdToHd(2),
					hdToSd(3),
					hdToHd(4)
				}
		MAX-ACCESS	read-write
		STATUS		current
		DESCRIPTION	"
			style='Radiobutton list'
			path='/display/Control/Dispaly Memory Setup/Output B Forced Mem'
		"
		::= { alchemistHdCtrlEntries 5368 }

	procEnhanceVertLock OBJECT-TYPE
		SYNTAX		INTEGER { enable(0), disable(1) }
		MAX-ACCESS	read-write
		STATUS		current
		DESCRIPTION	"
			style='Checkbox'
			path='/Enhancements/Enhance/Vertical lock'
		"
		::= { alchemistHdCtrlEntries 5372 }

	procEnhanceHorizLock OBJECT-TYPE
		SYNTAX		INTEGER { enable(0), disable(1) }
		MAX-ACCESS	read-write
		STATUS		current
		DESCRIPTION	"
			style='Checkbox'
			path='/Enhancements/Enhance/Horizontal lock'
		"
		::= { alchemistHdCtrlEntries 5375 }

	aliasSuppressionVertLock OBJECT-TYPE
		SYNTAX		INTEGER { enable(0), disable(1) }
		MAX-ACCESS	read-write
		STATUS		current
		DESCRIPTION	"
			style='Checkbox'
			path='/Enhancements/Alias Suppression/Vertical lock'
		"
		::= { alchemistHdCtrlEntries 5376 }

	aliasSuppressionHorizLock OBJECT-TYPE
		SYNTAX		INTEGER { enable(0), disable(1) }
		MAX-ACCESS	read-write
		STATUS		current
		DESCRIPTION	"
			style='Checkbox'
			path='/Enhancements/Alias Suppression/Horizontal lock'
		"
		::= { alchemistHdCtrlEntries 5377 }

	referenceEnable OBJECT-TYPE
		SYNTAX		INTEGER { enable(0), disable(1) }
		MAX-ACCESS	read-write
		STATUS		current
		DESCRIPTION	"
			style='Checkbox'
			path='/Reference/  Reference Enable'
		"
		::= { alchemistHdCtrlEntries 5400 }

	referenceSrc OBJECT-TYPE
		SYNTAX		INTEGER {
					auto(0),
					refA(1),
					refB(2),
					input(3)
				}
		MAX-ACCESS	read-write
		STATUS		current
		DESCRIPTION	"
			style='Radiobutton list'
			preset='input'
			path='/Reference/Reference Source'
		"
		::= { alchemistHdCtrlEntries 5410 }

	referenceOffsetHoriz OBJECT-TYPE
		SYNTAX		Integer32 (-2640..2640)
		MAX-ACCESS	read-write
		STATUS		current
		DESCRIPTION	"
			style='Numeric control'
			range='-2640..2640'
			path='/output/Output B/Offset/Ref Offset Horiz'
		"
		::= { alchemistHdCtrlEntries 5432 }

	referenceOffsetVert OBJECT-TYPE
		SYNTAX		Integer32 (-10..10)
		MAX-ACCESS	read-write
		STATUS		current
		DESCRIPTION	"
			style='Numeric control'
			range='-10..10'
			path='/output/Output B/Offset/Ref Offset Vert'
		"
		::= { alchemistHdCtrlEntries 5433 }

	referenceTimingHoriz OBJECT-TYPE
		SYNTAX		Integer32 (-2640..2640)
		MAX-ACCESS	read-write
		STATUS		current
		DESCRIPTION	"
			style='Numeric control'
			range='-2640pixels..2640pixels'
			path='/Reference/Horizontal timing'
		"
		::= { alchemistHdCtrlEntries 5437 }

	referenceTimingVert OBJECT-TYPE
		SYNTAX		Integer32 (-1249..1249)
		MAX-ACCESS	read-write
		STATUS		current
		DESCRIPTION	"
			style='Numeric control'
			range='-1249lines..1249lines'
			path='/Reference/Vertical timing'
		"
		::= { alchemistHdCtrlEntries 5438 }

	nvrLoad OBJECT-TYPE
		SYNTAX		INTEGER { ready(0), trigger(1) }
		MAX-ACCESS	read-write
		STATUS		current
		DESCRIPTION	"
			style='Event button'
			path='/Memory/Recall'
		"
		::= { alchemistHdCtrlEntries 5500 }

	nvrSave OBJECT-TYPE
		SYNTAX		INTEGER { ready(0), trigger(1) }
		MAX-ACCESS	read-write
		STATUS		current
		DESCRIPTION	"
			style='Event button'
			path='/Memory/Store'
		"
		::= { alchemistHdCtrlEntries 5501 }

	nvrSelect OBJECT-TYPE
		SYNTAX		INTEGER {
					memory1(1),
					memory2(2),
					memory3(3),
					memory4(4),
					memory5(5),
					memory6(6),
					factory(7),
					default(8)
				}
		MAX-ACCESS	read-write
		STATUS		current
		DESCRIPTION	"
			style='Radiobutton list'
			path='/Memory/Select'
		"
		::= { alchemistHdCtrlEntries 5510 }

	nvrRename OBJECT-TYPE
		SYNTAX		RollCallString
		MAX-ACCESS	read-write
		STATUS		current
		DESCRIPTION	"
			style='Editable string'
			path='/Memory/Rename'
		"
		::= { alchemistHdCtrlEntries 5530 }

	monoEnableA OBJECT-TYPE
		SYNTAX		INTEGER { enable(0), disable(1) }
		MAX-ACCESS	read-write
		STATUS		current
		DESCRIPTION	"
			style='Checkbox'
			path='/utils/Channel A/Mono'
		"
		::= { alchemistHdCtrlEntries 5601 }

	monoEnableB OBJECT-TYPE
		SYNTAX		INTEGER { enable(0), disable(1) }
		MAX-ACCESS	read-write
		STATUS		current
		DESCRIPTION	"
			style='Checkbox'
			path='/utils/Channel B/Mono'
		"
		::= { alchemistHdCtrlEntries 5602 }

	cutToBlackA OBJECT-TYPE
		SYNTAX		INTEGER { enable(0), disable(1) }
		MAX-ACCESS	read-write
		STATUS		current
		DESCRIPTION	"
			style='Checkbox'
			path='/utils/Channel A/Cut to black'
		"
		::= { alchemistHdCtrlEntries 5603 }

	cutToBlackB OBJECT-TYPE
		SYNTAX		INTEGER { enable(0), disable(1) }
		MAX-ACCESS	read-write
		STATUS		current
		DESCRIPTION	"
			style='Checkbox'
			path='/utils/Channel B/Cut to black'
		"
		::= { alchemistHdCtrlEntries 5604 }

	freezeControl OBJECT-TYPE
		SYNTAX		INTEGER {
					off(0),
					frame(3)
				}
		MAX-ACCESS	read-write
		STATUS		current
		DESCRIPTION	"
			style='Radiobutton list'
			preset='off'
			path='/utils/Channel A/Freeze'
		"
		::= { alchemistHdCtrlEntries 5611 }

	patternEnableA OBJECT-TYPE
		SYNTAX		INTEGER { enable(0), disable(1) }
		MAX-ACCESS	read-write
		STATUS		current
		DESCRIPTION	"
			style='Checkbox'
			path='/utils/Channel A/Pattern Enable'
		"
		::= { alchemistHdCtrlEntries 5620 }

	patternTypeA OBJECT-TYPE
		SYNTAX		INTEGER {
					v100PctBars(0),
					v75PctBars(1),
					smpteBars(2),
					tartan(3),
					pluge(4),
					ramp(5),
					sweep(6),
					pulseAndBar(7),
					burst(8)
				}
		MAX-ACCESS	read-write
		STATUS		current
		DESCRIPTION	"
			style='Radiobutton list'
			preset='v100PctBars'
			path='/utils/Channel A/Pattern Type'
		"
		::= { alchemistHdCtrlEntries 5621 }

	patternEnableB OBJECT-TYPE
		SYNTAX		INTEGER { enable(0), disable(1) }
		MAX-ACCESS	read-write
		STATUS		current
		DESCRIPTION	"
			style='Checkbox'
			path='/utils/Channel B/Pattern Enable'
		"
		::= { alchemistHdCtrlEntries 5622 }

	patternTypeB OBJECT-TYPE
		SYNTAX		INTEGER {
					v100PctBars(0),
					v75PctBars(1),
					smpteBars(2),
					tartan(3),
					pluge(4),
					ramp(5),
					sweep(6),
					pulseAndBar(7),
					burst(8)
				}
		MAX-ACCESS	read-write
		STATUS		current
		DESCRIPTION	"
			style='Radiobutton list'
			preset='v100PctBars'
			path='/utils/Channel B/Pattern Type'
		"
		::= { alchemistHdCtrlEntries 5623 }

	audioPair1CtlLeftLevel OBJECT-TYPE
		SYNTAX		Integer32 (0..11)
		MAX-ACCESS	read-only
		STATUS		current
		DESCRIPTION	"
			style='ReadOnly numeric'
			range='0..11'
			path='/System/Debug/audio levels 1-4/left/Left Level'
		"
		::= { alchemistHdCtrlEntries 5700 }

	audioPair1CtlRightLevel OBJECT-TYPE
		SYNTAX		Integer32 (0..11)
		MAX-ACCESS	read-only
		STATUS		current
		DESCRIPTION	"
			style='ReadOnly numeric'
			range='0..11'
			path='/System/Debug/audio levels 1-4/right/Right Level'
		"
		::= { alchemistHdCtrlEntries 5701 }

	audioPair1CtlGain OBJECT-TYPE
		SYNTAX		Integer32 (-120..120)
		MAX-ACCESS	read-write
		STATUS		current
		DESCRIPTION	"
			style='Numeric control'
			range='-12.0dB..12.0dB'
			stepsize='0.1dB'
			path='/audio_control/Audio Pair 1/Gain'
		"
		::= { alchemistHdCtrlEntries 5702 }

	audioPair1CtlDlyPreset OBJECT-TYPE
		SYNTAX		INTEGER { ready(0), trigger(1) }
		MAX-ACCESS	read-write
		STATUS		current
		DESCRIPTION	"
			style='Event button'
			path='/audio_control/Audio Pair 1/Preset'
		"
		::= { alchemistHdCtrlEntries 5703 }

	audioPair1CtlGainPreset OBJECT-TYPE
		SYNTAX		INTEGER { ready(0), trigger(1) }
		MAX-ACCESS	read-write
		STATUS		current
		DESCRIPTION	"
			style='Event button'
			path='/audio_control/Audio Pair 1/Preset'
		"
		::= { alchemistHdCtrlEntries 5704 }

	audioPair1CtlMute OBJECT-TYPE
		SYNTAX		INTEGER { enable(0), disable(1) }
		MAX-ACCESS	read-write
		STATUS		current
		DESCRIPTION	"
			style='Checkbox'
			path='/audio_control/Audio Pair 1/Mute'
		"
		::= { alchemistHdCtrlEntries 5706 }

	audioPair1CtlDelay OBJECT-TYPE
		SYNTAX		Integer32 (0..250)
		MAX-ACCESS	read-write
		STATUS		current
		DESCRIPTION	"
			style='Numeric control'
			range='0mS..250mS'
			path='/audio_control/Audio Pair 1/Delay'
		"
		::= { alchemistHdCtrlEntries 5707 }

	audioPair1CtlTone OBJECT-TYPE
		SYNTAX		INTEGER { enable(0), disable(1) }
		MAX-ACCESS	read-write
		STATUS		current
		DESCRIPTION	"
			style='Checkbox'
			path='/audio_control/Audio Pair 1/Tone'
		"
		::= { alchemistHdCtrlEntries 5708 }

	audioPair1CtlToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/audio_control/Audio Pair 1/Tone Type'
		"
		::= { alchemistHdCtrlEntries 5709 }

	audioPair2CtlLeftLevel OBJECT-TYPE
		SYNTAX		Integer32 (0..11)
		MAX-ACCESS	read-only
		STATUS		current
		DESCRIPTION	"
			style='ReadOnly numeric'
			range='0..11'
			path='/System/Debug/audio levels 1-4/left/Left Level'
		"
		::= { alchemistHdCtrlEntries 5710 }

	audioPair2CtlRightLevel OBJECT-TYPE
		SYNTAX		Integer32 (0..11)
		MAX-ACCESS	read-only
		STATUS		current
		DESCRIPTION	"
			style='ReadOnly numeric'
			range='0..11'
			path='/System/Debug/audio levels 1-4/right/Right Level'
		"
		::= { alchemistHdCtrlEntries 5711 }

	audioPair2CtlGain OBJECT-TYPE
		SYNTAX		Integer32 (-120..120)
		MAX-ACCESS	read-write
		STATUS		current
		DESCRIPTION	"
			style='Numeric control'
			range='-12.0dB..12.0dB'
			stepsize='0.1dB'
			path='/audio_control/Audio Pair 2/Gain'
		"
		::= { alchemistHdCtrlEntries 5712 }

	audioPair2CtlDlyPreset OBJECT-TYPE
		SYNTAX		INTEGER { ready(0), trigger(1) }
		MAX-ACCESS	read-write
		STATUS		current
		DESCRIPTION	"
			style='Event button'
			path='/audio_control/Audio Pair 2/Preset'
		"
		::= { alchemistHdCtrlEntries 5713 }

	audioPair2CtlGainPreset OBJECT-TYPE
		SYNTAX		INTEGER { ready(0), trigger(1) }
		MAX-ACCESS	read-write
		STATUS		current
		DESCRIPTION	"
			style='Event button'
			path='/audio_control/Audio Pair 2/Preset'
		"
		::= { alchemistHdCtrlEntries 5714 }

	audioPair2CtlMute OBJECT-TYPE
		SYNTAX		INTEGER { enable(0), disable(1) }
		MAX-ACCESS	read-write
		STATUS		current
		DESCRIPTION	"
			style='Checkbox'
			path='/audio_control/Audio Pair 2/Mute'
		"
		::= { alchemistHdCtrlEntries 5716 }

	audioPair2CtlDelay OBJECT-TYPE
		SYNTAX		Integer32 (0..250)
		MAX-ACCESS	read-write
		STATUS		current
		DESCRIPTION	"
			style='Numeric control'
			range='0mS..250mS'
			path='/audio_control/Audio Pair 2/Delay'
		"
		::= { alchemistHdCtrlEntries 5717 }

	audioPair2CtlTone OBJECT-TYPE
		SYNTAX		INTEGER { enable(0), disable(1) }
		MAX-ACCESS	read-write
		STATUS		current
		DESCRIPTION	"
			style='Checkbox'
			path='/audio_control/Audio Pair 2/Tone'
		"
		::= { alchemistHdCtrlEntries 5718 }

	audioPair2CtlToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/audio_control/Audio Pair 2/Tone Type'
		"
		::= { alchemistHdCtrlEntries 5719 }

	audioPair3CtlLeftLevel OBJECT-TYPE
		SYNTAX		Integer32 (0..11)
		MAX-ACCESS	read-only
		STATUS		current
		DESCRIPTION	"
			style='ReadOnly numeric'
			range='0..11'
			path='/System/Debug/audio levels 1-4/left/Left Level'
		"
		::= { alchemistHdCtrlEntries 5720 }

	audioPair3CtlRightLevel OBJECT-TYPE
		SYNTAX		Integer32 (0..11)
		MAX-ACCESS	read-only
		STATUS		current
		DESCRIPTION	"
			style='ReadOnly numeric'
			range='0..11'
			path='/System/Debug/audio levels 1-4/right/Right Level'
		"
		::= { alchemistHdCtrlEntries 5721 }

	audioPair3CtlGain OBJECT-TYPE
		SYNTAX		Integer32 (-120..120)
		MAX-ACCESS	read-write
		STATUS		current
		DESCRIPTION	"
			style='Numeric control'
			range='-12.0dB..12.0dB'
			stepsize='0.1dB'
			path='/audio_control/Audio Pair 3/Gain'
		"
		::= { alchemistHdCtrlEntries 5722 }

	audioPair3CtlDlyPreset OBJECT-TYPE
		SYNTAX		INTEGER { ready(0), trigger(1) }
		MAX-ACCESS	read-write
		STATUS		current
		DESCRIPTION	"
			style='Event button'
			path='/audio_control/Audio Pair 3/Preset'
		"
		::= { alchemistHdCtrlEntries 5723 }

	audioPair3CtlGainPreset OBJECT-TYPE
		SYNTAX		INTEGER { ready(0), trigger(1) }
		MAX-ACCESS	read-write
		STATUS		current
		DESCRIPTION	"
			style='Event button'
			path='/audio_control/Audio Pair 3/Preset'
		"
		::= { alchemistHdCtrlEntries 5724 }

	audioPair3CtlMute OBJECT-TYPE
		SYNTAX		INTEGER { enable(0), disable(1) }
		MAX-ACCESS	read-write
		STATUS		current
		DESCRIPTION	"
			style='Checkbox'
			path='/audio_control/Audio Pair 3/Mute'
		"
		::= { alchemistHdCtrlEntries 5726 }

	audioPair3CtlDelay OBJECT-TYPE
		SYNTAX		Integer32 (0..250)
		MAX-ACCESS	read-write
		STATUS		current
		DESCRIPTION	"
			style='Numeric control'
			range='0mS..250mS'
			path='/audio_control/Audio Pair 3/Delay'
		"
		::= { alchemistHdCtrlEntries 5727 }

	audioPair3CtlTone OBJECT-TYPE
		SYNTAX		INTEGER { enable(0), disable(1) }
		MAX-ACCESS	read-write
		STATUS		current
		DESCRIPTION	"
			style='Checkbox'
			path='/audio_control/Audio Pair 3/Tone'
		"
		::= { alchemistHdCtrlEntries 5728 }

	audioPair3CtlToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/audio_control/Audio Pair 3/Tone Type'
		"
		::= { alchemistHdCtrlEntries 5729 }

	audioPair4CtlLeftLevel OBJECT-TYPE
		SYNTAX		Integer32 (0..11)
		MAX-ACCESS	read-only
		STATUS		current
		DESCRIPTION	"
			style='ReadOnly numeric'
			range='0..11'
			path='/System/Debug/audio levels 1-4/left/Left Level'
		"
		::= { alchemistHdCtrlEntries 5730 }

	audioPair4CtlRightLevel OBJECT-TYPE
		SYNTAX		Integer32 (0..11)
		MAX-ACCESS	read-only
		STATUS		current
		DESCRIPTION	"
			style='ReadOnly numeric'
			range='0..11'
			path='/System/Debug/audio levels 1-4/right/Right Level'
		"
		::= { alchemistHdCtrlEntries 5731 }

	audioPair4CtlGain OBJECT-TYPE
		SYNTAX		Integer32 (-120..120)
		MAX-ACCESS	read-write
		STATUS		current
		DESCRIPTION	"
			style='Numeric control'
			range='-12.0dB..12.0dB'
			stepsize='0.1dB'
			path='/audio_control/Audio Pair 4/Gain'
		"
		::= { alchemistHdCtrlEntries 5732 }

	audioPair4CtlDlyPreset OBJECT-TYPE
		SYNTAX		INTEGER { ready(0), trigger(1) }
		MAX-ACCESS	read-write
		STATUS		current
		DESCRIPTION	"
			style='Event button'
			path='/audio_control/Audio Pair 4/Preset'
		"
		::= { alchemistHdCtrlEntries 5733 }

	audioPair4CtlGainPreset OBJECT-TYPE
		SYNTAX		INTEGER { ready(0), trigger(1) }
		MAX-ACCESS	read-write
		STATUS		current
		DESCRIPTION	"
			style='Event button'
			path='/audio_control/Audio Pair 4/Preset'
		"
		::= { alchemistHdCtrlEntries 5734 }

	audioPair4CtlMute OBJECT-TYPE
		SYNTAX		INTEGER { enable(0), disable(1) }
		MAX-ACCESS	read-write
		STATUS		current
		DESCRIPTION	"
			style='Checkbox'
			path='/audio_control/Audio Pair 4/Mute'
		"
		::= { alchemistHdCtrlEntries 5736 }

	audioPair4CtlDelay OBJECT-TYPE
		SYNTAX		Integer32 (0..250)
		MAX-ACCESS	read-write
		STATUS		current
		DESCRIPTION	"
			style='Numeric control'
			range='0mS..250mS'
			path='/audio_control/Audio Pair 4/Delay'
		"
		::= { alchemistHdCtrlEntries 5737 }

	audioPair4CtlTone OBJECT-TYPE
		SYNTAX		INTEGER { enable(0), disable(1) }
		MAX-ACCESS	read-write
		STATUS		current
		DESCRIPTION	"
			style='Checkbox'
			path='/audio_control/Audio Pair 4/Tone'
		"
		::= { alchemistHdCtrlEntries 5738 }

	audioPair4CtlToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/audio_control/Audio Pair 4/Tone Type'
		"
		::= { alchemistHdCtrlEntries 5739 }

	audioPair5CtlLeftLevel OBJECT-TYPE
		SYNTAX		Integer32 (0..11)
		MAX-ACCESS	read-only
		STATUS		current
		DESCRIPTION	"
			style='ReadOnly numeric'
			range='0..11'
			path='/System/Debug/audio levels 5-8/left/Left Level'
		"
		::= { alchemistHdCtrlEntries 5740 }

	audioPair5CtlRightLevel OBJECT-TYPE
		SYNTAX		Integer32 (0..11)
		MAX-ACCESS	read-only
		STATUS		current
		DESCRIPTION	"
			style='ReadOnly numeric'
			range='0..11'
			path='/System/Debug/audio levels 5-8/right/Right Level'
		"
		::= { alchemistHdCtrlEntries 5741 }

	audioPair5CtlGain OBJECT-TYPE
		SYNTAX		Integer32 (-120..120)
		MAX-ACCESS	read-write
		STATUS		current
		DESCRIPTION	"
			style='Numeric control'
			range='-12.0dB..12.0dB'
			stepsize='0.1dB'
			path='/audio_control/Audio Pair 5/Gain'
		"
		::= { alchemistHdCtrlEntries 5742 }

	audioPair5CtlDlyPreset OBJECT-TYPE
		SYNTAX		INTEGER { ready(0), trigger(1) }
		MAX-ACCESS	read-write
		STATUS		current
		DESCRIPTION	"
			style='Event button'
			path='/audio_control/Audio Pair 5/Preset'
		"
		::= { alchemistHdCtrlEntries 5743 }

	audioPair5CtlGainPreset OBJECT-TYPE
		SYNTAX		INTEGER { ready(0), trigger(1) }
		MAX-ACCESS	read-write
		STATUS		current
		DESCRIPTION	"
			style='Event button'
			path='/audio_control/Audio Pair 5/Preset'
		"
		::= { alchemistHdCtrlEntries 5744 }

	audioPair5CtlMute OBJECT-TYPE
		SYNTAX		INTEGER { enable(0), disable(1) }
		MAX-ACCESS	read-write
		STATUS		current
		DESCRIPTION	"
			style='Checkbox'
			path='/audio_control/Audio Pair 5/Mute'
		"
		::= { alchemistHdCtrlEntries 5746 }

	audioPair5CtlDelay OBJECT-TYPE
		SYNTAX		Integer32 (0..250)
		MAX-ACCESS	read-write
		STATUS		current
		DESCRIPTION	"
			style='Numeric control'
			range='0mS..250mS'
			path='/audio_control/Audio Pair 5/Delay'
		"
		::= { alchemistHdCtrlEntries 5747 }

	audioPair5CtlTone OBJECT-TYPE
		SYNTAX		INTEGER { enable(0), disable(1) }
		MAX-ACCESS	read-write
		STATUS		current
		DESCRIPTION	"
			style='Checkbox'
			path='/audio_control/Audio Pair 5/Tone'
		"
		::= { alchemistHdCtrlEntries 5748 }

	audioPair5CtlToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/audio_control/Audio Pair 5/Tone Type'
		"
		::= { alchemistHdCtrlEntries 5749 }

	audioPair6CtlLeftLevel OBJECT-TYPE
		SYNTAX		Integer32 (0..11)
		MAX-ACCESS	read-only
		STATUS		current
		DESCRIPTION	"
			style='ReadOnly numeric'
			range='0..11'
			path='/System/Debug/audio levels 5-8/left/Left Level'
		"
		::= { alchemistHdCtrlEntries 5750 }

	audioPair6CtlRightLevel OBJECT-TYPE
		SYNTAX		Integer32 (0..11)
		MAX-ACCESS	read-only
		STATUS		current
		DESCRIPTION	"
			style='ReadOnly numeric'
			range='0..11'
			path='/System/Debug/audio levels 5-8/right/Right Level'
		"
		::= { alchemistHdCtrlEntries 5751 }

	audioPair6CtlGain OBJECT-TYPE
		SYNTAX		Integer32 (-120..120)
		MAX-ACCESS	read-write
		STATUS		current
		DESCRIPTION	"
			style='Numeric control'
			range='-12.0dB..12.0dB'
			stepsize='0.1dB'
			path='/audio_control/Audio Pair 6/Gain'
		"
		::= { alchemistHdCtrlEntries 5752 }

	audioPair6CtlDlyPreset OBJECT-TYPE
		SYNTAX		INTEGER { ready(0), trigger(1) }
		MAX-ACCESS	read-write
		STATUS		current
		DESCRIPTION	"
			style='Event button'
			path='/audio_control/Audio Pair 6/Preset'
		"
		::= { alchemistHdCtrlEntries 5753 }

	audioPair6CtlGainPreset OBJECT-TYPE
		SYNTAX		INTEGER { ready(0), trigger(1) }
		MAX-ACCESS	read-write
		STATUS		current
		DESCRIPTION	"
			style='Event button'
			path='/audio_control/Audio Pair 6/Preset'
		"
		::= { alchemistHdCtrlEntries 5754 }

	audioPair6CtlMute OBJECT-TYPE
		SYNTAX		INTEGER { enable(0), disable(1) }
		MAX-ACCESS	read-write
		STATUS		current
		DESCRIPTION	"
			style='Checkbox'
			path='/audio_control/Audio Pair 6/Mute'
		"
		::= { alchemistHdCtrlEntries 5756 }

	audioPair6CtlDelay OBJECT-TYPE
		SYNTAX		Integer32 (0..250)
		MAX-ACCESS	read-write
		STATUS		current
		DESCRIPTION	"
			style='Numeric control'
			range='0mS..250mS'
			path='/audio_control/Audio Pair 6/Delay'
		"
		::= { alchemistHdCtrlEntries 5757 }

	audioPair6CtlTone OBJECT-TYPE
		SYNTAX		INTEGER { enable(0), disable(1) }
		MAX-ACCESS	read-write
		STATUS		current
		DESCRIPTION	"
			style='Checkbox'
			path='/audio_control/Audio Pair 6/Tone'
		"
		::= { alchemistHdCtrlEntries 5758 }

	audioPair6CtlToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/audio_control/Audio Pair 6/Tone Type'
		"
		::= { alchemistHdCtrlEntries 5759 }

	audioPair7CtlLeftLevel OBJECT-TYPE
		SYNTAX		Integer32 (0..11)
		MAX-ACCESS	read-only
		STATUS		current
		DESCRIPTION	"
			style='ReadOnly numeric'
			range='0..11'
			path='/System/Debug/audio levels 5-8/left/Left Level'
		"
		::= { alchemistHdCtrlEntries 5760 }

	audioPair7CtlRightLevel OBJECT-TYPE
		SYNTAX		Integer32 (0..11)
		MAX-ACCESS	read-only
		STATUS		current
		DESCRIPTION	"
			style='ReadOnly numeric'
			range='0..11'
			path='/System/Debug/audio levels 5-8/right/Right Level'
		"
		::= { alchemistHdCtrlEntries 5761 }

	audioPair7CtlGain OBJECT-TYPE
		SYNTAX		Integer32 (-120..120)
		MAX-ACCESS	read-write
		STATUS		current
		DESCRIPTION	"
			style='Numeric control'
			range='-12.0dB..12.0dB'
			stepsize='0.1dB'
			path='/audio_control/Audio Pair 7/Gain'
		"
		::= { alchemistHdCtrlEntries 5762 }

	audioPair7CtlDlyPreset OBJECT-TYPE
		SYNTAX		INTEGER { ready(0), trigger(1) }
		MAX-ACCESS	read-write
		STATUS		current
		DESCRIPTION	"
			style='Event button'
			path='/audio_control/Audio Pair 7/Preset'
		"
		::= { alchemistHdCtrlEntries 5763 }

	audioPair7CtlGainPreset OBJECT-TYPE
		SYNTAX		INTEGER { ready(0), trigger(1) }
		MAX-ACCESS	read-write
		STATUS		current
		DESCRIPTION	"
			style='Event button'
			path='/audio_control/Audio Pair 7/Preset'
		"
		::= { alchemistHdCtrlEntries 5764 }

	audioPair7CtlMute OBJECT-TYPE
		SYNTAX		INTEGER { enable(0), disable(1) }
		MAX-ACCESS	read-write
		STATUS		current
		DESCRIPTION	"
			style='Checkbox'
			path='/audio_control/Audio Pair 7/Mute'
		"
		::= { alchemistHdCtrlEntries 5766 }

	audioPair7CtlDelay OBJECT-TYPE
		SYNTAX		Integer32 (0..250)
		MAX-ACCESS	read-write
		STATUS		current
		DESCRIPTION	"
			style='Numeric control'
			range='0mS..250mS'
			path='/audio_control/Audio Pair 7/Delay'
		"
		::= { alchemistHdCtrlEntries 5767 }

	audioPair7CtlTone OBJECT-TYPE
		SYNTAX		INTEGER { enable(0), disable(1) }
		MAX-ACCESS	read-write
		STATUS		current
		DESCRIPTION	"
			style='Checkbox'
			path='/audio_control/Audio Pair 7/Tone'
		"
		::= { alchemistHdCtrlEntries 5768 }

	audioPair7CtlToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/audio_control/Audio Pair 7/Tone Type'
		"
		::= { alchemistHdCtrlEntries 5769 }

	audioPair8CtlLeftLevel OBJECT-TYPE
		SYNTAX		Integer32 (0..11)
		MAX-ACCESS	read-only
		STATUS		current
		DESCRIPTION	"
			style='ReadOnly numeric'
			range='0..11'
			path='/System/Debug/audio levels 5-8/left/Left Level'
		"
		::= { alchemistHdCtrlEntries 5770 }

	audioPair8CtlRightLevel OBJECT-TYPE
		SYNTAX		Integer32 (0..11)
		MAX-ACCESS	read-only
		STATUS		current
		DESCRIPTION	"
			style='ReadOnly numeric'
			range='0..11'
			path='/System/Debug/audio levels 5-8/right/Right Level'
		"
		::= { alchemistHdCtrlEntries 5771 }

	audioPair8CtlGain OBJECT-TYPE
		SYNTAX		Integer32 (-120..120)
		MAX-ACCESS	read-write
		STATUS		current
		DESCRIPTION	"
			style='Numeric control'
			range='-12.0dB..12.0dB'
			stepsize='0.1dB'
			path='/audio_control/Audio Pair 8/Gain'
		"
		::= { alchemistHdCtrlEntries 5772 }

	audioPair8CtlDlyPreset OBJECT-TYPE
		SYNTAX		INTEGER { ready(0), trigger(1) }
		MAX-ACCESS	read-write
		STATUS		current
		DESCRIPTION	"
			style='Event button'
			path='/audio_control/Audio Pair 8/Preset'
		"
		::= { alchemistHdCtrlEntries 5773 }

	audioPair8CtlGainPreset OBJECT-TYPE
		SYNTAX		INTEGER { ready(0), trigger(1) }
		MAX-ACCESS	read-write
		STATUS		current
		DESCRIPTION	"
			style='Event button'
			path='/audio_control/Audio Pair 8/Preset'
		"
		::= { alchemistHdCtrlEntries 5774 }

	audioPair8CtlMute OBJECT-TYPE
		SYNTAX		INTEGER { enable(0), disable(1) }
		MAX-ACCESS	read-write
		STATUS		current
		DESCRIPTION	"
			style='Checkbox'
			path='/audio_control/Audio Pair 8/Mute'
		"
		::= { alchemistHdCtrlEntries 5776 }

	audioPair8CtlDelay OBJECT-TYPE
		SYNTAX		Integer32 (0..250)
		MAX-ACCESS	read-write
		STATUS		current
		DESCRIPTION	"
			style='Numeric control'
			range='0mS..250mS'
			path='/audio_control/Audio Pair 8/Delay'
		"
		::= { alchemistHdCtrlEntries 5777 }

	audioPair8CtlTone OBJECT-TYPE
		SYNTAX		INTEGER { enable(0), disable(1) }
		MAX-ACCESS	read-write
		STATUS		current
		DESCRIPTION	"
			style='Checkbox'
			path='/audio_control/Audio Pair 8/Tone'
		"
		::= { alchemistHdCtrlEntries 5778 }

	audioPair8CtlToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/audio_control/Audio Pair 8/Tone Type'
		"
		::= { alchemistHdCtrlEntries 5779 }

	audioStatusPair1 OBJECT-TYPE
		SYNTAX		Integer32 (0..65535)
		MAX-ACCESS	read-only
		STATUS		current
		DESCRIPTION	"
			style='ReadOnly numeric'
			range='0..65535'
			path='/System/Debug/audio status/Audio Status Pair 1'
		"
		::= { alchemistHdCtrlEntries 5780 }

	audioStatusPair2 OBJECT-TYPE
		SYNTAX		Integer32 (0..65535)
		MAX-ACCESS	read-only
		STATUS		current
		DESCRIPTION	"
			style='ReadOnly numeric'
			range='0..65535'
			path='/System/Debug/audio status/Audio Status Pair 2'
		"
		::= { alchemistHdCtrlEntries 5781 }

	audioStatusPair3 OBJECT-TYPE
		SYNTAX		Integer32 (0..65535)
		MAX-ACCESS	read-only
		STATUS		current
		DESCRIPTION	"
			style='ReadOnly numeric'
			range='0..65535'
			path='/System/Debug/audio status/Audio Status Pair 3'
		"
		::= { alchemistHdCtrlEntries 5782 }

	audioStatusPair4 OBJECT-TYPE
		SYNTAX		Integer32 (0..65535)
		MAX-ACCESS	read-only
		STATUS		current
		DESCRIPTION	"
			style='ReadOnly numeric'
			range='0..65535'
			path='/System/Debug/audio status/Audio Status Pair 4'
		"
		::= { alchemistHdCtrlEntries 5783 }

	audioStatusPair5 OBJECT-TYPE
		SYNTAX		Integer32 (0..65535)
		MAX-ACCESS	read-only
		STATUS		current
		DESCRIPTION	"
			style='ReadOnly numeric'
			range='0..65535'
			path='/System/Debug/audio status/Audio Status Pair 5'
		"
		::= { alchemistHdCtrlEntries 5784 }

	audioStatusPair6 OBJECT-TYPE
		SYNTAX		Integer32 (0..65535)
		MAX-ACCESS	read-only
		STATUS		current
		DESCRIPTION	"
			style='ReadOnly numeric'
			range='0..65535'
			path='/System/Debug/audio status/Audio Status Pair 6'
		"
		::= { alchemistHdCtrlEntries 5785 }

	audioStatusPair7 OBJECT-TYPE
		SYNTAX		Integer32 (0..65535)
		MAX-ACCESS	read-only
		STATUS		current
		DESCRIPTION	"
			style='ReadOnly numeric'
			range='0..65535'
			path='/System/Debug/audio status/Audio Status Pair 7'
		"
		::= { alchemistHdCtrlEntries 5786 }

	audioStatusPair8 OBJECT-TYPE
		SYNTAX		Integer32 (0..65535)
		MAX-ACCESS	read-only
		STATUS		current
		DESCRIPTION	"
			style='ReadOnly numeric'
			range='0..65535'
			path='/System/Debug/audio status/Audio Status Pair 8'
		"
		::= { alchemistHdCtrlEntries 5787 }

	embeddedInputStatus OBJECT-TYPE
		SYNTAX		Integer32 (0..65535)
		MAX-ACCESS	read-only
		STATUS		current
		DESCRIPTION	"
			style='ReadOnly numeric'
			range='0..65535'
			path='/System/Debug/audio status/Embedded Input Status'
		"
		::= { alchemistHdCtrlEntries 5788 }

	aesInputStatus OBJECT-TYPE
		SYNTAX		Integer32 (0..65535)
		MAX-ACCESS	read-only
		STATUS		current
		DESCRIPTION	"
			style='ReadOnly numeric'
			range='0..65535'
			path='/System/Debug/audio status/AES Input Status'
		"
		::= { alchemistHdCtrlEntries 5789 }

	audioDelay OBJECT-TYPE
		SYNTAX		Integer32 (-190..250)
		MAX-ACCESS	read-write
		STATUS		current
		DESCRIPTION	"
			style='Numeric control'
			range='-190ms..250ms'
			path='/audio_control/Audio Delay Offset'
		"
		::= { alchemistHdCtrlEntries 5790 }

	selectedAudioStatus OBJECT-TYPE
		SYNTAX		Integer32 (0..65535)
		MAX-ACCESS	read-only
		STATUS		current
		DESCRIPTION	"
			style='ReadOnly numeric'
			range='0..65535'
			path='/System/Debug/audio status/selected Audio Status'
		"
		::= { alchemistHdCtrlEntries 5792 }

	dolby1SourcePresent OBJECT-TYPE
		SYNTAX		Integer32 (0..65535)
		MAX-ACCESS	read-only
		STATUS		current
		DESCRIPTION	"
			style='ReadOnly numeric'
			range='0..65535'
			path='/System/Debug/audio status/Dolby 1 Source Status'
		"
		::= { alchemistHdCtrlEntries 5793 }

	dolby2SourcePresent OBJECT-TYPE
		SYNTAX		Integer32 (0..65535)
		MAX-ACCESS	read-only
		STATUS		current
		DESCRIPTION	"
			style='ReadOnly numeric'
			range='0..65535'
			path='/System/Debug/audio status/Dolby 2 Source Status'
		"
		::= { alchemistHdCtrlEntries 5794 }

	dolby1Fitted OBJECT-TYPE
		SYNTAX		Integer32 (0..65535)
		MAX-ACCESS	read-only
		STATUS		current
		DESCRIPTION	"
			style='ReadOnly numeric'
			range='0..65535'
			path='/System/Debug/audio status/Dolby 1 Fitted'
		"
		::= { alchemistHdCtrlEntries 5795 }

	dolby2Fitted OBJECT-TYPE
		SYNTAX		Integer32 (0..65535)
		MAX-ACCESS	read-only
		STATUS		current
		DESCRIPTION	"
			style='ReadOnly numeric'
			range='0..65535'
			path='/System/Debug/audio status/Dolby 2 Fitted'
		"
		::= { alchemistHdCtrlEntries 5796 }

	audioPair1InputSrc OBJECT-TYPE
		SYNTAX		INTEGER {
					aes1(0),
					aes2(1),
					aes3(2),
					aes4(3),
					aes5(4),
					aes6(5),
					aes7(6),
					aes8(7),
					emb1(8),
					emb2(9),
					emb3(10),
					emb4(11),
					emb5(12),
					emb6(13),
					emb7(14),
					emb8(15),
					dec11(16),
					dec12(17),
					dec13(18),
					dec14(19),
					dec21(20),
					dec22(21),
					dec23(22),
					dec24(23),
					enc1(24),
					enc2(25)
				}
		MAX-ACCESS	read-write
		STATUS		current
		DESCRIPTION	"
			style='Radiobutton list'
			preset='emb1'
			path='/System 2/Audio Routing/Audio Pair 1/Source'
		"
		::= { alchemistHdCtrlEntries 5800 }

	audioPair1InputType OBJECT-TYPE
		SYNTAX		INTEGER {
					pcm(0),
					data(1)
				}
		MAX-ACCESS	read-write
		STATUS		current
		DESCRIPTION	"
			style='Radiobutton list'
			preset='pcm'
			path='/System 2/Audio Routing/Audio Pair 1/Input Type'
		"
		::= { alchemistHdCtrlEntries 5801 }

	audioPair1Name OBJECT-TYPE
		SYNTAX		RollCallString
		MAX-ACCESS	read-write
		STATUS		current
		DESCRIPTION	"
			style='Editable string'
			path='/System 2/Name'
		"
		::= { alchemistHdCtrlEntries 5802 }

	audioPair1InputSrcAes OBJECT-TYPE
		SYNTAX		INTEGER {
					aud1AesLost(0),
					aud2AesLost(1),
					aud3AesLost(2),
					aud4AesLost(3),
					aud5AesLost(4),
					aud6AesLost(5),
					aud7AesLost(6),
					aud8AesLost(7)
				}
		MAX-ACCESS	read-write
		STATUS		current
		DESCRIPTION	"
			style='Radiobutton list'
			path='/audio_input_1/Audio Pair 1/AES Inputs'
		"
		::= { alchemistHdCtrlEntries 5803 }

	audioPair1InputSrcEmb OBJECT-TYPE
		SYNTAX		INTEGER {
					aud1EmbLost(8),
					aud2EmbLost(9),
					aud3EmbLost(10),
					aud4EmbLost(11),
					aud5EmbLost(12),
					aud6EmbLost(13),
					aud7EmbLost(14),
					aud8EmbLost(15)
				}
		MAX-ACCESS	read-write
		STATUS		current
		DESCRIPTION	"
			style='Radiobutton list'
			preset='aud1EmbLost'
			path='/audio_input_1/Audio Pair 1/Embedded Inputs'
		"
		::= { alchemistHdCtrlEntries 5804 }

	audioPair1InputSrcDlbDec1 OBJECT-TYPE
		SYNTAX		INTEGER {
					audDlb1P1Lost(16),
					audDlb1P2Lost(17),
					audDlb1P3Lost(18),
					audDlb1P4Lost(19)
				}
		MAX-ACCESS	read-write
		STATUS		current
		DESCRIPTION	"
			style='Radiobutton list'
			path='/audio_input_1/Audio Pair 1/Dolby 1 Decoder'
		"
		::= { alchemistHdCtrlEntries 5805 }

	audioPair1InputSrcDlbDec2 OBJECT-TYPE
		SYNTAX		INTEGER {
					audDlb2P1Lost(20),
					audDlb2P2Lost(21),
					audDlb2P3Lost(22),
					audDlb2P4Lost(23)
				}
		MAX-ACCESS	read-write
		STATUS		current
		DESCRIPTION	"
			style='Radiobutton list'
			path='/audio_input_1/Audio Pair 1/Dolby 2 Decoder'
		"
		::= { alchemistHdCtrlEntries 5806 }

	audioPair1InputSrcDlbEnc OBJECT-TYPE
		SYNTAX		INTEGER {
					audDlb1EncLost(24),
					audDlb2EncLost(25)
				}
		MAX-ACCESS	read-write
		STATUS		current
		DESCRIPTION	"
			style='Radiobutton list'
			path='/audio_input_1/Audio Pair 1/Dolby Encoders'
		"
		::= { alchemistHdCtrlEntries 5807 }

	audioPair2InputSrc OBJECT-TYPE
		SYNTAX		INTEGER {
					aes1(0),
					aes2(1),
					aes3(2),
					aes4(3),
					aes5(4),
					aes6(5),
					aes7(6),
					aes8(7),
					emb1(8),
					emb2(9),
					emb3(10),
					emb4(11),
					emb5(12),
					emb6(13),
					emb7(14),
					emb8(15),
					dec11(16),
					dec12(17),
					dec13(18),
					dec14(19),
					dec21(20),
					dec22(21),
					dec23(22),
					dec24(23),
					enc1(24),
					enc2(25)
				}
		MAX-ACCESS	read-write
		STATUS		current
		DESCRIPTION	"
			style='Radiobutton list'
			preset='emb2'
			path='/System 2/Audio Routing/Audio Pair 2/Source'
		"
		::= { alchemistHdCtrlEntries 5810 }

	audioPair2InputType OBJECT-TYPE
		SYNTAX		INTEGER {
					pcm(0),
					data(1)
				}
		MAX-ACCESS	read-write
		STATUS		current
		DESCRIPTION	"
			style='Radiobutton list'
			preset='pcm'
			path='/System 2/Audio Routing/Audio Pair 2/Input Type'
		"
		::= { alchemistHdCtrlEntries 5811 }

	audioPair2Name OBJECT-TYPE
		SYNTAX		RollCallString
		MAX-ACCESS	read-write
		STATUS		current
		DESCRIPTION	"
			style='Editable string'
			path='/System 2/Name'
		"
		::= { alchemistHdCtrlEntries 5812 }

	audioPair2InputSrcAes OBJECT-TYPE
		SYNTAX		INTEGER {
					aud1AesLost(0),
					aud2AesLost(1),
					aud3AesLost(2),
					aud4AesLost(3),
					aud5AesLost(4),
					aud6AesLost(5),
					aud7AesLost(6),
					aud8AesLost(7)
				}
		MAX-ACCESS	read-write
		STATUS		current
		DESCRIPTION	"
			style='Radiobutton list'
			path='/audio_input_1/Audio Pair 2/AES Inputs'
		"
		::= { alchemistHdCtrlEntries 5813 }

	audioPair2InputSrcEmb OBJECT-TYPE
		SYNTAX		INTEGER {
					aud1EmbLost(8),
					aud2EmbLost(9),
					aud3EmbLost(10),
					aud4EmbLost(11),
					aud5EmbLost(12),
					aud6EmbLost(13),
					aud7EmbLost(14),
					aud8EmbLost(15)
				}
		MAX-ACCESS	read-write
		STATUS		current
		DESCRIPTION	"
			style='Radiobutton list'
			preset='aud2EmbLost'
			path='/audio_input_1/Audio Pair 2/Embedded Inputs'
		"
		::= { alchemistHdCtrlEntries 5814 }

	audioPair2InputSrcDlbDec1 OBJECT-TYPE
		SYNTAX		INTEGER {
					audDlb1P1Lost(16),
					audDlb1P2Lost(17),
					audDlb1P3Lost(18),
					audDlb1P4Lost(19)
				}
		MAX-ACCESS	read-write
		STATUS		current
		DESCRIPTION	"
			style='Radiobutton list'
			path='/audio_input_1/Audio Pair 2/Dolby 1 Decoder'
		"
		::= { alchemistHdCtrlEntries 5815 }

	audioPair2InputSrcDlbDec2 OBJECT-TYPE
		SYNTAX		INTEGER {
					audDlb2P1Lost(20),
					audDlb2P2Lost(21),
					audDlb2P3Lost(22),
					audDlb2P4Lost(23)
				}
		MAX-ACCESS	read-write
		STATUS		current
		DESCRIPTION	"
			style='Radiobutton list'
			path='/audio_input_1/Audio Pair 2/Dolby 2 Decoder'
		"
		::= { alchemistHdCtrlEntries 5816 }

	audioPair2InputSrcDlbEnc OBJECT-TYPE
		SYNTAX		INTEGER {
					audDlb1EncLost(24),
					audDlb2EncLost(25)
				}
		MAX-ACCESS	read-write
		STATUS		current
		DESCRIPTION	"
			style='Radiobutton list'
			path='/audio_input_1/Audio Pair 2/Dolby Encoders'
		"
		::= { alchemistHdCtrlEntries 5817 }

	audioPair3InputSrc OBJECT-TYPE
		SYNTAX		INTEGER {
					aes1(0),
					aes2(1),
					aes3(2),
					aes4(3),
					aes5(4),
					aes6(5),
					aes7(6),
					aes8(7),
					emb1(8),
					emb2(9),
					emb3(10),
					emb4(11),
					emb5(12),
					emb6(13),
					emb7(14),
					emb8(15),
					dec11(16),
					dec12(17),
					dec13(18),
					dec14(19),
					dec21(20),
					dec22(21),
					dec23(22),
					dec24(23),
					enc1(24),
					enc2(25)
				}
		MAX-ACCESS	read-write
		STATUS		current
		DESCRIPTION	"
			style='Radiobutton list'
			preset='emb3'
			path='/System 2/Audio Routing/Audio Pair 3/Source'
		"
		::= { alchemistHdCtrlEntries 5820 }

	audioPair3InputType OBJECT-TYPE
		SYNTAX		INTEGER {
					pcm(0),
					data(1)
				}
		MAX-ACCESS	read-write
		STATUS		current
		DESCRIPTION	"
			style='Radiobutton list'
			preset='pcm'
			path='/System 2/Audio Routing/Audio Pair 3/Input Type'
		"
		::= { alchemistHdCtrlEntries 5821 }

	audioPair3Name OBJECT-TYPE
		SYNTAX		RollCallString
		MAX-ACCESS	read-write
		STATUS		current
		DESCRIPTION	"
			style='Editable string'
			path='/System 2/Name'
		"
		::= { alchemistHdCtrlEntries 5822 }

	audioPair3InputSrcAes OBJECT-TYPE
		SYNTAX		INTEGER {
					aud1AesLost(0),
					aud2AesLost(1),
					aud3AesLost(2),
					aud4AesLost(3),
					aud5AesLost(4),
					aud6AesLost(5),
					aud7AesLost(6),
					aud8AesLost(7)
				}
		MAX-ACCESS	read-write
		STATUS		current
		DESCRIPTION	"
			style='Radiobutton list'
			path='/audio_input_1/Audio Pair 3/AES Inputs'
		"
		::= { alchemistHdCtrlEntries 5823 }

	audioPair3InputSrcEmb OBJECT-TYPE
		SYNTAX		INTEGER {
					aud1EmbLost(8),
					aud2EmbLost(9),
					aud3EmbLost(10),
					aud4EmbLost(11),
					aud5EmbLost(12),
					aud6EmbLost(13),
					aud7EmbLost(14),
					aud8EmbLost(15)
				}
		MAX-ACCESS	read-write
		STATUS		current
		DESCRIPTION	"
			style='Radiobutton list'
			preset='aud3EmbLost'
			path='/audio_input_1/Audio Pair 3/Embedded Inputs'
		"
		::= { alchemistHdCtrlEntries 5824 }

	audioPair3InputSrcDlbDec1 OBJECT-TYPE
		SYNTAX		INTEGER {
					audDlb1P1Lost(16),
					audDlb1P2Lost(17),
					audDlb1P3Lost(18),
					audDlb1P4Lost(19)
				}
		MAX-ACCESS	read-write
		STATUS		current
		DESCRIPTION	"
			style='Radiobutton list'
			path='/audio_input_1/Audio Pair 3/Dolby 1 Decoder'
		"
		::= { alchemistHdCtrlEntries 5825 }

	audioPair3InputSrcDlbDec2 OBJECT-TYPE
		SYNTAX		INTEGER {
					audDlb2P1Lost(20),
					audDlb2P2Lost(21),
					audDlb2P3Lost(22),
					audDlb2P4Lost(23)
				}
		MAX-ACCESS	read-write
		STATUS		current
		DESCRIPTION	"
			style='Radiobutton list'
			path='/audio_input_1/Audio Pair 3/Dolby 2 Decoder'
		"
		::= { alchemistHdCtrlEntries 5826 }

	audioPair3InputSrcDlbEnc OBJECT-TYPE
		SYNTAX		INTEGER {
					audDlb1EncLost(24),
					audDlb2EncLost(25)
				}
		MAX-ACCESS	read-write
		STATUS		current
		DESCRIPTION	"
			style='Radiobutton list'
			path='/audio_input_1/Audio Pair 3/Dolby Encoders'
		"
		::= { alchemistHdCtrlEntries 5827 }

	audioPair4InputSrc OBJECT-TYPE
		SYNTAX		INTEGER {
					aes1(0),
					aes2(1),
					aes3(2),
					aes4(3),
					aes5(4),
					aes6(5),
					aes7(6),
					aes8(7),
					emb1(8),
					emb2(9),
					emb3(10),
					emb4(11),
					emb5(12),
					emb6(13),
					emb7(14),
					emb8(15),
					dec11(16),
					dec12(17),
					dec13(18),
					dec14(19),
					dec21(20),
					dec22(21),
					dec23(22),
					dec24(23),
					enc1(24),
					enc2(25)
				}
		MAX-ACCESS	read-write
		STATUS		current
		DESCRIPTION	"
			style='Radiobutton list'
			preset='emb4'
			path='/System 2/Audio Routing/Audio Pair 4/Source'
		"
		::= { alchemistHdCtrlEntries 5830 }

	audioPair4InputType OBJECT-TYPE
		SYNTAX		INTEGER {
					pcm(0),
					data(1)
				}
		MAX-ACCESS	read-write
		STATUS		current
		DESCRIPTION	"
			style='Radiobutton list'
			preset='pcm'
			path='/System 2/Audio Routing/Audio Pair 4/Input Type'
		"
		::= { alchemistHdCtrlEntries 5831 }

	audioPair4Name OBJECT-TYPE
		SYNTAX		RollCallString
		MAX-ACCESS	read-write
		STATUS		current
		DESCRIPTION	"
			style='Editable string'
			path='/System 2/Name'
		"
		::= { alchemistHdCtrlEntries 5832 }

	audioPair4InputSrcAes OBJECT-TYPE
		SYNTAX		INTEGER {
					aud1AesLost(0),
					aud2AesLost(1),
					aud3AesLost(2),
					aud4AesLost(3),
					aud5AesLost(4),
					aud6AesLost(5),
					aud7AesLost(6),
					aud8AesLost(7)
				}
		MAX-ACCESS	read-write
		STATUS		current
		DESCRIPTION	"
			style='Radiobutton list'
			path='/audio_input_1/Audio Pair 4/AES Inputs'
		"
		::= { alchemistHdCtrlEntries 5833 }

	audioPair4InputSrcEmb OBJECT-TYPE
		SYNTAX		INTEGER {
					aud1EmbLost(8),
					aud2EmbLost(9),
					aud3EmbLost(10),
					aud4EmbLost(11),
					aud5EmbLost(12),
					aud6EmbLost(13),
					aud7EmbLost(14),
					aud8EmbLost(15)
				}
		MAX-ACCESS	read-write
		STATUS		current
		DESCRIPTION	"
			style='Radiobutton list'
			preset='aud4EmbLost'
			path='/audio_input_1/Audio Pair 4/Embedded Inputs'
		"
		::= { alchemistHdCtrlEntries 5834 }

	audioPair4InputSrcDlbDec1 OBJECT-TYPE
		SYNTAX		INTEGER {
					audDlb1P1Lost(16),
					audDlb1P2Lost(17),
					audDlb1P3Lost(18),
					audDlb1P4Lost(19)
				}
		MAX-ACCESS	read-write
		STATUS		current
		DESCRIPTION	"
			style='Radiobutton list'
			path='/audio_input_1/Audio Pair 4/Dolby 1 Decoder'
		"
		::= { alchemistHdCtrlEntries 5835 }

	audioPair4InputSrcDlbDec2 OBJECT-TYPE
		SYNTAX		INTEGER {
					audDlb2P1Lost(20),
					audDlb2P2Lost(21),
					audDlb2P3Lost(22),
					audDlb2P4Lost(23)
				}
		MAX-ACCESS	read-write
		STATUS		current
		DESCRIPTION	"
			style='Radiobutton list'
			path='/audio_input_1/Audio Pair 4/Dolby 2 Decoder'
		"
		::= { alchemistHdCtrlEntries 5836 }

	audioPair4InputSrcDlbEnc OBJECT-TYPE
		SYNTAX		INTEGER {
					audDlb1EncLost(24),
					audDlb2EncLost(25)
				}
		MAX-ACCESS	read-write
		STATUS		current
		DESCRIPTION	"
			style='Radiobutton list'
			path='/audio_input_1/Audio Pair 4/Dolby Encoders'
		"
		::= { alchemistHdCtrlEntries 5837 }

	audioPair5InputSrc OBJECT-TYPE
		SYNTAX		INTEGER {
					aes1(0),
					aes2(1),
					aes3(2),
					aes4(3),
					aes5(4),
					aes6(5),
					aes7(6),
					aes8(7),
					emb1(8),
					emb2(9),
					emb3(10),
					emb4(11),
					emb5(12),
					emb6(13),
					emb7(14),
					emb8(15),
					dec11(16),
					dec12(17),
					dec13(18),
					dec14(19),
					dec21(20),
					dec22(21),
					dec23(22),
					dec24(23),
					enc1(24),
					enc2(25)
				}
		MAX-ACCESS	read-write
		STATUS		current
		DESCRIPTION	"
			style='Radiobutton list'
			preset='emb5'
			path='/System 2/Audio Routing/Audio Pair 5/Source'
		"
		::= { alchemistHdCtrlEntries 5840 }

	audioPair5InputType OBJECT-TYPE
		SYNTAX		INTEGER {
					pcm(0),
					data(1)
				}
		MAX-ACCESS	read-write
		STATUS		current
		DESCRIPTION	"
			style='Radiobutton list'
			preset='pcm'
			path='/System 2/Audio Routing/Audio Pair 5/Input Type'
		"
		::= { alchemistHdCtrlEntries 5841 }

	audioPair5Name OBJECT-TYPE
		SYNTAX		RollCallString
		MAX-ACCESS	read-write
		STATUS		current
		DESCRIPTION	"
			style='Editable string'
			path='/System 2/Name'
		"
		::= { alchemistHdCtrlEntries 5842 }

	audioPair5InputSrcAes OBJECT-TYPE
		SYNTAX		INTEGER {
					aud1AesLost(0),
					aud2AesLost(1),
					aud3AesLost(2),
					aud4AesLost(3),
					aud5AesLost(4),
					aud6AesLost(5),
					aud7AesLost(6),
					aud8AesLost(7)
				}
		MAX-ACCESS	read-write
		STATUS		current
		DESCRIPTION	"
			style='Radiobutton list'
			path='/audio_input_2/Audio Pair 5/AES Inputs'
		"
		::= { alchemistHdCtrlEntries 5843 }

	audioPair5InputSrcEmb OBJECT-TYPE
		SYNTAX		INTEGER {
					aud1EmbLost(8),
					aud2EmbLost(9),
					aud3EmbLost(10),
					aud4EmbLost(11),
					aud5EmbLost(12),
					aud6EmbLost(13),
					aud7EmbLost(14),
					aud8EmbLost(15)
				}
		MAX-ACCESS	read-write
		STATUS		current
		DESCRIPTION	"
			style='Radiobutton list'
			preset='aud5EmbLost'
			path='/audio_input_2/Audio Pair 5/Embedded Inputs'
		"
		::= { alchemistHdCtrlEntries 5844 }

	audioPair5InputSrcDlbDec1 OBJECT-TYPE
		SYNTAX		INTEGER {
					audDlb1P1Lost(16),
					audDlb1P2Lost(17),
					audDlb1P3Lost(18),
					audDlb1P4Lost(19)
				}
		MAX-ACCESS	read-write
		STATUS		current
		DESCRIPTION	"
			style='Radiobutton list'
			path='/audio_input_2/Audio Pair 5/Dolby 1 Decoder'
		"
		::= { alchemistHdCtrlEntries 5845 }

	audioPair5InputSrcDlbDec2 OBJECT-TYPE
		SYNTAX		INTEGER {
					audDlb2P1Lost(20),
					audDlb2P2Lost(21),
					audDlb2P3Lost(22),
					audDlb2P4Lost(23)
				}
		MAX-ACCESS	read-write
		STATUS		current
		DESCRIPTION	"
			style='Radiobutton list'
			path='/audio_input_2/Audio Pair 5/Dolby 2 Decoder'
		"
		::= { alchemistHdCtrlEntries 5846 }

	audioPair5InputSrcDlbEnc OBJECT-TYPE
		SYNTAX		INTEGER {
					audDlb1EncLost(24),
					audDlb2EncLost(25)
				}
		MAX-ACCESS	read-write
		STATUS		current
		DESCRIPTION	"
			style='Radiobutton list'
			path='/audio_input_2/Audio Pair 5/Dolby Encoders'
		"
		::= { alchemistHdCtrlEntries 5847 }

	audioPair6InputSrc OBJECT-TYPE
		SYNTAX		INTEGER {
					aes1(0),
					aes2(1),
					aes3(2),
					aes4(3),
					aes5(4),
					aes6(5),
					aes7(6),
					aes8(7),
					emb1(8),
					emb2(9),
					emb3(10),
					emb4(11),
					emb5(12),
					emb6(13),
					emb7(14),
					emb8(15),
					dec11(16),
					dec12(17),
					dec13(18),
					dec14(19),
					dec21(20),
					dec22(21),
					dec23(22),
					dec24(23),
					enc1(24),
					enc2(25)
				}
		MAX-ACCESS	read-write
		STATUS		current
		DESCRIPTION	"
			style='Radiobutton list'
			preset='emb6'
			path='/System 2/Audio Routing/Audio Pair 6/Source'
		"
		::= { alchemistHdCtrlEntries 5850 }

	audioPair6InputType OBJECT-TYPE
		SYNTAX		INTEGER {
					pcm(0),
					data(1)
				}
		MAX-ACCESS	read-write
		STATUS		current
		DESCRIPTION	"
			style='Radiobutton list'
			preset='pcm'
			path='/System 2/Audio Routing/Audio Pair 6/Input Type'
		"
		::= { alchemistHdCtrlEntries 5851 }

	audioPair6Name OBJECT-TYPE
		SYNTAX		RollCallString
		MAX-ACCESS	read-write
		STATUS		current
		DESCRIPTION	"
			style='Editable string'
			path='/System 2/Name'
		"
		::= { alchemistHdCtrlEntries 5852 }

	audioPair6InputSrcAes OBJECT-TYPE
		SYNTAX		INTEGER {
					aud1AesLost(0),
					aud2AesLost(1),
					aud3AesLost(2),
					aud4AesLost(3),
					aud5AesLost(4),
					aud6AesLost(5),
					aud7AesLost(6),
					aud8AesLost(7)
				}
		MAX-ACCESS	read-write
		STATUS		current
		DESCRIPTION	"
			style='Radiobutton list'
			path='/audio_input_2/Audio Pair 6/AES Inputs'
		"
		::= { alchemistHdCtrlEntries 5853 }

	audioPair6InputSrcEmb OBJECT-TYPE
		SYNTAX		INTEGER {
					aud1EmbLost(8),
					aud2EmbLost(9),
					aud3EmbLost(10),
					aud4EmbLost(11),
					aud5EmbLost(12),
					aud6EmbLost(13),
					aud7EmbLost(14),
					aud8EmbLost(15)
				}
		MAX-ACCESS	read-write
		STATUS		current
		DESCRIPTION	"
			style='Radiobutton list'
			preset='aud6EmbLost'
			path='/audio_input_2/Audio Pair 6/Embedded Inputs'
		"
		::= { alchemistHdCtrlEntries 5854 }

	audioPair6InputSrcDlbDec1 OBJECT-TYPE
		SYNTAX		INTEGER {
					audDlb1P1Lost(16),
					audDlb1P2Lost(17),
					audDlb1P3Lost(18),
					audDlb1P4Lost(19)
				}
		MAX-ACCESS	read-write
		STATUS		current
		DESCRIPTION	"
			style='Radiobutton list'
			path='/audio_input_2/Audio Pair 6/Dolby 1 Decoder'
		"
		::= { alchemistHdCtrlEntries 5855 }

	audioPair6InputSrcDlbDec2 OBJECT-TYPE
		SYNTAX		INTEGER {
					audDlb2P1Lost(20),
					audDlb2P2Lost(21),
					audDlb2P3Lost(22),
					audDlb2P4Lost(23)
				}
		MAX-ACCESS	read-write
		STATUS		current
		DESCRIPTION	"
			style='Radiobutton list'
			path='/audio_input_2/Audio Pair 6/Dolby 2 Decoder'
		"
		::= { alchemistHdCtrlEntries 5856 }

	audioPair6InputSrcDlbEnc OBJECT-TYPE
		SYNTAX		INTEGER {
					audDlb1EncLost(24),
					audDlb2EncLost(25)
				}
		MAX-ACCESS	read-write
		STATUS		current
		DESCRIPTION	"
			style='Radiobutton list'
			path='/audio_input_2/Audio Pair 6/Dolby Encoders'
		"
		::= { alchemistHdCtrlEntries 5857 }

	audioPair7InputSrc OBJECT-TYPE
		SYNTAX		INTEGER {
					aes1(0),
					aes2(1),
					aes3(2),
					aes4(3),
					aes5(4),
					aes6(5),
					aes7(6),
					aes8(7),
					emb1(8),
					emb2(9),
					emb3(10),
					emb4(11),
					emb5(12),
					emb6(13),
					emb7(14),
					emb8(15),
					dec11(16),
					dec12(17),
					dec13(18),
					dec14(19),
					dec21(20),
					dec22(21),
					dec23(22),
					dec24(23),
					enc1(24),
					enc2(25)
				}
		MAX-ACCESS	read-write
		STATUS		current
		DESCRIPTION	"
			style='Radiobutton list'
			preset='emb7'
			path='/System 2/Audio Routing/Audio Pair 7/Source'
		"
		::= { alchemistHdCtrlEntries 5860 }

	audioPair7InputType OBJECT-TYPE
		SYNTAX		INTEGER {
					pcm(0),
					data(1)
				}
		MAX-ACCESS	read-write
		STATUS		current
		DESCRIPTION	"
			style='Radiobutton list'
			preset='pcm'
			path='/System 2/Audio Routing/Audio Pair 7/Input Type'
		"
		::= { alchemistHdCtrlEntries 5861 }

	audioPair7Name OBJECT-TYPE
		SYNTAX		RollCallString
		MAX-ACCESS	read-write
		STATUS		current
		DESCRIPTION	"
			style='Editable string'
			path='/System 2/Name'
		"
		::= { alchemistHdCtrlEntries 5862 }

	audioPair7InputSrcAes OBJECT-TYPE
		SYNTAX		INTEGER {
					aud1AesLost(0),
					aud2AesLost(1),
					aud3AesLost(2),
					aud4AesLost(3),
					aud5AesLost(4),
					aud6AesLost(5),
					aud7AesLost(6),
					aud8AesLost(7)
				}
		MAX-ACCESS	read-write
		STATUS		current
		DESCRIPTION	"
			style='Radiobutton list'
			path='/audio_input_2/Audio Pair 7/AES Inputs'
		"
		::= { alchemistHdCtrlEntries 5863 }

	audioPair7InputSrcEmb OBJECT-TYPE
		SYNTAX		INTEGER {
					aud1EmbLost(8),
					aud2EmbLost(9),
					aud3EmbLost(10),
					aud4EmbLost(11),
					aud5EmbLost(12),
					aud6EmbLost(13),
					aud7EmbLost(14),
					aud8EmbLost(15)
				}
		MAX-ACCESS	read-write
		STATUS		current
		DESCRIPTION	"
			style='Radiobutton list'
			preset='aud7EmbLost'
			path='/audio_input_2/Audio Pair 7/Embedded Inputs'
		"
		::= { alchemistHdCtrlEntries 5864 }

	audioPair7InputSrcDlbDec1 OBJECT-TYPE
		SYNTAX		INTEGER {
					audDlb1P1Lost(16),
					audDlb1P2Lost(17),
					audDlb1P3Lost(18),
					audDlb1P4Lost(19)
				}
		MAX-ACCESS	read-write
		STATUS		current
		DESCRIPTION	"
			style='Radiobutton list'
			path='/audio_input_2/Audio Pair 7/Dolby 1 Decoder'
		"
		::= { alchemistHdCtrlEntries 5865 }

	audioPair7InputSrcDlbDec2 OBJECT-TYPE
		SYNTAX		INTEGER {
					audDlb2P1Lost(20),
					audDlb2P2Lost(21),
					audDlb2P3Lost(22),
					audDlb2P4Lost(23)
				}
		MAX-ACCESS	read-write
		STATUS		current
		DESCRIPTION	"
			style='Radiobutton list'
			path='/audio_input_2/Audio Pair 7/Dolby 2 Decoder'
		"
		::= { alchemistHdCtrlEntries 5866 }

	audioPair7InputSrcDlbEnc OBJECT-TYPE
		SYNTAX		INTEGER {
					audDlb1EncLost(24),
					audDlb2EncLost(25)
				}
		MAX-ACCESS	read-write
		STATUS		current
		DESCRIPTION	"
			style='Radiobutton list'
			path='/audio_input_2/Audio Pair 7/Dolby Encoders'
		"
		::= { alchemistHdCtrlEntries 5867 }

	audioPair8InputSrc OBJECT-TYPE
		SYNTAX		INTEGER {
					aes1(0),
					aes2(1),
					aes3(2),
					aes4(3),
					aes5(4),
					aes6(5),
					aes7(6),
					aes8(7),
					emb1(8),
					emb2(9),
					emb3(10),
					emb4(11),
					emb5(12),
					emb6(13),
					emb7(14),
					emb8(15),
					dec11(16),
					dec12(17),
					dec13(18),
					dec14(19),
					dec21(20),
					dec22(21),
					dec23(22),
					dec24(23),
					enc1(24),
					enc2(25)
				}
		MAX-ACCESS	read-write
		STATUS		current
		DESCRIPTION	"
			style='Radiobutton list'
			preset='emb8'
			path='/System 2/Audio Routing/Audio Pair 8/Source'
		"
		::= { alchemistHdCtrlEntries 5870 }

	audioPair8InputType OBJECT-TYPE
		SYNTAX		INTEGER {
					pcm(0),
					data(1)
				}
		MAX-ACCESS	read-write
		STATUS		current
		DESCRIPTION	"
			style='Radiobutton list'
			preset='pcm'
			path='/System 2/Audio Routing/Audio Pair 8/Input Type'
		"
		::= { alchemistHdCtrlEntries 5871 }

	audioPair8Name OBJECT-TYPE
		SYNTAX		RollCallString
		MAX-ACCESS	read-write
		STATUS		current
		DESCRIPTION	"
			style='Editable string'
			path='/System 2/Name'
		"
		::= { alchemistHdCtrlEntries 5872 }

	audioPair8InputSrcAes OBJECT-TYPE
		SYNTAX		INTEGER {
					aud1AesLost(0),
					aud2AesLost(1),
					aud3AesLost(2),
					aud4AesLost(3),
					aud5AesLost(4),
					aud6AesLost(5),
					aud7AesLost(6),
					aud8AesLost(7)
				}
		MAX-ACCESS	read-write
		STATUS		current
		DESCRIPTION	"
			style='Radiobutton list'
			path='/audio_input_2/Audio Pair 8/AES Inputs'
		"
		::= { alchemistHdCtrlEntries 5873 }

	audioPair8InputSrcEmb OBJECT-TYPE
		SYNTAX		INTEGER {
					aud1EmbLost(8),
					aud2EmbLost(9),
					aud3EmbLost(10),
					aud4EmbLost(11),
					aud5EmbLost(12),
					aud6EmbLost(13),
					aud7EmbLost(14),
					aud8EmbLost(15)
				}
		MAX-ACCESS	read-write
		STATUS		current
		DESCRIPTION	"
			style='Radiobutton list'
			preset='aud8EmbLost'
			path='/audio_input_2/Audio Pair 8/Embedded Inputs'
		"
		::= { alchemistHdCtrlEntries 5874 }

	audioPair8InputSrcDlbDec1 OBJECT-TYPE
		SYNTAX		INTEGER {
					audDlb1P1Lost(16),
					audDlb1P2Lost(17),
					audDlb1P3Lost(18),
					audDlb1P4Lost(19)
				}
		MAX-ACCESS	read-write
		STATUS		current
		DESCRIPTION	"
			style='Radiobutton list'
			path='/audio_input_2/Audio Pair 8/Dolby 1 Decoder'
		"
		::= { alchemistHdCtrlEntries 5875 }

	audioPair8InputSrcDlbDec2 OBJECT-TYPE
		SYNTAX		INTEGER {
					audDlb2P1Lost(20),
					audDlb2P2Lost(21),
					audDlb2P3Lost(22),
					audDlb2P4Lost(23)
				}
		MAX-ACCESS	read-write
		STATUS		current
		DESCRIPTION	"
			style='Radiobutton list'
			path='/audio_input_2/Audio Pair 8/Dolby 2 Decoder'
		"
		::= { alchemistHdCtrlEntries 5876 }

	audioPair8InputSrcDlbEnc OBJECT-TYPE
		SYNTAX		INTEGER {
					audDlb1EncLost(24),
					audDlb2EncLost(25)
				}
		MAX-ACCESS	read-write
		STATUS		current
		DESCRIPTION	"
			style='Radiobutton list'
			path='/audio_input_2/Audio Pair 8/Dolby Encoders'
		"
		::= { alchemistHdCtrlEntries 5877 }

	dolby1Src OBJECT-TYPE
		SYNTAX		INTEGER {
					emb1(8),
					emb2(9),
					emb3(10),
					emb4(11),
					emb5(12),
					emb6(13),
					emb7(14),
					emb8(15),
					aes1(0),
					aes2(1),
					aes3(2),
					aes4(3),
					aes5(4),
					aes6(5),
					aes7(6),
					aes8(7)
				}
		MAX-ACCESS	read-write
		STATUS		current
		DESCRIPTION	"
			style='Radiobutton list'
			preset='aes1'
			path='/Dolby E/Dolby 1/Source'
		"
		::= { alchemistHdCtrlEntries 5880 }

	dolby1FrameDelay OBJECT-TYPE
		SYNTAX		INTEGER {
					advanced(1),
					coTimed(0),
					delayed(2)
				}
		MAX-ACCESS	read-write
		STATUS		current
		DESCRIPTION	"
			style='Radiobutton list'
			preset='coTimed'
			path='/Dolby E/Dolby 1/IP Alignment'
		"
		::= { alchemistHdCtrlEntries 5881 }

	dolby1FrameAdvance OBJECT-TYPE
		SYNTAX		INTEGER {
					advanced(1),
					coTimed(0),
					delayed(2)
				}
		MAX-ACCESS	read-write
		STATUS		current
		DESCRIPTION	"
			style='Radiobutton list'
			preset='coTimed'
			path='/Dolby E/Dolby 1/OP Alignment'
		"
		::= { alchemistHdCtrlEntries 5882 }

	dolby1MapDecode OBJECT-TYPE
		SYNTAX		INTEGER { ready(0), trigger(1) }
		MAX-ACCESS	read-write
		STATUS		current
		DESCRIPTION	"
			style='Event button'
			path='/Dolby E/Dolby 1/Map Decode'
		"
		::= { alchemistHdCtrlEntries 5883 }

	dolby1MonitorDecode OBJECT-TYPE
		SYNTAX		INTEGER { enable(0), disable(1) }
		MAX-ACCESS	read-write
		STATUS		current
		DESCRIPTION	"
			style='Checkbox'
			range='0..1'
			path='/Dolby E/Dolby 1/Monitor Decode'
		"
		::= { alchemistHdCtrlEntries 5884 }

	dolby1DecoderBitstreamStatus OBJECT-TYPE
		SYNTAX		Integer32
		MAX-ACCESS	read-only
		STATUS		current
		DESCRIPTION	"
			style='ReadOnly numeric'
			path='/System 2/dolby_1_dec_bitstream_status'
		"
		::= { alchemistHdCtrlEntries 5886 }

	dolby1DecoderProgramConfig OBJECT-TYPE
		SYNTAX		Integer32
		MAX-ACCESS	read-only
		STATUS		current
		DESCRIPTION	"
			style='ReadOnly numeric'
			path='/System 2/dolby_1_dec_program_config'
		"
		::= { alchemistHdCtrlEntries 5887 }

	dolby1EncoderBitstreamStatus OBJECT-TYPE
		SYNTAX		Integer32
		MAX-ACCESS	read-only
		STATUS		current
		DESCRIPTION	"
			style='ReadOnly numeric'
			path='/System 2/dolby_1_enc_bitstream_status'
		"
		::= { alchemistHdCtrlEntries 5888 }

	dolby1EncoderProgramConfig OBJECT-TYPE
		SYNTAX		Integer32
		MAX-ACCESS	read-only
		STATUS		current
		DESCRIPTION	"
			style='ReadOnly numeric'
			path='/System 2/dolby_1_enc_program_config'
		"
		::= { alchemistHdCtrlEntries 5889 }

	dolby2Src OBJECT-TYPE
		SYNTAX		INTEGER {
					emb1(8),
					emb2(9),
					emb3(10),
					emb4(11),
					emb5(12),
					emb6(13),
					emb7(14),
					emb8(15),
					aes1(0),
					aes2(1),
					aes3(2),
					aes4(3),
					aes5(4),
					aes6(5),
					aes7(6),
					aes8(7)
				}
		MAX-ACCESS	read-write
		STATUS		current
		DESCRIPTION	"
			style='Radiobutton list'
			preset='aes1'
			path='/Dolby E/Dolby 2/Source'
		"
		::= { alchemistHdCtrlEntries 5890 }

	dolby2FrameDelay OBJECT-TYPE
		SYNTAX		INTEGER {
					advanced(1),
					coTimed(0),
					delayed(2)
				}
		MAX-ACCESS	read-write
		STATUS		current
		DESCRIPTION	"
			style='Radiobutton list'
			preset='coTimed'
			path='/Dolby E/Dolby 2/IP Alignment'
		"
		::= { alchemistHdCtrlEntries 5891 }

	dolby2FrameAdvance OBJECT-TYPE
		SYNTAX		INTEGER {
					advanced(1),
					coTimed(0),
					delayed(2)
				}
		MAX-ACCESS	read-write
		STATUS		current
		DESCRIPTION	"
			style='Radiobutton list'
			preset='coTimed'
			path='/Dolby E/Dolby 2/OP Alignment'
		"
		::= { alchemistHdCtrlEntries 5892 }

	dolby2MapDecode OBJECT-TYPE
		SYNTAX		INTEGER { ready(0), trigger(1) }
		MAX-ACCESS	read-write
		STATUS		current
		DESCRIPTION	"
			style='Event button'
			path='/Dolby E/Dolby 2/Map Decode'
		"
		::= { alchemistHdCtrlEntries 5893 }

	dolby2MonitorDecode OBJECT-TYPE
		SYNTAX		INTEGER { enable(0), disable(1) }
		MAX-ACCESS	read-write
		STATUS		current
		DESCRIPTION	"
			style='Checkbox'
			range='0..1'
			path='/Dolby E/Dolby 2/Monitor Decode'
		"
		::= { alchemistHdCtrlEntries 5894 }

	dolby2DecoderBitstreamStatus OBJECT-TYPE
		SYNTAX		Integer32
		MAX-ACCESS	read-only
		STATUS		current
		DESCRIPTION	"
			style='ReadOnly numeric'
			path='/System 2/dolby_2_dec_bitstream_status'
		"
		::= { alchemistHdCtrlEntries 5896 }

	dolby2DecoderProgramConfig OBJECT-TYPE
		SYNTAX		Integer32
		MAX-ACCESS	read-only
		STATUS		current
		DESCRIPTION	"
			style='ReadOnly numeric'
			path='/System 2/dolby_2_dec_program_config'
		"
		::= { alchemistHdCtrlEntries 5897 }

	dolby2EncoderBitstreamStatus OBJECT-TYPE
		SYNTAX		Integer32
		MAX-ACCESS	read-only
		STATUS		current
		DESCRIPTION	"
			style='ReadOnly numeric'
			path='/System 2/dolby_2_enc_bitstream_status'
		"
		::= { alchemistHdCtrlEntries 5898 }

	dolby2EncoderProgramConfig OBJECT-TYPE
		SYNTAX		Integer32
		MAX-ACCESS	read-only
		STATUS		current
		DESCRIPTION	"
			style='ReadOnly numeric'
			path='/System 2/dolby_2_enc_program_config'
		"
		::= { alchemistHdCtrlEntries 5899 }

	filmtoolsOpStd23 OBJECT-TYPE
		SYNTAX		INTEGER {
					v62523Psf(28),
					v72023P(41),
					v108023Psf(24)
				}
		MAX-ACCESS	read-write
		STATUS		current
		DESCRIPTION	"
			style='Radiobutton list'
			path='/output/Output A Std/23.98Hz'
		"
		::= { alchemistHdCtrlEntries 5900 }

	filmtoolsOpStd24 OBJECT-TYPE
		SYNTAX		INTEGER {
					v62524Psf(27),
					v108024Psf(23),
					v72024P(40)
				}
		MAX-ACCESS	read-write
		STATUS		current
		DESCRIPTION	"
			style='Radiobutton list'
			path='/output/Output A Std/24Hz'
		"
		::= { alchemistHdCtrlEntries 5901 }

	filmtoolsOpStd25 OBJECT-TYPE
		SYNTAX		INTEGER {
					v62525Psf(1020),
					v108025Psf(36),
					v72025P(39)
				}
		MAX-ACCESS	read-write
		STATUS		current
		DESCRIPTION	"
			style='Radiobutton list'
			path='/output/Output A Std/25Hz'
		"
		::= { alchemistHdCtrlEntries 5902 }

	filmtoolsOpStd29 OBJECT-TYPE
		SYNTAX		INTEGER {
					v52529Psf(1019),
					v108029Psf(35),
					v72029P(38)
				}
		MAX-ACCESS	read-write
		STATUS		current
		DESCRIPTION	"
			style='Radiobutton list'
			path='/output/Output A Std/29.97Hz'
		"
		::= { alchemistHdCtrlEntries 5903 }

	filmtoolsOpStd30 OBJECT-TYPE
		SYNTAX		INTEGER {
					v72030P(37),
					v108030Psf(34)
				}
		MAX-ACCESS	read-write
		STATUS		current
		DESCRIPTION	"
			style='Radiobutton list'
			path='/output/Output A Std/30Hz'
		"
		::= { alchemistHdCtrlEntries 5904 }

	filmtoolsOpStd47 OBJECT-TYPE
		SYNTAX		INTEGER {
					v62547I(1028),
					v108047I(1024)
				}
		MAX-ACCESS	read-write
		STATUS		current
		DESCRIPTION	"
			style='Radiobutton list'
			path='/output/Output A Std/47.95Hz'
		"
		::= { alchemistHdCtrlEntries 5905 }

	filmtoolsOpStd48 OBJECT-TYPE
		SYNTAX		INTEGER {
					v62548I(1027),
					v108048I(1023)
				}
		MAX-ACCESS	read-write
		STATUS		current
		DESCRIPTION	"
			style='Radiobutton list'
			path='/output/Output A Std/48Hz'
		"
		::= { alchemistHdCtrlEntries 5906 }

	filmtoolsOpStd50 OBJECT-TYPE
		SYNTAX		INTEGER {
					v62550I(20),
					v108050I(8),
					v72050P(30)
				}
		MAX-ACCESS	read-write
		STATUS		current
		DESCRIPTION	"
			style='Radiobutton list'
			preset='v62550I'
			path='/output/Output A Std/50Hz'
		"
		::= { alchemistHdCtrlEntries 5907 }

	filmtoolsOpStd59 OBJECT-TYPE
		SYNTAX		INTEGER {
					v52559I(19),
					v108059I(7),
					v72059P(17)
				}
		MAX-ACCESS	read-write
		STATUS		current
		DESCRIPTION	"
			style='Radiobutton list'
			path='/output/Output A Std/59.94Hz'
		"
		::= { alchemistHdCtrlEntries 5908 }

	filmtoolsOpStd60 OBJECT-TYPE
		SYNTAX		INTEGER {
					v72060P(16),
					v108060I(6)
				}
		MAX-ACCESS	read-write
		STATUS		current
		DESCRIPTION	"
			style='Radiobutton list'
			path='/output/Output A Std/60Hz'
		"
		::= { alchemistHdCtrlEntries 5909 }

	filmtoolsOpStdAuto OBJECT-TYPE
		SYNTAX		INTEGER { enable(0), disable(1) }
		MAX-ACCESS	read-write
		STATUS		current
		DESCRIPTION	"
			style='Checkbox'
			range='0..1'
			path='/output/Output A Std/Auto'
		"
		::= { alchemistHdCtrlEntries 5910 }

	filmtoolsIpStd23 OBJECT-TYPE
		SYNTAX		INTEGER {
					v62523Psf(28),
					v108023Psf(24),
					v72023P(41)
				}
		MAX-ACCESS	read-write
		STATUS		current
		DESCRIPTION	"
			style='Radiobutton list'
			path='/output/Input Std/23.98Hz'
		"
		::= { alchemistHdCtrlEntries 5920 }

	filmtoolsIpStd24 OBJECT-TYPE
		SYNTAX		INTEGER {
					v62524Psf(27),
					v108024Psf(23),
					v72024P(40)
				}
		MAX-ACCESS	read-write
		STATUS		current
		DESCRIPTION	"
			style='Radiobutton list'
			path='/output/Input Std/24Hz'
		"
		::= { alchemistHdCtrlEntries 5921 }

	filmtoolsIpStd25 OBJECT-TYPE
		SYNTAX		INTEGER {
					v62525Psf(1020),
					v108025Psf(36),
					v72025P(39)
				}
		MAX-ACCESS	read-write
		STATUS		current
		DESCRIPTION	"
			style='Radiobutton list'
			path='/output/Input Std/25Hz'
		"
		::= { alchemistHdCtrlEntries 5922 }

	filmtoolsIpStd29 OBJECT-TYPE
		SYNTAX		INTEGER {
					v52529Psf(1019),
					v108029Psf(35),
					v72029P(38)
				}
		MAX-ACCESS	read-write
		STATUS		current
		DESCRIPTION	"
			style='Radiobutton list'
			path='/output/Input Std/29.97Hz'
		"
		::= { alchemistHdCtrlEntries 5923 }

	filmtoolsIpStd30 OBJECT-TYPE
		SYNTAX		INTEGER {
					v72030P(37),
					v108030Psf(34)
				}
		MAX-ACCESS	read-write
		STATUS		current
		DESCRIPTION	"
			style='Radiobutton list'
			path='/output/Input Std/30Hz'
		"
		::= { alchemistHdCtrlEntries 5924 }

	filmtoolsIpStd47 OBJECT-TYPE
		SYNTAX		INTEGER {
					v62547I(1028),
					v108047I(1024)
				}
		MAX-ACCESS	read-write
		STATUS		current
		DESCRIPTION	"
			style='Radiobutton list'
			path='/output/Input Std/47.95Hz'
		"
		::= { alchemistHdCtrlEntries 5925 }

	filmtoolsIpStd48 OBJECT-TYPE
		SYNTAX		INTEGER {
					v62548I(1027),
					v108048I(1023)
				}
		MAX-ACCESS	read-write
		STATUS		current
		DESCRIPTION	"
			style='Radiobutton list'
			path='/output/Input Std/48Hz'
		"
		::= { alchemistHdCtrlEntries 5926 }

	filmtoolsIpStd50 OBJECT-TYPE
		SYNTAX		INTEGER {
					v62550I(20),
					v108050I(8),
					v72050P(30)
				}
		MAX-ACCESS	read-write
		STATUS		current
		DESCRIPTION	"
			style='Radiobutton list'
			path='/output/Input Std/50Hz'
		"
		::= { alchemistHdCtrlEntries 5927 }

	filmtoolsIpStd59 OBJECT-TYPE
		SYNTAX		INTEGER {
					v52559I(19),
					v108059I(7),
					v72059P(17)
				}
		MAX-ACCESS	read-write
		STATUS		current
		DESCRIPTION	"
			style='Radiobutton list'
			path='/output/Input Std/59.94Hz'
		"
		::= { alchemistHdCtrlEntries 5928 }

	filmtoolsIpStd60 OBJECT-TYPE
		SYNTAX		INTEGER {
					v72060P(16),
					v108060I(6)
				}
		MAX-ACCESS	read-write
		STATUS		current
		DESCRIPTION	"
			style='Radiobutton list'
			path='/output/Input Std/60Hz'
		"
		::= { alchemistHdCtrlEntries 5929 }

	filmtoolsIpStdAuto OBJECT-TYPE
		SYNTAX		INTEGER { enable(0), disable(1) }
		MAX-ACCESS	read-write
		STATUS		current
		DESCRIPTION	"
			style='Checkbox'
			range='0..1'
			path='/output/Input Std/Auto'
		"
		::= { alchemistHdCtrlEntries 5930 }

	rollcallUnitAddr OBJECT-TYPE
		SYNTAX		Integer32 (16..255)
		MAX-ACCESS	read-write
		STATUS		current
		DESCRIPTION	"
			style='Numeric control'
			range='16..255'
			preset='42'
			path='/System/RollCall/Unit Addr'
		"
		::= { alchemistHdCtrlEntries 5950 }

	rollcallUnitName OBJECT-TYPE
		SYNTAX		RollCallString
		MAX-ACCESS	read-write
		STATUS		current
		DESCRIPTION	"
			style='Editable string'
			path='/System/RollCall/Unit Name'
		"
		::= { alchemistHdCtrlEntries 5951 }

	logServerName OBJECT-TYPE
		SYNTAX		RollCallString
		MAX-ACCESS	read-write
		STATUS		current
		DESCRIPTION	"
			style='Editable string'
			path='/System/RollCall/Log server name'
		"
		::= { alchemistHdCtrlEntries 5952 }

	logInp OBJECT-TYPE
		SYNTAX		INTEGER { enable(0), disable(1) }
		MAX-ACCESS	read-write
		STATUS		current
		DESCRIPTION	"
			style='Checkbox'
			path='/System/RollCall/Log items/Input Status'
		"
		::= { alchemistHdCtrlEntries 5960 }

	logInpStd OBJECT-TYPE
		SYNTAX		INTEGER { enable(0), disable(1) }
		MAX-ACCESS	read-write
		STATUS		current
		DESCRIPTION	"
			style='Checkbox'
			path='/System/RollCall/Log items/Input Standard'
		"
		::= { alchemistHdCtrlEntries 5961 }

	logRefStd OBJECT-TYPE
		SYNTAX		INTEGER { enable(0), disable(1) }
		MAX-ACCESS	read-write
		STATUS		current
		DESCRIPTION	"
			style='Checkbox'
			path='/System/RollCall/Log items/Reference Status'
		"
		::= { alchemistHdCtrlEntries 5962 }

	logOutAStd OBJECT-TYPE
		SYNTAX		INTEGER { enable(0), disable(1) }
		MAX-ACCESS	read-write
		STATUS		current
		DESCRIPTION	"
			style='Checkbox'
			path='/System/RollCall/Log items/Output A Standard'
		"
		::= { alchemistHdCtrlEntries 5966 }

	logOutBStd OBJECT-TYPE
		SYNTAX		INTEGER { enable(0), disable(1) }
		MAX-ACCESS	read-write
		STATUS		current
		DESCRIPTION	"
			style='Checkbox'
			path='/System/RollCall/Log items/Output B Standard'
		"
		::= { alchemistHdCtrlEntries 5967 }

	logStatus OBJECT-TYPE
		SYNTAX		INTEGER { enable(0), disable(1) }
		MAX-ACCESS	read-write
		STATUS		current
		DESCRIPTION	"
			style='Checkbox'
			path='/System/RollCall/Log items/System Status'
		"
		::= { alchemistHdCtrlEntries 5971 }

	activeLineLength OBJECT-TYPE
		SYNTAX		INTEGER {
					digital(0),
					analog(1)
				}
		MAX-ACCESS	read-write
		STATUS		current
		DESCRIPTION	"
			style='Radiobutton list'
			preset='digital'
			path='/utils/Setup/Active Line Length'
		"
		::= { alchemistHdCtrlEntries 5980 }

	shapedBlanking OBJECT-TYPE
		SYNTAX		INTEGER {
					off(0),
					on(1)
				}
		MAX-ACCESS	read-write
		STATUS		current
		DESCRIPTION	"
			style='Radiobutton list'
			preset='off'
			path='/utils/Setup/Shaped Horizontal Blanking'
		"
		::= { alchemistHdCtrlEntries 5981 }

	blankToAnalogLine OBJECT-TYPE
		SYNTAX		INTEGER {
					off(0),
					on(1)
				}
		MAX-ACCESS	read-write
		STATUS		current
		DESCRIPTION	"
			style='Radiobutton list'
			preset='off'
			path='/utils/Setup/Analog Blanking'
		"
		::= { alchemistHdCtrlEntries 5982 }

	autoAesRealign OBJECT-TYPE
		SYNTAX		INTEGER {
					off(0),
					on(1)
				}
		MAX-ACCESS	read-write
		STATUS		current
		DESCRIPTION	"
			style='Radiobutton list'
			preset='on'
			path='/utils/Setup/Auto AES re-align'
		"
		::= { alchemistHdCtrlEntries 5983 }

	realignAesNow OBJECT-TYPE
		SYNTAX		INTEGER { ready(0), trigger(1) }
		MAX-ACCESS	read-write
		STATUS		current
		DESCRIPTION	"
			style='Event button'
			path='/utils/Setup/Re-align AES Now'
		"
		::= { alchemistHdCtrlEntries 5984 }

	minimumDelay OBJECT-TYPE
		SYNTAX		INTEGER {
					off(0),
					on(1)
				}
		MAX-ACCESS	read-write
		STATUS		current
		DESCRIPTION	"
			style='Radiobutton list'
			preset='on'
			path='/utils/Setup/Minimum Delay'
		"
		::= { alchemistHdCtrlEntries 5985 }

	aesInputStatusInvalid OBJECT-TYPE
		SYNTAX		Integer32 (0..65535)
		MAX-ACCESS	read-only
		STATUS		current
		DESCRIPTION	"
			style='ReadOnly numeric'
			range='0..65535'
			path='/System/Debug/audio status/AES Status invalid'
		"
		::= { alchemistHdCtrlEntries 5999 }

	audioStatus OBJECT-TYPE
		SYNTAX		RollCallString
		MAX-ACCESS	read-only
		STATUS		current
		DESCRIPTION	"
			style='ReadOnly string'
			path='/System/Debug/status/status1/audio_status'
		"
		::= { alchemistHdCtrlEntries 6003 }

	audioDelayStatus OBJECT-TYPE
		SYNTAX		RollCallString
		MAX-ACCESS	read-only
		STATUS		current
		DESCRIPTION	"
			style='ReadOnly string'
			path='/System/Debug/status/status1/audio_delay_status 6'
		"
		::= { alchemistHdCtrlEntries 6005 }

	outputAName OBJECT-TYPE
		SYNTAX		RollCallString
		MAX-ACCESS	read-write
		STATUS		current
		DESCRIPTION	"
			style='Editable string'
			path='/output/Output A/Output Name'
		"
		::= { alchemistHdCtrlEntries 6007 }

	outputBName OBJECT-TYPE
		SYNTAX		RollCallString
		MAX-ACCESS	read-write
		STATUS		current
		DESCRIPTION	"
			style='Editable string'
			path='/output/Output B/Output Name'
		"
		::= { alchemistHdCtrlEntries 6008 }

	rollcallState OBJECT-TYPE
		SYNTAX		Integer32 (0..2)
		MAX-ACCESS	read-only
		STATUS		current
		DESCRIPTION	"
			style='ReadOnly numeric'
			range='0..2'
			path='/System/Debug/status/status1/rollcall_state'
		"
		::= { alchemistHdCtrlEntries 6009 }

	tempWarn OBJECT-TYPE
		SYNTAX		Integer32 (0..1)
		MAX-ACCESS	read-only
		STATUS		current
		DESCRIPTION	"
			style='ReadOnly numeric'
			range='0..1'
			path='/System/Debug/status/status2/temp_warn'
		"
		::= { alchemistHdCtrlEntries 6010 }

	outputAAspectStatus OBJECT-TYPE
		SYNTAX		Integer32 (0..65535)
		MAX-ACCESS	read-only
		STATUS		current
		DESCRIPTION	"
			style='ReadOnly numeric'
			range='0..65535'
			path='/System/Debug/status/status1/output_a_aspect_status'
		"
		::= { alchemistHdCtrlEntries 6012 }

	outputBAspectStatus OBJECT-TYPE
		SYNTAX		Integer32 (0..65535)
		MAX-ACCESS	read-only
		STATUS		current
		DESCRIPTION	"
			style='ReadOnly numeric'
			range='0..65535'
			path='/System/Debug/status/status1/output_b_aspect_status'
		"
		::= { alchemistHdCtrlEntries 6013 }

	inputAspectStatus OBJECT-TYPE
		SYNTAX		Integer32 (0..8)
		MAX-ACCESS	read-only
		STATUS		current
		DESCRIPTION	"
			style='ReadOnly numeric'
			range='0..8'
			path='/System/Debug/status/status1/input_aspect_status'
		"
		::= { alchemistHdCtrlEntries 6014 }

	systemDelayString OBJECT-TYPE
		SYNTAX		RollCallString
		MAX-ACCESS	read-only
		STATUS		current
		DESCRIPTION	"
			style='ReadOnly string'
			path='/System/Debug/status/status1/system_delay_string'
		"
		::= { alchemistHdCtrlEntries 6026 }

	inputCadenceStr OBJECT-TYPE
		SYNTAX		Integer32
		MAX-ACCESS	read-only
		STATUS		current
		DESCRIPTION	"
			style='ReadOnly numeric'
			path='/System 2/Input Cadence Str'
		"
		::= { alchemistHdCtrlEntries 6027 }

	dispMemSetupAsp OBJECT-TYPE
		SYNTAX		RollCallString
		MAX-ACCESS	read-only
		STATUS		current
		DESCRIPTION	"
			style='ReadOnly string'
			path='/System/Debug/status/status2/disp_mem_setup_asp'
		"
		::= { alchemistHdCtrlEntries 6028 }

	dispMemSetupPan OBJECT-TYPE
		SYNTAX		RollCallString
		MAX-ACCESS	read-only
		STATUS		current
		DESCRIPTION	"
			style='ReadOnly string'
			path='/System/Debug/status/status2/disp_mem_setup_pan'
		"
		::= { alchemistHdCtrlEntries 6029 }

	dispMemSetupPos OBJECT-TYPE
		SYNTAX		RollCallString
		MAX-ACCESS	read-only
		STATUS		current
		DESCRIPTION	"
			style='ReadOnly string'
			path='/System/Debug/status/status2/disp_mem_setup_pos'
		"
		::= { alchemistHdCtrlEntries 6030 }

	dispMemSetupName OBJECT-TYPE
		SYNTAX		RollCallString
		MAX-ACCESS	read-only
		STATUS		current
		DESCRIPTION	"
			style='ReadOnly string'
			path='/System/Debug/status/status2/disp_mem_setup_name'
		"
		::= { alchemistHdCtrlEntries 6031 }

	dispMemSetupAfd OBJECT-TYPE
		SYNTAX		Integer32 (0..31)
		MAX-ACCESS	read-only
		STATUS		current
		DESCRIPTION	"
			style='ReadOnly numeric'
			range='0..31'
			path='/System/Debug/status/status2/disp_mem_setup_afd'
		"
		::= { alchemistHdCtrlEntries 6032 }

	audioPair1CtlTotal OBJECT-TYPE
		SYNTAX		Integer32 (0..1000)
		MAX-ACCESS	read-only
		STATUS		current
		DESCRIPTION	"
			style='ReadOnly numeric'
			range='0mS..1000mS'
			path='/audio_control/Audio Pair 1/Total'
		"
		::= { alchemistHdCtrlEntries 6102 }

	audioPair2CtlTotal OBJECT-TYPE
		SYNTAX		Integer32 (0..1000)
		MAX-ACCESS	read-only
		STATUS		current
		DESCRIPTION	"
			style='ReadOnly numeric'
			range='0mS..1000mS'
			path='/audio_control/Audio Pair 2/Total'
		"
		::= { alchemistHdCtrlEntries 6112 }

	audioPair3CtlTotal OBJECT-TYPE
		SYNTAX		Integer32 (0..1000)
		MAX-ACCESS	read-only
		STATUS		current
		DESCRIPTION	"
			style='ReadOnly numeric'
			range='0mS..1000mS'
			path='/audio_control/Audio Pair 3/Total'
		"
		::= { alchemistHdCtrlEntries 6122 }

	audioPair4CtlTotal OBJECT-TYPE
		SYNTAX		Integer32 (0..1000)
		MAX-ACCESS	read-only
		STATUS		current
		DESCRIPTION	"
			style='ReadOnly numeric'
			range='0mS..1000mS'
			path='/audio_control/Audio Pair 4/Total'
		"
		::= { alchemistHdCtrlEntries 6132 }

	audioPair5CtlTotal OBJECT-TYPE
		SYNTAX		Integer32 (0..1000)
		MAX-ACCESS	read-only
		STATUS		current
		DESCRIPTION	"
			style='ReadOnly numeric'
			range='0mS..1000mS'
			path='/audio_control/Audio Pair 5/Total'
		"
		::= { alchemistHdCtrlEntries 6142 }

	audioPair6CtlTotal OBJECT-TYPE
		SYNTAX		Integer32 (0..1000)
		MAX-ACCESS	read-only
		STATUS		current
		DESCRIPTION	"
			style='ReadOnly numeric'
			range='0mS..1000mS'
			path='/audio_control/Audio Pair 6/Total'
		"
		::= { alchemistHdCtrlEntries 6152 }

	audioPair7CtlTotal OBJECT-TYPE
		SYNTAX		Integer32 (0..1000)
		MAX-ACCESS	read-only
		STATUS		current
		DESCRIPTION	"
			style='ReadOnly numeric'
			range='0mS..1000mS'
			path='/audio_control/Audio Pair 7/Total'
		"
		::= { alchemistHdCtrlEntries 6162 }

	audioPair8CtlTotal OBJECT-TYPE
		SYNTAX		Integer32 (0..1000)
		MAX-ACCESS	read-only
		STATUS		current
		DESCRIPTION	"
			style='ReadOnly numeric'
			range='0mS..1000mS'
			path='/audio_control/Audio Pair 8/Total'
		"
		::= { alchemistHdCtrlEntries 6172 }

	ftEnable OBJECT-TYPE
		SYNTAX		INTEGER {
					off(0),
					on(1)
				}
		MAX-ACCESS	read-write
		STATUS		current
		DESCRIPTION	"
			style='Radiobutton list'
			preset='on'
			path='/Convert/FilmTools'
		"
		::= { alchemistHdCtrlEntries 6190 }

	recursiveEnable OBJECT-TYPE
		SYNTAX		INTEGER { enable(0), disable(1) }
		MAX-ACCESS	read-write
		STATUS		current
		DESCRIPTION	"
			style='Checkbox'
			range='0..1'
			path='/Noise Reduction/Enable'
		"
		::= { alchemistHdCtrlEntries 6200 }

	recursiveStrength OBJECT-TYPE
		SYNTAX		Integer32 (0..30)
		MAX-ACCESS	read-write
		STATUS		current
		DESCRIPTION	"
			style='Numeric control'
			range='0..30'
			path='/Noise Reduction/Y Strength'
		"
		::= { alchemistHdCtrlEntries 6201 }

	recursiveSplitScreen OBJECT-TYPE
		SYNTAX		INTEGER { enable(0), disable(1) }
		MAX-ACCESS	read-write
		STATUS		current
		DESCRIPTION	"
			style='Checkbox'
			range='0..1'
			path='/Noise Reduction/Split Screen'
		"
		::= { alchemistHdCtrlEntries 6202 }

	recursiveStrengthC OBJECT-TYPE
		SYNTAX		Integer32 (0..30)
		MAX-ACCESS	read-write
		STATUS		current
		DESCRIPTION	"
			style='Numeric control'
			range='0..30'
			path='/Noise Reduction/C Strength'
		"
		::= { alchemistHdCtrlEntries 6203 }

	recursiveBias OBJECT-TYPE
		SYNTAX		Integer32 (-7..7)
		MAX-ACCESS	read-write
		STATUS		current
		DESCRIPTION	"
			style='Numeric control'
			range='-7..7'
			path='/Noise Reduction/Bias'
		"
		::= { alchemistHdCtrlEntries 6204 }

	recursiveWeight OBJECT-TYPE
		SYNTAX		INTEGER {
					uniform(0),
					black(1),
					white(2)
				}
		MAX-ACCESS	read-write
		STATUS		current
		DESCRIPTION	"
			style='Radiobutton list'
			preset='uniform'
			path='/Noise Reduction/Weight'
		"
		::= { alchemistHdCtrlEntries 6205 }

	recursiveOverlay OBJECT-TYPE
		SYNTAX		INTEGER { enable(0), disable(1) }
		MAX-ACCESS	read-write
		STATUS		current
		DESCRIPTION	"
			style='Checkbox'
			range='0..1'
			path='/Noise Reduction/Overlay'
		"
		::= { alchemistHdCtrlEntries 6206 }

	diagnosticTpgInA OBJECT-TYPE
		SYNTAX		INTEGER { enable(0), disable(1) }
		MAX-ACCESS	read-write
		STATUS		current
		DESCRIPTION	"
			style='Checkbox'
			path='/System/Diagnostics/TPG In A (1)'
		"
		::= { alchemistHdCtrlEntries 6500 }

	diagnosticTpgInB OBJECT-TYPE
		SYNTAX		INTEGER { enable(0), disable(1) }
		MAX-ACCESS	read-write
		STATUS		current
		DESCRIPTION	"
			style='Checkbox'
			path='/System/Diagnostics/TPG In B (2)'
		"
		::= { alchemistHdCtrlEntries 6501 }

	diagnosticTpgOutA OBJECT-TYPE
		SYNTAX		INTEGER { enable(0), disable(1) }
		MAX-ACCESS	read-write
		STATUS		current
		DESCRIPTION	"
			style='Checkbox'
			path='/System/Diagnostics/TPG Out A (3)'
		"
		::= { alchemistHdCtrlEntries 6502 }

	diagnosticTpgOutB OBJECT-TYPE
		SYNTAX		INTEGER { enable(0), disable(1) }
		MAX-ACCESS	read-write
		STATUS		current
		DESCRIPTION	"
			style='Checkbox'
			path='/System/Diagnostics/TPG Out B (4)'
		"
		::= { alchemistHdCtrlEntries 6503 }

	diagnosticLoopRioA OBJECT-TYPE
		SYNTAX		INTEGER { enable(0), disable(1) }
		MAX-ACCESS	read-write
		STATUS		current
		DESCRIPTION	"
			style='Checkbox'
			path='/System/Diagnostics/Loop RIO A (A)'
		"
		::= { alchemistHdCtrlEntries 6504 }

	diagnosticLoopRioB OBJECT-TYPE
		SYNTAX		INTEGER { enable(0), disable(1) }
		MAX-ACCESS	read-write
		STATUS		current
		DESCRIPTION	"
			style='Checkbox'
			path='/System/Diagnostics/Loop RIO B (B)'
		"
		::= { alchemistHdCtrlEntries 6505 }

	diagnosticLoopMioInA OBJECT-TYPE
		SYNTAX		INTEGER { enable(0), disable(1) }
		MAX-ACCESS	read-write
		STATUS		current
		DESCRIPTION	"
			style='Checkbox'
			path='/System/Diagnostics/Loop MIO In A (C)'
		"
		::= { alchemistHdCtrlEntries 6506 }

	diagnosticLoopMioInB OBJECT-TYPE
		SYNTAX		INTEGER { enable(0), disable(1) }
		MAX-ACCESS	read-write
		STATUS		current
		DESCRIPTION	"
			style='Checkbox'
			path='/System/Diagnostics/Loop MIO In B (D)'
		"
		::= { alchemistHdCtrlEntries 6507 }

	diagnosticLoopMioOutA OBJECT-TYPE
		SYNTAX		INTEGER { enable(0), disable(1) }
		MAX-ACCESS	read-write
		STATUS		current
		DESCRIPTION	"
			style='Checkbox'
			path='/System/Diagnostics/Loop MIO Out A (F)'
		"
		::= { alchemistHdCtrlEntries 6508 }

	diagnosticLoopMioOutB OBJECT-TYPE
		SYNTAX		INTEGER { enable(0), disable(1) }
		MAX-ACCESS	read-write
		STATUS		current
		DESCRIPTION	"
			style='Checkbox'
			path='/System/Diagnostics/Loop MIO Out B (G)'
		"
		::= { alchemistHdCtrlEntries 6509 }

	diagnosticLoopDcvOut OBJECT-TYPE
		SYNTAX		INTEGER { enable(0), disable(1) }
		MAX-ACCESS	read-write
		STATUS		current
		DESCRIPTION	"
			style='Checkbox'
			path='/System/Diagnostics/Loop DCV Out (E)'
		"
		::= { alchemistHdCtrlEntries 6510 }

	diagnosticReset OBJECT-TYPE
		SYNTAX		INTEGER { ready(0), trigger(1) }
		MAX-ACCESS	read-write
		STATUS		current
		DESCRIPTION	"
			style='Event button'
			path='/System/Diagnostics/Reset Diagnostics'
		"
		::= { alchemistHdCtrlEntries 6511 }

	audioAesInputStatus OBJECT-TYPE
		SYNTAX		RollCallString
		MAX-ACCESS	read-only
		STATUS		current
		DESCRIPTION	"
			style='ReadOnly string'
			path='/System 2/audio_aes_input_status'
		"
		::= { alchemistHdCtrlEntries 6536 }

	audioEmbInputStatus OBJECT-TYPE
		SYNTAX		RollCallString
		MAX-ACCESS	read-only
		STATUS		current
		DESCRIPTION	"
			style='ReadOnly string'
			path='/System 2/audio_emb_input_status'
		"
		::= { alchemistHdCtrlEntries 6537 }

	referenceState OBJECT-TYPE
		SYNTAX		INTEGER {
					ok(0),
					bad(1)
				}
		MAX-ACCESS	read-only
		STATUS		current
		DESCRIPTION	"
			style='Radiobutton list'
			preset='ok'
			path='/System/Debug/status/reference_state'
		"
		::= { alchemistHdCtrlEntries 6667 }

	audioPair2CtlMono OBJECT-TYPE
		SYNTAX		INTEGER { enable(0), disable(1) }
		MAX-ACCESS	read-write
		STATUS		current
		DESCRIPTION	"
			style='Checkbox'
			path='/audio_control/Audio Pair 2/Mono'
		"
		::= { alchemistHdCtrlEntries 6709 }

	audioPair1CtlMono OBJECT-TYPE
		SYNTAX		INTEGER { enable(0), disable(1) }
		MAX-ACCESS	read-write
		STATUS		current
		DESCRIPTION	"
			style='Checkbox'
			path='/audio_control/Audio Pair 1/Mono'
		"
		::= { alchemistHdCtrlEntries 6710 }

	audioPair3CtlMono OBJECT-TYPE
		SYNTAX		INTEGER { enable(0), disable(1) }
		MAX-ACCESS	read-write
		STATUS		current
		DESCRIPTION	"
			style='Checkbox'
			path='/audio_control/Audio Pair 3/Mono'
		"
		::= { alchemistHdCtrlEntries 6711 }

	audioPair4CtlMono OBJECT-TYPE
		SYNTAX		INTEGER { enable(0), disable(1) }
		MAX-ACCESS	read-write
		STATUS		current
		DESCRIPTION	"
			style='Checkbox'
			path='/audio_control/Audio Pair 4/Mono'
		"
		::= { alchemistHdCtrlEntries 6713 }

	audioPair5CtlMono OBJECT-TYPE
		SYNTAX		INTEGER { enable(0), disable(1) }
		MAX-ACCESS	read-write
		STATUS		current
		DESCRIPTION	"
			style='Checkbox'
			path='/audio_control/Audio Pair 5/Mono'
		"
		::= { alchemistHdCtrlEntries 6715 }

	audioPair6CtlMono OBJECT-TYPE
		SYNTAX		INTEGER { enable(0), disable(1) }
		MAX-ACCESS	read-write
		STATUS		current
		DESCRIPTION	"
			style='Checkbox'
			path='/audio_control/Audio Pair 6/Mono'
		"
		::= { alchemistHdCtrlEntries 6717 }

	audioPair7CtlMono OBJECT-TYPE
		SYNTAX		INTEGER { enable(0), disable(1) }
		MAX-ACCESS	read-write
		STATUS		current
		DESCRIPTION	"
			style='Checkbox'
			path='/audio_control/Audio Pair 7/Mono'
		"
		::= { alchemistHdCtrlEntries 6719 }

	audioPair8CtlMono OBJECT-TYPE
		SYNTAX		INTEGER { enable(0), disable(1) }
		MAX-ACCESS	read-write
		STATUS		current
		DESCRIPTION	"
			style='Checkbox'
			path='/audio_control/Audio Pair 8/Mono'
		"
		::= { alchemistHdCtrlEntries 6721 }

	systemVersionStatus OBJECT-TYPE
		SYNTAX		Integer32 (0..1)
		MAX-ACCESS	read-only
		STATUS		current
		DESCRIPTION	"
			style='ReadOnly numeric'
			range='0..1'
			path='/System/Debug/status/status1/Version Status'
		"
		::= { alchemistHdCtrlEntries 6798 }

	systemVersion OBJECT-TYPE
		SYNTAX		RollCallString
		MAX-ACCESS	read-only
		STATUS		current
		DESCRIPTION	"
			style='ReadOnly string'
			path='/System/Info/Version'
		"
		::= { alchemistHdCtrlEntries 6799 }

	mioVersion OBJECT-TYPE
		SYNTAX		RollCallString
		MAX-ACCESS	read-only
		STATUS		current
		DESCRIPTION	"
			style='ReadOnly string'
			path='/System/Info/MIO'
		"
		::= { alchemistHdCtrlEntries 6800 }

	hmiVersion OBJECT-TYPE
		SYNTAX		RollCallString
		MAX-ACCESS	read-only
		STATUS		current
		DESCRIPTION	"
			style='ReadOnly string'
			path='/System/Info/HMI'
		"
		::= { alchemistHdCtrlEntries 6801 }

	meVersion OBJECT-TYPE
		SYNTAX		RollCallString
		MAX-ACCESS	read-only
		STATUS		current
		DESCRIPTION	"
			style='ReadOnly string'
			path='/System/Info/ME'
		"
		::= { alchemistHdCtrlEntries 6802 }

	frpVersion OBJECT-TYPE
		SYNTAX		RollCallString
		MAX-ACCESS	read-only
		STATUS		current
		DESCRIPTION	"
			style='ReadOnly string'
			path='/System/Info/FRP'
		"
		::= { alchemistHdCtrlEntries 6803 }

	mioAutotest OBJECT-TYPE
		SYNTAX		INTEGER { ready(0), trigger(1) }
		MAX-ACCESS	read-write
		STATUS		current
		DESCRIPTION	"
			style='Event button'
			path='/System/Autotest/MIO Autotest'
		"
		::= { alchemistHdCtrlEntries 6804 }

	hmiAutotest OBJECT-TYPE
		SYNTAX		INTEGER { ready(0), trigger(1) }
		MAX-ACCESS	read-write
		STATUS		current
		DESCRIPTION	"
			style='Event button'
			path='/System/Autotest/HMI Autotest'
		"
		::= { alchemistHdCtrlEntries 6805 }

	meAutotest OBJECT-TYPE
		SYNTAX		INTEGER { ready(0), trigger(1) }
		MAX-ACCESS	read-write
		STATUS		current
		DESCRIPTION	"
			style='Event button'
			path='/System/Autotest/ME Autotest'
		"
		::= { alchemistHdCtrlEntries 6806 }

	mioAutotestStatus OBJECT-TYPE
		SYNTAX		Integer32 (0..30)
		MAX-ACCESS	read-only
		STATUS		current
		DESCRIPTION	"
			style='ReadOnly numeric'
			range='0..30'
			path='/System/Autotest/MIO Autotest Status'
		"
		::= { alchemistHdCtrlEntries 6807 }

	hmiAutotestStatus OBJECT-TYPE
		SYNTAX		Integer32 (0..30)
		MAX-ACCESS	read-only
		STATUS		current
		DESCRIPTION	"
			style='ReadOnly numeric'
			range='0..30'
			path='/System/Autotest/HMI Autotest Status'
		"
		::= { alchemistHdCtrlEntries 6808 }

	meAutotestStatus OBJECT-TYPE
		SYNTAX		Integer32 (0..30)
		MAX-ACCESS	read-only
		STATUS		current
		DESCRIPTION	"
			style='ReadOnly numeric'
			range='0..30'
			path='/System/Autotest/ME Autotest Status'
		"
		::= { alchemistHdCtrlEntries 6809 }

	mioSerno OBJECT-TYPE
		SYNTAX		RollCallString
		MAX-ACCESS	read-only
		STATUS		current
		DESCRIPTION	"
			style='ReadOnly string'
			path='/System/Info/MIO serno'
		"
		::= { alchemistHdCtrlEntries 6810 }

	hmiSerno OBJECT-TYPE
		SYNTAX		RollCallString
		MAX-ACCESS	read-only
		STATUS		current
		DESCRIPTION	"
			style='ReadOnly string'
			path='/System/Info/HMI serno'
		"
		::= { alchemistHdCtrlEntries 6811 }

	meSerno OBJECT-TYPE
		SYNTAX		RollCallString
		MAX-ACCESS	read-only
		STATUS		current
		DESCRIPTION	"
			style='ReadOnly string'
			path='/System/Info/ME serno'
		"
		::= { alchemistHdCtrlEntries 6812 }

	frpSerno OBJECT-TYPE
		SYNTAX		RollCallString
		MAX-ACCESS	read-only
		STATUS		current
		DESCRIPTION	"
			style='ReadOnly string'
			path='/System/Info/FRP serno'
		"
		::= { alchemistHdCtrlEntries 6813 }

	systemSerno OBJECT-TYPE
		SYNTAX		RollCallString
		MAX-ACCESS	read-only
		STATUS		current
		DESCRIPTION	"
			style='ReadOnly string'
			path='/System/Info/System serno'
		"
		::= { alchemistHdCtrlEntries 6815 }

	timecodeInfo OBJECT-TYPE
		SYNTAX		INTEGER { enable(0), disable(1) }
		MAX-ACCESS	read-write
		STATUS		current
		DESCRIPTION	"
			style='Checkbox'
			path='/System/Debug/status/status1/TimecodeInfo'
		"
		::= { alchemistHdCtrlEntries 6816 }

	audioInfo OBJECT-TYPE
		SYNTAX		INTEGER { enable(0), disable(1) }
		MAX-ACCESS	read-write
		STATUS		current
		DESCRIPTION	"
			style='Checkbox'
			path='/System/Debug/status/status1/AudioInfo'
		"
		::= { alchemistHdCtrlEntries 6817 }

	timecodeInfoOn OBJECT-TYPE
		SYNTAX		Integer32
		MAX-ACCESS	read-write
		STATUS		current
		DESCRIPTION	"
			style='Numeric control'
			path='/System 2/'
		"
		::= { alchemistHdCtrlEntries 6818 }

	audioInfoOn OBJECT-TYPE
		SYNTAX		Integer32
		MAX-ACCESS	read-write
		STATUS		current
		DESCRIPTION	"
			style='Numeric control'
			preset='1'
			path='/System 2/'
		"
		::= { alchemistHdCtrlEntries 6819 }

	ftInfo OBJECT-TYPE
		SYNTAX		INTEGER { enable(0), disable(1) }
		MAX-ACCESS	read-write
		STATUS		current
		DESCRIPTION	"
			style='Checkbox'
			path='/System/Debug/status/status1/FilmToolsInfo'
		"
		::= { alchemistHdCtrlEntries 6820 }

	ftInfoOn OBJECT-TYPE
		SYNTAX		Integer32
		MAX-ACCESS	read-write
		STATUS		current
		DESCRIPTION	"
			style='Numeric control'
			preset='1'
			path='/System 2/'
		"
		::= { alchemistHdCtrlEntries 6821 }

	outputNotPsf OBJECT-TYPE
		SYNTAX		Integer32
		MAX-ACCESS	read-write
		STATUS		current
		DESCRIPTION	"
			style='Numeric control'
			preset='1'
			path='/System 2/'
		"
		::= { alchemistHdCtrlEntries 6822 }

	dlbVersion OBJECT-TYPE
		SYNTAX		RollCallString
		MAX-ACCESS	read-only
		STATUS		current
		DESCRIPTION	"
			style='ReadOnly string'
			path='/System/Info/DLB'
		"
		::= { alchemistHdCtrlEntries 6823 }

	dlbAutotest OBJECT-TYPE
		SYNTAX		INTEGER { ready(0), trigger(1) }
		MAX-ACCESS	read-write
		STATUS		current
		DESCRIPTION	"
			style='Event button'
			path='/System/Autotest/DLB Autotest'
		"
		::= { alchemistHdCtrlEntries 6824 }

	outputIsPsf OBJECT-TYPE
		SYNTAX		Integer32
		MAX-ACCESS	read-write
		STATUS		current
		DESCRIPTION	"
			style='Numeric control'
			path='/System 2/'
		"
		::= { alchemistHdCtrlEntries 6825 }

	dummyRef OBJECT-TYPE
		SYNTAX		Integer32
		MAX-ACCESS	read-write
		STATUS		current
		DESCRIPTION	"
			style='Numeric control'
			preset='1'
			path='/System 2/'
		"
		::= { alchemistHdCtrlEntries 6826 }

	cadenceInputOffset OBJECT-TYPE
		SYNTAX		Integer32 (-50..50)
		MAX-ACCESS	read-write
		STATUS		current
		DESCRIPTION	"
			style='Numeric control'
			range='-50..50'
			path='/FilmTools/Input/Cadence Offset/Cadence Offset'
		"
		::= { alchemistHdCtrlEntries 6827 }

	cadenceOutputOffset OBJECT-TYPE
		SYNTAX		Integer32 (-50..50)
		MAX-ACCESS	read-write
		STATUS		current
		DESCRIPTION	"
			style='Numeric control'
			range='-50..50'
			path='/FilmTools/Output/Cadence Offset/Cadence Offset'
		"
		::= { alchemistHdCtrlEntries 6828 }

	dlbAutotestStatus OBJECT-TYPE
		SYNTAX		Integer32 (0..30)
		MAX-ACCESS	read-only
		STATUS		current
		DESCRIPTION	"
			style='ReadOnly numeric'
			range='0..30'
			path='/System/Autotest/DLB Autotest Status'
		"
		::= { alchemistHdCtrlEntries 6829 }

	dlbSerno OBJECT-TYPE
		SYNTAX		RollCallString
		MAX-ACCESS	read-only
		STATUS		current
		DESCRIPTION	"
			style='ReadOnly string'
			path='/System/Info/DLB serno'
		"
		::= { alchemistHdCtrlEntries 6830 }

	ftMode OBJECT-TYPE
		SYNTAX		INTEGER {
					auto(0),
					synchronise(1),
					interpolate(2)
				}
		MAX-ACCESS	read-write
		STATUS		current
		DESCRIPTION	"
			style='Radiobutton list'
			preset='auto'
			path='/FilmTools/Control/Mode'
		"
		::= { alchemistHdCtrlEntries 6900 }

	ftAperture OBJECT-TYPE
		SYNTAX		INTEGER {
					normal(0),
					sharp(1),
					safe(2)
				}
		MAX-ACCESS	read-write
		STATUS		current
		DESCRIPTION	"
			style='Radiobutton list'
			preset='normal'
			path='/FilmTools/Control/Film Aperture'
		"
		::= { alchemistHdCtrlEntries 6901 }

	ftBlurMode OBJECT-TYPE
		SYNTAX		INTEGER {
					off(0),
					auto(1),
					manual(2)
				}
		MAX-ACCESS	read-write
		STATUS		current
		DESCRIPTION	"
			style='Radiobutton list'
			preset='off'
			path='/System 2/Video Blur Mode'
		"
		::= { alchemistHdCtrlEntries 6902 }

	ftBlur OBJECT-TYPE
		SYNTAX		Integer32 (1..10)
		MAX-ACCESS	read-write
		STATUS		current
		DESCRIPTION	"
			style='Numeric control'
			range='1..10'
			preset='1'
			path='/System 2/Manual Video Blur'
		"
		::= { alchemistHdCtrlEntries 6903 }

	ftInCadAlignment OBJECT-TYPE
		SYNTAX		INTEGER {
					auto(0),
					detect(1),
					v1x1(2),
					v2x2F12Psf(3),
					v2x2F21(4),
					v2x3TcDatum(5),
					v2x3Tc0And5(6),
					v2x3Freerun(7)
				}
		MAX-ACCESS	read-write
		STATUS		current
		DESCRIPTION	"
			style='Radiobutton list'
			preset='auto'
			path='/FilmTools/Input/Cadence Control'
		"
		::= { alchemistHdCtrlEntries 6910 }

	ftInCadOffInc OBJECT-TYPE
		SYNTAX		INTEGER { ready(0), trigger(1) }
		MAX-ACCESS	read-write
		STATUS		current
		DESCRIPTION	"
			style='Event button'
			path='/FilmTools/Input/Cadence Offset/>'
		"
		::= { alchemistHdCtrlEntries 6913 }

	ftInCadOffDec OBJECT-TYPE
		SYNTAX		INTEGER { ready(0), trigger(1) }
		MAX-ACCESS	read-write
		STATUS		current
		DESCRIPTION	"
			style='Event button'
			path='/FilmTools/Input/Cadence Offset/<'
		"
		::= { alchemistHdCtrlEntries 6914 }

	ftUseInTrigger OBJECT-TYPE
		SYNTAX		INTEGER { enable(0), disable(1) }
		MAX-ACCESS	read-write
		STATUS		current
		DESCRIPTION	"
			style='Checkbox'
			range='0..1'
			path='/FilmTools/Input/Cadence Datum/   Use   '
		"
		::= { alchemistHdCtrlEntries 6915 }

	ftUseIndTrigger OBJECT-TYPE
		SYNTAX		INTEGER { enable(0), disable(1) }
		MAX-ACCESS	read-write
		STATUS		current
		DESCRIPTION	"
			style='Checkbox'
			range='0..1'
			path='/FilmTools/Input/Cadence Datum/   Use   '
		"
		::= { alchemistHdCtrlEntries 6916 }

	ftEditIndTrigger OBJECT-TYPE
		SYNTAX		INTEGER { enable(0), disable(1) }
		MAX-ACCESS	read-write
		STATUS		current
		DESCRIPTION	"
			style='Checkbox'
			range='0..1'
			path='/FilmTools/Input/Cadence Datum/   Edit   '
		"
		::= { alchemistHdCtrlEntries 6917 }

	ftInCadence OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Input/2:3 Datum Cadence'
		"
		::= { alchemistHdCtrlEntries 6918 }

	ftInCadenceValid OBJECT-TYPE
		SYNTAX		INTEGER {
					atDatumPoint(0),
					onValidTc(1)
				}
		MAX-ACCESS	read-write
		STATUS		current
		DESCRIPTION	"
			style='Radiobutton list'
			preset='onValidTc'
			path='/FilmTools/Input/2:3 Cadence reset'
		"
		::= { alchemistHdCtrlEntries 6919 }

	ftInCadencePre OBJECT-TYPE
		SYNTAX		Integer32 (0..23)
		MAX-ACCESS	read-write
		STATUS		current
		DESCRIPTION	"
			style='Numeric control'
			range='0hrs..23hrs'
			preset='12hrs'
			path='/FilmTools/Input/Max time pre-datum'
		"
		::= { alchemistHdCtrlEntries 6920 }

	ftDetectVidOn OBJECT-TYPE
		SYNTAX		INTEGER {
					off(0),
					on(1)
				}
		MAX-ACCESS	read-write
		STATUS		current
		DESCRIPTION	"
			style='Radiobutton list'
			preset='on'
			path='/FilmTools/Detection/Video Enable'
		"
		::= { alchemistHdCtrlEntries 6930 }

	ftDetectFilmOn OBJECT-TYPE
		SYNTAX		INTEGER {
					any(1),
					off(0),
					v2x2(2),
					v2x3(3),
					animation(4)
				}
		MAX-ACCESS	read-write
		STATUS		current
		DESCRIPTION	"
			style='Radiobutton list'
			preset='any'
			path='/FilmTools/Detection/Film Enable'
		"
		::= { alchemistHdCtrlEntries 6931 }

	ftDetectBias OBJECT-TYPE
		SYNTAX		INTEGER {
					video2(0),
					video1(1),
					normal(2),
					film1(3),
					film2(4)
				}
		MAX-ACCESS	read-write
		STATUS		current
		DESCRIPTION	"
			style='Radiobutton list'
			preset='normal'
			path='/FilmTools/Detection/Bias'
		"
		::= { alchemistHdCtrlEntries 6932 }

	ftDetectWindow OBJECT-TYPE
		SYNTAX		INTEGER {
					auto(0),
					tracking(1),
					user(2)
				}
		MAX-ACCESS	read-write
		STATUS		current
		DESCRIPTION	"
			style='Radiobutton list'
			preset='auto'
			path='/FilmTools/Detection/Window Mode'
		"
		::= { alchemistHdCtrlEntries 6933 }

	ftDetectOverlay OBJECT-TYPE
		SYNTAX		INTEGER {
					off(0),
					darken(1),
					greyed(2)
				}
		MAX-ACCESS	read-write
		STATUS		current
		DESCRIPTION	"
			style='Radiobutton list'
			preset='off'
			path='/FilmTools/Detection/Overlay'
		"
		::= { alchemistHdCtrlEntries 6934 }

	ftDetectWinValFtDetectWinLeft OBJECT-TYPE
		SYNTAX		Integer32 (0..1000)
		MAX-ACCESS	read-write
		STATUS		current
		DESCRIPTION	"
			style='Numeric control'
			range='0.0%..100.0%'
			stepsize='0.1%'
			preset='2.0%'
			path='/FilmTools/Detection/User Window Left'
		"
		::= { alchemistHdCtrlEntries 6935 }

	ftDetectWinValFtDetectWinRight OBJECT-TYPE
		SYNTAX		Integer32 (0..1000)
		MAX-ACCESS	read-write
		STATUS		current
		DESCRIPTION	"
			style='Numeric control'
			range='0.0%..100.0%'
			stepsize='0.1%'
			preset='98.0%'
			path='/FilmTools/Detection/User Window Right'
		"
		::= { alchemistHdCtrlEntries 6936 }

	ftDetectWinValFtDetectWinTop OBJECT-TYPE
		SYNTAX		Integer32 (0..1000)
		MAX-ACCESS	read-write
		STATUS		current
		DESCRIPTION	"
			style='Numeric control'
			range='0.0%..100.0%'
			stepsize='0.1%'
			preset='2.0%'
			path='/FilmTools/Detection/User Window Top'
		"
		::= { alchemistHdCtrlEntries 6937 }

	ftDetectWinValFtDetectWinBottom OBJECT-TYPE
		SYNTAX		Integer32 (0..1000)
		MAX-ACCESS	read-write
		STATUS		current
		DESCRIPTION	"
			style='Numeric control'
			range='0.0%..100.0%'
			stepsize='0.1%'
			preset='98.0%'
			path='/FilmTools/Detection/User Window Bottom'
		"
		::= { alchemistHdCtrlEntries 6938 }

	ftOutCadAlignment OBJECT-TYPE
		SYNTAX		INTEGER {
					off(2),
					v2x2F12Psf(3),
					v2x2F21(4),
					v2x3TcDatum(5),
					v2x3Tc0And5(6),
					v2x3Freerun(7)
				}
		MAX-ACCESS	read-write
		STATUS		current
		DESCRIPTION	"
			style='Radiobutton list'
			preset='off'
			path='/FilmTools/Output/Cadence Control'
		"
		::= { alchemistHdCtrlEntries 6940 }

	ftOutCadOffInc OBJECT-TYPE
		SYNTAX		INTEGER { ready(0), trigger(1) }
		MAX-ACCESS	read-write
		STATUS		current
		DESCRIPTION	"
			style='Event button'
			path='/FilmTools/Output/Cadence Offset/>'
		"
		::= { alchemistHdCtrlEntries 6943 }

	ftOutCadOffDec OBJECT-TYPE
		SYNTAX		INTEGER { ready(0), trigger(1) }
		MAX-ACCESS	read-write
		STATUS		current
		DESCRIPTION	"
			style='Event button'
			path='/FilmTools/Output/Cadence Offset/<'
		"
		::= { alchemistHdCtrlEntries 6944 }

	ftOutUseOutTrigger OBJECT-TYPE
		SYNTAX		INTEGER { enable(0), disable(1) }
		MAX-ACCESS	read-write
		STATUS		current
		DESCRIPTION	"
			style='Checkbox'
			range='0..1'
			path='/FilmTools/Output/Cadence Datum/   Use   '
		"
		::= { alchemistHdCtrlEntries 6945 }

	ftOutUseIndTrigger OBJECT-TYPE
		SYNTAX		INTEGER { enable(0), disable(1) }
		MAX-ACCESS	read-write
		STATUS		current
		DESCRIPTION	"
			style='Checkbox'
			range='0..1'
			path='/FilmTools/Output/Cadence Datum/   Use   '
		"
		::= { alchemistHdCtrlEntries 6946 }

	ftOutEditIndTrigger OBJECT-TYPE
		SYNTAX		INTEGER { enable(0), disable(1) }
		MAX-ACCESS	read-write
		STATUS		current
		DESCRIPTION	"
			style='Checkbox'
			range='0..1'
			path='/FilmTools/Output/Cadence Datum/   Edit   '
		"
		::= { alchemistHdCtrlEntries 6947 }

	ftOutCadence OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Output/2:3 Datum Cadence'
		"
		::= { alchemistHdCtrlEntries 6948 }

	ftOutCadenceValid OBJECT-TYPE
		SYNTAX		INTEGER {
					atDatumPoint(0),
					onValidTc(1)
				}
		MAX-ACCESS	read-write
		STATUS		current
		DESCRIPTION	"
			style='Radiobutton list'
			preset='onValidTc'
			path='/FilmTools/Output/2:3 Cadence reset'
		"
		::= { alchemistHdCtrlEntries 6949 }

	ftOutCadencePre OBJECT-TYPE
		SYNTAX		Integer32 (0..23)
		MAX-ACCESS	read-write
		STATUS		current
		DESCRIPTION	"
			style='Numeric control'
			range='0hrs..23hrs'
			preset='12hrs'
			path='/FilmTools/Output/Max time pre-datum'
		"
		::= { alchemistHdCtrlEntries 6950 }

	ftIn05Cadence OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Input/0 and 5 Cadence'
		"
		::= { alchemistHdCtrlEntries 6951 }

	ftOut05Cadence OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Output/0 and 5 Cadence'
		"
		::= { alchemistHdCtrlEntries 6952 }

	ftTcEntry0 OBJECT-TYPE
		SYNTAX		INTEGER { ready(0), trigger(1) }
		MAX-ACCESS	read-write
		STATUS		current
		DESCRIPTION	"
			style='Event button'
			path='/FilmTools/Input/Timecode Entry/0'
		"
		::= { alchemistHdCtrlEntries 6970 }

	ftTcEntry1 OBJECT-TYPE
		SYNTAX		INTEGER { ready(0), trigger(1) }
		MAX-ACCESS	read-write
		STATUS		current
		DESCRIPTION	"
			style='Event button'
			path='/FilmTools/Input/Timecode Entry/1'
		"
		::= { alchemistHdCtrlEntries 6971 }

	ftTcEntry2 OBJECT-TYPE
		SYNTAX		INTEGER { ready(0), trigger(1) }
		MAX-ACCESS	read-write
		STATUS		current
		DESCRIPTION	"
			style='Event button'
			path='/FilmTools/Input/Timecode Entry/2'
		"
		::= { alchemistHdCtrlEntries 6972 }

	ftTcEntry3 OBJECT-TYPE
		SYNTAX		INTEGER { ready(0), trigger(1) }
		MAX-ACCESS	read-write
		STATUS		current
		DESCRIPTION	"
			style='Event button'
			path='/FilmTools/Input/Timecode Entry/3'
		"
		::= { alchemistHdCtrlEntries 6973 }

	ftTcEntry4 OBJECT-TYPE
		SYNTAX		INTEGER { ready(0), trigger(1) }
		MAX-ACCESS	read-write
		STATUS		current
		DESCRIPTION	"
			style='Event button'
			path='/FilmTools/Input/Timecode Entry/4'
		"
		::= { alchemistHdCtrlEntries 6974 }

	ftTcEntry5 OBJECT-TYPE
		SYNTAX		INTEGER { ready(0), trigger(1) }
		MAX-ACCESS	read-write
		STATUS		current
		DESCRIPTION	"
			style='Event button'
			path='/FilmTools/Input/Timecode Entry/5'
		"
		::= { alchemistHdCtrlEntries 6975 }

	ftTcEntry6 OBJECT-TYPE
		SYNTAX		INTEGER { ready(0), trigger(1) }
		MAX-ACCESS	read-write
		STATUS		current
		DESCRIPTION	"
			style='Event button'
			path='/FilmTools/Input/Timecode Entry/6'
		"
		::= { alchemistHdCtrlEntries 6976 }

	ftTcEntry7 OBJECT-TYPE
		SYNTAX		INTEGER { ready(0), trigger(1) }
		MAX-ACCESS	read-write
		STATUS		current
		DESCRIPTION	"
			style='Event button'
			path='/FilmTools/Input/Timecode Entry/7'
		"
		::= { alchemistHdCtrlEntries 6977 }

	ftTcEntry8 OBJECT-TYPE
		SYNTAX		INTEGER { ready(0), trigger(1) }
		MAX-ACCESS	read-write
		STATUS		current
		DESCRIPTION	"
			style='Event button'
			path='/FilmTools/Input/Timecode Entry/8'
		"
		::= { alchemistHdCtrlEntries 6978 }

	ftTcEntry9 OBJECT-TYPE
		SYNTAX		INTEGER { ready(0), trigger(1) }
		MAX-ACCESS	read-write
		STATUS		current
		DESCRIPTION	"
			style='Event button'
			path='/FilmTools/Input/Timecode Entry/9'
		"
		::= { alchemistHdCtrlEntries 6979 }

	ftTcEntryPst10H OBJECT-TYPE
		SYNTAX		INTEGER { ready(0), trigger(1) }
		MAX-ACCESS	read-write
		STATUS		current
		DESCRIPTION	"
			style='Event button'
			path='/FilmTools/Input/Timecode Entry/10h 00m 00s 00f'
		"
		::= { alchemistHdCtrlEntries 6980 }

	ftTcEntryPst1H OBJECT-TYPE
		SYNTAX		INTEGER { ready(0), trigger(1) }
		MAX-ACCESS	read-write
		STATUS		current
		DESCRIPTION	"
			style='Event button'
			path='/FilmTools/Input/Timecode Entry/01h 00m 00s 00f'
		"
		::= { alchemistHdCtrlEntries 6981 }

	ftTcEntryClear OBJECT-TYPE
		SYNTAX		INTEGER { ready(0), trigger(1) }
		MAX-ACCESS	read-write
		STATUS		current
		DESCRIPTION	"
			style='Event button'
			path='/FilmTools/Input/Timecode Entry/Clear'
		"
		::= { alchemistHdCtrlEntries 6982 }

	ftTcEntry00 OBJECT-TYPE
		SYNTAX		INTEGER { ready(0), trigger(1) }
		MAX-ACCESS	read-write
		STATUS		current
		DESCRIPTION	"
			style='Event button'
			path='/FilmTools/Input/Timecode Entry/00'
		"
		::= { alchemistHdCtrlEntries 6983 }

	ftTcEntryBack OBJECT-TYPE
		SYNTAX		INTEGER { ready(0), trigger(1) }
		MAX-ACCESS	read-write
		STATUS		current
		DESCRIPTION	"
			style='Event button'
			path='/FilmTools/Input/Timecode Entry/Backspace'
		"
		::= { alchemistHdCtrlEntries 6984 }

	ftTcEntry OBJECT-TYPE
		SYNTAX		Integer32
		MAX-ACCESS	read-only
		STATUS		current
		DESCRIPTION	"
			style='ReadOnly numeric'
			path='/System 2/FilmTools TC Entry'
		"
		::= { alchemistHdCtrlEntries 6985 }

	ftInTcTrigger OBJECT-TYPE
		SYNTAX		Integer32
		MAX-ACCESS	read-only
		STATUS		current
		DESCRIPTION	"
			style='ReadOnly numeric'
			path='/System 2/FilmTools IP trigger'
		"
		::= { alchemistHdCtrlEntries 6986 }

	ftOutTcTrigger OBJECT-TYPE
		SYNTAX		Integer32
		MAX-ACCESS	read-only
		STATUS		current
		DESCRIPTION	"
			style='ReadOnly numeric'
			path='/System 2/FilmTools OP trigger'
		"
		::= { alchemistHdCtrlEntries 6987 }

	ftOutTcEntryCancel OBJECT-TYPE
		SYNTAX		INTEGER { ready(0), trigger(1) }
		MAX-ACCESS	read-write
		STATUS		current
		DESCRIPTION	"
			style='Event button'
			path='/FilmTools/Input/Timecode Entry/Cancel'
		"
		::= { alchemistHdCtrlEntries 6990 }

	ftOutTcEntryOkay OBJECT-TYPE
		SYNTAX		INTEGER { ready(0), trigger(1) }
		MAX-ACCESS	read-write
		STATUS		current
		DESCRIPTION	"
			style='Event button'
			path='/FilmTools/Input/Timecode Entry/OK'
		"
		::= { alchemistHdCtrlEntries 6991 }

	ftInCadOffset OBJECT-TYPE
		SYNTAX		Integer32 (-50..50)
		MAX-ACCESS	read-write
		STATUS		current
		DESCRIPTION	"
			style='Numeric control'
			range='-50..50'
			path='/System/Debug/status/status1/Cadence Input Offset'
		"
		::= { alchemistHdCtrlEntries 6995 }

	ftOutCadOffset OBJECT-TYPE
		SYNTAX		Integer32 (-50..50)
		MAX-ACCESS	read-write
		STATUS		current
		DESCRIPTION	"
			style='Numeric control'
			range='-50..50'
			path='/System/Debug/status/status1/Cadence Output Offset'
		"
		::= { alchemistHdCtrlEntries 6996 }

	ftInTcEntryCancel OBJECT-TYPE
		SYNTAX		INTEGER { ready(0), trigger(1) }
		MAX-ACCESS	read-write
		STATUS		current
		DESCRIPTION	"
			style='Event button'
			path='/FilmTools/Input/Timecode Entry/Cancel'
		"
		::= { alchemistHdCtrlEntries 6998 }

	ftInTcEntryOkay OBJECT-TYPE
		SYNTAX		INTEGER { ready(0), trigger(1) }
		MAX-ACCESS	read-write
		STATUS		current
		DESCRIPTION	"
			style='Event button'
			path='/FilmTools/Input/Timecode Entry/OK'
		"
		::= { alchemistHdCtrlEntries 6999 }

	tcSdSource OBJECT-TYPE
		SYNTAX		INTEGER {
					vitc(0),
					ltc(1)
				}
		MAX-ACCESS	read-write
		STATUS		current
		DESCRIPTION	"
			style='Radiobutton list'
			preset='vitc'
			path='/Timecode/Timecode In/SD Source'
		"
		::= { alchemistHdCtrlEntries 7000 }

	tcHdSource OBJECT-TYPE
		SYNTAX		INTEGER {
					embeddedVitc(0),
					embeddedLtc(1),
					ltc(2)
				}
		MAX-ACCESS	read-write
		STATUS		current
		DESCRIPTION	"
			style='Radiobutton list'
			preset='embeddedVitc'
			path='/Timecode/Timecode In/HD Source'
		"
		::= { alchemistHdCtrlEntries 7001 }

	tcSdVitcOutEn OBJECT-TYPE
		SYNTAX		INTEGER { enable(0), disable(1) }
		MAX-ACCESS	read-write
		STATUS		current
		DESCRIPTION	"
			style='Checkbox'
			path='/Timecode/Timecode Out/  VITC  '
		"
		::= { alchemistHdCtrlEntries 7010 }

	tcSdVitcOut2NdLineEn OBJECT-TYPE
		SYNTAX		INTEGER { enable(0), disable(1) }
		MAX-ACCESS	read-write
		STATUS		current
		DESCRIPTION	"
			style='Checkbox'
			path='/Timecode/Timecode Out/Repeat line'
		"
		::= { alchemistHdCtrlEntries 7011 }

	tcSdVitcOutLineVitcOutLine525 OBJECT-TYPE
		SYNTAX		Integer32 (10..17)
		MAX-ACCESS	read-write
		STATUS		current
		DESCRIPTION	"
			style='Numeric control'
			range='10..17'
			preset='14'
			path='/Timecode/Timecode Out/VITC Insertion 525'
		"
		::= { alchemistHdCtrlEntries 7012 }

	tcSdVitcOutLineVitcOutLine625 OBJECT-TYPE
		SYNTAX		Integer32 (6..20)
		MAX-ACCESS	read-write
		STATUS		current
		DESCRIPTION	"
			style='Numeric control'
			range='6..20'
			preset='19'
			path='/Timecode/Timecode Out/VITC Insertion 625'
		"
		::= { alchemistHdCtrlEntries 7013 }

	tcHdVitcOutEn OBJECT-TYPE
		SYNTAX		INTEGER { enable(0), disable(1) }
		MAX-ACCESS	read-write
		STATUS		current
		DESCRIPTION	"
			style='Checkbox'
			path='/Timecode/Timecode Out/Emb VITC'
		"
		::= { alchemistHdCtrlEntries 7020 }

	tcHdLtcOutEn OBJECT-TYPE
		SYNTAX		INTEGER { enable(0), disable(1) }
		MAX-ACCESS	read-write
		STATUS		current
		DESCRIPTION	"
			style='Checkbox'
			path='/Timecode/Timecode Out/Emb LTC'
		"
		::= { alchemistHdCtrlEntries 7021 }

	tcDropFrameOuta OBJECT-TYPE
		SYNTAX		INTEGER {
					nonDropFrame(0),
					dropFrame(1)
				}
		MAX-ACCESS	read-write
		STATUS		current
		DESCRIPTION	"
			style='Radiobutton list'
			preset='dropFrame'
			path='/Timecode/Timecode Out/Frame Mode A'
		"
		::= { alchemistHdCtrlEntries 7030 }

	tcDropFrameOutb OBJECT-TYPE
		SYNTAX		INTEGER {
					nonDropFrame(0),
					dropFrame(1)
				}
		MAX-ACCESS	read-write
		STATUS		current
		DESCRIPTION	"
			style='Radiobutton list'
			preset='dropFrame'
			path='/Timecode/Timecode Out/Frame Mode B'
		"
		::= { alchemistHdCtrlEntries 7031 }

	tcInMaxFrames OBJECT-TYPE
		SYNTAX		INTEGER {
					detect(0),
					format(1),
					v24(2),
					v25(3),
					v30(4)
				}
		MAX-ACCESS	read-write
		STATUS		current
		DESCRIPTION	"
			style='Radiobutton list'
			preset='detect'
			path='/Timecode/Timecode In/Frame Count'
		"
		::= { alchemistHdCtrlEntries 7032 }

	tcOutMaxFramesOuta OBJECT-TYPE
		SYNTAX		INTEGER {
					auto(0),
					v24(1),
					v25(2),
					v30(3)
				}
		MAX-ACCESS	read-write
		STATUS		current
		DESCRIPTION	"
			style='Radiobutton list'
			preset='auto'
			path='/Timecode/Timecode Out/Frame Count A'
		"
		::= { alchemistHdCtrlEntries 7033 }

	tcOutMaxFramesOutb OBJECT-TYPE
		SYNTAX		INTEGER {
					auto(0),
					v24(1),
					v25(2),
					v30(3)
				}
		MAX-ACCESS	read-write
		STATUS		current
		DESCRIPTION	"
			style='Radiobutton list'
			preset='auto'
			path='/Timecode/Timecode Out/Frame Count B'
		"
		::= { alchemistHdCtrlEntries 7034 }

	tcMode OBJECT-TYPE
		SYNTAX		INTEGER {
					freeRun(0),
					syncAuto(1),
					syncManual(2),
					syncPrerun(3),
					eE(4),
					eERegen(5),
					triggerLoad(6)
				}
		MAX-ACCESS	read-write
		STATUS		current
		DESCRIPTION	"
			style='Radiobutton list'
			preset='freeRun'
			path='/Timecode/Timecode Conversion/Timecode Mode'
		"
		::= { alchemistHdCtrlEntries 7035 }

	tcLoadNow OBJECT-TYPE
		SYNTAX		INTEGER { ready(0), trigger(1) }
		MAX-ACCESS	read-write
		STATUS		current
		DESCRIPTION	"
			style='Event button'
			path='/Timecode/Timecode Conversion/Load Now'
		"
		::= { alchemistHdCtrlEntries 7036 }

	tcTrigger OBJECT-TYPE
		SYNTAX		Integer32
		MAX-ACCESS	read-only
		STATUS		current
		DESCRIPTION	"
			style='ReadOnly numeric'
			path='/System/Debug/status/status1/Timecode Conversion/Trigger and Load/Input trigger value'
		"
		::= { alchemistHdCtrlEntries 7040 }

	tcLoadOuta OBJECT-TYPE
		SYNTAX		Integer32
		MAX-ACCESS	read-only
		STATUS		current
		DESCRIPTION	"
			style='ReadOnly numeric'
			path='/System/Debug/status/status1/Timecode Conversion/Trigger and Load/Output A load value'
		"
		::= { alchemistHdCtrlEntries 7041 }

	tcLoadOutb OBJECT-TYPE
		SYNTAX		Integer32
		MAX-ACCESS	read-only
		STATUS		current
		DESCRIPTION	"
			style='ReadOnly numeric'
			path='/System/Debug/status/status1/Timecode Conversion/Trigger and Load/Output B load value'
		"
		::= { alchemistHdCtrlEntries 7042 }

	tcSynchroPrerun OBJECT-TYPE
		SYNTAX		Integer32
		MAX-ACCESS	read-only
		STATUS		current
		DESCRIPTION	"
			style='ReadOnly numeric'
			path='/System/Debug/status/status1/Timecode Conversion/Trigger and Load/Auto Synchro Pre-run'
		"
		::= { alchemistHdCtrlEntries 7043 }

	tcSynchroStatusA OBJECT-TYPE
		SYNTAX		Integer32
		MAX-ACCESS	read-only
		STATUS		current
		DESCRIPTION	"
			style='ReadOnly numeric'
			path='/System/Debug/status/status1/Synchro Status/Synchro Status A'
		"
		::= { alchemistHdCtrlEntries 7044 }

	tcSynchroLastTrigger OBJECT-TYPE
		SYNTAX		RollCallString
		MAX-ACCESS	read-only
		STATUS		current
		DESCRIPTION	"
			style='ReadOnly string'
			path='/System/Debug/status/status1/Synchro Status/Synchro Last Trigger'
		"
		::= { alchemistHdCtrlEntries 7045 }

	tcInputTc OBJECT-TYPE
		SYNTAX		Integer32
		MAX-ACCESS	read-only
		STATUS		current
		DESCRIPTION	"
			style='ReadOnly numeric'
			path='/System/Debug/status/status1/Timecode Conversion/Actual Timecode/Input Timecode'
		"
		::= { alchemistHdCtrlEntries 7046 }

	tcOutputaTc OBJECT-TYPE
		SYNTAX		Integer32
		MAX-ACCESS	read-only
		STATUS		current
		DESCRIPTION	"
			style='ReadOnly numeric'
			path='/System/Debug/status/status1/Timecode Conversion/Actual Timecode/Output A Timecode'
		"
		::= { alchemistHdCtrlEntries 7047 }

	tcOutputbTc OBJECT-TYPE
		SYNTAX		Integer32
		MAX-ACCESS	read-only
		STATUS		current
		DESCRIPTION	"
			style='ReadOnly numeric'
			path='/System/Debug/status/status1/Timecode Conversion/Actual Timecode/Output B Timecode'
		"
		::= { alchemistHdCtrlEntries 7048 }

	tcEntry OBJECT-TYPE
		SYNTAX		Integer32
		MAX-ACCESS	read-only
		STATUS		current
		DESCRIPTION	"
			style='ReadOnly numeric'
			path='/System/Debug/status/status1/Timecode Conversion/Trigger and Load/Timecode Entry value'
		"
		::= { alchemistHdCtrlEntries 7049 }

	tcIpOverlay OBJECT-TYPE
		SYNTAX		INTEGER { enable(0), disable(1) }
		MAX-ACCESS	read-write
		STATUS		current
		DESCRIPTION	"
			style='Checkbox'
			range='0..1'
			path='/Timecode/Timecode Overlay/Input TC Overlay'
		"
		::= { alchemistHdCtrlEntries 7050 }

	tcOpaOverlay OBJECT-TYPE
		SYNTAX		INTEGER { enable(0), disable(1) }
		MAX-ACCESS	read-write
		STATUS		current
		DESCRIPTION	"
			style='Checkbox'
			range='0..1'
			path='/Timecode/Timecode Overlay/Output A TC Overlay'
		"
		::= { alchemistHdCtrlEntries 7051 }

	tcOpbOverlay OBJECT-TYPE
		SYNTAX		INTEGER { enable(0), disable(1) }
		MAX-ACCESS	read-write
		STATUS		current
		DESCRIPTION	"
			style='Checkbox'
			range='0..1'
			path='/Timecode/Timecode Overlay/Output B TC Overlay'
		"
		::= { alchemistHdCtrlEntries 7052 }

	templateTcEntry OBJECT-TYPE
		SYNTAX		RollCallString
		MAX-ACCESS	read-write
		STATUS		current
		DESCRIPTION	"
			style='Editable string'
			path='/Timecode/Timecode Conversion/TC Entry'
		"
		::= { alchemistHdCtrlEntries 7055 }

	tcE2eWindow OBJECT-TYPE
		SYNTAX		INTEGER {
					minimum(0),
					v05S(1),
					v1s(2),
					v2s(3),
					v5s(4)
				}
		MAX-ACCESS	read-write
		STATUS		current
		DESCRIPTION	"
			style='Radiobutton list'
			preset='minimum'
			path='/Timecode/Timecode Conversion/E-E Error Window'
		"
		::= { alchemistHdCtrlEntries 7060 }

	tcTriggerSet OBJECT-TYPE
		SYNTAX		INTEGER { ready(0), trigger(1) }
		MAX-ACCESS	read-write
		STATUS		current
		DESCRIPTION	"
			style='Event button'
			path='/Timecode/Timecode Conversion/Trigger Set'
		"
		::= { alchemistHdCtrlEntries 7070 }

	tcLoadOutaSet OBJECT-TYPE
		SYNTAX		INTEGER { ready(0), trigger(1) }
		MAX-ACCESS	read-write
		STATUS		current
		DESCRIPTION	"
			style='Event button'
			path='/Timecode/Timecode Conversion/Output A Set'
		"
		::= { alchemistHdCtrlEntries 7071 }

	tcLoadOutbSet OBJECT-TYPE
		SYNTAX		INTEGER { ready(0), trigger(1) }
		MAX-ACCESS	read-write
		STATUS		current
		DESCRIPTION	"
			style='Event button'
			path='/Timecode/Timecode Conversion/Output B Set'
		"
		::= { alchemistHdCtrlEntries 7072 }

	tcSynchroPrerunSet OBJECT-TYPE
		SYNTAX		INTEGER { ready(0), trigger(1) }
		MAX-ACCESS	read-write
		STATUS		current
		DESCRIPTION	"
			style='Event button'
			path='/Timecode/Timecode Conversion/Prerun Set'
		"
		::= { alchemistHdCtrlEntries 7073 }

	tcTriggerGrab OBJECT-TYPE
		SYNTAX		INTEGER { ready(0), trigger(1) }
		MAX-ACCESS	read-write
		STATUS		current
		DESCRIPTION	"
			style='Event button'
			path='/Timecode/Timecode Conversion/Trigger Grab'
		"
		::= { alchemistHdCtrlEntries 7074 }

	tcLoadOutaGrab OBJECT-TYPE
		SYNTAX		INTEGER { ready(0), trigger(1) }
		MAX-ACCESS	read-write
		STATUS		current
		DESCRIPTION	"
			style='Event button'
			path='/Timecode/Timecode Conversion/Output A Grab'
		"
		::= { alchemistHdCtrlEntries 7075 }

	tcLoadOutbGrab OBJECT-TYPE
		SYNTAX		INTEGER { ready(0), trigger(1) }
		MAX-ACCESS	read-write
		STATUS		current
		DESCRIPTION	"
			style='Event button'
			path='/Timecode/Timecode Conversion/Output B Grab'
		"
		::= { alchemistHdCtrlEntries 7076 }

	tcSynchroPrerunPreset OBJECT-TYPE
		SYNTAX		INTEGER { ready(0), trigger(1) }
		MAX-ACCESS	read-write
		STATUS		current
		DESCRIPTION	"
			style='Event button'
			path='/Timecode/Timecode Conversion/Prerun Preset'
		"
		::= { alchemistHdCtrlEntries 7077 }

	tcEntry0 OBJECT-TYPE
		SYNTAX		INTEGER { ready(0), trigger(1) }
		MAX-ACCESS	read-write
		STATUS		current
		DESCRIPTION	"
			style='Event button'
			path='/System 2/0'
		"
		::= { alchemistHdCtrlEntries 7100 }

	tcEntry1 OBJECT-TYPE
		SYNTAX		INTEGER { ready(0), trigger(1) }
		MAX-ACCESS	read-write
		STATUS		current
		DESCRIPTION	"
			style='Event button'
			path='/System 2/1'
		"
		::= { alchemistHdCtrlEntries 7101 }

	tcEntry2 OBJECT-TYPE
		SYNTAX		INTEGER { ready(0), trigger(1) }
		MAX-ACCESS	read-write
		STATUS		current
		DESCRIPTION	"
			style='Event button'
			path='/System 2/2'
		"
		::= { alchemistHdCtrlEntries 7102 }

	tcEntry3 OBJECT-TYPE
		SYNTAX		INTEGER { ready(0), trigger(1) }
		MAX-ACCESS	read-write
		STATUS		current
		DESCRIPTION	"
			style='Event button'
			path='/System 2/3'
		"
		::= { alchemistHdCtrlEntries 7103 }

	tcEntry4 OBJECT-TYPE
		SYNTAX		INTEGER { ready(0), trigger(1) }
		MAX-ACCESS	read-write
		STATUS		current
		DESCRIPTION	"
			style='Event button'
			path='/System 2/4'
		"
		::= { alchemistHdCtrlEntries 7104 }

	tcEntry5 OBJECT-TYPE
		SYNTAX		INTEGER { ready(0), trigger(1) }
		MAX-ACCESS	read-write
		STATUS		current
		DESCRIPTION	"
			style='Event button'
			path='/System 2/5'
		"
		::= { alchemistHdCtrlEntries 7105 }

	tcEntry6 OBJECT-TYPE
		SYNTAX		INTEGER { ready(0), trigger(1) }
		MAX-ACCESS	read-write
		STATUS		current
		DESCRIPTION	"
			style='Event button'
			path='/System 2/6'
		"
		::= { alchemistHdCtrlEntries 7106 }

	tcEntry7 OBJECT-TYPE
		SYNTAX		INTEGER { ready(0), trigger(1) }
		MAX-ACCESS	read-write
		STATUS		current
		DESCRIPTION	"
			style='Event button'
			path='/System 2/7'
		"
		::= { alchemistHdCtrlEntries 7107 }

	tcEntry8 OBJECT-TYPE
		SYNTAX		INTEGER { ready(0), trigger(1) }
		MAX-ACCESS	read-write
		STATUS		current
		DESCRIPTION	"
			style='Event button'
			path='/System 2/8'
		"
		::= { alchemistHdCtrlEntries 7108 }

	tcEntry9 OBJECT-TYPE
		SYNTAX		INTEGER { ready(0), trigger(1) }
		MAX-ACCESS	read-write
		STATUS		current
		DESCRIPTION	"
			style='Event button'
			path='/System 2/9'
		"
		::= { alchemistHdCtrlEntries 7109 }

	tcEntryPst10H OBJECT-TYPE
		SYNTAX		INTEGER { ready(0), trigger(1) }
		MAX-ACCESS	read-write
		STATUS		current
		DESCRIPTION	"
			style='Event button'
			path='/System 2/10h 00m 00s 00f'
		"
		::= { alchemistHdCtrlEntries 7110 }

	tcEntryPst1H OBJECT-TYPE
		SYNTAX		INTEGER { ready(0), trigger(1) }
		MAX-ACCESS	read-write
		STATUS		current
		DESCRIPTION	"
			style='Event button'
			path='/System 2/01h 00m 00s 00f'
		"
		::= { alchemistHdCtrlEntries 7111 }

	tcEntryClear OBJECT-TYPE
		SYNTAX		INTEGER { ready(0), trigger(1) }
		MAX-ACCESS	read-write
		STATUS		current
		DESCRIPTION	"
			style='Event button'
			path='/System 2/Clear'
		"
		::= { alchemistHdCtrlEntries 7112 }

	tcEntry00 OBJECT-TYPE
		SYNTAX		INTEGER { ready(0), trigger(1) }
		MAX-ACCESS	read-write
		STATUS		current
		DESCRIPTION	"
			style='Event button'
			path='/System 2/00'
		"
		::= { alchemistHdCtrlEntries 7113 }

	tcEntryBackspace OBJECT-TYPE
		SYNTAX		INTEGER { ready(0), trigger(1) }
		MAX-ACCESS	read-write
		STATUS		current
		DESCRIPTION	"
			style='Event button'
			path='/System 2/Backspace'
		"
		::= { alchemistHdCtrlEntries 7114 }

	triggerMemory OBJECT-TYPE
		SYNTAX		RollCallString
		MAX-ACCESS	read-write
		STATUS		current
		DESCRIPTION	"
			style='Editable string'
			path='/System 2/Trigger Memory'
		"
		::= { alchemistHdCtrlEntries 7120 }

	loadAMemory OBJECT-TYPE
		SYNTAX		RollCallString
		MAX-ACCESS	read-write
		STATUS		current
		DESCRIPTION	"
			style='Editable string'
			path='/System 2/Load A Memory'
		"
		::= { alchemistHdCtrlEntries 7121 }

	loadBMemory OBJECT-TYPE
		SYNTAX		RollCallString
		MAX-ACCESS	read-write
		STATUS		current
		DESCRIPTION	"
			style='Editable string'
			path='/System 2/Load B Memory'
		"
		::= { alchemistHdCtrlEntries 7122 }

	prerunMemory OBJECT-TYPE
		SYNTAX		RollCallString
		MAX-ACCESS	read-write
		STATUS		current
		DESCRIPTION	"
			style='Editable string'
			path='/System 2/Prerun Memory'
		"
		::= { alchemistHdCtrlEntries 7123 }

	tcCadenceInMemory OBJECT-TYPE
		SYNTAX		RollCallString
		MAX-ACCESS	read-write
		STATUS		current
		DESCRIPTION	"
			style='Editable string'
			path='/System 2/TC Cadence In Memory'
		"
		::= { alchemistHdCtrlEntries 7124 }

	tcCadenceOutMemory OBJECT-TYPE
		SYNTAX		RollCallString
		MAX-ACCESS	read-write
		STATUS		current
		DESCRIPTION	"
			style='Editable string'
			path='/System 2/TC Cadence Out Memory'
		"
		::= { alchemistHdCtrlEntries 7125 }

	inputCadence OBJECT-TYPE
		SYNTAX		Integer32
		MAX-ACCESS	read-only
		STATUS		current
		DESCRIPTION	"
			style='ReadOnly numeric'
			path='/System 2/Input Cadence'
		"
		::= { alchemistHdCtrlEntries 7126 }

	outputCadence OBJECT-TYPE
		SYNTAX		Integer32
		MAX-ACCESS	read-only
		STATUS		current
		DESCRIPTION	"
			style='ReadOnly numeric'
			path='/System 2/Output Cadence'
		"
		::= { alchemistHdCtrlEntries 7127 }

	tcSynchroStatusB OBJECT-TYPE
		SYNTAX		Integer32
		MAX-ACCESS	read-only
		STATUS		current
		DESCRIPTION	"
			style='ReadOnly numeric'
			path='/System/Debug/status/status1/Synchro Status/Synchro Status B'
		"
		::= { alchemistHdCtrlEntries 7144 }

	tcModeStr OBJECT-TYPE
		SYNTAX		Integer32
		MAX-ACCESS	read-only
		STATUS		current
		DESCRIPTION	"
			style='ReadOnly numeric'
			path='/System/Debug/status/status1/Timecode Mode'
		"
		::= { alchemistHdCtrlEntries 7145 }

	tcSynchroTriggerElapse OBJECT-TYPE
		SYNTAX		Integer32
		MAX-ACCESS	read-only
		STATUS		current
		DESCRIPTION	"
			style='ReadOnly numeric'
			path='/System/Debug/status/status1/Synchro Status/Synchro Trigger Elapse'
		"
		::= { alchemistHdCtrlEntries 7146 }

	lumaClipperAEnable OBJECT-TYPE
		SYNTAX		INTEGER { enable(0), disable(1) }
		MAX-ACCESS	read-write
		STATUS		current
		DESCRIPTION	"
			style='Checkbox'
			range='0..1'
			path='/utils/Luma Clipper A/Enable'
		"
		::= { alchemistHdCtrlEntries 7170 }

	whiteMaxA OBJECT-TYPE
		SYNTAX		Integer32 (900..1090)
		MAX-ACCESS	read-write
		STATUS		current
		DESCRIPTION	"
			style='Numeric control'
			range='90.0%..109.0%'
			stepsize='0.1%'
			preset='103.0%'
			path='/utils/Luma Clipper A/White Max'
		"
		::= { alchemistHdCtrlEntries 7171 }

	whiteKneeA OBJECT-TYPE
		SYNTAX		Integer32 (600..1090)
		MAX-ACCESS	read-write
		STATUS		current
		DESCRIPTION	"
			style='Numeric control'
			range='60.0%..109.0%'
			stepsize='0.1%'
			preset='100.0%'
			path='/utils/Luma Clipper A/White Knee'
		"
		::= { alchemistHdCtrlEntries 7172 }

	blackMinA OBJECT-TYPE
		SYNTAX		Integer32 (-70..100)
		MAX-ACCESS	read-write
		STATUS		current
		DESCRIPTION	"
			style='Numeric control'
			range='-7.0%..10.0%'
			stepsize='0.1%'
			preset='-1.0%'
			path='/utils/Luma Clipper A/Black Min'
		"
		::= { alchemistHdCtrlEntries 7173 }

	blackKneeA OBJECT-TYPE
		SYNTAX		Integer32 (-70..600)
		MAX-ACCESS	read-write
		STATUS		current
		DESCRIPTION	"
			style='Numeric control'
			range='-7.0%..60.0%'
			stepsize='0.1%'
			path='/utils/Luma Clipper A/Black Knee'
		"
		::= { alchemistHdCtrlEntries 7174 }

	lumaClipperBEnable OBJECT-TYPE
		SYNTAX		INTEGER { enable(0), disable(1) }
		MAX-ACCESS	read-write
		STATUS		current
		DESCRIPTION	"
			style='Checkbox'
			range='0..10'
			path='/utils/Luma Clipper B/Enable'
		"
		::= { alchemistHdCtrlEntries 7180 }

	whiteMaxB OBJECT-TYPE
		SYNTAX		Integer32 (900..1090)
		MAX-ACCESS	read-write
		STATUS		current
		DESCRIPTION	"
			style='Numeric control'
			range='90.0%..109.0%'
			stepsize='0.1%'
			preset='103.0%'
			path='/utils/Luma Clipper B/White Max'
		"
		::= { alchemistHdCtrlEntries 7181 }

	whiteKneeB OBJECT-TYPE
		SYNTAX		Integer32 (600..1090)
		MAX-ACCESS	read-write
		STATUS		current
		DESCRIPTION	"
			style='Numeric control'
			range='60.0%..109.0%'
			stepsize='0.1%'
			preset='100.0%'
			path='/utils/Luma Clipper B/White Knee'
		"
		::= { alchemistHdCtrlEntries 7182 }

	blackMinB OBJECT-TYPE
		SYNTAX		Integer32 (-70..100)
		MAX-ACCESS	read-write
		STATUS		current
		DESCRIPTION	"
			style='Numeric control'
			range='-7.0%..10.0%'
			stepsize='0.1%'
			preset='-1.0%'
			path='/utils/Luma Clipper B/Black Min'
		"
		::= { alchemistHdCtrlEntries 7183 }

	blackKneeB OBJECT-TYPE
		SYNTAX		Integer32 (-70..600)
		MAX-ACCESS	read-write
		STATUS		current
		DESCRIPTION	"
			style='Numeric control'
			range='-7.0%..60.0%'
			stepsize='0.1%'
			path='/utils/Luma Clipper B/Black Knee'
		"
		::= { alchemistHdCtrlEntries 7184 }

	ftInCadAlignmentTem OBJECT-TYPE
		SYNTAX		INTEGER {
					auto(0),
					detect(1),
					v1x1(2),
					v2x2F12Psf(3),
					v2x2F21(4),
					v2x3TcDatum(5),
					v2x3Tc0And5(6),
					v2x3Freerun(7)
				}
		MAX-ACCESS	read-write
		STATUS		current
		DESCRIPTION	"
			style='Radiobutton list'
			preset='auto'
			path='/FilmTools/Input/Cadence Control'
		"
		::= { alchemistHdCtrlEntries 7210 }

	ftUseInTriggerTem OBJECT-TYPE
		SYNTAX		INTEGER { enable(0), disable(1) }
		MAX-ACCESS	read-write
		STATUS		current
		DESCRIPTION	"
			style='Checkbox'
			range='0..1'
			path='/FilmTools/Input/Cadence Datum/Use Inp Trigger TC'
		"
		::= { alchemistHdCtrlEntries 7215 }

	ftUseIndTriggerTem OBJECT-TYPE
		SYNTAX		INTEGER { enable(0), disable(1) }
		MAX-ACCESS	read-write
		STATUS		current
		DESCRIPTION	"
			style='Checkbox'
			range='0..1'
			path='/FilmTools/Input/Cadence Datum/Use Datum Timecode '
		"
		::= { alchemistHdCtrlEntries 7216 }

	ftEditIndTriggerTem OBJECT-TYPE
		SYNTAX		RollCallString
		MAX-ACCESS	read-write
		STATUS		current
		DESCRIPTION	"
			style='Editable string'
			path='/FilmTools/Input/Cadence Datum/Datum Timecode'
		"
		::= { alchemistHdCtrlEntries 7217 }

	ftInCadenceTem OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Input/2:3 Datum Cadence'
		"
		::= { alchemistHdCtrlEntries 7218 }

	ftInCadenceValidTem OBJECT-TYPE
		SYNTAX		INTEGER {
					atDatumPoint(0),
					onValidTc(1)
				}
		MAX-ACCESS	read-write
		STATUS		current
		DESCRIPTION	"
			style='Radiobutton list'
			preset='onValidTc'
			path='/FilmTools/Input/2:3 Cadence reset'
		"
		::= { alchemistHdCtrlEntries 7219 }

	ftInCadencePreTem OBJECT-TYPE
		SYNTAX		Integer32 (0..23)
		MAX-ACCESS	read-write
		STATUS		current
		DESCRIPTION	"
			style='Numeric control'
			range='0..23'
			preset='12'
			path='/FilmTools/Input/Max time pre-datum'
		"
		::= { alchemistHdCtrlEntries 7220 }

	ftOutCadAlignmentTem OBJECT-TYPE
		SYNTAX		INTEGER {
					off(2),
					v2x2F12Psf(3),
					v2x2F21(4),
					v2x3TcDatum(5),
					v2x3Tc0And5(6),
					v2x3Freerun(7)
				}
		MAX-ACCESS	read-write
		STATUS		current
		DESCRIPTION	"
			style='Radiobutton list'
			preset='off'
			path='/FilmTools/Output/Cadence Control'
		"
		::= { alchemistHdCtrlEntries 7240 }

	tcSynchroStatus OBJECT-TYPE
		SYNTAX		Integer32
		MAX-ACCESS	read-only
		STATUS		current
		DESCRIPTION	"
			style='ReadOnly numeric'
			path='/System 2/Synchro Status'
		"
		::= { alchemistHdCtrlEntries 7244 }

	ftOutUseOutTriggerTem OBJECT-TYPE
		SYNTAX		INTEGER { enable(0), disable(1) }
		MAX-ACCESS	read-write
		STATUS		current
		DESCRIPTION	"
			style='Checkbox'
			range='0..1'
			path='/FilmTools/Output/Cadence Datum/Use Inp Trigger TC'
		"
		::= { alchemistHdCtrlEntries 7245 }

	ftOutUseIndTriggerTem OBJECT-TYPE
		SYNTAX		INTEGER { enable(0), disable(1) }
		MAX-ACCESS	read-write
		STATUS		current
		DESCRIPTION	"
			style='Checkbox'
			range='0..1'
			path='/FilmTools/Output/Cadence Datum/Use Datum Timecode '
		"
		::= { alchemistHdCtrlEntries 7246 }

	ftOutEditIndTriggerTem OBJECT-TYPE
		SYNTAX		RollCallString
		MAX-ACCESS	read-write
		STATUS		current
		DESCRIPTION	"
			style='Editable string'
			path='/FilmTools/Output/Cadence Datum/Datum Timecode'
		"
		::= { alchemistHdCtrlEntries 7247 }

	ftOutCadenceTem OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Output/2:3 Datum Cadence'
		"
		::= { alchemistHdCtrlEntries 7248 }

	ftOutCadenceValidTem OBJECT-TYPE
		SYNTAX		INTEGER {
					atDatumPoint(0),
					onValidTc(1)
				}
		MAX-ACCESS	read-write
		STATUS		current
		DESCRIPTION	"
			style='Radiobutton list'
			preset='onValidTc'
			path='/FilmTools/Output/2:3 Cadence reset'
		"
		::= { alchemistHdCtrlEntries 7249 }

	ftOutCadencePreTem OBJECT-TYPE
		SYNTAX		Integer32 (0..23)
		MAX-ACCESS	read-write
		STATUS		current
		DESCRIPTION	"
			style='Numeric control'
			range='0..23'
			preset='12'
			path='/FilmTools/Output/Max time pre-datum'
		"
		::= { alchemistHdCtrlEntries 7250 }

	ftIn05CadenceTem OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Input/0 and 5 Cadence'
		"
		::= { alchemistHdCtrlEntries 7251 }

	ftOut05CadenceTem OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Output/0 and 5 Cadence'
		"
		::= { alchemistHdCtrlEntries 7252 }

	dolby2Tone OBJECT-TYPE
		SYNTAX		INTEGER { enable(0), disable(1) }
		MAX-ACCESS	read-write
		STATUS		current
		DESCRIPTION	"
			style='Checkbox'
			range='0..1'
			path='/Dolby E/Dolby 2/Tone'
		"
		::= { alchemistHdCtrlEntries 7281 }

	dolby2ToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/Dolby E/Dolby 2/Tone Type'
		"
		::= { alchemistHdCtrlEntries 7282 }

	dolby2Mute OBJECT-TYPE
		SYNTAX		INTEGER { enable(0), disable(1) }
		MAX-ACCESS	read-write
		STATUS		current
		DESCRIPTION	"
			style='Checkbox'
			range='0..1'
			path='/Dolby E/Dolby 2/Mute'
		"
		::= { alchemistHdCtrlEntries 7283 }

	dolby2DelayOffset OBJECT-TYPE
		SYNTAX		Integer32 (0..250)
		MAX-ACCESS	read-write
		STATUS		current
		DESCRIPTION	"
			style='Numeric control'
			range='0mS..250mS'
			path='/Dolby E/Dolby 2/Delay Offset'
		"
		::= { alchemistHdCtrlEntries 7284 }

	dolby1Tone OBJECT-TYPE
		SYNTAX		INTEGER { enable(0), disable(1) }
		MAX-ACCESS	read-write
		STATUS		current
		DESCRIPTION	"
			style='Checkbox'
			range='0..1'
			path='/Dolby E/Dolby 1/Tone'
		"
		::= { alchemistHdCtrlEntries 7285 }

	dolby1ToneType OBJECT-TYPE
		SYNTAX		INTEGER {
					v1khz20Dbfs(0),
					v4khz20Dbfs(1),
					v1khz18Dbfs(2),
					v4khz18Dbfs(3)
				}
		MAX-ACCESS	read-write
		STATUS		current
		DESCRIPTION	"
			style='Radiobutton list'
			preset='v1khz20Dbfs'
			path='/Dolby E/Dolby 1/Tone Type'
		"
		::= { alchemistHdCtrlEntries 7286 }

	dolby1Mute OBJECT-TYPE
		SYNTAX		INTEGER { enable(0), disable(1) }
		MAX-ACCESS	read-write
		STATUS		current
		DESCRIPTION	"
			style='Checkbox'
			range='0..1'
			path='/Dolby E/Dolby 1/Mute'
		"
		::= { alchemistHdCtrlEntries 7287 }

	dolby1DelayOffset OBJECT-TYPE
		SYNTAX		Integer32 (0..250)
		MAX-ACCESS	read-write
		STATUS		current
		DESCRIPTION	"
			style='Numeric control'
			range='0mS..250mS'
			path='/Dolby E/Dolby 1/Delay Offset'
		"
		::= { alchemistHdCtrlEntries 7288 }

	dolby1DelayTotal OBJECT-TYPE
		SYNTAX		Integer32 (0..1000)
		MAX-ACCESS	read-only
		STATUS		current
		DESCRIPTION	"
			style='ReadOnly numeric'
			range='0mS..1000mS'
			path='/System/Debug/status/status1/Total'
		"
		::= { alchemistHdCtrlEntries 7290 }

	dolby2DelayTotal OBJECT-TYPE
		SYNTAX		Integer32 (0..1000)
		MAX-ACCESS	read-only
		STATUS		current
		DESCRIPTION	"
			style='ReadOnly numeric'
			range='0mS..1000mS'
			path='/System/Debug/status/status1/Total'
		"
		::= { alchemistHdCtrlEntries 7291 }

	inputDropFrameStatus OBJECT-TYPE
		SYNTAX		Integer32 (0..2)
		MAX-ACCESS	read-only
		STATUS		current
		DESCRIPTION	"
			style='ReadOnly numeric'
			range='0..2'
			path='/System/Debug/status/status1/input_drop_frame_status'
		"
		::= { alchemistHdCtrlEntries 7665 }

	outputADropFrameStatus OBJECT-TYPE
		SYNTAX		Integer32 (0..2)
		MAX-ACCESS	read-only
		STATUS		current
		DESCRIPTION	"
			style='ReadOnly numeric'
			range='0..2'
			path='/System/Debug/status/status1/output_a_drop_frame_status'
		"
		::= { alchemistHdCtrlEntries 7666 }

	outputBDropFrameStatus OBJECT-TYPE
		SYNTAX		Integer32 (0..2)
		MAX-ACCESS	read-only
		STATUS		current
		DESCRIPTION	"
			style='ReadOnly numeric'
			range='0..2'
			path='/System/Debug/status/status1/output_b_drop_frame_status'
		"
		::= { alchemistHdCtrlEntries 7667 }

	dispMemSetupSize OBJECT-TYPE
		SYNTAX		RollCallString
		MAX-ACCESS	read-only
		STATUS		current
		DESCRIPTION	"
			style='ReadOnly string'
			path='/System/Debug/status/status2/disp_mem_setup_size'
		"
		::= { alchemistHdCtrlEntries 8027 }

	audioActive1 OBJECT-TYPE
		SYNTAX		Integer32 (0..8)
		MAX-ACCESS	read-write
		STATUS		current
		DESCRIPTION	"
			style='Numeric control'
			range='0..8'
			path='/System/Debug/status/status1/Audio Monitor 1'
		"
		::= { alchemistHdCtrlEntries 8791 }

	audioActive2 OBJECT-TYPE
		SYNTAX		Integer32 (0..8)
		MAX-ACCESS	read-write
		STATUS		current
		DESCRIPTION	"
			style='Numeric control'
			range='0..8'
			path='/System/Debug/status/status1/Audio Monitor 2'
		"
		::= { alchemistHdCtrlEntries 8792 }

	audioActive3 OBJECT-TYPE
		SYNTAX		Integer32 (0..8)
		MAX-ACCESS	read-write
		STATUS		current
		DESCRIPTION	"
			style='Numeric control'
			range='0..8'
			path='/System/Debug/status/status1/Audio Monitor 3'
		"
		::= { alchemistHdCtrlEntries 8793 }

	audioActive4 OBJECT-TYPE
		SYNTAX		Integer32 (0..8)
		MAX-ACCESS	read-write
		STATUS		current
		DESCRIPTION	"
			style='Numeric control'
			range='0..8'
			path='/System/Debug/status/status1/Audio Monitor 4'
		"
		::= { alchemistHdCtrlEntries 8794 }

	audioActive5 OBJECT-TYPE
		SYNTAX		Integer32 (0..8)
		MAX-ACCESS	read-write
		STATUS		current
		DESCRIPTION	"
			style='Numeric control'
			range='0..8'
			path='/System/Debug/status/status1/Audio Monitor 5'
		"
		::= { alchemistHdCtrlEntries 8795 }

	audioActive6 OBJECT-TYPE
		SYNTAX		Integer32 (0..8)
		MAX-ACCESS	read-write
		STATUS		current
		DESCRIPTION	"
			style='Numeric control'
			range='0..8'
			path='/System/Debug/status/status1/Audio Monitor 6'
		"
		::= { alchemistHdCtrlEntries 8796 }

	audioActive7 OBJECT-TYPE
		SYNTAX		Integer32 (0..8)
		MAX-ACCESS	read-write
		STATUS		current
		DESCRIPTION	"
			style='Numeric control'
			range='0..8'
			path='/System/Debug/status/status1/Audio Monitor 7'
		"
		::= { alchemistHdCtrlEntries 8797 }

	audioActive8 OBJECT-TYPE
		SYNTAX		Integer32 (0..8)
		MAX-ACCESS	read-write
		STATUS		current
		DESCRIPTION	"
			style='Numeric control'
			range='0..8'
			path='/System/Debug/status/status1/Audio Monitor 8'
		"
		::= { alchemistHdCtrlEntries 8798 }

	dummy1 OBJECT-TYPE
		SYNTAX		INTEGER {
					v1(0),
					v2(1)
				}
		MAX-ACCESS	read-write
		STATUS		current
		DESCRIPTION	"
			style='Radiobutton list'
			preset='v1'
			path='/System 2/ '
		"
		::= { alchemistHdCtrlEntries 20000 }

	dummy2 OBJECT-TYPE
		SYNTAX		INTEGER {
					v1(0),
					v2(1)
				}
		MAX-ACCESS	read-write
		STATUS		current
		DESCRIPTION	"
			style='Radiobutton list'
			preset='v1'
			path='/System 2/ '
		"
		::= { alchemistHdCtrlEntries 20001 }

	release OBJECT-TYPE
		SYNTAX		Integer32 (0..1)
		MAX-ACCESS	read-write
		STATUS		current
		DESCRIPTION	"
			style='Numeric control'
			range='0..1'
			path='/System 2/'
		"
		::= { alchemistHdCtrlEntries 20003 }

	rtrkSelect1 OBJECT-TYPE
		SYNTAX		INTEGER {
					off(1),
					on(2)
				}
		MAX-ACCESS	read-write
		STATUS		current
		DESCRIPTION	"
			style='Radiobutton list'
			preset='off'
			path='/System/RollCall/RollTrack/RTrack-1/RollTrack 1'
		"
		::= { alchemistHdCtrlEntries 20131 }

	rtrkAddrId1 OBJECT-TYPE
		SYNTAX		RollCallString
		MAX-ACCESS	read-write
		STATUS		current
		DESCRIPTION	"
			style='RollTrack address*match-id'
			path='/System/RollCall/RollTrack/RTrack-1/RollTrack 1 Address'
		"
		::= { alchemistHdCtrlEntries 20132 }

	rtrkCmdVal1 OBJECT-TYPE
		SYNTAX		RollCallString
		MAX-ACCESS	read-write
		STATUS		current
		DESCRIPTION	"
			style='RollTrack command*value'
			path='/System/Debug/status/status2/Cmd*Val'
		"
		::= { alchemistHdCtrlEntries 20133 }

	rtrkStatus1 OBJECT-TYPE
		SYNTAX		RollCallString
		MAX-ACCESS	read-only
		STATUS		current
		DESCRIPTION	"
			style='ReadOnly string'
			path='/System/Debug/status/status2/Status'
		"
		::= { alchemistHdCtrlEntries 20134 }

	rtrkCmd1 OBJECT-TYPE
		SYNTAX		INTEGER {
					channel114(1),
					channel215(2),
					channel316(3),
					channel417(4)
				}
		MAX-ACCESS	read-write
		STATUS		current
		DESCRIPTION	"
			style='Radiobutton list'
			preset='channel114'
			path='/System/RollCall/RollTrack/RTrack-1/Audio Delay Channel'
		"
		::= { alchemistHdCtrlEntries 20135 }

	ipDhcp OBJECT-TYPE
		SYNTAX		INTEGER {
					disable(1),
					enable(2)
				}
		MAX-ACCESS	read-write
		STATUS		current
		DESCRIPTION	"
			style='Radiobutton list'
			preset='enable'
			path='/System/Ethernet/DHCP'
		"
		::= { alchemistHdCtrlEntries 20139 }

	ipAddr OBJECT-TYPE
		SYNTAX		IpAddress
		MAX-ACCESS	read-write
		STATUS		current
		DESCRIPTION	"
			style='IPv4 address'
			preset='192'
			path='/System/Ethernet/Address'
		"
		::= { alchemistHdCtrlEntries 20140 }

	ipMask OBJECT-TYPE
		SYNTAX		IpAddress
		MAX-ACCESS	read-write
		STATUS		current
		DESCRIPTION	"
			style='IPv4 netmask'
			preset='255'
			path='/System/Ethernet/Netmask'
		"
		::= { alchemistHdCtrlEntries 20141 }

	ipGate OBJECT-TYPE
		SYNTAX		IpAddress
		MAX-ACCESS	read-write
		STATUS		current
		DESCRIPTION	"
			style='IPv4 address'
			path='/System/Ethernet/Gateway'
		"
		::= { alchemistHdCtrlEntries 20142 }

	ipAddrGot OBJECT-TYPE
		SYNTAX		RollCallString
		MAX-ACCESS	read-only
		STATUS		current
		DESCRIPTION	"
			style='ReadOnly string'
			path='/System/Ethernet/Current address'
		"
		::= { alchemistHdCtrlEntries 20144 }

	ipDhcpGot OBJECT-TYPE
		SYNTAX		RollCallString
		MAX-ACCESS	read-only
		STATUS		current
		DESCRIPTION	"
			style='ReadOnly string'
			path='/System 2/ip_dhcp_got'
		"
		::= { alchemistHdCtrlEntries 20145 }

	ipGateGot OBJECT-TYPE
		SYNTAX		RollCallString
		MAX-ACCESS	read-only
		STATUS		current
		DESCRIPTION	"
			style='ReadOnly string'
			path='/System 2/ip_gate_got'
		"
		::= { alchemistHdCtrlEntries 20146 }

	ipMaskGot OBJECT-TYPE
		SYNTAX		RollCallString
		MAX-ACCESS	read-only
		STATUS		current
		DESCRIPTION	"
			style='ReadOnly string'
			path='/System 2/ip_mask_got'
		"
		::= { alchemistHdCtrlEntries 20147 }

	rcLogsrvAddrGot OBJECT-TYPE
		SYNTAX		RollCallString
		MAX-ACCESS	read-only
		STATUS		current
		DESCRIPTION	"
			style='ReadOnly string'
			path='/System 2/rc_log_srv_addr_got'
		"
		::= { alchemistHdCtrlEntries 20148 }

	rcLogsrvGot OBJECT-TYPE
		SYNTAX		RollCallString
		MAX-ACCESS	read-only
		STATUS		current
		DESCRIPTION	"
			style='ReadOnly string'
			path='/System 2/rc_logsrv_got'
		"
		::= { alchemistHdCtrlEntries 20149 }

	rtrkSelect2 OBJECT-TYPE
		SYNTAX		INTEGER {
					off(1),
					on(2)
				}
		MAX-ACCESS	read-write
		STATUS		current
		DESCRIPTION	"
			style='Radiobutton list'
			preset='off'
			path='/System/RollCall/RollTrack/RTrack-2/RollTrack 2'
		"
		::= { alchemistHdCtrlEntries 20161 }

	rtrkAddrId2 OBJECT-TYPE
		SYNTAX		RollCallString
		MAX-ACCESS	read-write
		STATUS		current
		DESCRIPTION	"
			style='RollTrack address*match-id'
			path='/System/RollCall/RollTrack/RTrack-2/RollTrack 2 Address'
		"
		::= { alchemistHdCtrlEntries 20162 }

	rtrkCmdVal2 OBJECT-TYPE
		SYNTAX		RollCallString
		MAX-ACCESS	read-write
		STATUS		current
		DESCRIPTION	"
			style='RollTrack command*value'
			path='/System/Debug/status/status2/Cmd*Val'
		"
		::= { alchemistHdCtrlEntries 20163 }

	rtrkStatus2 OBJECT-TYPE
		SYNTAX		RollCallString
		MAX-ACCESS	read-only
		STATUS		current
		DESCRIPTION	"
			style='ReadOnly string'
			path='/System/Debug/status/status2/Status'
		"
		::= { alchemistHdCtrlEntries 20164 }

	rtrkCmd2 OBJECT-TYPE
		SYNTAX		INTEGER {
					channel114(1),
					channel215(2),
					channel316(3),
					channel417(4)
				}
		MAX-ACCESS	read-write
		STATUS		current
		DESCRIPTION	"
			style='Radiobutton list'
			preset='channel114'
			path='/System/RollCall/RollTrack/RTrack-2/Audio Delay Channel'
		"
		::= { alchemistHdCtrlEntries 20165 }

	reservedCcTest OBJECT-TYPE
		SYNTAX		Integer32 (0..255)
		MAX-ACCESS	read-write
		STATUS		current
		DESCRIPTION	"
			style='Numeric control'
			range='0..255'
			path='/System 2/reserved_cc_test'
		"
		::= { alchemistHdCtrlEntries 30000 }

	dummyRedraw OBJECT-TYPE
		SYNTAX		Integer32
		MAX-ACCESS	read-write
		STATUS		current
		DESCRIPTION	"
			style='Numeric control'
			path='/System 2/'
		"
		::= { alchemistHdCtrlEntries 32760 }

	snmpPort OBJECT-TYPE
		SYNTAX		Integer32 (1..65535)
		MAX-ACCESS	read-write
		STATUS		current
		DESCRIPTION	"
			style='Numeric control'
			range='1..65535'
			preset='161'
			path='/System/SNMP/Physical/UDP Port'
		"
		::= { alchemistHdCtrlEntries 59906 }


-- ********************************
-- Status

	alchemistHdStatEntries OBJECT IDENTIFIER ::= { conversionAlchemistHd 2 }

	logInpLossStat OBJECT-TYPE
		SYNTAX		RollCallString
		MAX-ACCESS	read-only
		STATUS		current
		DESCRIPTION	"
			style='ReadOnly string'
			path='/System/Debug/status/status1/Inp Loss Status'
		"
		::= { alchemistHdStatEntries 5964 }

	logInpStdStat OBJECT-TYPE
		SYNTAX		RollCallString
		MAX-ACCESS	read-only
		STATUS		current
		DESCRIPTION	"
			style='ReadOnly string'
			path='/System/Debug/status/status1/Inp Std Status'
		"
		::= { alchemistHdStatEntries 5965 }

	logOutAStdStat OBJECT-TYPE
		SYNTAX		RollCallString
		MAX-ACCESS	read-only
		STATUS		current
		DESCRIPTION	"
			style='ReadOnly string'
			path='/System/Debug/status/status1/Out A Std Status'
		"
		::= { alchemistHdStatEntries 5968 }

	logOutBStdStat OBJECT-TYPE
		SYNTAX		RollCallString
		MAX-ACCESS	read-only
		STATUS		current
		DESCRIPTION	"
			style='ReadOnly string'
			path='/System/Debug/status/status1/Out B Std Status'
		"
		::= { alchemistHdStatEntries 5969 }

	logRefStdStat OBJECT-TYPE
		SYNTAX		RollCallString
		MAX-ACCESS	read-only
		STATUS		current
		DESCRIPTION	"
			style='ReadOnly string'
			path='/System/Debug/status/status1/Ref Std Status'
		"
		::= { alchemistHdStatEntries 5970 }

	logStatusStat OBJECT-TYPE
		SYNTAX		RollCallString
		MAX-ACCESS	read-only
		STATUS		current
		DESCRIPTION	"
			style='ReadOnly string'
			path='/System/Debug/status/status1/Status Status'
		"
		::= { alchemistHdStatEntries 5972 }


-- ********************************
-- Config

	alchemistHdConfEntries OBJECT IDENTIFIER ::= { conversionAlchemistHd 3 }

	snmpEnab OBJECT-TYPE
		SYNTAX		INTEGER { enable(0), disable(1) }
		MAX-ACCESS	read-write
		STATUS		current
		DESCRIPTION	"
			style='Checkbox'
			path='/System/SNMP/Physical/Enable SNMP'
		"
		::= { alchemistHdConfEntries 59900 }

	snmpRdcommunity OBJECT-TYPE
		SYNTAX		RollCallString
		MAX-ACCESS	read-write
		STATUS		current
		DESCRIPTION	"
			style='Editable string'
			path='/System/SNMP/Interface/Read Community'
		"
		::= { alchemistHdConfEntries 59902 }

	snmpWrcommunity OBJECT-TYPE
		SYNTAX		RollCallString
		MAX-ACCESS	read-write
		STATUS		current
		DESCRIPTION	"
			style='Editable string'
			path='/System/SNMP/Interface/Write Community'
		"
		::= { alchemistHdConfEntries 59903 }

	snmpContact OBJECT-TYPE
		SYNTAX		RollCallString
		MAX-ACCESS	read-write
		STATUS		current
		DESCRIPTION	"
			style='Editable string'
			path='/System/SNMP/Interface/Contact eMail'
		"
		::= { alchemistHdConfEntries 59904 }

	snmpLocation OBJECT-TYPE
		SYNTAX		RollCallString
		MAX-ACCESS	read-write
		STATUS		current
		DESCRIPTION	"
			style='Editable string'
			path='/System/SNMP/Interface/Physical Location'
		"
		::= { alchemistHdConfEntries 59905 }

	snmpSendall OBJECT-TYPE
		SYNTAX		INTEGER { ready(0), trigger(1) }
		MAX-ACCESS	read-write
		STATUS		current
		DESCRIPTION	"
			style='Event button'
			path='/System/SNMP/Physical/Resend all Traps'
		"
		::= { alchemistHdConfEntries 59907 }

	snmpTrap1Enab OBJECT-TYPE
		SYNTAX		INTEGER { enable(0), disable(1) }
		MAX-ACCESS	read-write
		STATUS		current
		DESCRIPTION	"
			style='Checkbox'
			path='/System/SNMP/Traps/Trap 1/Trap 1 Enable'
		"
		::= { alchemistHdConfEntries 59910 }

	snmpTrap1Addr OBJECT-TYPE
		SYNTAX		IpAddress
		MAX-ACCESS	read-write
		STATUS		current
		DESCRIPTION	"
			style='IPv4 address'
			path='/System/SNMP/Traps/Trap 1/Trap 1 IP Address'
		"
		::= { alchemistHdConfEntries 59911 }

	snmpTrap1Port OBJECT-TYPE
		SYNTAX		Integer32 (1..65535)
		MAX-ACCESS	read-write
		STATUS		current
		DESCRIPTION	"
			style='Numeric control'
			range='1..65535'
			preset='162'
			path='/System/SNMP/Traps/Trap 1/Trap 1 UDP Port'
		"
		::= { alchemistHdConfEntries 59912 }

	snmpTrap1Community OBJECT-TYPE
		SYNTAX		RollCallString
		MAX-ACCESS	read-write
		STATUS		current
		DESCRIPTION	"
			style='Editable string'
			path='/System/SNMP/Traps/Trap 1/Trap 1 Community'
		"
		::= { alchemistHdConfEntries 59913 }

	snmpTrap2Enab OBJECT-TYPE
		SYNTAX		INTEGER { enable(0), disable(1) }
		MAX-ACCESS	read-write
		STATUS		current
		DESCRIPTION	"
			style='Checkbox'
			path='/System/SNMP/Traps/Trap 2/Trap 2 Enable'
		"
		::= { alchemistHdConfEntries 59920 }

	snmpTrap2Addr OBJECT-TYPE
		SYNTAX		IpAddress
		MAX-ACCESS	read-write
		STATUS		current
		DESCRIPTION	"
			style='IPv4 address'
			path='/System/SNMP/Traps/Trap 2/Trap 2 IP Address'
		"
		::= { alchemistHdConfEntries 59921 }

	snmpTrap2Port OBJECT-TYPE
		SYNTAX		Integer32 (1..65535)
		MAX-ACCESS	read-write
		STATUS		current
		DESCRIPTION	"
			style='Numeric control'
			range='1..65535'
			preset='162'
			path='/System/SNMP/Traps/Trap 2/Trap 2 UDP Port'
		"
		::= { alchemistHdConfEntries 59922 }

	snmpTrap2Community OBJECT-TYPE
		SYNTAX		RollCallString
		MAX-ACCESS	read-write
		STATUS		current
		DESCRIPTION	"
			style='Editable string'
			path='/System/SNMP/Traps/Trap 2/Trap 2 Community'
		"
		::= { alchemistHdConfEntries 59923 }

	snmpTrap3Enab OBJECT-TYPE
		SYNTAX		INTEGER { enable(0), disable(1) }
		MAX-ACCESS	read-write
		STATUS		current
		DESCRIPTION	"
			style='Checkbox'
			path='/System/SNMP/Traps/Trap 3/Trap 3 Enable'
		"
		::= { alchemistHdConfEntries 59930 }

	snmpTrap3Addr OBJECT-TYPE
		SYNTAX		IpAddress
		MAX-ACCESS	read-write
		STATUS		current
		DESCRIPTION	"
			style='IPv4 address'
			path='/System/SNMP/Traps/Trap 3/Trap 3 IP Address'
		"
		::= { alchemistHdConfEntries 59931 }

	snmpTrap3Port OBJECT-TYPE
		SYNTAX		Integer32 (1..65535)
		MAX-ACCESS	read-write
		STATUS		current
		DESCRIPTION	"
			style='Numeric control'
			range='1..65535'
			preset='162'
			path='/System/SNMP/Traps/Trap 3/Trap 3 UDP Port'
		"
		::= { alchemistHdConfEntries 59932 }

	snmpTrap3Community OBJECT-TYPE
		SYNTAX		RollCallString
		MAX-ACCESS	read-write
		STATUS		current
		DESCRIPTION	"
			style='Editable string'
			path='/System/SNMP/Traps/Trap 3/Trap 3 Community'
		"
		::= { alchemistHdConfEntries 59933 }

	snmpTrap4Enab OBJECT-TYPE
		SYNTAX		INTEGER { enable(0), disable(1) }
		MAX-ACCESS	read-write
		STATUS		current
		DESCRIPTION	"
			style='Checkbox'
			path='/System/SNMP/Traps/Trap 4/Trap 4 Enable'
		"
		::= { alchemistHdConfEntries 59940 }

	snmpTrap4Addr OBJECT-TYPE
		SYNTAX		IpAddress
		MAX-ACCESS	read-write
		STATUS		current
		DESCRIPTION	"
			style='IPv4 address'
			path='/System/SNMP/Traps/Trap 4/Trap 4 IP Address'
		"
		::= { alchemistHdConfEntries 59941 }

	snmpTrap4Port OBJECT-TYPE
		SYNTAX		Integer32 (1..65535)
		MAX-ACCESS	read-write
		STATUS		current
		DESCRIPTION	"
			style='Numeric control'
			range='1..65535'
			preset='162'
			path='/System/SNMP/Traps/Trap 4/Trap 4 UDP Port'
		"
		::= { alchemistHdConfEntries 59942 }

	snmpTrap4Community OBJECT-TYPE
		SYNTAX		RollCallString
		MAX-ACCESS	read-write
		STATUS		current
		DESCRIPTION	"
			style='Editable string'
			path='/System/SNMP/Traps/Trap 4/Trap 4 Community'
		"
		::= { alchemistHdConfEntries 59943 }

END
