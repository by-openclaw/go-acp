-- ************************************************************************************
--       Product:LC350

--       Product Id#:736
--       Command Set:1
--       Filename:SNELL-LC350.mib
--       Source File:LC350

--       Source Ver:1.1..11
--       Date:18/09/2014
--       Time:15:48
--
--       Copyright (c) 2014 Snell Ltd
--       All rights reserved.
--
-- ************************************************************************************

SNELL-LC350-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    conversionLC350,
    conversionLC350Mib
        FROM SNELL-WILCOX-PRODUCT-REG;

conversionLC350Mi MODULE-IDENTITY
    LAST-UPDATED "1409181548Z"
    ORGANIZATION "Snell Ltd"
    CONTACT-INFO
        "Primary Author:Generated by Kudos Lite PCMIB tool

         postal:    Hartman House
                    Danehill
                    Lower Earley,
                    Reading, Berks
                    RG6 4PB
         phone:     +44 (0)118 9866123
         email:     support.uk@snellgroup.com"
    DESCRIPTION
        "This file defines the Snell card, command set translations."
    
    REVISION "1409181548Z"
    DESCRIPTION "Sole revision, this file generated on each release"
    ::= { conversionLC350Mib 1 }




--********************************************************************************
--*
--*  Snell Card:
--*  command set:
--*  list commands/menus:
--*
--******************************************************************************
    lC350 OBJECT IDENTIFIER ::= { conversionLC350 0 }
    lC350NoteEntries OBJECT IDENTIFIER ::= { lC350 0 }


    iSerialNumberStatus NOTIFICATION-TYPE
        OBJECTS            { iMiscLoggingSerialNumberStatus } 
        STATUS            current
        DESCRIPTION
                "CMNT: - 
                 TYPE: - Display
                 PAGE: - Misc. Logging
                    Serial Number Status  cmdID= 5000  "
        ::= { lC350NoteEntries 5000 }


    iUpTimeStatus NOTIFICATION-TYPE
        OBJECTS            { iMiscLoggingUpTimeStatus } 
        STATUS            current
        DESCRIPTION
                "CMNT: - 
                 TYPE: - Display
                 PAGE: - Misc. Logging
                    Up Time Status  cmdID= 5001  "
        ::= { lC350NoteEntries 5001 }


    iPowerUsageStateStatus NOTIFICATION-TYPE
        OBJECTS            { iMiscLoggingPowerUsageStateStatus } 
        STATUS            current
        DESCRIPTION
                "CMNT: - 
                 TYPE: - Display
                 PAGE: - Misc. Logging
                    Power Usage State Status  cmdID= 5002  "
        ::= { lC350NoteEntries 5002 }


    iPowerUsageState2Status NOTIFICATION-TYPE
        OBJECTS            { iMiscLoggingPowerUsageState2Status } 
        STATUS            current
        DESCRIPTION
                "CMNT: - 
                 TYPE: - Display
                 PAGE: - Misc. Logging
                    Power Usage State 2 Status  cmdID= 5003  "
        ::= { lC350NoteEntries 5003 }


    iVideoInput1Type NOTIFICATION-TYPE
        OBJECTS            { iVideoLoggingVideoInput1Type } 
        STATUS            current
        DESCRIPTION
                "CMNT: - 
                 TYPE: - Display
                 PAGE: - Video Logging
                    Video Input 1 Type  cmdID= 5004  "
        ::= { lC350NoteEntries 5004 }


    iVideoInput1State NOTIFICATION-TYPE
        OBJECTS            { iVideoLoggingVideoInput1State } 
        STATUS            current
        DESCRIPTION
                "CMNT: - 
                 TYPE: - Display
                 PAGE: - Video Logging
                    Video Input 1 State  cmdID= 5005  "
        ::= { lC350NoteEntries 5005 }


    iVideoInput1Std NOTIFICATION-TYPE
        OBJECTS            { iVideoLoggingVideoInput1Std } 
        STATUS            current
        DESCRIPTION
                "CMNT: - 
                 TYPE: - Display
                 PAGE: - Video Logging
                    Video Input 1 Std  cmdID= 5006  "
        ::= { lC350NoteEntries 5006 }


    iVideoInput2Type NOTIFICATION-TYPE
        OBJECTS            { iVideoLoggingVideoInput2Type } 
        STATUS            current
        DESCRIPTION
                "CMNT: - 
                 TYPE: - Display
                 PAGE: - Video Logging
                    Video Input 2 Type  cmdID= 5007  "
        ::= { lC350NoteEntries 5007 }


    iVideoInput2State NOTIFICATION-TYPE
        OBJECTS            { iVideoLoggingVideoInput2State } 
        STATUS            current
        DESCRIPTION
                "CMNT: - 
                 TYPE: - Display
                 PAGE: - Video Logging
                    Video Input 2 State  cmdID= 5008  "
        ::= { lC350NoteEntries 5008 }


    iVideoInput2Std NOTIFICATION-TYPE
        OBJECTS            { iVideoLoggingVideoInput2Std } 
        STATUS            current
        DESCRIPTION
                "CMNT: - 
                 TYPE: - Display
                 PAGE: - Video Logging
                    Video Input 2 Std  cmdID= 5009  "
        ::= { lC350NoteEntries 5009 }


    iVideoInput3Type NOTIFICATION-TYPE
        OBJECTS            { iVideoLoggingVideoInput3Type } 
        STATUS            current
        DESCRIPTION
                "CMNT: - 
                 TYPE: - Display
                 PAGE: - Video Logging
                    Video Input 3 Type  cmdID= 5010  "
        ::= { lC350NoteEntries 5010 }


    iVideoInput3State NOTIFICATION-TYPE
        OBJECTS            { iVideoLoggingVideoInput3State } 
        STATUS            current
        DESCRIPTION
                "CMNT: - 
                 TYPE: - Display
                 PAGE: - Video Logging
                    Video Input 3 State  cmdID= 5011  "
        ::= { lC350NoteEntries 5011 }


    iVideoInput3Std NOTIFICATION-TYPE
        OBJECTS            { iVideoLoggingVideoInput3Std } 
        STATUS            current
        DESCRIPTION
                "CMNT: - 
                 TYPE: - Display
                 PAGE: - Video Logging
                    Video Input 3 Std  cmdID= 5012  "
        ::= { lC350NoteEntries 5012 }


    iVideoInput4Type NOTIFICATION-TYPE
        OBJECTS            { iVideoLoggingVideoInput4Type } 
        STATUS            current
        DESCRIPTION
                "CMNT: - 
                 TYPE: - Display
                 PAGE: - Video Logging
                    Video Input 4 Type  cmdID= 5013  "
        ::= { lC350NoteEntries 5013 }


    iVideoInput4State NOTIFICATION-TYPE
        OBJECTS            { iVideoLoggingVideoInput4State } 
        STATUS            current
        DESCRIPTION
                "CMNT: - 
                 TYPE: - Display
                 PAGE: - Video Logging
                    Video Input 4 State  cmdID= 5014  "
        ::= { lC350NoteEntries 5014 }


    iVideoInput4Std NOTIFICATION-TYPE
        OBJECTS            { iVideoLoggingVideoInput4Std } 
        STATUS            current
        DESCRIPTION
                "CMNT: - 
                 TYPE: - Display
                 PAGE: - Video Logging
                    Video Input 4 Std  cmdID= 5015  "
        ::= { lC350NoteEntries 5015 }


    iVideoInput5Type NOTIFICATION-TYPE
        OBJECTS            { iVideoLoggingVideoInput5Type } 
        STATUS            current
        DESCRIPTION
                "CMNT: - 
                 TYPE: - Display
                 PAGE: - Video Logging
                    Video Input 5 Type  cmdID= 5016  "
        ::= { lC350NoteEntries 5016 }


    iVideoInput5State NOTIFICATION-TYPE
        OBJECTS            { iVideoLoggingVideoInput5State } 
        STATUS            current
        DESCRIPTION
                "CMNT: - 
                 TYPE: - Display
                 PAGE: - Video Logging
                    Video Input 5 State  cmdID= 5017  "
        ::= { lC350NoteEntries 5017 }


    iVideoInput5Std NOTIFICATION-TYPE
        OBJECTS            { iVideoLoggingVideoInput5Std } 
        STATUS            current
        DESCRIPTION
                "CMNT: - 
                 TYPE: - Display
                 PAGE: - Video Logging
                    Video Input 5 Std  cmdID= 5018  "
        ::= { lC350NoteEntries 5018 }


    iVideoOutput1Type NOTIFICATION-TYPE
        OBJECTS            { iVideoLoggingVideoOutput1Type } 
        STATUS            current
        DESCRIPTION
                "CMNT: - 
                 TYPE: - Display
                 PAGE: - Video Logging
                    Video Output 1 Type  cmdID= 5019  "
        ::= { lC350NoteEntries 5019 }


    iVideoOutput1State NOTIFICATION-TYPE
        OBJECTS            { iVideoLoggingVideoOutput1State } 
        STATUS            current
        DESCRIPTION
                "CMNT: - 
                 TYPE: - Display
                 PAGE: - Video Logging
                    Video Output 1 State  cmdID= 5020  "
        ::= { lC350NoteEntries 5020 }


    iVideoOutput1Std NOTIFICATION-TYPE
        OBJECTS            { iVideoLoggingVideoOutput1Std } 
        STATUS            current
        DESCRIPTION
                "CMNT: - 
                 TYPE: - Display
                 PAGE: - Video Logging
                    Video Output 1 Std  cmdID= 5021  "
        ::= { lC350NoteEntries 5021 }


    iAudioOutputEmbPair1type NOTIFICATION-TYPE
        OBJECTS            { iAudioLoggingAudioOutputEmbPair1type } 
        STATUS            current
        DESCRIPTION
                "CMNT: - 
                 TYPE: - Display
                 PAGE: - Audio Logging
                    Audio Output Emb.Pair 1 type  cmdID= 5022  "
        ::= { lC350NoteEntries 5022 }


    iAudioOutputEmbPair2type NOTIFICATION-TYPE
        OBJECTS            { iAudioLoggingAudioOutputEmbPair2type } 
        STATUS            current
        DESCRIPTION
                "CMNT: - 
                 TYPE: - Display
                 PAGE: - Audio Logging
                    Audio Output Emb.Pair 2 type  cmdID= 5023  "
        ::= { lC350NoteEntries 5023 }


    iAudioOutputEmbPair3type NOTIFICATION-TYPE
        OBJECTS            { iAudioLoggingAudioOutputEmbPair3type } 
        STATUS            current
        DESCRIPTION
                "CMNT: - 
                 TYPE: - Display
                 PAGE: - Audio Logging
                    Audio Output Emb.Pair 3 type  cmdID= 5024  "
        ::= { lC350NoteEntries 5024 }


    iAudioOutputEmbPair4type NOTIFICATION-TYPE
        OBJECTS            { iAudioLoggingAudioOutputEmbPair4type } 
        STATUS            current
        DESCRIPTION
                "CMNT: - 
                 TYPE: - Display
                 PAGE: - Audio Logging
                    Audio Output Emb.Pair 4 type  cmdID= 5025  "
        ::= { lC350NoteEntries 5025 }


    iAudioOutputEmbPair5type NOTIFICATION-TYPE
        OBJECTS            { iAudioLoggingAudioOutputEmbPair5type } 
        STATUS            current
        DESCRIPTION
                "CMNT: - 
                 TYPE: - Display
                 PAGE: - Audio Logging
                    Audio Output Emb.Pair 5 type  cmdID= 5026  "
        ::= { lC350NoteEntries 5026 }


    iAudioOutputEmbPair6type NOTIFICATION-TYPE
        OBJECTS            { iAudioLoggingAudioOutputEmbPair6type } 
        STATUS            current
        DESCRIPTION
                "CMNT: - 
                 TYPE: - Display
                 PAGE: - Audio Logging
                    Audio Output Emb.Pair 6 type  cmdID= 5027  "
        ::= { lC350NoteEntries 5027 }


    iAudioOutputEmbPair7type NOTIFICATION-TYPE
        OBJECTS            { iAudioLoggingAudioOutputEmbPair7type } 
        STATUS            current
        DESCRIPTION
                "CMNT: - 
                 TYPE: - Display
                 PAGE: - Audio Logging
                    Audio Output Emb.Pair 7 type  cmdID= 5028  "
        ::= { lC350NoteEntries 5028 }


    iAudioOutputEmbPair8type NOTIFICATION-TYPE
        OBJECTS            { iAudioLoggingAudioOutputEmbPair8type } 
        STATUS            current
        DESCRIPTION
                "CMNT: - 
                 TYPE: - Display
                 PAGE: - Audio Logging
                    Audio Output Emb.Pair 8 type  cmdID= 5029  "
        ::= { lC350NoteEntries 5029 }


    iAudioOutputEmbPair1state NOTIFICATION-TYPE
        OBJECTS            { iAudioLoggingAudioOutputEmbPair1state } 
        STATUS            current
        DESCRIPTION
                "CMNT: - 
                 TYPE: - Display
                 PAGE: - Audio Logging
                    Audio Output Emb.Pair 1 state  cmdID= 5030  "
        ::= { lC350NoteEntries 5030 }


    iAudioOutputEmbPair2state NOTIFICATION-TYPE
        OBJECTS            { iAudioLoggingAudioOutputEmbPair2state } 
        STATUS            current
        DESCRIPTION
                "CMNT: - 
                 TYPE: - Display
                 PAGE: - Audio Logging
                    Audio Output Emb.Pair 2 state  cmdID= 5031  "
        ::= { lC350NoteEntries 5031 }


    iAudioOutputEmbPair3state NOTIFICATION-TYPE
        OBJECTS            { iAudioLoggingAudioOutputEmbPair3state } 
        STATUS            current
        DESCRIPTION
                "CMNT: - 
                 TYPE: - Display
                 PAGE: - Audio Logging
                    Audio Output Emb.Pair 3 state  cmdID= 5032  "
        ::= { lC350NoteEntries 5032 }


    iAudioOutputEmbPair4state NOTIFICATION-TYPE
        OBJECTS            { iAudioLoggingAudioOutputEmbPair4state } 
        STATUS            current
        DESCRIPTION
                "CMNT: - 
                 TYPE: - Display
                 PAGE: - Audio Logging
                    Audio Output Emb.Pair 4 state  cmdID= 5033  "
        ::= { lC350NoteEntries 5033 }


    iAudioOutputEmbPair5state NOTIFICATION-TYPE
        OBJECTS            { iAudioLoggingAudioOutputEmbPair5state } 
        STATUS            current
        DESCRIPTION
                "CMNT: - 
                 TYPE: - Display
                 PAGE: - Audio Logging
                    Audio Output Emb.Pair 5 state  cmdID= 5034  "
        ::= { lC350NoteEntries 5034 }


    iAudioOutputEmbPair6state NOTIFICATION-TYPE
        OBJECTS            { iAudioLoggingAudioOutputEmbPair6state } 
        STATUS            current
        DESCRIPTION
                "CMNT: - 
                 TYPE: - Display
                 PAGE: - Audio Logging
                    Audio Output Emb.Pair 6 state  cmdID= 5035  "
        ::= { lC350NoteEntries 5035 }


    iAudioOutputEmbPair7state NOTIFICATION-TYPE
        OBJECTS            { iAudioLoggingAudioOutputEmbPair7state } 
        STATUS            current
        DESCRIPTION
                "CMNT: - 
                 TYPE: - Display
                 PAGE: - Audio Logging
                    Audio Output Emb.Pair 7 state  cmdID= 5036  "
        ::= { lC350NoteEntries 5036 }


    iAudioOutputEmbPair8state NOTIFICATION-TYPE
        OBJECTS            { iAudioLoggingAudioOutputEmbPair8state } 
        STATUS            current
        DESCRIPTION
                "CMNT: - 
                 TYPE: - Display
                 PAGE: - Audio Logging
                    Audio Output Emb.Pair 8 state  cmdID= 5037  "
        ::= { lC350NoteEntries 5037 }
    lC350CtrlEntries OBJECT IDENTIFIER ::= { lC350 1 }


    iInputSourceCh1InputSelect OBJECT-TYPE
        SYNTAX            INTEGER {
                            valSDI1(0),
                            valSDI2(1),
                            valSFP1(2),
                            valSFP2(3),
                            valCVBS(4)
                            }
        MAX-ACCESS        read-write
        STATUS            current
        DESCRIPTION
                "CMNT: - 
                 TYPE: - RadiobuttonList
                 PAGE: - Input
                    Input Select  cmdID= 10000
                    SDI 1  value= 0
                    SDI 2  value= 1
                    SFP 1  value= 2
                    SFP 2  value= 3
                    CVBS  value= 4  "
        ::= { lC350CtrlEntries 10000 }


    iInputSourceCh1StatusSDI1 OBJECT-TYPE
        SYNTAX            RollCallString
        MAX-ACCESS        read-only
        STATUS            current
        DESCRIPTION
                "CMNT: - 
                 TYPE: - Display
                 PAGE: - Input Source Ch 1
                    SDI 1  cmdID= 10001  "
        ::= { lC350CtrlEntries 10001 }


    iInputSourceCh1StatusSDI2 OBJECT-TYPE
        SYNTAX            RollCallString
        MAX-ACCESS        read-only
        STATUS            current
        DESCRIPTION
                "CMNT: - 
                 TYPE: - Display
                 PAGE: - Input Source Ch 1
                    SDI 2  cmdID= 10002  "
        ::= { lC350CtrlEntries 10002 }


    iInputSourceCh1StatusSFP1 OBJECT-TYPE
        SYNTAX            RollCallString
        MAX-ACCESS        read-only
        STATUS            current
        DESCRIPTION
                "CMNT: - 
                 TYPE: - Display
                 PAGE: - Input Source Ch 1
                    SFP 1  cmdID= 10004  "
        ::= { lC350CtrlEntries 10004 }


    iInputSourceCh1StatusSFP2 OBJECT-TYPE
        SYNTAX            RollCallString
        MAX-ACCESS        read-only
        STATUS            current
        DESCRIPTION
                "CMNT: - 
                 TYPE: - Display
                 PAGE: - Input Source Ch 1
                    SFP 2  cmdID= 10005  "
        ::= { lC350CtrlEntries 10005 }


    iInputSourceCh1StatusCVBS OBJECT-TYPE
        SYNTAX            RollCallString
        MAX-ACCESS        read-only
        STATUS            current
        DESCRIPTION
                "CMNT: - 
                 TYPE: - Display
                 PAGE: - Input Source Ch 1
                    CVBS  cmdID= 10003  "
        ::= { lC350CtrlEntries 10003 }


    iInputSourceCh1StatusCurrentInputStandard OBJECT-TYPE
        SYNTAX            RollCallString
        MAX-ACCESS        read-only
        STATUS            current
        DESCRIPTION
                "CMNT: - 
                 TYPE: - Display
                 PAGE: - Input Source Ch 1
                    Current Input Standard  cmdID= 10006  "
        ::= { lC350CtrlEntries 10006 }


    iCVBSDecoderSetupSource OBJECT-TYPE
        SYNTAX            INTEGER {
                            valCVBS1(0),
                            valCVBS2(1),
                            valYC(2)
                            }
        MAX-ACCESS        read-write
        STATUS            current
        DESCRIPTION
                "CMNT: - 
                 TYPE: - RadiobuttonList
                 PAGE: - CVBS Decoder
                    Source  cmdID= 10007
                    CVBS1  value= 0
                    CVBS2  value= 1
                    Y/C  value= 2  "
        ::= { lC350CtrlEntries 10007 }


    iCVBSDecoderSetupACC OBJECT-TYPE
        SYNTAX            INTEGER { disable(0), enable(1)  }
        MAX-ACCESS        read-write
        STATUS            current
        DESCRIPTION
                "CMNT: - 
                 TYPE: - Checkbox
                 PAGE: - CVBS Decoder
                    ACC  cmdID= 10008  "
        ::= { lC350CtrlEntries 10008 }


    iCVBSDecoderSetupCTI OBJECT-TYPE
        SYNTAX            INTEGER { disable(0), enable(1)  }
        MAX-ACCESS        read-write
        STATUS            current
        DESCRIPTION
                "CMNT: - 
                 TYPE: - Checkbox
                 PAGE: - CVBS Decoder
                    CTI  cmdID= 10009  "
        ::= { lC350CtrlEntries 10009 }


    iCVBSDecoderSetupNTSCHue OBJECT-TYPE
        SYNTAX            INTEGER
        MAX-ACCESS        read-write
        STATUS            current
        DESCRIPTION
                "CMNT: - 
                 TYPE: - Number
                 PAGE: - CVBS Decoder
                    NTSC Hue  cmdID= 10011
                    min= -90  max= 90  step= 1  format= %d deg  div_scale= 1  preset= 0
                    Min = -90 deg  Max = 90 deg  Step = 1 deg  Preset = 0 deg  "
        ::= { lC350CtrlEntries 10011 }


    iCVBSDecoderSetupPedestal OBJECT-TYPE
        SYNTAX            INTEGER {
                            valOff(0),
                            valOn(1)
                            }
        MAX-ACCESS        read-write
        STATUS            current
        DESCRIPTION
                "CMNT: - 
                 TYPE: - RadiobuttonList
                 PAGE: - CVBS Decoder
                    Pedestal  cmdID= 10010
                    Off  value= 0
                    On  value= 1  "
        ::= { lC350CtrlEntries 10010 }


    iCVBSDecoderCalibrationLumaGain OBJECT-TYPE
        SYNTAX            INTEGER
        MAX-ACCESS        read-write
        STATUS            current
        DESCRIPTION
                "CMNT: - 
                 TYPE: - Number
                 PAGE: - CVBS Decoder
                    Luma Gain  cmdID= 10012
                    min= -40  max= 40  step= 1  format= %d  div_scale= 1  preset= 0
                    Min = -40  Max = 40  Step = 1  Preset = 0  "
        ::= { lC350CtrlEntries 10012 }


    iCVBSDecoderCalibrationSaveDecoder OBJECT-TYPE
        SYNTAX            INTEGER { noAction(0),valSaveDecoder(1) }
        MAX-ACCESS        read-write
        STATUS            current
        DESCRIPTION
                "CMNT: - 
                 TYPE: - Button
                 PAGE: - CVBS Decoder
                    Save Decoder  cmdID= 10013
                    value= 1  "
        ::= { lC350CtrlEntries 10013 }


    iOutputStandardStandard OBJECT-TYPE
        SYNTAX            INTEGER {
                            val62550i(2),
                            val52559i(3),
                            val72023p(4),
                            val72024p(5),
                            val72025p(6),
                            val72029p(7),
                            val72030p(8),
                            val72050p(9),
                            val72059p(10),
                            val72060p(11),
                            val108023p(12),
                            val108024p(13),
                            val108025p(14),
                            val108029p(15),
                            val108030p(16),
                            val108050i(17),
                            val108059i(18),
                            val108060i(19),
                            val108023psf(20),
                            val108024psf(21),
                            val108025psf(50),
                            val108029psf(51),
                            val108050pnA(22),
                            val108059pnA(23),
                            val108060pnA(24),
                            val108050pnB(25),
                            val108059pnB(26),
                            val108060pnB(27)
                            }
        MAX-ACCESS        read-write
        STATUS            current
        DESCRIPTION
                "CMNT: - 
                 TYPE: - RadiobuttonList
                 PAGE: - Output
                    Standard  cmdID= 10015
                    625 50i  value= 2
                    525 59i  value= 3
                    720 23p  value= 4
                    720 24p  value= 5
                    720 25p  value= 6
                    720 29p  value= 7
                    720 30p  value= 8
                    720 50p  value= 9
                    720 59p  value= 10
                    720 60p  value= 11
                    1080 23p  value= 12
                    1080 24p  value= 13
                    1080 25p  value= 14
                    1080 29p  value= 15
                    1080 30p  value= 16
                    1080 50i  value= 17
                    1080 59i  value= 18
                    1080 60i  value= 19
                    1080 23psf  value= 20
                    1080 24psf  value= 21
                    1080 25psf  value= 50
                    1080 29psf  value= 51
                    1080 50p-A  value= 22
                    1080 59p-A  value= 23
                    1080 60p-A  value= 24
                    1080 50p-B  value= 25
                    1080 59p-B  value= 26
                    1080 60p-B  value= 27  "
        ::= { lC350CtrlEntries 10015 }


    iOutputStandardFormat OBJECT-TYPE
        SYNTAX            INTEGER {
                            val525625(0),
                            val720p(1),
                            val1080i(2),
                            val1080pnA(3),
                            val1080pnB(4)
                            }
        MAX-ACCESS        read-write
        STATUS            current
        DESCRIPTION
                "CMNT: - 
                 TYPE: - RadiobuttonList
                 PAGE: - Output
                    Format  cmdID= 10016
                    525/625  value= 0
                    720p  value= 1
                    1080i  value= 2
                    1080p-A  value= 3
                    1080p-B  value= 4  "
        ::= { lC350CtrlEntries 10016 }


    iOutputStandardDefaultFieldRate OBJECT-TYPE
        SYNTAX            INTEGER {
                            valLastValidInput(0),
                            val23Hz(1),
                            val24Hz(2),
                            val25Hz(3),
                            val29Hz(4),
                            val30Hz(5),
                            val50Hz(6),
                            val59Hz(7),
                            val60Hz(8)
                            }
        MAX-ACCESS        read-write
        STATUS            current
        DESCRIPTION
                "CMNT: - 
                 TYPE: - RadiobuttonList
                 PAGE: - Output
                    Default Field Rate  cmdID= 10017
                    Last Valid Input  value= 0
                    23 Hz  value= 1
                    24 Hz  value= 2
                    25 Hz  value= 3
                    29 Hz  value= 4
                    30 Hz  value= 5
                    50 Hz  value= 6
                    59 Hz  value= 7
                    60 Hz  value= 8  "
        ::= { lC350CtrlEntries 10017 }


    iOutputStandardCurrentOutputStandard OBJECT-TYPE
        SYNTAX            RollCallString
        MAX-ACCESS        read-only
        STATUS            current
        DESCRIPTION
                "CMNT: - 
                 TYPE: - Display
                 PAGE: - Output
                    Current Output Standard  cmdID= 10018  "
        ::= { lC350CtrlEntries 10018 }


    iOutputScrollingCaptionGeneratorCaptionEntry OBJECT-TYPE
        SYNTAX            RollCallString
        MAX-ACCESS        read-write
        STATUS            current
        DESCRIPTION
                "CMNT: - 
                 TYPE: - Editstring
                 PAGE: - Output
                    Caption Entry  cmdID= 10034
                    preset= Channel 1"
        ::= { lC350CtrlEntries 10034 }


    iOutputScrollingCaptionGeneratorCaptionScroll OBJECT-TYPE
        SYNTAX            INTEGER { disable(0), enable(1)  }
        MAX-ACCESS        read-write
        STATUS            current
        DESCRIPTION
                "CMNT: - 
                 TYPE: - Checkbox
                 PAGE: - Output
                    Caption Scroll  cmdID= 10036  "
        ::= { lC350CtrlEntries 10036 }


    iOutputScrollingCaptionGeneratorCaptionEnable OBJECT-TYPE
        SYNTAX            INTEGER { disable(0), enable(1)  }
        MAX-ACCESS        read-write
        STATUS            current
        DESCRIPTION
                "CMNT: - 
                 TYPE: - Checkbox
                 PAGE: - Output
                    Caption Enable  cmdID= 10035  "
        ::= { lC350CtrlEntries 10035 }


    iOutputForceFreeze OBJECT-TYPE
        SYNTAX            INTEGER { disable(0), enable(1)  }
        MAX-ACCESS        read-write
        STATUS            current
        DESCRIPTION
                "CMNT: - 
                 TYPE: - Checkbox
                 PAGE: - Output
                    Force Freeze  cmdID= 10019  "
        ::= { lC350CtrlEntries 10019 }


    iOutputLegalization OBJECT-TYPE
        SYNTAX            INTEGER {
                            valOff(0),
                            val700mV(1),
                            val721mV(2),
                            val735mV(3),
                            val746mV(4)
                            }
        MAX-ACCESS        read-write
        STATUS            current
        DESCRIPTION
                "CMNT: - 
                 TYPE: - RadiobuttonList
                 PAGE: - Output
                    Legalization  cmdID= 10031
                    Off  value= 0
                    700mV  value= 1
                    721mV  value= 2
                    735mV  value= 3
                    746mV  value= 4  "
        ::= { lC350CtrlEntries 10031 }


    iOutputBlankingEmbeddedAudio OBJECT-TYPE
        SYNTAX            INTEGER {
                            valEnable(0),
                            valBlank(1)
                            }
        MAX-ACCESS        read-write
        STATUS            current
        DESCRIPTION
                "CMNT: - 
                 TYPE: - RadiobuttonList
                 PAGE: - Output
                    Embedded Audio  cmdID= 10032
                    Enable  value= 0
                    Blank  value= 1  "
        ::= { lC350CtrlEntries 10032 }


    iOutputBlankingSDHalfLine OBJECT-TYPE
        SYNTAX            INTEGER {
                            valPass(0),
                            valBlank(1)
                            }
        MAX-ACCESS        read-write
        STATUS            current
        DESCRIPTION
                "CMNT: - 
                 TYPE: - RadiobuttonList
                 PAGE: - Output
                    SD Half Line  cmdID= 10033
                    Pass  value= 0
                    Blank  value= 1  "
        ::= { lC350CtrlEntries 10033 }


    iOutputTestPatterns OBJECT-TYPE
        SYNTAX            INTEGER {
                            valOff(0),
                            valBlack(1),
                            valRamp(2),
                            valBars(3)
                            }
        MAX-ACCESS        read-write
        STATUS            current
        DESCRIPTION
                "CMNT: - 
                 TYPE: - RadiobuttonList
                 PAGE: - Output
                    Test Patterns  cmdID= 10020
                    Off  value= 0
                    Black  value= 1
                    Ramp  value= 2
                    Bars  value= 3  "
        ::= { lC350CtrlEntries 10020 }


    iOutputLogoControlPreShaped OBJECT-TYPE
        SYNTAX            INTEGER { disable(0), enable(1)  }
        MAX-ACCESS        read-write
        STATUS            current
        DESCRIPTION
                "CMNT: - 
                 TYPE: - Checkbox
                 PAGE: - Output
                    Pre-Shaped  cmdID= 10021  "
        ::= { lC350CtrlEntries 10021 }


    iOutputLogoControlShow OBJECT-TYPE
        SYNTAX            INTEGER { disable(0), enable(1)  }
        MAX-ACCESS        read-write
        STATUS            current
        DESCRIPTION
                "CMNT: - 
                 TYPE: - Checkbox
                 PAGE: - Output
                    Show  cmdID= 10022  "
        ::= { lC350CtrlEntries 10022 }


    iOutputLogoControlHPosition OBJECT-TYPE
        SYNTAX            INTEGER
        MAX-ACCESS        read-write
        STATUS            current
        DESCRIPTION
                "CMNT: - 
                 TYPE: - Number
                 PAGE: - Output
                    H Position  cmdID= 10023
                    min= 0  max= 100  step= 1  format= %0.0f  div_scale= 1  preset= 10
                    Min = 0  Max = 100  Step = 1  Preset = 10  "
        ::= { lC350CtrlEntries 10023 }


    iOutputLogoControlVPosition OBJECT-TYPE
        SYNTAX            INTEGER
        MAX-ACCESS        read-write
        STATUS            current
        DESCRIPTION
                "CMNT: - 
                 TYPE: - Number
                 PAGE: - Output
                    V Position  cmdID= 10024
                    min= 0  max= 100  step= 1  format= %0.0f  div_scale= 1  preset= 10
                    Min = 0  Max = 100  Step = 1  Preset = 10  "
        ::= { lC350CtrlEntries 10024 }


    iOutputLogoControlTransparency OBJECT-TYPE
        SYNTAX            INTEGER
        MAX-ACCESS        read-write
        STATUS            current
        DESCRIPTION
                "CMNT: - 
                 TYPE: - Number
                 PAGE: - Output
                    Transparency  cmdID= 10025
                    min= 0  max= 100  step= 1  format= %0.0f  div_scale= 1  preset= 0
                    Min = 0  Max = 100  Step = 1  Preset = 0  "
        ::= { lC350CtrlEntries 10025 }


    iOutputLogoControlDelete OBJECT-TYPE
        SYNTAX            INTEGER { noAction(0),valDelete(1) }
        MAX-ACCESS        read-write
        STATUS            current
        DESCRIPTION
                "CMNT: - 
                 TYPE: - Button
                 PAGE: - Output
                    Delete  cmdID= 10026
                    value= 1  "
        ::= { lC350CtrlEntries 10026 }


    iOutputLogoControlLoad OBJECT-TYPE
        SYNTAX            INTEGER { noAction(0),valLoad(1) }
        MAX-ACCESS        read-write
        STATUS            current
        DESCRIPTION
                "CMNT: - 
                 TYPE: - Button
                 PAGE: - Output
                    Load  cmdID= 10030
                    value= 1  "
        ::= { lC350CtrlEntries 10030 }


    iOutputLogoControlLogoSelected OBJECT-TYPE
        SYNTAX            RollCallString
        MAX-ACCESS        read-only
        STATUS            current
        DESCRIPTION
                "CMNT: - 
                 TYPE: - Display
                 PAGE: - Output
                    Logo Selected  cmdID= 10028  "
        ::= { lC350CtrlEntries 10028 }


    iOutputLogoControlState OBJECT-TYPE
        SYNTAX            RollCallString
        MAX-ACCESS        read-only
        STATUS            current
        DESCRIPTION
                "CMNT: - 
                 TYPE: - Display
                 PAGE: - Output
                    State  cmdID= 10029  "
        ::= { lC350CtrlEntries 10029 }


    iOutputLogoControlLogoSelect OBJECT-TYPE
        SYNTAX            INTEGER {
                            valNoneSelected(-1),
                            valLogo1(1),
                            valLogo2(2),
                            valLogo3(3),
                            valLogo4(4),
                            valLogo5(5),
                            valLogo6(6),
                            valLogo7(7),
                            valLogo8(8),
                            valLogo9(9),
                            valLogo10(10),
                            valLogo11(11),
                            valLogo12(12),
                            valLogo13(13),
                            valLogo14(14),
                            valLogo15(15),
                            valLogo16(16),
                            valLogo17(17),
                            valLogo18(18),
                            valLogo19(19),
                            valLogo20(20),
                            valLogo21(21),
                            valLogo22(22),
                            valLogo23(23),
                            valLogo24(24),
                            valLogo25(25),
                            valLogo26(26),
                            valLogo27(27),
                            valLogo28(28),
                            valLogo29(29),
                            valLogo30(30),
                            valLogo31(31),
                            valLogo32(32),
                            valLogo33(33),
                            valLogo34(34),
                            valLogo35(35),
                            valLogo36(36),
                            valLogo37(37),
                            valLogo38(38),
                            valLogo39(39),
                            valLogo40(40),
                            valLogo41(41),
                            valLogo42(42),
                            valLogo43(43),
                            valLogo44(44),
                            valLogo45(45),
                            valLogo46(46),
                            valLogo47(47),
                            valLogo48(48),
                            valLogo49(49),
                            valLogo50(50),
                            valLogo51(51),
                            valLogo52(52),
                            valLogo53(53),
                            valLogo54(54),
                            valLogo55(55),
                            valLogo56(56),
                            valLogo57(57),
                            valLogo58(58),
                            valLogo59(59),
                            valLogo60(60),
                            valLogo61(61),
                            valLogo62(62),
                            valLogo63(63),
                            valLogo64(64)
                            }
        MAX-ACCESS        read-write
        STATUS            current
        DESCRIPTION
                "CMNT: - 
                 TYPE: - RadiobuttonList
                 PAGE: - Output
                    Logo Select  cmdID= 10027
                    None Selected  value= -1
                    Logo 1  value= 1
                    Logo 2  value= 2
                    Logo 3  value= 3
                    Logo 4  value= 4
                    Logo 5  value= 5
                    Logo 6  value= 6
                    Logo 7  value= 7
                    Logo 8  value= 8
                    Logo 9  value= 9
                    Logo 10  value= 10
                    Logo 11  value= 11
                    Logo 12  value= 12
                    Logo 13  value= 13
                    Logo 14  value= 14
                    Logo 15  value= 15
                    Logo 16  value= 16
                    Logo 17  value= 17
                    Logo 18  value= 18
                    Logo 19  value= 19
                    Logo 20  value= 20
                    Logo 21  value= 21
                    Logo 22  value= 22
                    Logo 23  value= 23
                    Logo 24  value= 24
                    Logo 25  value= 25
                    Logo 26  value= 26
                    Logo 27  value= 27
                    Logo 28  value= 28
                    Logo 29  value= 29
                    Logo 30  value= 30
                    Logo 31  value= 31
                    Logo 32  value= 32
                    Logo 33  value= 33
                    Logo 34  value= 34
                    Logo 35  value= 35
                    Logo 36  value= 36
                    Logo 37  value= 37
                    Logo 38  value= 38
                    Logo 39  value= 39
                    Logo 40  value= 40
                    Logo 41  value= 41
                    Logo 42  value= 42
                    Logo 43  value= 43
                    Logo 44  value= 44
                    Logo 45  value= 45
                    Logo 46  value= 46
                    Logo 47  value= 47
                    Logo 48  value= 48
                    Logo 49  value= 49
                    Logo 50  value= 50
                    Logo 51  value= 51
                    Logo 52  value= 52
                    Logo 53  value= 53
                    Logo 54  value= 54
                    Logo 55  value= 55
                    Logo 56  value= 56
                    Logo 57  value= 57
                    Logo 58  value= 58
                    Logo 59  value= 59
                    Logo 60  value= 60
                    Logo 61  value= 61
                    Logo 62  value= 62
                    Logo 63  value= 63
                    Logo 64  value= 64  "
        ::= { lC350CtrlEntries 10027 }


    iCVBSEncoderASetupFormat OBJECT-TYPE
        SYNTAX            INTEGER {
                            valPALNTSC(0),
                            valPALnNPALnM(1),
                            valPALNTSCnJ(2)
                            }
        MAX-ACCESS        read-write
        STATUS            current
        DESCRIPTION
                "CMNT: - 
                 TYPE: - RadiobuttonList
                 PAGE: - CVBS Encoder A
                    Format  cmdID= 10038
                    PAL/NTSC  value= 0
                    PAL-N/PAL-M  value= 1
                    PAL/NTSC-J  value= 2  "
        ::= { lC350CtrlEntries 10038 }


    iCVBSEncoderACalibrationDACGain OBJECT-TYPE
        SYNTAX            INTEGER
        MAX-ACCESS        read-write
        STATUS            current
        DESCRIPTION
                "CMNT: - 
                 TYPE: - Number
                 PAGE: - CVBS Encoder A
                    DAC Gain  cmdID= 10039
                    min= -64  max= 64  step= 1  format= %d  div_scale= 1  preset= 0
                    Min = -64  Max = 64  Step = 1  Preset = 0  "
        ::= { lC350CtrlEntries 10039 }


    iCVBSEncoderACalibrationSaveEncoder OBJECT-TYPE
        SYNTAX            INTEGER { noAction(0),valSaveEncoder(1) }
        MAX-ACCESS        read-write
        STATUS            current
        DESCRIPTION
                "CMNT: - 
                 TYPE: - Button
                 PAGE: - CVBS Encoder A
                    Save Encoder  cmdID= 10040
                    value= 1  "
        ::= { lC350CtrlEntries 10040 }


    iOutputSFPOutputRoutingSFP1Source OBJECT-TYPE
        SYNTAX            INTEGER {
                            valCh1(0),
                            valCh2(1)
                            }
        MAX-ACCESS        read-write
        STATUS            current
        DESCRIPTION
                "CMNT: - 
                 TYPE: - RadiobuttonList
                 PAGE: - Output
                    SFP 1 Source  cmdID= 10045
                    Ch 1  value= 0
                    Ch 2  value= 1  "
        ::= { lC350CtrlEntries 10045 }


    iOutputSFPOutputRoutingSFP2Source OBJECT-TYPE
        SYNTAX            INTEGER {
                            valCh1(0),
                            valCh2(1)
                            }
        MAX-ACCESS        read-write
        STATUS            current
        DESCRIPTION
                "CMNT: - 
                 TYPE: - RadiobuttonList
                 PAGE: - Output
                    SFP 2 Source  cmdID= 10046
                    Ch 1  value= 0
                    Ch 2  value= 1  "
        ::= { lC350CtrlEntries 10046 }


    iVideoProcAmpEnable OBJECT-TYPE
        SYNTAX            INTEGER { disable(0), enable(1)  }
        MAX-ACCESS        read-write
        STATUS            current
        DESCRIPTION
                "CMNT: - 
                 TYPE: - Checkbox
                 PAGE: - Video
                    Enable  cmdID= 10053  "
        ::= { lC350CtrlEntries 10053 }


    iVideoProcAmpContrast OBJECT-TYPE
        SYNTAX            INTEGER
        MAX-ACCESS        read-write
        STATUS            current
        DESCRIPTION
                "CMNT: - 
                 TYPE: - Number
                 PAGE: - Video
                    Contrast  cmdID= 10047
                    min= -60  max= 60  step= 2  format= %0.1fdB  div_scale= 10  preset= 0
                    Min = -6.0dB  Max = 6.0dB  Step = 0.2dB  Preset = 0.0dB  "
        ::= { lC350CtrlEntries 10047 }


    iVideoProcAmpSaturation OBJECT-TYPE
        SYNTAX            INTEGER
        MAX-ACCESS        read-write
        STATUS            current
        DESCRIPTION
                "CMNT: - 
                 TYPE: - Number
                 PAGE: - Video
                    Saturation  cmdID= 10048
                    min= -60  max= 60  step= 2  format= %0.1fdB  div_scale= 10  preset= 0
                    Min = -6.0dB  Max = 6.0dB  Step = 0.2dB  Preset = 0.0dB  "
        ::= { lC350CtrlEntries 10048 }


    iVideoProcAmpBlackLevel OBJECT-TYPE
        SYNTAX            INTEGER
        MAX-ACCESS        read-write
        STATUS            current
        DESCRIPTION
                "CMNT: - 
                 TYPE: - Number
                 PAGE: - Video
                    Black Level  cmdID= 10049
                    min= -1000  max= 1000  step= 8  format= %0.1fmV  div_scale= 10  preset= 0
                    Min = -100.0mV  Max = 100.0mV  Step = 0.8mV  Preset = 0.0mV  "
        ::= { lC350CtrlEntries 10049 }


    iVideoProcAmpGamma OBJECT-TYPE
        SYNTAX            INTEGER
        MAX-ACCESS        read-write
        STATUS            current
        DESCRIPTION
                "CMNT: - 
                 TYPE: - Number
                 PAGE: - Video
                    Gamma  cmdID= 10050
                    min= 4  max= 17  step= 1  format= %0.1f  div_scale= 10  preset= 10
                    Min = 0.4  Max = 1.7  Step = 0.1  Preset = 1.0  "
        ::= { lC350CtrlEntries 10050 }


    iVideoProcAmpYCOffset OBJECT-TYPE
        SYNTAX            INTEGER
        MAX-ACCESS        read-write
        STATUS            current
        DESCRIPTION
                "CMNT: - 
                 TYPE: - Number
                 PAGE: - Video
                    YC Offset  cmdID= 10051
                    min= -20  max= 20  step= 2  format= %0.0f  div_scale= 1  preset= 0
                    Min = -20  Max = 20  Step = 2  Preset = 0  "
        ::= { lC350CtrlEntries 10051 }


    iVideoProcAmpMasterGain OBJECT-TYPE
        SYNTAX            INTEGER
        MAX-ACCESS        read-write
        STATUS            current
        DESCRIPTION
                "CMNT: - 
                 TYPE: - Number
                 PAGE: - Video
                    Master Gain  cmdID= 10052
                    min= -60  max= 60  step= 2  format= %0.1fdB  div_scale= 10  preset= 0
                    Min = -6.0dB  Max = 6.0dB  Step = 0.2dB  Preset = 0.0dB  "
        ::= { lC350CtrlEntries 10052 }


    iVideoEnhancePreset OBJECT-TYPE
        SYNTAX            INTEGER { noAction(0),valPreset(1) }
        MAX-ACCESS        read-write
        STATUS            current
        DESCRIPTION
                "CMNT: - 
                 TYPE: - Button
                 PAGE: - Video
                    Preset  cmdID= 10057
                    value= 1  "
        ::= { lC350CtrlEntries 10057 }


    iVideoEnhanceHEnhanceLevel OBJECT-TYPE
        SYNTAX            INTEGER {
                            val0(0),
                            val1(1),
                            val2(2),
                            val3(3),
                            val4(4)
                            }
        MAX-ACCESS        read-write
        STATUS            current
        DESCRIPTION
                "CMNT: - 
                 TYPE: - RadiobuttonList
                 PAGE: - Enhance
                    Level  cmdID= 10058
                    0  value= 0
                    1  value= 1
                    2  value= 2
                    3  value= 3
                    4  value= 4  "
        ::= { lC350CtrlEntries 10058 }


    iVideoEnhanceHEnhanceFrequencyBand OBJECT-TYPE
        SYNTAX            INTEGER {
                            valMid(0),
                            valHigh(1)
                            }
        MAX-ACCESS        read-write
        STATUS            current
        DESCRIPTION
                "CMNT: - 
                 TYPE: - RadiobuttonList
                 PAGE: - Enhance
                    Frequency Band  cmdID= 10056
                    Mid  value= 0
                    High  value= 1  "
        ::= { lC350CtrlEntries 10056 }


    iVideoEnhanceHFilterShape OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Enhance
                    Shape  cmdID= 10521
                    Soft 2  value= 0
                    Soft 1  value= 1
                    Normal  value= 2
                    Sharp 1  value= 3
                    Sharp 2  value= 4  "
        ::= { lC350CtrlEntries 10521 }


    iVideoEnhanceHFilterFrequencyBand OBJECT-TYPE
        SYNTAX            INTEGER {
                            valLow2(0),
                            valLow1(1),
                            valNormal(2),
                            valHigh1(3),
                            valHigh2(4)
                            }
        MAX-ACCESS        read-write
        STATUS            current
        DESCRIPTION
                "CMNT: - 
                 TYPE: - RadiobuttonList
                 PAGE: - Enhance
                    Frequency Band  cmdID= 10520
                    Low 2  value= 0
                    Low 1  value= 1
                    Normal  value= 2
                    High 1  value= 3
                    High 2  value= 4  "
        ::= { lC350CtrlEntries 10520 }


    iVideoEnhanceVEnhanceShape OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Enhance
                    Shape  cmdID= 10055
                    Soft 2  value= 0
                    Soft 1  value= 1
                    Normal  value= 2
                    Sharp 1  value= 3
                    Sharp 2  value= 4  "
        ::= { lC350CtrlEntries 10055 }


    iVideoEnhanceVEnhanceFrequencyBand OBJECT-TYPE
        SYNTAX            INTEGER {
                            valLow(0),
                            valMid(1),
                            valHigh(2)
                            }
        MAX-ACCESS        read-write
        STATUS            current
        DESCRIPTION
                "CMNT: - 
                 TYPE: - RadiobuttonList
                 PAGE: - Enhance
                    Frequency Band  cmdID= 10054
                    Low  value= 0
                    Mid  value= 1
                    High  value= 2  "
        ::= { lC350CtrlEntries 10054 }


    iVideoNoiseReductionEnable OBJECT-TYPE
        SYNTAX            INTEGER { disable(0), enable(1)  }
        MAX-ACCESS        read-write
        STATUS            current
        DESCRIPTION
                "CMNT: - 
                 TYPE: - Checkbox
                 PAGE: - Video
                    Enable  cmdID= 10060  "
        ::= { lC350CtrlEntries 10060 }


    iVideoNoiseReductionRecursiveLuma OBJECT-TYPE
        SYNTAX            INTEGER
        MAX-ACCESS        read-write
        STATUS            current
        DESCRIPTION
                "CMNT: - 
                 TYPE: - Number
                 PAGE: - Noise Reduction
                    Luma  cmdID= 10072
                    min= 0  max= 7  step= 1  format= %0.0f  div_scale= 1  preset= 0
                    Min = 0  Max = 7  Step = 1  Preset = 0  "
        ::= { lC350CtrlEntries 10072 }


    iVideoNoiseReductionRecursiveChroma OBJECT-TYPE
        SYNTAX            INTEGER
        MAX-ACCESS        read-write
        STATUS            current
        DESCRIPTION
                "CMNT: - 
                 TYPE: - Number
                 PAGE: - Noise Reduction
                    Chroma  cmdID= 10059
                    min= 0  max= 7  step= 1  format= %0.0f  div_scale= 1  preset= 0
                    Min = 0  Max = 7  Step = 1  Preset = 0  "
        ::= { lC350CtrlEntries 10059 }


    iVideoNoiseReductionRecursiveMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10061
                    Auto  value= 0
                    Manual  value= 1  "
        ::= { lC350CtrlEntries 10061 }


    iVideoNoiseReductionRecursiveThreshold OBJECT-TYPE
        SYNTAX            INTEGER
        MAX-ACCESS        read-write
        STATUS            current
        DESCRIPTION
                "CMNT: - 
                 TYPE: - Number
                 PAGE: - Noise Reduction
                    Threshold  cmdID= 10071
                    min= 0  max= 7  step= 1  format= %0.0f  div_scale= 1  preset= 0
                    Min = 0  Max = 7  Step = 1  Preset = 0  "
        ::= { lC350CtrlEntries 10071 }


    iVideoNoiseReductionSpatialLevel OBJECT-TYPE
        SYNTAX            INTEGER
        MAX-ACCESS        read-write
        STATUS            current
        DESCRIPTION
                "CMNT: - 
                 TYPE: - Number
                 PAGE: - Noise Reduction
                    Level  cmdID= 10067
                    min= 0  max= 7  step= 1  format= %0.0f  div_scale= 1  preset= 0
                    Min = 0  Max = 7  Step = 1  Preset = 0  "
        ::= { lC350CtrlEntries 10067 }


    iVideoNoiseReductionSpatialMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10068
                    Auto  value= 0
                    Manual  value= 1  "
        ::= { lC350CtrlEntries 10068 }


    iVideoNoiseReductionSpatialThreshold OBJECT-TYPE
        SYNTAX            INTEGER
        MAX-ACCESS        read-write
        STATUS            current
        DESCRIPTION
                "CMNT: - 
                 TYPE: - Number
                 PAGE: - Noise Reduction
                    Threshold  cmdID= 10069
                    min= 1  max= 4  step= 1  format= %0.0f  div_scale= 1  preset= 1
                    Min = 1  Max = 4  Step = 1  Preset = 1  "
        ::= { lC350CtrlEntries 10069 }


    iVideoNoiseReductionSplitScreen OBJECT-TYPE
        SYNTAX            INTEGER { disable(0), enable(1)  }
        MAX-ACCESS        read-write
        STATUS            current
        DESCRIPTION
                "CMNT: - 
                 TYPE: - Checkbox
                 PAGE: - Video
                    Split Screen  cmdID= 10070  "
        ::= { lC350CtrlEntries 10070 }


    iConvertUpConversionCleanEdgeUpconversion OBJECT-TYPE
        SYNTAX            INTEGER { disable(0), enable(1)  }
        MAX-ACCESS        read-write
        STATUS            current
        DESCRIPTION
                "CMNT: - 
                 TYPE: - Checkbox
                 PAGE: - Convert
                    Clean Edge Upconversion  cmdID= 10078  "
        ::= { lC350CtrlEntries 10078 }


    iConvertMotionProcessingMotionProcess OBJECT-TYPE
        SYNTAX            INTEGER { disable(0), enable(1)  }
        MAX-ACCESS        read-write
        STATUS            current
        DESCRIPTION
                "CMNT: - 
                 TYPE: - Checkbox
                 PAGE: - Convert
                    Motion Process  cmdID= 10073  "
        ::= { lC350CtrlEntries 10073 }


    iConvertMotionProcessingEnhancedMotion OBJECT-TYPE
        SYNTAX            INTEGER { disable(0), enable(1)  }
        MAX-ACCESS        read-write
        STATUS            current
        DESCRIPTION
                "CMNT: - 
                 TYPE: - Checkbox
                 PAGE: - Convert
                    Enhanced Motion  cmdID= 10075  "
        ::= { lC350CtrlEntries 10075 }


    iConvertMotionProcessingStillProcess OBJECT-TYPE
        SYNTAX            INTEGER { disable(0), enable(1)  }
        MAX-ACCESS        read-write
        STATUS            current
        DESCRIPTION
                "CMNT: - 
                 TYPE: - Checkbox
                 PAGE: - Convert
                    Still Process  cmdID= 10074  "
        ::= { lC350CtrlEntries 10074 }


    iConvertMotionProcessingEnhancedStill OBJECT-TYPE
        SYNTAX            INTEGER { disable(0), enable(1)  }
        MAX-ACCESS        read-write
        STATUS            current
        DESCRIPTION
                "CMNT: - 
                 TYPE: - Checkbox
                 PAGE: - Convert
                    Enhanced Still  cmdID= 10076  "
        ::= { lC350CtrlEntries 10076 }


    iConvertMotionProcessingEnhancedFilm OBJECT-TYPE
        SYNTAX            INTEGER { disable(0), enable(1)  }
        MAX-ACCESS        read-write
        STATUS            current
        DESCRIPTION
                "CMNT: - 
                 TYPE: - Checkbox
                 PAGE: - Convert
                    Enhanced Film  cmdID= 10077  "
        ::= { lC350CtrlEntries 10077 }


    iConvertMotionProcessingEnhancedDeinterlace OBJECT-TYPE
        SYNTAX            INTEGER { disable(0), enable(1)  }
        MAX-ACCESS        read-write
        STATUS            current
        DESCRIPTION
                "CMNT: - 
                 TYPE: - Checkbox
                 PAGE: - Convert
                    Enhanced De-interlace  cmdID= 10080  "
        ::= { lC350CtrlEntries 10080 }


    iConvertMotionProcessingCleanCut OBJECT-TYPE
        SYNTAX            INTEGER { disable(0), enable(1)  }
        MAX-ACCESS        read-write
        STATUS            current
        DESCRIPTION
                "CMNT: - 
                 TYPE: - Checkbox
                 PAGE: - Convert
                    Clean Cut  cmdID= 10079  "
        ::= { lC350CtrlEntries 10079 }


    iConvertInputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10082  "
        ::= { lC350CtrlEntries 10082 }


    iConvertInputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10081
                    2:3  value= 0
                    2:2 (psf)  value= 1  "
        ::= { lC350CtrlEntries 10081 }


    iConvertInputCadence23Source OBJECT-TYPE
        SYNTAX            INTEGER {
                            valAutomatic(0),
                            valInputTimecode(1)
                            }
        MAX-ACCESS        read-write
        STATUS            current
        DESCRIPTION
                "CMNT: - 
                 TYPE: - RadiobuttonList
                 PAGE: - Convert
                    2:3 Source  cmdID= 10083
                    Automatic  value= 0
                    Input Timecode  value= 1  "
        ::= { lC350CtrlEntries 10083 }


    iConvertInputCadence23StartHour OBJECT-TYPE
        SYNTAX            INTEGER
        MAX-ACCESS        read-write
        STATUS            current
        DESCRIPTION
                "CMNT: - 
                 TYPE: - Number
                 PAGE: - Convert
                    2:3 Start Hour  cmdID= 10084
                    min= 0  max= 23  step= 1  format= %0.0f  div_scale= 1  preset= 1
                    Min = 0  Max = 23  Step = 1  Preset = 1  "
        ::= { lC350CtrlEntries 10084 }


    iConvertOutputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10086  "
        ::= { lC350CtrlEntries 10086 }


    iConvertOutputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10085
                    2:3  value= 0
                    2:2 (psf)  value= 1  "
        ::= { lC350CtrlEntries 10085 }


    iConvertOutputCadence23Source OBJECT-TYPE
        SYNTAX            INTEGER {
                            valFreeRun(0),
                            valOutputTimecode(1)
                            }
        MAX-ACCESS        read-write
        STATUS            current
        DESCRIPTION
                "CMNT: - 
                 TYPE: - RadiobuttonList
                 PAGE: - Convert
                    2:3 Source  cmdID= 10087
                    Free Run  value= 0
                    Output Timecode  value= 1  "
        ::= { lC350CtrlEntries 10087 }


    iConvertOutputCadence23StartHour OBJECT-TYPE
        SYNTAX            INTEGER
        MAX-ACCESS        read-write
        STATUS            current
        DESCRIPTION
                "CMNT: - 
                 TYPE: - Number
                 PAGE: - Convert
                    2:3 Start Hour  cmdID= 10088
                    min= 0  max= 23  step= 1  format= %0.0f  div_scale= 1  preset= 1
                    Min = 0  Max = 23  Step = 1  Preset = 1  "
        ::= { lC350CtrlEntries 10088 }


    iARCSidebarKeyerSyncMode OBJECT-TYPE
        SYNTAX            INTEGER { disable(0), enable(1)  }
        MAX-ACCESS        read-write
        STATUS            current
        DESCRIPTION
                "CMNT: - 
                 TYPE: - Checkbox
                 PAGE: - ARC & Sidebar Keyer
                    Sync Mode  cmdID= 10101  "
        ::= { lC350CtrlEntries 10101 }


    iARCSidebarKeyerSignallingDetected OBJECT-TYPE
        SYNTAX            RollCallString
        MAX-ACCESS        read-only
        STATUS            current
        DESCRIPTION
                "CMNT: - 
                 TYPE: - Display
                 PAGE: - ARC & Sidebar Keyer
                    Signalling Detected  cmdID= 10089  "
        ::= { lC350CtrlEntries 10089 }


    iARCSidebarKeyerSidebarKeyingOutputCropMode OBJECT-TYPE
        SYNTAX            INTEGER {
                            valOff(0),
                            valOutputCrop(1),
                            valSidebarKey(2)
                            }
        MAX-ACCESS        read-write
        STATUS            current
        DESCRIPTION
                "CMNT: - 
                 TYPE: - RadiobuttonList
                 PAGE: - ARC & Sidebar Keyer
                    Mode  cmdID= 10090
                    Off  value= 0
                    Output Crop  value= 1
                    Sidebar Key  value= 2  "
        ::= { lC350CtrlEntries 10090 }


    iARCSidebarKeyerSidebarKeyingOutputCropSidebarKeySource OBJECT-TYPE
        SYNTAX            INTEGER {
                            valSDI1(0),
                            valSDI2(1),
                            valSFP1(2),
                            valSFP2(3),
                            valCVBS(4)
                            }
        MAX-ACCESS        read-write
        STATUS            current
        DESCRIPTION
                "CMNT: - 
                 TYPE: - RadiobuttonList
                 PAGE: - ARC & Sidebar Keyer
                    Sidebar Key Source  cmdID= 10091
                    SDI 1  value= 0
                    SDI 2  value= 1
                    SFP 1  value= 2
                    SFP 2  value= 3
                    CVBS  value= 4  "
        ::= { lC350CtrlEntries 10091 }


    iARCSidebarKeyingOutputCropOutputCropPositionTop OBJECT-TYPE
        SYNTAX            INTEGER
        MAX-ACCESS        read-write
        STATUS            current
        DESCRIPTION
                "CMNT: - 
                 TYPE: - Number
                 PAGE: - Sidebar Keying & Output Crop
                    Top  cmdID= 10092
                    min= 0  max= 99  step= 1  format= %0.0f%%  div_scale= 1  preset= 0
                    Min = 0%  Max = 99%  Step = 1%  Preset = 0%  "
        ::= { lC350CtrlEntries 10092 }


    iARCSidebarKeyingOutputCropOutputCropPositionBottom OBJECT-TYPE
        SYNTAX            INTEGER
        MAX-ACCESS        read-write
        STATUS            current
        DESCRIPTION
                "CMNT: - 
                 TYPE: - Number
                 PAGE: - Sidebar Keying & Output Crop
                    Bottom  cmdID= 10093
                    min= 0  max= 99  step= 1  format= %0.0f%%  div_scale= 1  preset= 0
                    Min = 0%  Max = 99%  Step = 1%  Preset = 0%  "
        ::= { lC350CtrlEntries 10093 }


    iARCSidebarKeyingOutputCropOutputCropPositionLeft OBJECT-TYPE
        SYNTAX            INTEGER
        MAX-ACCESS        read-write
        STATUS            current
        DESCRIPTION
                "CMNT: - 
                 TYPE: - Number
                 PAGE: - Sidebar Keying & Output Crop
                    Left  cmdID= 10094
                    min= 0  max= 99  step= 1  format= %0.0f%%  div_scale= 1  preset= 0
                    Min = 0%  Max = 99%  Step = 1%  Preset = 0%  "
        ::= { lC350CtrlEntries 10094 }


    iARCSidebarKeyingOutputCropOutputCropPositionRight OBJECT-TYPE
        SYNTAX            INTEGER
        MAX-ACCESS        read-write
        STATUS            current
        DESCRIPTION
                "CMNT: - 
                 TYPE: - Number
                 PAGE: - Sidebar Keying & Output Crop
                    Right  cmdID= 10095
                    min= 0  max= 99  step= 1  format= %0.0f%%  div_scale= 1  preset= 0
                    Min = 0%  Max = 99%  Step = 1%  Preset = 0%  "
        ::= { lC350CtrlEntries 10095 }


    iARCSidebarKeyerPostScalingControlPostScalingEnable OBJECT-TYPE
        SYNTAX            INTEGER { disable(0), enable(1)  }
        MAX-ACCESS        read-write
        STATUS            current
        DESCRIPTION
                "CMNT: - 
                 TYPE: - Checkbox
                 PAGE: - ARC & Sidebar Keyer
                    Post Scaling Enable  cmdID= 10100  "
        ::= { lC350CtrlEntries 10100 }


    iARCSidebarKeyerPostScalingControlSize OBJECT-TYPE
        SYNTAX            INTEGER
        MAX-ACCESS        read-write
        STATUS            current
        DESCRIPTION
                "CMNT: - 
                 TYPE: - Number
                 PAGE: - ARC & Sidebar Keyer
                    Size  cmdID= 10096
                    min= 80  max= 120  step= 1  format= %0.0f%%  div_scale= 1  preset= 100
                    Min = 80%  Max = 120%  Step = 1%  Preset = 100%  "
        ::= { lC350CtrlEntries 10096 }


    iARCSidebarKeyerPostScalingControlAspect OBJECT-TYPE
        SYNTAX            INTEGER
        MAX-ACCESS        read-write
        STATUS            current
        DESCRIPTION
                "CMNT: - 
                 TYPE: - Number
                 PAGE: - ARC & Sidebar Keyer
                    Aspect  cmdID= 10097
                    min= 70  max= 150  step= 1  format= %0.0f%%  div_scale= 1  preset= 100
                    Min = 70%  Max = 150%  Step = 1%  Preset = 100%  "
        ::= { lC350CtrlEntries 10097 }


    iARCSidebarKeyerPostScalingControlPan OBJECT-TYPE
        SYNTAX            INTEGER
        MAX-ACCESS        read-write
        STATUS            current
        DESCRIPTION
                "CMNT: - 
                 TYPE: - Number
                 PAGE: - ARC & Sidebar Keyer
                    Pan  cmdID= 10098
                    min= -50  max= 50  step= 1  format= %0.0f%  div_scale= 1  preset= 0
                    Min = -50  Max = 50  Step = 1  Preset = 0  "
        ::= { lC350CtrlEntries 10098 }


    iARCSidebarKeyerPostScalingControlTilt OBJECT-TYPE
        SYNTAX            INTEGER
        MAX-ACCESS        read-write
        STATUS            current
        DESCRIPTION
                "CMNT: - 
                 TYPE: - Number
                 PAGE: - ARC & Sidebar Keyer
                    Tilt  cmdID= 10099
                    min= -50  max= 50  step= 1  format= %0.0f%  div_scale= 1  preset= 0
                    Min = -50  Max = 50  Step = 1  Preset = 0  "
        ::= { lC350CtrlEntries 10099 }


    iARCSidebarKeyerScalerConfigUsePresets OBJECT-TYPE
        SYNTAX            INTEGER { disable(0), enable(1)  }
        MAX-ACCESS        read-write
        STATUS            current
        DESCRIPTION
                "CMNT: - 
                 TYPE: - Checkbox
                 PAGE: - ARC & Sidebar Keyer
                    Use Presets  cmdID= 10127  "
        ::= { lC350CtrlEntries 10127 }


    iARCScalerConfigPresetsSDInputis702 OBJECT-TYPE
        SYNTAX            INTEGER { disable(0), enable(1)  }
        MAX-ACCESS        read-write
        STATUS            current
        DESCRIPTION
                "CMNT: - 
                 TYPE: - Checkbox
                 PAGE: - Scaler Config
                    SD Input is 702  cmdID= 10102  "
        ::= { lC350CtrlEntries 10102 }


    iARCScalerConfigPresetsSDOutputis702 OBJECT-TYPE
        SYNTAX            INTEGER { disable(0), enable(1)  }
        MAX-ACCESS        read-write
        STATUS            current
        DESCRIPTION
                "CMNT: - 
                 TYPE: - Checkbox
                 PAGE: - Scaler Config
                    SD Output is 702  cmdID= 10103  "
        ::= { lC350CtrlEntries 10103 }


    iARCPresetsSDCrossConversionSelectStdPreset OBJECT-TYPE
        SYNTAX            INTEGER {
                            valNone(0),
                            val169LB43HC(1),
                            val169LB169Ana(2),
                            val169LB149LB(3),
                            val169Ana43HC(4),
                            val169Ana169LB(5),
                            val169Ana149LB(6)
                            }
        MAX-ACCESS        read-write
        STATUS            current
        DESCRIPTION
                "CMNT: - 
                 TYPE: - RadiobuttonList
                 PAGE: - Presets
                    Select Std Preset  cmdID= 10104
                    None  value= 0
                    16:9 LB > 4:3 HC  value= 1
                    16:9 LB > 16:9 Ana  value= 2
                    16:9 LB > 14:9 LB  value= 3
                    16:9 Ana > 4:3 HC  value= 4
                    16:9 Ana > 16:9 LB  value= 5
                    16:9 Ana > 14:9 LB  value= 6  "
        ::= { lC350CtrlEntries 10104 }


    iARCPresetsHDCrossConversionSelectStdPreset OBJECT-TYPE
        SYNTAX            INTEGER {
                            valNone(0),
                            val149PB169VC(1),
                            val43PB169VC(2),
                            val43PB149PBVC(3)
                            }
        MAX-ACCESS        read-write
        STATUS            current
        DESCRIPTION
                "CMNT: - 
                 TYPE: - RadiobuttonList
                 PAGE: - Presets
                    Select Std Preset  cmdID= 10105
                    None  value= 0
                    14:9 PB > 16:9 VC  value= 1
                    4:3 PB > 16:9 VC  value= 2
                    4:3 PB > 14:9 PB VC  value= 3  "
        ::= { lC350CtrlEntries 10105 }


    iARCPresetsUpConversionSelectStdPreset OBJECT-TYPE
        SYNTAX            INTEGER {
                            val43169VC(0),
                            val4343PB(1),
                            val169LB169(2),
                            val169Ana169(3),
                            val149LB149PB(4)
                            }
        MAX-ACCESS        read-write
        STATUS            current
        DESCRIPTION
                "CMNT: - 
                 TYPE: - RadiobuttonList
                 PAGE: - Presets
                    Select Std Preset  cmdID= 10106
                    4:3 > 16:9 VC  value= 0
                    4:3 > 4:3 PB  value= 1
                    16:9 LB > 16:9  value= 2
                    16:9 Ana > 16:9  value= 3
                    14:9 LB > 14:9 PB  value= 4  "
        ::= { lC350CtrlEntries 10106 }


    iARCPresetsDownConversionSelectStdPreset OBJECT-TYPE
        SYNTAX            INTEGER {
                            val16943HC(0),
                            val169169LB(1),
                            val169169Ana(2),
                            val43PB43(3),
                            val149PB149LB(4)
                            }
        MAX-ACCESS        read-write
        STATUS            current
        DESCRIPTION
                "CMNT: - 
                 TYPE: - RadiobuttonList
                 PAGE: - Presets
                    Select Std Preset  cmdID= 10107
                    16:9 > 4:3 HC  value= 0
                    16:9 > 16:9 LB  value= 1
                    16:9 > 16:9 Ana  value= 2
                    4:3 PB > 4:3  value= 3
                    14:9 PB > 14:9 LB  value= 4  "
        ::= { lC350CtrlEntries 10107 }


    iARCScalerConfigInputConfigInputSignallingSource OBJECT-TYPE
        SYNTAX            INTEGER {
                            valSMPTE2016(0),
                            valL23ETSI(1),
                            valL23AFD(2),
                            valVISMPTE(3),
                            valVIAFD(4)
                            }
        MAX-ACCESS        read-write
        STATUS            current
        DESCRIPTION
                "CMNT: - 
                 TYPE: - RadiobuttonList
                 PAGE: - Scaler Config
                    Input Signalling Source  cmdID= 10112
                    SMPTE 2016  value= 0
                    L23 ETSI  value= 1
                    L23 AFD  value= 2
                    VI SMPTE  value= 3
                    VI AFD  value= 4  "
        ::= { lC350CtrlEntries 10112 }


    iARCInputConfigIfInputSignallingNotPresentForceInputFormat OBJECT-TYPE
        SYNTAX            INTEGER { disable(0), enable(1)  }
        MAX-ACCESS        read-write
        STATUS            current
        DESCRIPTION
                "CMNT: - 
                 TYPE: - Checkbox
                 PAGE: - Input Config
                    Force Input Format  cmdID= 10126  "
        ::= { lC350CtrlEntries 10126 }


    iARCInputConfigIfInputSignallingNotPresentSDInputFormat OBJECT-TYPE
        SYNTAX            INTEGER {
                            valNormal(0),
                            valAnamorphic(1),
                            val169Letterbox(2),
                            val149Letterbox(3)
                            }
        MAX-ACCESS        read-write
        STATUS            current
        DESCRIPTION
                "CMNT: - 
                 TYPE: - RadiobuttonList
                 PAGE: - Input Config
                    SD Input Format  cmdID= 10108
                    Normal  value= 0
                    Anamorphic  value= 1
                    16:9 Letterbox  value= 2
                    14:9 Letterbox  value= 3  "
        ::= { lC350CtrlEntries 10108 }


    iARCInputConfigIfInputSignallingNotPresentHDInputFormat OBJECT-TYPE
        SYNTAX            INTEGER {
                            valNormal(0),
                            val149Pillarbox(1),
                            val43Pillarbox(2)
                            }
        MAX-ACCESS        read-write
        STATUS            current
        DESCRIPTION
                "CMNT: - 
                 TYPE: - RadiobuttonList
                 PAGE: - Input Config
                    HD Input Format  cmdID= 10109
                    Normal  value= 0
                    14:9 Pillarbox  value= 1
                    4:3 Pillarbox  value= 2  "
        ::= { lC350CtrlEntries 10109 }


    iARCScalerConfigOutputConfigConversionScaling OBJECT-TYPE
        SYNTAX            INTEGER {
                            valFittoHeight(0),
                            valFittoWidth(1),
                            val149(2)
                            }
        MAX-ACCESS        read-write
        STATUS            current
        DESCRIPTION
                "CMNT: - 
                 TYPE: - RadiobuttonList
                 PAGE: - Scaler Config
                    Conversion Scaling  cmdID= 10111
                    Fit to Height  value= 0
                    Fit to Width  value= 1
                    14:9  value= 2  "
        ::= { lC350CtrlEntries 10111 }


    iARCScalerConfigOutputConfigSDOutputFormat OBJECT-TYPE
        SYNTAX            INTEGER {
                            valNormal(0),
                            valAnamorphic(1)
                            }
        MAX-ACCESS        read-write
        STATUS            current
        DESCRIPTION
                "CMNT: - 
                 TYPE: - RadiobuttonList
                 PAGE: - Scaler Config
                    SD Output Format  cmdID= 10110
                    Normal  value= 0
                    Anamorphic  value= 1  "
        ::= { lC350CtrlEntries 10110 }


    iARCSidebarKeyerMemoriesRecallMemory OBJECT-TYPE
        SYNTAX            INTEGER {
                            valNoneSelected(0),
                            valArcMemory1(1),
                            valArcMemory2(2),
                            valArcMemory3(3),
                            valArcMemory4(4),
                            valArcMemory5(5),
                            valArcMemory6(6),
                            valArcMemory7(7),
                            valArcMemory8(8),
                            valArcMemory9(9),
                            valArcMemory10(10),
                            valArcMemory11(11),
                            valArcMemory12(12),
                            valArcMemory13(13),
                            valArcMemory14(14),
                            valArcMemory15(15),
                            valArcMemory16(16),
                            valArcMemory17(17),
                            valArcMemory18(18),
                            valArcMemory19(19),
                            valArcMemory20(20),
                            valArcMemory21(21),
                            valArcMemory22(22),
                            valArcMemory23(23),
                            valArcMemory24(24),
                            valArcMemory25(25),
                            valArcMemory26(26),
                            valArcMemory27(27),
                            valArcMemory28(28),
                            valArcMemory29(29),
                            valArcMemory30(30),
                            valArcMemory31(31),
                            valArcMemory32(32)
                            }
        MAX-ACCESS        read-write
        STATUS            current
        DESCRIPTION
                "CMNT: - 
                 TYPE: - RadiobuttonList
                 PAGE: - ARC & Sidebar Keyer
                    Recall Memory  cmdID= 10136
                    None Selected  value= 0
                    Arc Memory 1  value= 1
                    Arc Memory 2  value= 2
                    Arc Memory 3  value= 3
                    Arc Memory 4  value= 4
                    Arc Memory 5  value= 5
                    Arc Memory 6  value= 6
                    Arc Memory 7  value= 7
                    Arc Memory 8  value= 8
                    Arc Memory 9  value= 9
                    Arc Memory 10  value= 10
                    Arc Memory 11  value= 11
                    Arc Memory 12  value= 12
                    Arc Memory 13  value= 13
                    Arc Memory 14  value= 14
                    Arc Memory 15  value= 15
                    Arc Memory 16  value= 16
                    Arc Memory 17  value= 17
                    Arc Memory 18  value= 18
                    Arc Memory 19  value= 19
                    Arc Memory 20  value= 20
                    Arc Memory 21  value= 21
                    Arc Memory 22  value= 22
                    Arc Memory 23  value= 23
                    Arc Memory 24  value= 24
                    Arc Memory 25  value= 25
                    Arc Memory 26  value= 26
                    Arc Memory 27  value= 27
                    Arc Memory 28  value= 28
                    Arc Memory 29  value= 29
                    Arc Memory 30  value= 30
                    Arc Memory 31  value= 31
                    Arc Memory 32  value= 32  "
        ::= { lC350CtrlEntries 10136 }


    iARCSidebarKeyerMemoriesSelMemory OBJECT-TYPE
        SYNTAX            INTEGER {
                            valArcMemory1(1),
                            valArcMemory2(2),
                            valArcMemory3(3),
                            valArcMemory4(4),
                            valArcMemory5(5),
                            valArcMemory6(6),
                            valArcMemory7(7),
                            valArcMemory8(8),
                            valArcMemory9(9),
                            valArcMemory10(10),
                            valArcMemory11(11),
                            valArcMemory12(12),
                            valArcMemory13(13),
                            valArcMemory14(14),
                            valArcMemory15(15),
                            valArcMemory16(16),
                            valArcMemory17(17),
                            valArcMemory18(18),
                            valArcMemory19(19),
                            valArcMemory20(20),
                            valArcMemory21(21),
                            valArcMemory22(22),
                            valArcMemory23(23),
                            valArcMemory24(24),
                            valArcMemory25(25),
                            valArcMemory26(26),
                            valArcMemory27(27),
                            valArcMemory28(28),
                            valArcMemory29(29),
                            valArcMemory30(30),
                            valArcMemory31(31),
                            valArcMemory32(32)
                            }
        MAX-ACCESS        read-write
        STATUS            current
        DESCRIPTION
                "CMNT: - 
                 TYPE: - RadiobuttonList
                 PAGE: - ARC & Sidebar Keyer
                    Sel Memory  cmdID= 10134
                    Arc Memory 1  value= 1
                    Arc Memory 2  value= 2
                    Arc Memory 3  value= 3
                    Arc Memory 4  value= 4
                    Arc Memory 5  value= 5
                    Arc Memory 6  value= 6
                    Arc Memory 7  value= 7
                    Arc Memory 8  value= 8
                    Arc Memory 9  value= 9
                    Arc Memory 10  value= 10
                    Arc Memory 11  value= 11
                    Arc Memory 12  value= 12
                    Arc Memory 13  value= 13
                    Arc Memory 14  value= 14
                    Arc Memory 15  value= 15
                    Arc Memory 16  value= 16
                    Arc Memory 17  value= 17
                    Arc Memory 18  value= 18
                    Arc Memory 19  value= 19
                    Arc Memory 20  value= 20
                    Arc Memory 21  value= 21
                    Arc Memory 22  value= 22
                    Arc Memory 23  value= 23
                    Arc Memory 24  value= 24
                    Arc Memory 25  value= 25
                    Arc Memory 26  value= 26
                    Arc Memory 27  value= 27
                    Arc Memory 28  value= 28
                    Arc Memory 29  value= 29
                    Arc Memory 30  value= 30
                    Arc Memory 31  value= 31
                    Arc Memory 32  value= 32  "
        ::= { lC350CtrlEntries 10134 }


    iARCSidebarKeyerMemoriesSaveMemory OBJECT-TYPE
        SYNTAX            INTEGER { noAction(0),valSaveMemory(1) }
        MAX-ACCESS        read-write
        STATUS            current
        DESCRIPTION
                "CMNT: - 
                 TYPE: - Button
                 PAGE: - ARC & Sidebar Keyer
                    Save Memory  cmdID= 10135
                    value= 1  "
        ::= { lC350CtrlEntries 10135 }


    iARCSidebarKeyerMemoriesClearMemory OBJECT-TYPE
        SYNTAX            INTEGER { noAction(0),valClearMemory(1) }
        MAX-ACCESS        read-write
        STATUS            current
        DESCRIPTION
                "CMNT: - 
                 TYPE: - Button
                 PAGE: - ARC & Sidebar Keyer
                    Clear Memory  cmdID= 10139
                    value= 1  "
        ::= { lC350CtrlEntries 10139 }


    iMemoriesMemoryNameArcChangeName OBJECT-TYPE
        SYNTAX            RollCallString
        MAX-ACCESS        read-write
        STATUS            current
        DESCRIPTION
                "CMNT: - 
                 TYPE: - Editstring
                 PAGE: - Memories
                    Arc Change Name  cmdID= 10137
                    preset= Preset Identifier"
        ::= { lC350CtrlEntries 10137 }


    iARCSidebarKeyerMemoriesLastDisplayMemory OBJECT-TYPE
        SYNTAX            RollCallString
        MAX-ACCESS        read-only
        STATUS            current
        DESCRIPTION
                "CMNT: - 
                 TYPE: - Display
                 PAGE: - ARC & Sidebar Keyer
                    Last Display Memory  cmdID= 10138  "
        ::= { lC350CtrlEntries 10138 }


    iARCOutputSignallingConfigSMPTE2016Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10121
                    Auto  value= 0
                    Pass  value= 1
                    Force  value= 2
                    Delete  value= 3  "
        ::= { lC350CtrlEntries 10121 }


    iARCOutputSignallingConfigSMPTE2016OutputLine625 OBJECT-TYPE
        SYNTAX            INTEGER
        MAX-ACCESS        read-write
        STATUS            current
        DESCRIPTION
                "CMNT: - 
                 TYPE: - Number
                 PAGE: - Output Signalling Config
                    Output Line 625  cmdID= 10131
                    min= 7  max= 22  step= 1  format= %0.0f  div_scale= 1  preset= 12
                    Min = 7  Max = 22  Step = 1  Preset = 12  "
        ::= { lC350CtrlEntries 10131 }


    iARCOutputSignallingConfigSMPTE2016OutputLine525 OBJECT-TYPE
        SYNTAX            INTEGER
        MAX-ACCESS        read-write
        STATUS            current
        DESCRIPTION
                "CMNT: - 
                 TYPE: - Number
                 PAGE: - Output Signalling Config
                    Output Line 525  cmdID= 10132
                    min= 11  max= 19  step= 1  format= %0.0f  div_scale= 1  preset= 11
                    Min = 11  Max = 19  Step = 1  Preset = 11  "
        ::= { lC350CtrlEntries 10132 }


    iARCOutputSignallingConfigSMPTE2016OutputLineHD OBJECT-TYPE
        SYNTAX            INTEGER
        MAX-ACCESS        read-write
        STATUS            current
        DESCRIPTION
                "CMNT: - 
                 TYPE: - Number
                 PAGE: - Output Signalling Config
                    Output Line HD  cmdID= 10130
                    min= 9  max= 20  step= 1  format= %0.0f  div_scale= 1  preset= 11
                    Min = 9  Max = 20  Step = 1  Preset = 11  "
        ::= { lC350CtrlEntries 10130 }


    iARCOutputSignallingConfigSMPTE2016OutputLineStatus OBJECT-TYPE
        SYNTAX            RollCallString
        MAX-ACCESS        read-only
        STATUS            current
        DESCRIPTION
                "CMNT: - 
                 TYPE: - Display
                 PAGE: - Output Signalling Config
                    Output Line Status  cmdID= 10133  "
        ::= { lC350CtrlEntries 10133 }


    iARCOutputSignallingConfigVIMode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10118
                    Auto  value= 0
                    Pass  value= 1
                    Force  value= 2
                    Delete  value= 3  "
        ::= { lC350CtrlEntries 10118 }


    iARCOutputSignallingConfigVIOutputFormat OBJECT-TYPE
        SYNTAX            INTEGER {
                            valSMPTE(0),
                            valAFD(1)
                            }
        MAX-ACCESS        read-write
        STATUS            current
        DESCRIPTION
                "CMNT: - 
                 TYPE: - RadiobuttonList
                 PAGE: - Output Signalling Config
                    Output Format  cmdID= 10119
                    SMPTE  value= 0
                    AFD  value= 1  "
        ::= { lC350CtrlEntries 10119 }


    iARCSidebarKeyerOutputSignallingConfigVIPassData OBJECT-TYPE
        SYNTAX            INTEGER { disable(0), enable(1)  }
        MAX-ACCESS        read-write
        STATUS            current
        DESCRIPTION
                "CMNT: - 
                 TYPE: - Checkbox
                 PAGE: - ARC & Sidebar Keyer
                    VI Pass Data  cmdID= 10120  "
        ::= { lC350CtrlEntries 10120 }


    iARCOutputSignallingConfigL23Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10116
                    Auto  value= 0
                    Pass  value= 1
                    Force  value= 2
                    Delete  value= 3  "
        ::= { lC350CtrlEntries 10116 }


    iARCOutputSignallingConfigL23OutputFormat OBJECT-TYPE
        SYNTAX            INTEGER {
                            valETSI(0),
                            valAFD(1)
                            }
        MAX-ACCESS        read-write
        STATUS            current
        DESCRIPTION
                "CMNT: - 
                 TYPE: - RadiobuttonList
                 PAGE: - Output Signalling Config
                    Output Format  cmdID= 10117
                    ETSI  value= 0
                    AFD  value= 1  "
        ::= { lC350CtrlEntries 10117 }


    iARCOutputSignallingConfigL23InputLine OBJECT-TYPE
        SYNTAX            INTEGER
        MAX-ACCESS        read-write
        STATUS            current
        DESCRIPTION
                "CMNT: - 
                 TYPE: - Number
                 PAGE: - Output Signalling Config
                    Input Line  cmdID= 10113
                    min= 10  max= 23  step= 1  format= %0.0f  div_scale= 1  preset= 23
                    Min = 10  Max = 23  Step = 1  Preset = 23  "
        ::= { lC350CtrlEntries 10113 }


    iARCOutputSignallingConfigL23OutputLine OBJECT-TYPE
        SYNTAX            INTEGER
        MAX-ACCESS        read-write
        STATUS            current
        DESCRIPTION
                "CMNT: - 
                 TYPE: - Number
                 PAGE: - Output Signalling Config
                    Output Line  cmdID= 10114
                    min= 10  max= 23  step= 1  format= %0.0f  div_scale= 1  preset= 23
                    Min = 10  Max = 23  Step = 1  Preset = 23  "
        ::= { lC350CtrlEntries 10114 }


    iARCOutputSignallingConfigL23OutputLineStatus OBJECT-TYPE
        SYNTAX            RollCallString
        MAX-ACCESS        read-only
        STATUS            current
        DESCRIPTION
                "CMNT: - 
                 TYPE: - Display
                 PAGE: - Output Signalling Config
                    Output Line Status  cmdID= 10115  "
        ::= { lC350CtrlEntries 10115 }


    iARCL23AFDUserBitsForceUserBitsValue OBJECT-TYPE
        SYNTAX            INTEGER { disable(0), enable(1)  }
        MAX-ACCESS        read-write
        STATUS            current
        DESCRIPTION
                "CMNT: - 
                 TYPE: - Checkbox
                 PAGE: - L23
                    Force User Bits Value  cmdID= 10128  "
        ::= { lC350CtrlEntries 10128 }


    iARCL23AFDUserBitsUserBitsValue OBJECT-TYPE
        SYNTAX            INTEGER
        MAX-ACCESS        read-write
        STATUS            current
        DESCRIPTION
                "CMNT: - 
                 TYPE: - Number
                 PAGE: - L23
                    User Bits Value  cmdID= 10129
                    min= 0  max= 15  step= 1  format= %0.0f  div_scale= 1  preset= 0
                    Min = 0  Max = 15  Step = 1  Preset = 0  "
        ::= { lC350CtrlEntries 10129 }


    iARCOutputSignallingConfigForceModeConfigSMPTE2016 OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val43AFD8(8),
                            val43AFD9(9),
                            val43AFD10(10),
                            val43AFD11(11),
                            val43AFD12(12),
                            val43AFD13(13),
                            val43AFD14(14),
                            val43AFD15(15),
                            val169AFD0(16),
                            val169AFD1(17),
                            val169AFD2(18),
                            val169AFD3(19),
                            val169AFD4(20),
                            val169AFD5(21),
                            val169AFD6(22),
                            val169AFD7(23),
                            val169AFD8(24),
                            val169AFD9(25),
                            val169AFD10(26),
                            val169AFD11(27),
                            val169AFD12(28),
                            val169AFD13(29),
                            val169AFD14(30),
                            val169AFD15(31)
                            }
        MAX-ACCESS        read-write
        STATUS            current
        DESCRIPTION
                "CMNT: - 
                 TYPE: - RadiobuttonList
                 PAGE: - Output Signalling Config
                    SMPTE 2016  cmdID= 10124
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    4:3 AFD 8  value= 8
                    4:3 AFD 9  value= 9
                    4:3 AFD 10  value= 10
                    4:3 AFD 11  value= 11
                    4:3 AFD 12  value= 12
                    4:3 AFD 13  value= 13
                    4:3 AFD 14  value= 14
                    4:3 AFD 15  value= 15
                    16:9 AFD 0  value= 16
                    16:9 AFD 1  value= 17
                    16:9 AFD 2  value= 18
                    16:9 AFD 3  value= 19
                    16:9 AFD 4  value= 20
                    16:9 AFD 5  value= 21
                    16:9 AFD 6  value= 22
                    16:9 AFD 7  value= 23
                    16:9 AFD 8  value= 24
                    16:9 AFD 9  value= 25
                    16:9 AFD 10  value= 26
                    16:9 AFD 11  value= 27
                    16:9 AFD 12  value= 28
                    16:9 AFD 13  value= 29
                    16:9 AFD 14  value= 30
                    16:9 AFD 15  value= 31  "
        ::= { lC350CtrlEntries 10124 }


    iARCOutputSignallingConfigForceModeConfigSMPTERP186 OBJECT-TYPE
        SYNTAX            INTEGER {
                            val43(0),
                            val169(1)
                            }
        MAX-ACCESS        read-write
        STATUS            current
        DESCRIPTION
                "CMNT: - 
                 TYPE: - RadiobuttonList
                 PAGE: - Output Signalling Config
                    SMPTE RP186  cmdID= 10125
                    4:3  value= 0
                    16:9  value= 1  "
        ::= { lC350CtrlEntries 10125 }


    iARCOutputSignallingConfigForceModeConfigAFD OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val169AFD0(8),
                            val169AFD1(9),
                            val169AFD2(10),
                            val169AFD3(11),
                            val169AFD4(12),
                            val169AFD5(13),
                            val169AFD6(14),
                            val169AFD7(15)
                            }
        MAX-ACCESS        read-write
        STATUS            current
        DESCRIPTION
                "CMNT: - 
                 TYPE: - RadiobuttonList
                 PAGE: - Output Signalling Config
                    AFD  cmdID= 10122
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    16:9 AFD 0  value= 8
                    16:9 AFD 1  value= 9
                    16:9 AFD 2  value= 10
                    16:9 AFD 3  value= 11
                    16:9 AFD 4  value= 12
                    16:9 AFD 5  value= 13
                    16:9 AFD 6  value= 14
                    16:9 AFD 7  value= 15  "
        ::= { lC350CtrlEntries 10122 }


    iARCOutputSignallingConfigForceModeConfigETSI OBJECT-TYPE
        SYNTAX            INTEGER {
                            val43FullFormat(0),
                            val149BoxCentre(1),
                            val149BoxTop(2),
                            val169BoxCentre(3),
                            val169BoxTop(4),
                            valBox169Centre(5),
                            val43SP149Centre(6),
                            val169FullFormat(7)
                            }
        MAX-ACCESS        read-write
        STATUS            current
        DESCRIPTION
                "CMNT: - 
                 TYPE: - RadiobuttonList
                 PAGE: - Output Signalling Config
                    ETSI  cmdID= 10123
                    4:3 Full Format  value= 0
                    14:9 Box Centre  value= 1
                    14:9 Box Top  value= 2
                    16:9 Box Centre  value= 3
                    16:9 Box Top  value= 4
                    Box > 16:9 Centre  value= 5
                    4:3 SP 14:9 Centre  value= 6
                    16:9 Full Format  value= 7  "
        ::= { lC350CtrlEntries 10123 }


    iAudioRoutingInputPairsStatusEmbedded1 OBJECT-TYPE
        SYNTAX            RollCallString
        MAX-ACCESS        read-only
        STATUS            current
        DESCRIPTION
                "CMNT: - 
                 TYPE: - Display
                 PAGE: - Audio Routing
                    Embedded 1  cmdID= 10148  "
        ::= { lC350CtrlEntries 10148 }


    iAudioRoutingInputPairsStatusEmbedded2 OBJECT-TYPE
        SYNTAX            RollCallString
        MAX-ACCESS        read-only
        STATUS            current
        DESCRIPTION
                "CMNT: - 
                 TYPE: - Display
                 PAGE: - Audio Routing
                    Embedded 2  cmdID= 10149  "
        ::= { lC350CtrlEntries 10149 }


    iAudioRoutingInputPairsStatusEmbedded3 OBJECT-TYPE
        SYNTAX            RollCallString
        MAX-ACCESS        read-only
        STATUS            current
        DESCRIPTION
                "CMNT: - 
                 TYPE: - Display
                 PAGE: - Audio Routing
                    Embedded 3  cmdID= 10150  "
        ::= { lC350CtrlEntries 10150 }


    iAudioRoutingInputPairsStatusEmbedded4 OBJECT-TYPE
        SYNTAX            RollCallString
        MAX-ACCESS        read-only
        STATUS            current
        DESCRIPTION
                "CMNT: - 
                 TYPE: - Display
                 PAGE: - Audio Routing
                    Embedded 4  cmdID= 10151  "
        ::= { lC350CtrlEntries 10151 }


    iAudioRoutingInputPairsStatusEmbedded5 OBJECT-TYPE
        SYNTAX            RollCallString
        MAX-ACCESS        read-only
        STATUS            current
        DESCRIPTION
                "CMNT: - 
                 TYPE: - Display
                 PAGE: - Audio Routing
                    Embedded 5  cmdID= 10152  "
        ::= { lC350CtrlEntries 10152 }


    iAudioRoutingInputPairsStatusEmbedded6 OBJECT-TYPE
        SYNTAX            RollCallString
        MAX-ACCESS        read-only
        STATUS            current
        DESCRIPTION
                "CMNT: - 
                 TYPE: - Display
                 PAGE: - Audio Routing
                    Embedded 6  cmdID= 10153  "
        ::= { lC350CtrlEntries 10153 }


    iAudioRoutingInputPairsStatusEmbedded7 OBJECT-TYPE
        SYNTAX            RollCallString
        MAX-ACCESS        read-only
        STATUS            current
        DESCRIPTION
                "CMNT: - 
                 TYPE: - Display
                 PAGE: - Audio Routing
                    Embedded 7  cmdID= 10154  "
        ::= { lC350CtrlEntries 10154 }


    iAudioRoutingInputPairsStatusEmbedded8 OBJECT-TYPE
        SYNTAX            RollCallString
        MAX-ACCESS        read-only
        STATUS            current
        DESCRIPTION
                "CMNT: - 
                 TYPE: - Display
                 PAGE: - Audio Routing
                    Embedded 8  cmdID= 10155  "
        ::= { lC350CtrlEntries 10155 }


    iAudioRoutingInputPairsStatusAES1 OBJECT-TYPE
        SYNTAX            RollCallString
        MAX-ACCESS        read-only
        STATUS            current
        DESCRIPTION
                "CMNT: - 
                 TYPE: - Display
                 PAGE: - Audio Routing
                    AES 1  cmdID= 10156  "
        ::= { lC350CtrlEntries 10156 }


    iAudioRoutingInputPairsStatusAES2 OBJECT-TYPE
        SYNTAX            RollCallString
        MAX-ACCESS        read-only
        STATUS            current
        DESCRIPTION
                "CMNT: - 
                 TYPE: - Display
                 PAGE: - Audio Routing
                    AES 2  cmdID= 10157  "
        ::= { lC350CtrlEntries 10157 }


    iAudioRoutingInputPairsStatusAES3 OBJECT-TYPE
        SYNTAX            RollCallString
        MAX-ACCESS        read-only
        STATUS            current
        DESCRIPTION
                "CMNT: - 
                 TYPE: - Display
                 PAGE: - Audio Routing
                    AES 3  cmdID= 10158  "
        ::= { lC350CtrlEntries 10158 }


    iAudioRoutingInputPairsStatusAES4 OBJECT-TYPE
        SYNTAX            RollCallString
        MAX-ACCESS        read-only
        STATUS            current
        DESCRIPTION
                "CMNT: - 
                 TYPE: - Display
                 PAGE: - Audio Routing
                    AES 4  cmdID= 10159  "
        ::= { lC350CtrlEntries 10159 }


    iAudioRoutingInputPairsStatusAES5 OBJECT-TYPE
        SYNTAX            RollCallString
        MAX-ACCESS        read-only
        STATUS            current
        DESCRIPTION
                "CMNT: - 
                 TYPE: - Display
                 PAGE: - Audio Routing
                    AES 5  cmdID= 10160  "
        ::= { lC350CtrlEntries 10160 }


    iAudioRoutingInputPairsStatusAES6 OBJECT-TYPE
        SYNTAX            RollCallString
        MAX-ACCESS        read-only
        STATUS            current
        DESCRIPTION
                "CMNT: - 
                 TYPE: - Display
                 PAGE: - Audio Routing
                    AES 6  cmdID= 10161  "
        ::= { lC350CtrlEntries 10161 }


    iAudioRoutingInputPairsStatusAES7 OBJECT-TYPE
        SYNTAX            RollCallString
        MAX-ACCESS        read-only
        STATUS            current
        DESCRIPTION
                "CMNT: - 
                 TYPE: - Display
                 PAGE: - Audio Routing
                    AES 7  cmdID= 10162  "
        ::= { lC350CtrlEntries 10162 }


    iAudioRoutingInputPairsStatusAES8 OBJECT-TYPE
        SYNTAX            RollCallString
        MAX-ACCESS        read-only
        STATUS            current
        DESCRIPTION
                "CMNT: - 
                 TYPE: - Display
                 PAGE: - Audio Routing
                    AES 8  cmdID= 10163  "
        ::= { lC350CtrlEntries 10163 }


    iAudioRoutingInputPairsStatusAnalog1 OBJECT-TYPE
        SYNTAX            RollCallString
        MAX-ACCESS        read-only
        STATUS            current
        DESCRIPTION
                "CMNT: - 
                 TYPE: - Display
                 PAGE: - Audio Routing
                    Analog 1  cmdID= 10164  "
        ::= { lC350CtrlEntries 10164 }


    iAudioRoutingInputPairsStatusAnalog2 OBJECT-TYPE
        SYNTAX            RollCallString
        MAX-ACCESS        read-only
        STATUS            current
        DESCRIPTION
                "CMNT: - 
                 TYPE: - Display
                 PAGE: - Audio Routing
                    Analog 2  cmdID= 10165  "
        ::= { lC350CtrlEntries 10165 }


    iAudioRoutingInputPairsStatusDolbyDecoder1 OBJECT-TYPE
        SYNTAX            RollCallString
        MAX-ACCESS        read-only
        STATUS            current
        DESCRIPTION
                "CMNT: - 
                 TYPE: - Display
                 PAGE: - Audio Routing
                    Dolby Decoder 1  cmdID= 10166  "
        ::= { lC350CtrlEntries 10166 }


    iAudioRoutingInputPairsStatusDolbyDecoder2 OBJECT-TYPE
        SYNTAX            RollCallString
        MAX-ACCESS        read-only
        STATUS            current
        DESCRIPTION
                "CMNT: - 
                 TYPE: - Display
                 PAGE: - Audio Routing
                    Dolby Decoder 2  cmdID= 10167  "
        ::= { lC350CtrlEntries 10167 }


    iAudioRoutingInputPairsStatusDolbyDecoder3 OBJECT-TYPE
        SYNTAX            RollCallString
        MAX-ACCESS        read-only
        STATUS            current
        DESCRIPTION
                "CMNT: - 
                 TYPE: - Display
                 PAGE: - Audio Routing
                    Dolby Decoder 3  cmdID= 10168  "
        ::= { lC350CtrlEntries 10168 }


    iAudioRoutingInputPairsStatusDolbyDecoder4 OBJECT-TYPE
        SYNTAX            RollCallString
        MAX-ACCESS        read-only
        STATUS            current
        DESCRIPTION
                "CMNT: - 
                 TYPE: - Display
                 PAGE: - Audio Routing
                    Dolby Decoder 4  cmdID= 10169  "
        ::= { lC350CtrlEntries 10169 }


    iAudioRoutingInputPairsStatusDolbyDownmix OBJECT-TYPE
        SYNTAX            RollCallString
        MAX-ACCESS        read-only
        STATUS            current
        DESCRIPTION
                "CMNT: - 
                 TYPE: - Display
                 PAGE: - Audio Routing
                    Dolby Downmix  cmdID= 10170  "
        ::= { lC350CtrlEntries 10170 }


    iAudioRoutingInputPairsStatusDolbyEncoder OBJECT-TYPE
        SYNTAX            RollCallString
        MAX-ACCESS        read-only
        STATUS            current
        DESCRIPTION
                "CMNT: - 
                 TYPE: - Display
                 PAGE: - Audio Routing
                    Dolby Encoder  cmdID= 10171  "
        ::= { lC350CtrlEntries 10171 }


    iProcessPairs18Pair1InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAES5(13),
                            valAES6(14),
                            valAES7(15),
                            valAES8(16),
                            valAnalog1(17),
                            valAnalog2(18),
                            valDolbyDecoder1(19),
                            valDolbyDecoder2(20),
                            valDolbyDecoder3(21),
                            valDolbyDecoder4(22),
                            valDolbyDownmix(23),
                            valDolbyEncoder(24)
                            }
        MAX-ACCESS        read-write
        STATUS            current
        DESCRIPTION
                "CMNT: - 
                 TYPE: - RadiobuttonList
                 PAGE: - Process Pairs 1-8
                    Input Pairs Source  cmdID= 10140
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    AES 5  value= 13
                    AES 6  value= 14
                    AES 7  value= 15
                    AES 8  value= 16
                    Analog 1  value= 17
                    Analog 2  value= 18
                    Dolby Decoder 1  value= 19
                    Dolby Decoder 2  value= 20
                    Dolby Decoder 3  value= 21
                    Dolby Decoder 4  value= 22
                    Dolby Downmix  value= 23
                    Dolby Encoder  value= 24  "
        ::= { lC350CtrlEntries 10140 }


    iProcessPairs18Pair2InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAES5(13),
                            valAES6(14),
                            valAES7(15),
                            valAES8(16),
                            valAnalog1(17),
                            valAnalog2(18),
                            valDolbyDecoder1(19),
                            valDolbyDecoder2(20),
                            valDolbyDecoder3(21),
                            valDolbyDecoder4(22),
                            valDolbyDownmix(23),
                            valDolbyEncoder(24)
                            }
        MAX-ACCESS        read-write
        STATUS            current
        DESCRIPTION
                "CMNT: - 
                 TYPE: - RadiobuttonList
                 PAGE: - Process Pairs 1-8
                    Input Pairs Source  cmdID= 10141
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    AES 5  value= 13
                    AES 6  value= 14
                    AES 7  value= 15
                    AES 8  value= 16
                    Analog 1  value= 17
                    Analog 2  value= 18
                    Dolby Decoder 1  value= 19
                    Dolby Decoder 2  value= 20
                    Dolby Decoder 3  value= 21
                    Dolby Decoder 4  value= 22
                    Dolby Downmix  value= 23
                    Dolby Encoder  value= 24  "
        ::= { lC350CtrlEntries 10141 }


    iProcessPairs18Pair3InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAES5(13),
                            valAES6(14),
                            valAES7(15),
                            valAES8(16),
                            valAnalog1(17),
                            valAnalog2(18),
                            valDolbyDecoder1(19),
                            valDolbyDecoder2(20),
                            valDolbyDecoder3(21),
                            valDolbyDecoder4(22),
                            valDolbyDownmix(23),
                            valDolbyEncoder(24)
                            }
        MAX-ACCESS        read-write
        STATUS            current
        DESCRIPTION
                "CMNT: - 
                 TYPE: - RadiobuttonList
                 PAGE: - Process Pairs 1-8
                    Input Pairs Source  cmdID= 10142
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    AES 5  value= 13
                    AES 6  value= 14
                    AES 7  value= 15
                    AES 8  value= 16
                    Analog 1  value= 17
                    Analog 2  value= 18
                    Dolby Decoder 1  value= 19
                    Dolby Decoder 2  value= 20
                    Dolby Decoder 3  value= 21
                    Dolby Decoder 4  value= 22
                    Dolby Downmix  value= 23
                    Dolby Encoder  value= 24  "
        ::= { lC350CtrlEntries 10142 }


    iProcessPairs18Pair4InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAES5(13),
                            valAES6(14),
                            valAES7(15),
                            valAES8(16),
                            valAnalog1(17),
                            valAnalog2(18),
                            valDolbyDecoder1(19),
                            valDolbyDecoder2(20),
                            valDolbyDecoder3(21),
                            valDolbyDecoder4(22),
                            valDolbyDownmix(23),
                            valDolbyEncoder(24)
                            }
        MAX-ACCESS        read-write
        STATUS            current
        DESCRIPTION
                "CMNT: - 
                 TYPE: - RadiobuttonList
                 PAGE: - Process Pairs 1-8
                    Input Pairs Source  cmdID= 10143
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    AES 5  value= 13
                    AES 6  value= 14
                    AES 7  value= 15
                    AES 8  value= 16
                    Analog 1  value= 17
                    Analog 2  value= 18
                    Dolby Decoder 1  value= 19
                    Dolby Decoder 2  value= 20
                    Dolby Decoder 3  value= 21
                    Dolby Decoder 4  value= 22
                    Dolby Downmix  value= 23
                    Dolby Encoder  value= 24  "
        ::= { lC350CtrlEntries 10143 }


    iProcessPairs18Pair5InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAES5(13),
                            valAES6(14),
                            valAES7(15),
                            valAES8(16),
                            valAnalog1(17),
                            valAnalog2(18),
                            valDolbyDecoder1(19),
                            valDolbyDecoder2(20),
                            valDolbyDecoder3(21),
                            valDolbyDecoder4(22),
                            valDolbyDownmix(23),
                            valDolbyEncoder(24)
                            }
        MAX-ACCESS        read-write
        STATUS            current
        DESCRIPTION
                "CMNT: - 
                 TYPE: - RadiobuttonList
                 PAGE: - Process Pairs 1-8
                    Input Pairs Source  cmdID= 10144
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    AES 5  value= 13
                    AES 6  value= 14
                    AES 7  value= 15
                    AES 8  value= 16
                    Analog 1  value= 17
                    Analog 2  value= 18
                    Dolby Decoder 1  value= 19
                    Dolby Decoder 2  value= 20
                    Dolby Decoder 3  value= 21
                    Dolby Decoder 4  value= 22
                    Dolby Downmix  value= 23
                    Dolby Encoder  value= 24  "
        ::= { lC350CtrlEntries 10144 }


    iProcessPairs18Pair6InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAES5(13),
                            valAES6(14),
                            valAES7(15),
                            valAES8(16),
                            valAnalog1(17),
                            valAnalog2(18),
                            valDolbyDecoder1(19),
                            valDolbyDecoder2(20),
                            valDolbyDecoder3(21),
                            valDolbyDecoder4(22),
                            valDolbyDownmix(23),
                            valDolbyEncoder(24)
                            }
        MAX-ACCESS        read-write
        STATUS            current
        DESCRIPTION
                "CMNT: - 
                 TYPE: - RadiobuttonList
                 PAGE: - Process Pairs 1-8
                    Input Pairs Source  cmdID= 10145
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    AES 5  value= 13
                    AES 6  value= 14
                    AES 7  value= 15
                    AES 8  value= 16
                    Analog 1  value= 17
                    Analog 2  value= 18
                    Dolby Decoder 1  value= 19
                    Dolby Decoder 2  value= 20
                    Dolby Decoder 3  value= 21
                    Dolby Decoder 4  value= 22
                    Dolby Downmix  value= 23
                    Dolby Encoder  value= 24  "
        ::= { lC350CtrlEntries 10145 }


    iProcessPairs18Pair7InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAES5(13),
                            valAES6(14),
                            valAES7(15),
                            valAES8(16),
                            valAnalog1(17),
                            valAnalog2(18),
                            valDolbyDecoder1(19),
                            valDolbyDecoder2(20),
                            valDolbyDecoder3(21),
                            valDolbyDecoder4(22),
                            valDolbyDownmix(23),
                            valDolbyEncoder(24)
                            }
        MAX-ACCESS        read-write
        STATUS            current
        DESCRIPTION
                "CMNT: - 
                 TYPE: - RadiobuttonList
                 PAGE: - Process Pairs 1-8
                    Input Pairs Source  cmdID= 10146
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    AES 5  value= 13
                    AES 6  value= 14
                    AES 7  value= 15
                    AES 8  value= 16
                    Analog 1  value= 17
                    Analog 2  value= 18
                    Dolby Decoder 1  value= 19
                    Dolby Decoder 2  value= 20
                    Dolby Decoder 3  value= 21
                    Dolby Decoder 4  value= 22
                    Dolby Downmix  value= 23
                    Dolby Encoder  value= 24  "
        ::= { lC350CtrlEntries 10146 }


    iProcessPairs18Pair8InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAES5(13),
                            valAES6(14),
                            valAES7(15),
                            valAES8(16),
                            valAnalog1(17),
                            valAnalog2(18),
                            valDolbyDecoder1(19),
                            valDolbyDecoder2(20),
                            valDolbyDecoder3(21),
                            valDolbyDecoder4(22),
                            valDolbyDownmix(23),
                            valDolbyEncoder(24)
                            }
        MAX-ACCESS        read-write
        STATUS            current
        DESCRIPTION
                "CMNT: - 
                 TYPE: - RadiobuttonList
                 PAGE: - Process Pairs 1-8
                    Input Pairs Source  cmdID= 10147
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    AES 5  value= 13
                    AES 6  value= 14
                    AES 7  value= 15
                    AES 8  value= 16
                    Analog 1  value= 17
                    Analog 2  value= 18
                    Dolby Decoder 1  value= 19
                    Dolby Decoder 2  value= 20
                    Dolby Decoder 3  value= 21
                    Dolby Decoder 4  value= 22
                    Dolby Downmix  value= 23
                    Dolby Encoder  value= 24  "
        ::= { lC350CtrlEntries 10147 }


    iAudioRoutingProcessPairs18StatusPair1 OBJECT-TYPE
        SYNTAX            RollCallString
        MAX-ACCESS        read-only
        STATUS            current
        DESCRIPTION
                "CMNT: - 
                 TYPE: - Display
                 PAGE: - Audio Routing
                    Pair 1  cmdID= 10172  "
        ::= { lC350CtrlEntries 10172 }


    iAudioRoutingProcessPairs18StatusPair2 OBJECT-TYPE
        SYNTAX            RollCallString
        MAX-ACCESS        read-only
        STATUS            current
        DESCRIPTION
                "CMNT: - 
                 TYPE: - Display
                 PAGE: - Audio Routing
                    Pair 2  cmdID= 10173  "
        ::= { lC350CtrlEntries 10173 }


    iAudioRoutingProcessPairs18StatusPair3 OBJECT-TYPE
        SYNTAX            RollCallString
        MAX-ACCESS        read-only
        STATUS            current
        DESCRIPTION
                "CMNT: - 
                 TYPE: - Display
                 PAGE: - Audio Routing
                    Pair 3  cmdID= 10174  "
        ::= { lC350CtrlEntries 10174 }


    iAudioRoutingProcessPairs18StatusPair4 OBJECT-TYPE
        SYNTAX            RollCallString
        MAX-ACCESS        read-only
        STATUS            current
        DESCRIPTION
                "CMNT: - 
                 TYPE: - Display
                 PAGE: - Audio Routing
                    Pair 4  cmdID= 10175  "
        ::= { lC350CtrlEntries 10175 }


    iAudioRoutingProcessPairs18StatusPair5 OBJECT-TYPE
        SYNTAX            RollCallString
        MAX-ACCESS        read-only
        STATUS            current
        DESCRIPTION
                "CMNT: - 
                 TYPE: - Display
                 PAGE: - Audio Routing
                    Pair 5  cmdID= 10176  "
        ::= { lC350CtrlEntries 10176 }


    iAudioRoutingProcessPairs18StatusPair6 OBJECT-TYPE
        SYNTAX            RollCallString
        MAX-ACCESS        read-only
        STATUS            current
        DESCRIPTION
                "CMNT: - 
                 TYPE: - Display
                 PAGE: - Audio Routing
                    Pair 6  cmdID= 10177  "
        ::= { lC350CtrlEntries 10177 }


    iAudioRoutingProcessPairs18StatusPair7 OBJECT-TYPE
        SYNTAX            RollCallString
        MAX-ACCESS        read-only
        STATUS            current
        DESCRIPTION
                "CMNT: - 
                 TYPE: - Display
                 PAGE: - Audio Routing
                    Pair 7  cmdID= 10178  "
        ::= { lC350CtrlEntries 10178 }


    iAudioRoutingProcessPairs18StatusPair8 OBJECT-TYPE
        SYNTAX            RollCallString
        MAX-ACCESS        read-only
        STATUS            current
        DESCRIPTION
                "CMNT: - 
                 TYPE: - Display
                 PAGE: - Audio Routing
                    Pair 8  cmdID= 10179  "
        ::= { lC350CtrlEntries 10179 }


    iOutputPairs18OutputPair1LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10180
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10180 }


    iOutputPairs18OutputPair1LInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10196  "
        ::= { lC350CtrlEntries 10196 }


    iOutputPairs18OutputPair1LControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10212
                    Tone  value= 1  "
        ::= { lC350CtrlEntries 10212 }


    iOutputPairs18OutputPair1RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10188
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10188 }


    iOutputPairs18OutputPair1RInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10204  "
        ::= { lC350CtrlEntries 10204 }


    iOutputPairs18OutputPair1RControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10220
                    Tone  value= 1  "
        ::= { lC350CtrlEntries 10220 }


    iOutputPairs18OutputPair2LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10181
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10181 }


    iOutputPairs18OutputPair2LInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10197  "
        ::= { lC350CtrlEntries 10197 }


    iOutputPairs18OutputPair2LControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10213
                    Tone  value= 1  "
        ::= { lC350CtrlEntries 10213 }


    iOutputPairs18OutputPair2RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10189
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10189 }


    iOutputPairs18OutputPair2RInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10205  "
        ::= { lC350CtrlEntries 10205 }


    iOutputPairs18OutputPair2RControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10221
                    Tone  value= 1  "
        ::= { lC350CtrlEntries 10221 }


    iOutputPairs18OutputPair3LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10182
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10182 }


    iOutputPairs18OutputPair3LInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10198  "
        ::= { lC350CtrlEntries 10198 }


    iOutputPairs18OutputPair3LControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10214
                    Tone  value= 1  "
        ::= { lC350CtrlEntries 10214 }


    iOutputPairs18OutputPair3RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10190
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10190 }


    iOutputPairs18OutputPair3RInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10206  "
        ::= { lC350CtrlEntries 10206 }


    iOutputPairs18OutputPair3RControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10222
                    Tone  value= 1  "
        ::= { lC350CtrlEntries 10222 }


    iOutputPairs18OutputPair4LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10183
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10183 }


    iOutputPairs18OutputPair4LInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10199  "
        ::= { lC350CtrlEntries 10199 }


    iOutputPairs18OutputPair4LControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10215
                    Tone  value= 1  "
        ::= { lC350CtrlEntries 10215 }


    iOutputPairs18OutputPair4RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10191
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10191 }


    iOutputPairs18OutputPair4RInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10207  "
        ::= { lC350CtrlEntries 10207 }


    iOutputPairs18OutputPair4RControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10223
                    Tone  value= 1  "
        ::= { lC350CtrlEntries 10223 }


    iOutputPairs18OutputPair5LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10184
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10184 }


    iOutputPairs18OutputPair5LInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10200  "
        ::= { lC350CtrlEntries 10200 }


    iOutputPairs18OutputPair5LControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10216
                    Tone  value= 1  "
        ::= { lC350CtrlEntries 10216 }


    iOutputPairs18OutputPair5RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10192
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10192 }


    iOutputPairs18OutputPair5RInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10208  "
        ::= { lC350CtrlEntries 10208 }


    iOutputPairs18OutputPair5RControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10224
                    Tone  value= 1  "
        ::= { lC350CtrlEntries 10224 }


    iOutputPairs18OutputPair6LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10185
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10185 }


    iOutputPairs18OutputPair6LInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10201  "
        ::= { lC350CtrlEntries 10201 }


    iOutputPairs18OutputPair6LControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10217
                    Tone  value= 1  "
        ::= { lC350CtrlEntries 10217 }


    iOutputPairs18OutputPair6RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10193
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10193 }


    iOutputPairs18OutputPair6RInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10209  "
        ::= { lC350CtrlEntries 10209 }


    iOutputPairs18OutputPair6RControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10225
                    Tone  value= 1  "
        ::= { lC350CtrlEntries 10225 }


    iOutputPairs18OutputPair7LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10186
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10186 }


    iOutputPairs18OutputPair7LInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10202  "
        ::= { lC350CtrlEntries 10202 }


    iOutputPairs18OutputPair7LControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10218
                    Tone  value= 1  "
        ::= { lC350CtrlEntries 10218 }


    iOutputPairs18OutputPair7RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10194
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10194 }


    iOutputPairs18OutputPair7RInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10210  "
        ::= { lC350CtrlEntries 10210 }


    iOutputPairs18OutputPair7RControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10226
                    Tone  value= 1  "
        ::= { lC350CtrlEntries 10226 }


    iOutputPairs18OutputPair8LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10187
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10187 }


    iOutputPairs18OutputPair8LInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10203  "
        ::= { lC350CtrlEntries 10203 }


    iOutputPairs18OutputPair8LControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10219
                    Tone  value= 1  "
        ::= { lC350CtrlEntries 10219 }


    iOutputPairs18OutputPair8RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Output Pairs 1-8
                    Process Pairs Source  cmdID= 10195
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { lC350CtrlEntries 10195 }


    iOutputPairs18OutputPair8RInvertPhase OBJECT-TYPE
        SYNTAX            INTEGER { disable(0), enable(1)  }
        MAX-ACCESS        read-write
        STATUS            current
        DESCRIPTION
                "CMNT: - 
                 TYPE: - Checkbox
                 PAGE: - Output Pairs 1-8
                    Invert Phase  cmdID= 10211  "
        ::= { lC350CtrlEntries 10211 }


    iOutputPairs18OutputPair8RControl OBJECT-TYPE
        SYNTAX            INTEGER {
                            valTone(1)
                            }
        MAX-ACCESS        read-write
        STATUS            current
        DESCRIPTION
                "CMNT: - 
                 TYPE: - RadiobuttonList
                 PAGE: - Output Pairs 1-8
                    Control  cmdID= 10227
                    Tone  value= 1  "
        ::= { lC350CtrlEntries 10227 }


    iAudioShuffleOutputPairs18StatusPair1 OBJECT-TYPE
        SYNTAX            RollCallString
        MAX-ACCESS        read-only
        STATUS            current
        DESCRIPTION
                "CMNT: - 
                 TYPE: - Display
                 PAGE: - Audio Shuffle
                    Pair 1  cmdID= 10228  "
        ::= { lC350CtrlEntries 10228 }


    iAudioShuffleOutputPairs18StatusPair2 OBJECT-TYPE
        SYNTAX            RollCallString
        MAX-ACCESS        read-only
        STATUS            current
        DESCRIPTION
                "CMNT: - 
                 TYPE: - Display
                 PAGE: - Audio Shuffle
                    Pair 2  cmdID= 10229  "
        ::= { lC350CtrlEntries 10229 }


    iAudioShuffleOutputPairs18StatusPair3 OBJECT-TYPE
        SYNTAX            RollCallString
        MAX-ACCESS        read-only
        STATUS            current
        DESCRIPTION
                "CMNT: - 
                 TYPE: - Display
                 PAGE: - Audio Shuffle
                    Pair 3  cmdID= 10230  "
        ::= { lC350CtrlEntries 10230 }


    iAudioShuffleOutputPairs18StatusPair4 OBJECT-TYPE
        SYNTAX            RollCallString
        MAX-ACCESS        read-only
        STATUS            current
        DESCRIPTION
                "CMNT: - 
                 TYPE: - Display
                 PAGE: - Audio Shuffle
                    Pair 4  cmdID= 10231  "
        ::= { lC350CtrlEntries 10231 }


    iAudioShuffleOutputPairs18StatusPair5 OBJECT-TYPE
        SYNTAX            RollCallString
        MAX-ACCESS        read-only
        STATUS            current
        DESCRIPTION
                "CMNT: - 
                 TYPE: - Display
                 PAGE: - Audio Shuffle
                    Pair 5  cmdID= 10232  "
        ::= { lC350CtrlEntries 10232 }


    iAudioShuffleOutputPairs18StatusPair6 OBJECT-TYPE
        SYNTAX            RollCallString
        MAX-ACCESS        read-only
        STATUS            current
        DESCRIPTION
                "CMNT: - 
                 TYPE: - Display
                 PAGE: - Audio Shuffle
                    Pair 6  cmdID= 10233  "
        ::= { lC350CtrlEntries 10233 }


    iAudioShuffleOutputPairs18StatusPair7 OBJECT-TYPE
        SYNTAX            RollCallString
        MAX-ACCESS        read-only
        STATUS            current
        DESCRIPTION
                "CMNT: - 
                 TYPE: - Display
                 PAGE: - Audio Shuffle
                    Pair 7  cmdID= 10234  "
        ::= { lC350CtrlEntries 10234 }


    iAudioShuffleOutputPairs18StatusPair8 OBJECT-TYPE
        SYNTAX            RollCallString
        MAX-ACCESS        read-only
        STATUS            current
        DESCRIPTION
                "CMNT: - 
                 TYPE: - Display
                 PAGE: - Audio Shuffle
                    Pair 8  cmdID= 10235  "
        ::= { lC350CtrlEntries 10235 }


    iAudioShuffleNewDisplay OBJECT-TYPE
        SYNTAX            RollCallString
        MAX-ACCESS        read-only
        STATUS            current
        DESCRIPTION
                "CMNT: - Hide CH2 Controls
                 TYPE: - Display
                 PAGE: - Audio Shuffle
                    New Display  cmdID= 10515  "
        ::= { lC350CtrlEntries 10515 }


    iAudioControlGainPair1L OBJECT-TYPE
        SYNTAX            INTEGER
        MAX-ACCESS        read-write
        STATUS            current
        DESCRIPTION
                "CMNT: - 
                 TYPE: - Number
                 PAGE: - Audio Control
                    Pair 1 L  cmdID= 10236
                    min= -180  max= 180  step= 1  format= %0.1fdB  div_scale= 10  preset= 0
                    Min = -18.0dB  Max = 18.0dB  Step = 0.1dB  Preset = 0.0dB  "
        ::= { lC350CtrlEntries 10236 }


    iAudioControlGainPair1R OBJECT-TYPE
        SYNTAX            INTEGER
        MAX-ACCESS        read-write
        STATUS            current
        DESCRIPTION
                "CMNT: - 
                 TYPE: - Number
                 PAGE: - Audio Control
                    Pair 1 R  cmdID= 10237
                    min= -180  max= 180  step= 1  format= %0.1fdB  div_scale= 10  preset= 0
                    Min = -18.0dB  Max = 18.0dB  Step = 0.1dB  Preset = 0.0dB  "
        ::= { lC350CtrlEntries 10237 }


    iAudioControlGainPair2L OBJECT-TYPE
        SYNTAX            INTEGER
        MAX-ACCESS        read-write
        STATUS            current
        DESCRIPTION
                "CMNT: - 
                 TYPE: - Number
                 PAGE: - Audio Control
                    Pair 2 L  cmdID= 10238
                    min= -180  max= 180  step= 1  format= %0.1fdB  div_scale= 10  preset= 0
                    Min = -18.0dB  Max = 18.0dB  Step = 0.1dB  Preset = 0.0dB  "
        ::= { lC350CtrlEntries 10238 }


    iAudioControlGainPair2R OBJECT-TYPE
        SYNTAX            INTEGER
        MAX-ACCESS        read-write
        STATUS            current
        DESCRIPTION
                "CMNT: - 
                 TYPE: - Number
                 PAGE: - Audio Control
                    Pair 2 R  cmdID= 10239
                    min= -180  max= 180  step= 1  format= %0.1fdB  div_scale= 10  preset= 0
                    Min = -18.0dB  Max = 18.0dB  Step = 0.1dB  Preset = 0.0dB  "
        ::= { lC350CtrlEntries 10239 }


    iAudioControlGainPair3L OBJECT-TYPE
        SYNTAX            INTEGER
        MAX-ACCESS        read-write
        STATUS            current
        DESCRIPTION
                "CMNT: - 
                 TYPE: - Number
                 PAGE: - Audio Control
                    Pair 3 L  cmdID= 10240
                    min= -180  max= 180  step= 1  format= %0.1fdB  div_scale= 10  preset= 0
                    Min = -18.0dB  Max = 18.0dB  Step = 0.1dB  Preset = 0.0dB  "
        ::= { lC350CtrlEntries 10240 }


    iAudioControlGainPair3R OBJECT-TYPE
        SYNTAX            INTEGER
        MAX-ACCESS        read-write
        STATUS            current
        DESCRIPTION
                "CMNT: - 
                 TYPE: - Number
                 PAGE: - Audio Control
                    Pair 3 R  cmdID= 10241
                    min= -180  max= 180  step= 1  format= %0.1fdB  div_scale= 10  preset= 0
                    Min = -18.0dB  Max = 18.0dB  Step = 0.1dB  Preset = 0.0dB  "
        ::= { lC350CtrlEntries 10241 }


    iAudioControlGainPair4L OBJECT-TYPE
        SYNTAX            INTEGER
        MAX-ACCESS        read-write
        STATUS            current
        DESCRIPTION
                "CMNT: - 
                 TYPE: - Number
                 PAGE: - Audio Control
                    Pair 4 L  cmdID= 10242
                    min= -180  max= 180  step= 1  format= %0.1fdB  div_scale= 10  preset= 0
                    Min = -18.0dB  Max = 18.0dB  Step = 0.1dB  Preset = 0.0dB  "
        ::= { lC350CtrlEntries 10242 }


    iAudioControlGainPair4R OBJECT-TYPE
        SYNTAX            INTEGER
        MAX-ACCESS        read-write
        STATUS            current
        DESCRIPTION
                "CMNT: - 
                 TYPE: - Number
                 PAGE: - Audio Control
                    Pair 4 R  cmdID= 10243
                    min= -180  max= 180  step= 1  format= %0.1fdB  div_scale= 10  preset= 0
                    Min = -18.0dB  Max = 18.0dB  Step = 0.1dB  Preset = 0.0dB  "
        ::= { lC350CtrlEntries 10243 }


    iAudioControlGainPair5L OBJECT-TYPE
        SYNTAX            INTEGER
        MAX-ACCESS        read-write
        STATUS            current
        DESCRIPTION
                "CMNT: - 
                 TYPE: - Number
                 PAGE: - Audio Control
                    Pair 5 L  cmdID= 10244
                    min= -180  max= 180  step= 1  format= %0.1fdB  div_scale= 10  preset= 0
                    Min = -18.0dB  Max = 18.0dB  Step = 0.1dB  Preset = 0.0dB  "
        ::= { lC350CtrlEntries 10244 }


    iAudioControlGainPair5R OBJECT-TYPE
        SYNTAX            INTEGER
        MAX-ACCESS        read-write
        STATUS            current
        DESCRIPTION
                "CMNT: - 
                 TYPE: - Number
                 PAGE: - Audio Control
                    Pair 5 R  cmdID= 10245
                    min= -180  max= 180  step= 1  format= %0.1fdB  div_scale= 10  preset= 0
                    Min = -18.0dB  Max = 18.0dB  Step = 0.1dB  Preset = 0.0dB  "
        ::= { lC350CtrlEntries 10245 }


    iAudioControlGainPair6L OBJECT-TYPE
        SYNTAX            INTEGER
        MAX-ACCESS        read-write
        STATUS            current
        DESCRIPTION
                "CMNT: - 
                 TYPE: - Number
                 PAGE: - Audio Control
                    Pair 6 L  cmdID= 10246
                    min= -180  max= 180  step= 1  format= %0.1fdB  div_scale= 10  preset= 0
                    Min = -18.0dB  Max = 18.0dB  Step = 0.1dB  Preset = 0.0dB  "
        ::= { lC350CtrlEntries 10246 }


    iAudioControlGainPair6R OBJECT-TYPE
        SYNTAX            INTEGER
        MAX-ACCESS        read-write
        STATUS            current
        DESCRIPTION
                "CMNT: - 
                 TYPE: - Number
                 PAGE: - Audio Control
                    Pair 6 R  cmdID= 10247
                    min= -180  max= 180  step= 1  format= %0.1fdB  div_scale= 10  preset= 0
                    Min = -18.0dB  Max = 18.0dB  Step = 0.1dB  Preset = 0.0dB  "
        ::= { lC350CtrlEntries 10247 }


    iAudioControlGainPair7L OBJECT-TYPE
        SYNTAX            INTEGER
        MAX-ACCESS        read-write
        STATUS            current
        DESCRIPTION
                "CMNT: - 
                 TYPE: - Number
                 PAGE: - Audio Control
                    Pair 7 L  cmdID= 10248
                    min= -180  max= 180  step= 1  format= %0.1fdB  div_scale= 10  preset= 0
                    Min = -18.0dB  Max = 18.0dB  Step = 0.1dB  Preset = 0.0dB  "
        ::= { lC350CtrlEntries 10248 }


    iAudioControlGainPair7R OBJECT-TYPE
        SYNTAX            INTEGER
        MAX-ACCESS        read-write
        STATUS            current
        DESCRIPTION
                "CMNT: - 
                 TYPE: - Number
                 PAGE: - Audio Control
                    Pair 7 R  cmdID= 10249
                    min= -180  max= 180  step= 1  format= %0.1fdB  div_scale= 10  preset= 0
                    Min = -18.0dB  Max = 18.0dB  Step = 0.1dB  Preset = 0.0dB  "
        ::= { lC350CtrlEntries 10249 }


    iAudioControlGainPair8L OBJECT-TYPE
        SYNTAX            INTEGER
        MAX-ACCESS        read-write
        STATUS            current
        DESCRIPTION
                "CMNT: - 
                 TYPE: - Number
                 PAGE: - Audio Control
                    Pair 8 L  cmdID= 10250
                    min= -180  max= 180  step= 1  format= %0.1fdB  div_scale= 10  preset= 0
                    Min = -18.0dB  Max = 18.0dB  Step = 0.1dB  Preset = 0.0dB  "
        ::= { lC350CtrlEntries 10250 }


    iAudioControlGainPair8R OBJECT-TYPE
        SYNTAX            INTEGER
        MAX-ACCESS        read-write
        STATUS            current
        DESCRIPTION
                "CMNT: - 
                 TYPE: - Number
                 PAGE: - Audio Control
                    Pair 8 R  cmdID= 10251
                    min= -180  max= 180  step= 1  format= %0.1fdB  div_scale= 10  preset= 0
                    Min = -18.0dB  Max = 18.0dB  Step = 0.1dB  Preset = 0.0dB  "
        ::= { lC350CtrlEntries 10251 }


    iAudioControlToneFrequency OBJECT-TYPE
        SYNTAX            INTEGER
        MAX-ACCESS        read-write
        STATUS            current
        DESCRIPTION
                "CMNT: - 
                 TYPE: - Number
                 PAGE: - Audio Control
                    Tone Frequency  cmdID= 10252
                    min= 100  max= 10000  step= 100  format= %0.1f KHz  div_scale= 1000  preset= 1000
                    Min = 0.1 KHz  Max = 10.0 KHz  Step = 0.1 KHz  Preset = 1.0 KHz  "
        ::= { lC350CtrlEntries 10252 }


    iAudioControlDolbyEAlignmentOffset OBJECT-TYPE
        SYNTAX            INTEGER
        MAX-ACCESS        read-write
        STATUS            current
        DESCRIPTION
                "CMNT: - 
                 TYPE: - Number
                 PAGE: - Audio Control
                    Dolby E Alignment Offset  cmdID= 10253
                    min= -10  max= 10  step= 1  format= %0.0f Lines  div_scale= 1  preset= 0
                    Min = -10 Lines  Max = 10 Lines  Step = 1 Lines  Preset = 0 Lines  "
        ::= { lC350CtrlEntries 10253 }


    iAudioDelayGlobalDelayPairOffsetsPair1 OBJECT-TYPE
        SYNTAX            INTEGER
        MAX-ACCESS        read-write
        STATUS            current
        DESCRIPTION
                "CMNT: - 
                 TYPE: - Number
                 PAGE: - Delay
                    Pair 1  cmdID= 10254
                    min= -40  max= 200  step= 1  format= %0.0f ms  div_scale= 1  preset= 0
                    Min = -40 ms  Max = 200 ms  Step = 1 ms  Preset = 0 ms  "
        ::= { lC350CtrlEntries 10254 }


    iAudioDelayGlobalDelayPairOffsetsPair1Total OBJECT-TYPE
        SYNTAX            RollCallString
        MAX-ACCESS        read-only
        STATUS            current
        DESCRIPTION
                "CMNT: - 
                 TYPE: - Display
                 PAGE: - Delay
                    Pair 1 Total  cmdID= 10263  "
        ::= { lC350CtrlEntries 10263 }


    iAudioDelayGlobalDelayPairOffsetsPair2 OBJECT-TYPE
        SYNTAX            INTEGER
        MAX-ACCESS        read-write
        STATUS            current
        DESCRIPTION
                "CMNT: - 
                 TYPE: - Number
                 PAGE: - Delay
                    Pair 2  cmdID= 10255
                    min= -40  max= 200  step= 1  format= %0.0f ms  div_scale= 1  preset= 0
                    Min = -40 ms  Max = 200 ms  Step = 1 ms  Preset = 0 ms  "
        ::= { lC350CtrlEntries 10255 }


    iAudioDelayGlobalDelayPairOffsetsPair2Total OBJECT-TYPE
        SYNTAX            RollCallString
        MAX-ACCESS        read-only
        STATUS            current
        DESCRIPTION
                "CMNT: - 
                 TYPE: - Display
                 PAGE: - Delay
                    Pair 2 Total  cmdID= 10264  "
        ::= { lC350CtrlEntries 10264 }


    iAudioDelayGlobalDelayPairOffsetsPair3 OBJECT-TYPE
        SYNTAX            INTEGER
        MAX-ACCESS        read-write
        STATUS            current
        DESCRIPTION
                "CMNT: - 
                 TYPE: - Number
                 PAGE: - Delay
                    Pair 3  cmdID= 10256
                    min= -40  max= 200  step= 1  format= %0.0f ms  div_scale= 1  preset= 0
                    Min = -40 ms  Max = 200 ms  Step = 1 ms  Preset = 0 ms  "
        ::= { lC350CtrlEntries 10256 }


    iAudioDelayGlobalDelayPairOffsetsPair3Total OBJECT-TYPE
        SYNTAX            RollCallString
        MAX-ACCESS        read-only
        STATUS            current
        DESCRIPTION
                "CMNT: - 
                 TYPE: - Display
                 PAGE: - Delay
                    Pair 3 Total  cmdID= 10265  "
        ::= { lC350CtrlEntries 10265 }


    iAudioDelayGlobalDelayPairOffsetsPair4 OBJECT-TYPE
        SYNTAX            INTEGER
        MAX-ACCESS        read-write
        STATUS            current
        DESCRIPTION
                "CMNT: - 
                 TYPE: - Number
                 PAGE: - Delay
                    Pair 4  cmdID= 10257
                    min= -40  max= 200  step= 1  format= %0.0f ms  div_scale= 1  preset= 0
                    Min = -40 ms  Max = 200 ms  Step = 1 ms  Preset = 0 ms  "
        ::= { lC350CtrlEntries 10257 }


    iAudioDelayGlobalDelayPairOffsetsPair4Total OBJECT-TYPE
        SYNTAX            RollCallString
        MAX-ACCESS        read-only
        STATUS            current
        DESCRIPTION
                "CMNT: - 
                 TYPE: - Display
                 PAGE: - Delay
                    Pair 4 Total  cmdID= 10266  "
        ::= { lC350CtrlEntries 10266 }


    iAudioDelayGlobalDelayPairOffsetsPair5 OBJECT-TYPE
        SYNTAX            INTEGER
        MAX-ACCESS        read-write
        STATUS            current
        DESCRIPTION
                "CMNT: - 
                 TYPE: - Number
                 PAGE: - Delay
                    Pair 5  cmdID= 10258
                    min= -40  max= 200  step= 1  format= %0.0f ms  div_scale= 1  preset= 0
                    Min = -40 ms  Max = 200 ms  Step = 1 ms  Preset = 0 ms  "
        ::= { lC350CtrlEntries 10258 }


    iAudioDelayGlobalDelayPairOffsetsPair5Total OBJECT-TYPE
        SYNTAX            RollCallString
        MAX-ACCESS        read-only
        STATUS            current
        DESCRIPTION
                "CMNT: - 
                 TYPE: - Display
                 PAGE: - Delay
                    Pair 5 Total  cmdID= 10267  "
        ::= { lC350CtrlEntries 10267 }


    iAudioDelayGlobalDelayPairOffsetsPair6 OBJECT-TYPE
        SYNTAX            INTEGER
        MAX-ACCESS        read-write
        STATUS            current
        DESCRIPTION
                "CMNT: - 
                 TYPE: - Number
                 PAGE: - Delay
                    Pair 6  cmdID= 10259
                    min= -40  max= 200  step= 1  format= %0.0f ms  div_scale= 1  preset= 0
                    Min = -40 ms  Max = 200 ms  Step = 1 ms  Preset = 0 ms  "
        ::= { lC350CtrlEntries 10259 }


    iAudioDelayGlobalDelayPairOffsetsPair6Total OBJECT-TYPE
        SYNTAX            RollCallString
        MAX-ACCESS        read-only
        STATUS            current
        DESCRIPTION
                "CMNT: - 
                 TYPE: - Display
                 PAGE: - Delay
                    Pair 6 Total  cmdID= 10268  "
        ::= { lC350CtrlEntries 10268 }


    iAudioDelayGlobalDelayPairOffsetsPair7 OBJECT-TYPE
        SYNTAX            INTEGER
        MAX-ACCESS        read-write
        STATUS            current
        DESCRIPTION
                "CMNT: - 
                 TYPE: - Number
                 PAGE: - Delay
                    Pair 7  cmdID= 10260
                    min= -40  max= 200  step= 1  format= %0.0f ms  div_scale= 1  preset= 0
                    Min = -40 ms  Max = 200 ms  Step = 1 ms  Preset = 0 ms  "
        ::= { lC350CtrlEntries 10260 }


    iAudioDelayGlobalDelayPairOffsetsPair7Total OBJECT-TYPE
        SYNTAX            RollCallString
        MAX-ACCESS        read-only
        STATUS            current
        DESCRIPTION
                "CMNT: - 
                 TYPE: - Display
                 PAGE: - Delay
                    Pair 7 Total  cmdID= 10269  "
        ::= { lC350CtrlEntries 10269 }


    iAudioDelayGlobalDelayPairOffsetsPair8 OBJECT-TYPE
        SYNTAX            INTEGER
        MAX-ACCESS        read-write
        STATUS            current
        DESCRIPTION
                "CMNT: - 
                 TYPE: - Number
                 PAGE: - Delay
                    Pair 8  cmdID= 10261
                    min= -40  max= 200  step= 1  format= %0.0f ms  div_scale= 1  preset= 0
                    Min = -40 ms  Max = 200 ms  Step = 1 ms  Preset = 0 ms  "
        ::= { lC350CtrlEntries 10261 }


    iAudioDelayGlobalDelayPairOffsetsPair8Total OBJECT-TYPE
        SYNTAX            RollCallString
        MAX-ACCESS        read-only
        STATUS            current
        DESCRIPTION
                "CMNT: - 
                 TYPE: - Display
                 PAGE: - Delay
                    Pair 8 Total  cmdID= 10270  "
        ::= { lC350CtrlEntries 10270 }


    iAudioDelayGlobalDelayAudio OBJECT-TYPE
        SYNTAX            INTEGER
        MAX-ACCESS        read-write
        STATUS            current
        DESCRIPTION
                "CMNT: - 
                 TYPE: - Number
                 PAGE: - Delay
                    Audio  cmdID= 10262
                    min= -40  max= 200  step= 1  format= %0.0f ms  div_scale= 1  preset= 0
                    Min = -40 ms  Max = 200 ms  Step = 1 ms  Preset = 0 ms  "
        ::= { lC350CtrlEntries 10262 }


    iAudioDelayGlobalDelayAudioTotal OBJECT-TYPE
        SYNTAX            RollCallString
        MAX-ACCESS        read-only
        STATUS            current
        DESCRIPTION
                "CMNT: - 
                 TYPE: - Display
                 PAGE: - Delay
                    Audio Total  cmdID= 10271  "
        ::= { lC350CtrlEntries 10271 }


    iAudioDelayGlobalDelayVideoTotal OBJECT-TYPE
        SYNTAX            RollCallString
        MAX-ACCESS        read-only
        STATUS            current
        DESCRIPTION
                "CMNT: - 
                 TYPE: - Display
                 PAGE: - Delay
                    Video Total  cmdID= 10272  "
        ::= { lC350CtrlEntries 10272 }


    iAudioControlNewDisplay OBJECT-TYPE
        SYNTAX            RollCallString
        MAX-ACCESS        read-only
        STATUS            current
        DESCRIPTION
                "CMNT: - Hide CH2 Controls
                 TYPE: - Display
                 PAGE: - Audio Control
                    New Display  cmdID= 10516  "
        ::= { lC350CtrlEntries 10516 }


    iAudioIOAESAESOutput14AES1 OBJECT-TYPE
        SYNTAX            INTEGER {
                            valUseasInput(0),
                            valPair1(1),
                            valPair2(2),
                            valPair3(3),
                            valPair4(4),
                            valPair5(5),
                            valPair6(6),
                            valPair7(7),
                            valPair8(8)
                            }
        MAX-ACCESS        read-write
        STATUS            current
        DESCRIPTION
                "CMNT: - 
                 TYPE: - RadiobuttonList
                 PAGE: - Audio I/O AES
                    AES 1  cmdID= 10273
                    Use as Input  value= 0
                    Pair 1  value= 1
                    Pair 2  value= 2
                    Pair 3  value= 3
                    Pair 4  value= 4
                    Pair 5  value= 5
                    Pair 6  value= 6
                    Pair 7  value= 7
                    Pair 8  value= 8  "
        ::= { lC350CtrlEntries 10273 }


    iAudioIOAESAESOutput14AES2 OBJECT-TYPE
        SYNTAX            INTEGER {
                            valUseasInput(0),
                            valPair1(1),
                            valPair2(2),
                            valPair3(3),
                            valPair4(4),
                            valPair5(5),
                            valPair6(6),
                            valPair7(7),
                            valPair8(8)
                            }
        MAX-ACCESS        read-write
        STATUS            current
        DESCRIPTION
                "CMNT: - 
                 TYPE: - RadiobuttonList
                 PAGE: - Audio I/O AES
                    AES 2  cmdID= 10274
                    Use as Input  value= 0
                    Pair 1  value= 1
                    Pair 2  value= 2
                    Pair 3  value= 3
                    Pair 4  value= 4
                    Pair 5  value= 5
                    Pair 6  value= 6
                    Pair 7  value= 7
                    Pair 8  value= 8  "
        ::= { lC350CtrlEntries 10274 }


    iAudioIOAESAESOutput14AES3 OBJECT-TYPE
        SYNTAX            INTEGER {
                            valUseasInput(0),
                            valPair1(1),
                            valPair2(2),
                            valPair3(3),
                            valPair4(4),
                            valPair5(5),
                            valPair6(6),
                            valPair7(7),
                            valPair8(8)
                            }
        MAX-ACCESS        read-write
        STATUS            current
        DESCRIPTION
                "CMNT: - 
                 TYPE: - RadiobuttonList
                 PAGE: - Audio I/O AES
                    AES 3  cmdID= 10275
                    Use as Input  value= 0
                    Pair 1  value= 1
                    Pair 2  value= 2
                    Pair 3  value= 3
                    Pair 4  value= 4
                    Pair 5  value= 5
                    Pair 6  value= 6
                    Pair 7  value= 7
                    Pair 8  value= 8  "
        ::= { lC350CtrlEntries 10275 }


    iAudioIOAESAESOutput14AES4 OBJECT-TYPE
        SYNTAX            INTEGER {
                            valUseasInput(0),
                            valPair1(1),
                            valPair2(2),
                            valPair3(3),
                            valPair4(4),
                            valPair5(5),
                            valPair6(6),
                            valPair7(7),
                            valPair8(8)
                            }
        MAX-ACCESS        read-write
        STATUS            current
        DESCRIPTION
                "CMNT: - 
                 TYPE: - RadiobuttonList
                 PAGE: - Audio I/O AES
                    AES 4  cmdID= 10276
                    Use as Input  value= 0
                    Pair 1  value= 1
                    Pair 2  value= 2
                    Pair 3  value= 3
                    Pair 4  value= 4
                    Pair 5  value= 5
                    Pair 6  value= 6
                    Pair 7  value= 7
                    Pair 8  value= 8  "
        ::= { lC350CtrlEntries 10276 }


    iAudioIOAESAESOutput58AES5 OBJECT-TYPE
        SYNTAX            INTEGER {
                            valUseasInput(0),
                            valPair1(1),
                            valPair2(2),
                            valPair3(3),
                            valPair4(4),
                            valPair5(5),
                            valPair6(6),
                            valPair7(7),
                            valPair8(8)
                            }
        MAX-ACCESS        read-write
        STATUS            current
        DESCRIPTION
                "CMNT: - 
                 TYPE: - RadiobuttonList
                 PAGE: - Audio I/O AES
                    AES 5  cmdID= 10277
                    Use as Input  value= 0
                    Pair 1  value= 1
                    Pair 2  value= 2
                    Pair 3  value= 3
                    Pair 4  value= 4
                    Pair 5  value= 5
                    Pair 6  value= 6
                    Pair 7  value= 7
                    Pair 8  value= 8  "
        ::= { lC350CtrlEntries 10277 }


    iAudioIOAESAESOutput58AES6 OBJECT-TYPE
        SYNTAX            INTEGER {
                            valUseasInput(0),
                            valPair1(1),
                            valPair2(2),
                            valPair3(3),
                            valPair4(4),
                            valPair5(5),
                            valPair6(6),
                            valPair7(7),
                            valPair8(8)
                            }
        MAX-ACCESS        read-write
        STATUS            current
        DESCRIPTION
                "CMNT: - 
                 TYPE: - RadiobuttonList
                 PAGE: - Audio I/O AES
                    AES 6  cmdID= 10278
                    Use as Input  value= 0
                    Pair 1  value= 1
                    Pair 2  value= 2
                    Pair 3  value= 3
                    Pair 4  value= 4
                    Pair 5  value= 5
                    Pair 6  value= 6
                    Pair 7  value= 7
                    Pair 8  value= 8  "
        ::= { lC350CtrlEntries 10278 }


    iAudioIOAESAESOutput58AES7 OBJECT-TYPE
        SYNTAX            INTEGER {
                            valUseasInput(0),
                            valPair1(1),
                            valPair2(2),
                            valPair3(3),
                            valPair4(4),
                            valPair5(5),
                            valPair6(6),
                            valPair7(7),
                            valPair8(8)
                            }
        MAX-ACCESS        read-write
        STATUS            current
        DESCRIPTION
                "CMNT: - 
                 TYPE: - RadiobuttonList
                 PAGE: - Audio I/O AES
                    AES 7  cmdID= 10279
                    Use as Input  value= 0
                    Pair 1  value= 1
                    Pair 2  value= 2
                    Pair 3  value= 3
                    Pair 4  value= 4
                    Pair 5  value= 5
                    Pair 6  value= 6
                    Pair 7  value= 7
                    Pair 8  value= 8  "
        ::= { lC350CtrlEntries 10279 }


    iAudioIOAESAESOutput58AES8 OBJECT-TYPE
        SYNTAX            INTEGER {
                            valUseasInput(0),
                            valPair1(1),
                            valPair2(2),
                            valPair3(3),
                            valPair4(4),
                            valPair5(5),
                            valPair6(6),
                            valPair7(7),
                            valPair8(8)
                            }
        MAX-ACCESS        read-write
        STATUS            current
        DESCRIPTION
                "CMNT: - 
                 TYPE: - RadiobuttonList
                 PAGE: - Audio I/O AES
                    AES 8  cmdID= 10280
                    Use as Input  value= 0
                    Pair 1  value= 1
                    Pair 2  value= 2
                    Pair 3  value= 3
                    Pair 4  value= 4
                    Pair 5  value= 5
                    Pair 6  value= 6
                    Pair 7  value= 7
                    Pair 8  value= 8  "
        ::= { lC350CtrlEntries 10280 }


    iAudioIOAESAESInputTypeAllPairs OBJECT-TYPE
        SYNTAX            INTEGER {
                            valBalanced(0),
                            valUnbalanced(1)
                            }
        MAX-ACCESS        read-write
        STATUS            current
        DESCRIPTION
                "CMNT: - 
                 TYPE: - RadiobuttonList
                 PAGE: - Audio I/O AES
                    All Pairs  cmdID= 10281
                    Balanced  value= 0
                    Unbalanced  value= 1  "
        ::= { lC350CtrlEntries 10281 }


    iAudioIOAESNewDisplay OBJECT-TYPE
        SYNTAX            RollCallString
        MAX-ACCESS        read-only
        STATUS            current
        DESCRIPTION
                "CMNT: - 
                 TYPE: - Display
                 PAGE: - Audio I/O AES
                    New Display  cmdID= 10286  "
        ::= { lC350CtrlEntries 10286 }


    iAudioIOAnalogAnalogOutput12Analog1 OBJECT-TYPE
        SYNTAX            INTEGER {
                            valPair1(0),
                            valPair2(1),
                            valPair3(2),
                            valPair4(3),
                            valPair5(4),
                            valPair6(5),
                            valPair7(6),
                            valPair8(7)
                            }
        MAX-ACCESS        read-write
        STATUS            current
        DESCRIPTION
                "CMNT: - 
                 TYPE: - RadiobuttonList
                 PAGE: - Audio I/O Analog
                    Analog 1  cmdID= 10282
                    Pair 1  value= 0
                    Pair 2  value= 1
                    Pair 3  value= 2
                    Pair 4  value= 3
                    Pair 5  value= 4
                    Pair 6  value= 5
                    Pair 7  value= 6
                    Pair 8  value= 7  "
        ::= { lC350CtrlEntries 10282 }


    iAudioIOAnalogAnalogOutput12Analog2 OBJECT-TYPE
        SYNTAX            INTEGER {
                            valPair1(0),
                            valPair2(1),
                            valPair3(2),
                            valPair4(3),
                            valPair5(4),
                            valPair6(5),
                            valPair7(6),
                            valPair8(7)
                            }
        MAX-ACCESS        read-write
        STATUS            current
        DESCRIPTION
                "CMNT: - 
                 TYPE: - RadiobuttonList
                 PAGE: - Audio I/O Analog
                    Analog 2  cmdID= 10283
                    Pair 1  value= 0
                    Pair 2  value= 1
                    Pair 3  value= 2
                    Pair 4  value= 3
                    Pair 5  value= 4
                    Pair 6  value= 5
                    Pair 7  value= 6
                    Pair 8  value= 7  "
        ::= { lC350CtrlEntries 10283 }


    iInputAnalogInADCHeadroomPair1 OBJECT-TYPE
        SYNTAX            INTEGER
        MAX-ACCESS        read-write
        STATUS            current
        DESCRIPTION
                "CMNT: - 
                 TYPE: - Number
                 PAGE: - Input
                    Pair 1  cmdID= 10284
                    min= 24  max= 48  step= 1  format= %d  div_scale= 2  preset= 36
                    Min = 12  Max = 24  Step = 0  Preset = 18  "
        ::= { lC350CtrlEntries 10284 }


    iInputAnalogInADCHeadroomPair2 OBJECT-TYPE
        SYNTAX            INTEGER
        MAX-ACCESS        read-write
        STATUS            current
        DESCRIPTION
                "CMNT: - 
                 TYPE: - Number
                 PAGE: - Input
                    Pair 2  cmdID= 10285
                    min= 24  max= 48  step= 1  format= %d  div_scale= 2  preset= 36
                    Min = 12  Max = 24  Step = 0  Preset = 18  "
        ::= { lC350CtrlEntries 10285 }


    iOutputAnalogOutDACLevelPair1 OBJECT-TYPE
        SYNTAX            INTEGER
        MAX-ACCESS        read-write
        STATUS            current
        DESCRIPTION
                "CMNT: - 
                 TYPE: - Number
                 PAGE: - Output
                    Pair 1  cmdID= 10288
                    min= 24  max= 48  step= 1  format= %d  div_scale= 2  preset= 36
                    Min = 12  Max = 24  Step = 0  Preset = 18  "
        ::= { lC350CtrlEntries 10288 }


    iOutputAnalogOutDACLevelPair2 OBJECT-TYPE
        SYNTAX            INTEGER
        MAX-ACCESS        read-write
        STATUS            current
        DESCRIPTION
                "CMNT: - 
                 TYPE: - Number
                 PAGE: - Output
                    Pair 2  cmdID= 10289
                    min= 24  max= 48  step= 1  format= %d  div_scale= 2  preset= 36
                    Min = 12  Max = 24  Step = 0  Preset = 18  "
        ::= { lC350CtrlEntries 10289 }


    iAudioIOAnalogNewDisplay OBJECT-TYPE
        SYNTAX            RollCallString
        MAX-ACCESS        read-only
        STATUS            current
        DESCRIPTION
                "CMNT: - 
                 TYPE: - Display
                 PAGE: - Audio I/O Analog
                    New Display  cmdID= 10287  "
        ::= { lC350CtrlEntries 10287 }


    iDolbySetupDolbyCh1Mode OBJECT-TYPE
        SYNTAX            INTEGER {
                            valDecode(0),
                            valEncode(1),
                            valTranscode(2)
                            }
        MAX-ACCESS        read-write
        STATUS            current
        DESCRIPTION
                "CMNT: - 
                 TYPE: - RadiobuttonList
                 PAGE: - Dolby Setup
                    Mode  cmdID= 10466
                    Decode  value= 0
                    Encode  value= 1
                    Transcode  value= 2  "
        ::= { lC350CtrlEntries 10466 }


    iDolbySetupDolbyCh1DolbyEDelayCompensation OBJECT-TYPE
        SYNTAX            INTEGER {
                            valEarlyEarly(0),
                            valEarlyNormal(1),
                            valEarlyLate(2),
                            valNormalNormal(3),
                            valNormalLate(4),
                            valLateLate(5)
                            }
        MAX-ACCESS        read-write
        STATUS            current
        DESCRIPTION
                "CMNT: - 
                 TYPE: - RadiobuttonList
                 PAGE: - Dolby Setup
                    DolbyE Delay Compensation  cmdID= 10453
                    Early > Early  value= 0
                    Early > Normal  value= 1
                    Early > Late  value= 2
                    Normal > Normal  value= 3
                    Normal > Late  value= 4
                    Late > Late  value= 5  "
        ::= { lC350CtrlEntries 10453 }


    iDolbySetupDolbyCh1MetadataSource OBJECT-TYPE
        SYNTAX            INTEGER {
                            valDolbyDecoder(0),
                            valSMPTE2020(1)
                            }
        MAX-ACCESS        read-write
        STATUS            current
        DESCRIPTION
                "CMNT: - 
                 TYPE: - RadiobuttonList
                 PAGE: - Dolby Setup
                    Metadata Source  cmdID= 10452
                    Dolby Decoder  value= 0
                    SMPTE 2020  value= 1  "
        ::= { lC350CtrlEntries 10452 }


    iDolbyCh1SMPTE2020OutputOutputLine OBJECT-TYPE
        SYNTAX            INTEGER
        MAX-ACCESS        read-write
        STATUS            current
        DESCRIPTION
                "CMNT: - 
                 TYPE: - Number
                 PAGE: - Dolby Ch1
                    Output Line  cmdID= 10456
                    min= 8  max= 20  step= 1  format= %0.0f  div_scale= 1  preset= 10
                    Min = 8  Max = 20  Step = 1  Preset = 10  "
        ::= { lC350CtrlEntries 10456 }


    iDolbyCh1SMPTE2020OutputOutputEnable OBJECT-TYPE
        SYNTAX            INTEGER { disable(0), enable(1)  }
        MAX-ACCESS        read-write
        STATUS            current
        DESCRIPTION
                "CMNT: - 
                 TYPE: - Checkbox
                 PAGE: - Dolby Ch1
                    Output Enable  cmdID= 10455  "
        ::= { lC350CtrlEntries 10455 }


    iDolbySetupDolbyCh1DecoderSource OBJECT-TYPE
        SYNTAX            INTEGER {
                            valEmbedded1(0),
                            valEmbedded2(1),
                            valEmbedded3(2),
                            valEmbedded4(3),
                            valEmbedded5(4),
                            valEmbedded6(5),
                            valEmbedded7(6),
                            valEmbedded8(7),
                            valAES1(8),
                            valAES2(9),
                            valAES3(10),
                            valAES4(11),
                            valAES5(12),
                            valAES6(13),
                            valAES7(14),
                            valAES8(15)
                            }
        MAX-ACCESS        read-write
        STATUS            current
        DESCRIPTION
                "CMNT: - 
                 TYPE: - RadiobuttonList
                 PAGE: - Dolby Setup
                    Decoder Source  cmdID= 10447
                    Embedded 1  value= 0
                    Embedded 2  value= 1
                    Embedded 3  value= 2
                    Embedded 4  value= 3
                    Embedded 5  value= 4
                    Embedded 6  value= 5
                    Embedded 7  value= 6
                    Embedded 8  value= 7
                    AES 1  value= 8
                    AES 2  value= 9
                    AES 3  value= 10
                    AES 4  value= 11
                    AES 5  value= 12
                    AES 6  value= 13
                    AES 7  value= 14
                    AES 8  value= 15  "
        ::= { lC350CtrlEntries 10447 }


    iDolbySetupDolbyCh1EncoderSource1 OBJECT-TYPE
        SYNTAX            INTEGER {
                            valEmbedded1(0),
                            valEmbedded2(1),
                            valEmbedded3(2),
                            valEmbedded4(3),
                            valEmbedded5(4),
                            valEmbedded6(5),
                            valEmbedded7(6),
                            valEmbedded8(7),
                            valAES1(8),
                            valAES2(9),
                            valAES3(10),
                            valAES4(11),
                            valAES5(12),
                            valAES6(13),
                            valAES7(14),
                            valAES8(15)
                            }
        MAX-ACCESS        read-write
        STATUS            current
        DESCRIPTION
                "CMNT: - 
                 TYPE: - RadiobuttonList
                 PAGE: - Dolby Setup
                    Encoder Source 1  cmdID= 10457
                    Embedded 1  value= 0
                    Embedded 2  value= 1
                    Embedded 3  value= 2
                    Embedded 4  value= 3
                    Embedded 5  value= 4
                    Embedded 6  value= 5
                    Embedded 7  value= 6
                    Embedded 8  value= 7
                    AES 1  value= 8
                    AES 2  value= 9
                    AES 3  value= 10
                    AES 4  value= 11
                    AES 5  value= 12
                    AES 6  value= 13
                    AES 7  value= 14
                    AES 8  value= 15  "
        ::= { lC350CtrlEntries 10457 }


    iDolbySetupDolbyCh1EncoderSource2 OBJECT-TYPE
        SYNTAX            INTEGER {
                            valEmbedded1(0),
                            valEmbedded2(1),
                            valEmbedded3(2),
                            valEmbedded4(3),
                            valEmbedded5(4),
                            valEmbedded6(5),
                            valEmbedded7(6),
                            valEmbedded8(7),
                            valAES1(8),
                            valAES2(9),
                            valAES3(10),
                            valAES4(11),
                            valAES5(12),
                            valAES6(13),
                            valAES7(14),
                            valAES8(15)
                            }
        MAX-ACCESS        read-write
        STATUS            current
        DESCRIPTION
                "CMNT: - 
                 TYPE: - RadiobuttonList
                 PAGE: - Dolby Setup
                    Encoder Source 2  cmdID= 10458
                    Embedded 1  value= 0
                    Embedded 2  value= 1
                    Embedded 3  value= 2
                    Embedded 4  value= 3
                    Embedded 5  value= 4
                    Embedded 6  value= 5
                    Embedded 7  value= 6
                    Embedded 8  value= 7
                    AES 1  value= 8
                    AES 2  value= 9
                    AES 3  value= 10
                    AES 4  value= 11
                    AES 5  value= 12
                    AES 6  value= 13
                    AES 7  value= 14
                    AES 8  value= 15  "
        ::= { lC350CtrlEntries 10458 }


    iDolbySetupDolbyCh1EncoderSource3 OBJECT-TYPE
        SYNTAX            INTEGER {
                            valEmbedded1(0),
                            valEmbedded2(1),
                            valEmbedded3(2),
                            valEmbedded4(3),
                            valEmbedded5(4),
                            valEmbedded6(5),
                            valEmbedded7(6),
                            valEmbedded8(7),
                            valAES1(8),
                            valAES2(9),
                            valAES3(10),
                            valAES4(11),
                            valAES5(12),
                            valAES6(13),
                            valAES7(14),
                            valAES8(15)
                            }
        MAX-ACCESS        read-write
        STATUS            current
        DESCRIPTION
                "CMNT: - 
                 TYPE: - RadiobuttonList
                 PAGE: - Dolby Setup
                    Encoder Source 3  cmdID= 10459
                    Embedded 1  value= 0
                    Embedded 2  value= 1
                    Embedded 3  value= 2
                    Embedded 4  value= 3
                    Embedded 5  value= 4
                    Embedded 6  value= 5
                    Embedded 7  value= 6
                    Embedded 8  value= 7
                    AES 1  value= 8
                    AES 2  value= 9
                    AES 3  value= 10
                    AES 4  value= 11
                    AES 5  value= 12
                    AES 6  value= 13
                    AES 7  value= 14
                    AES 8  value= 15  "
        ::= { lC350CtrlEntries 10459 }


    iDolbySetupDolbyCh1EncoderSource4 OBJECT-TYPE
        SYNTAX            INTEGER {
                            valEmbedded1(0),
                            valEmbedded2(1),
                            valEmbedded3(2),
                            valEmbedded4(3),
                            valEmbedded5(4),
                            valEmbedded6(5),
                            valEmbedded7(6),
                            valEmbedded8(7),
                            valAES1(8),
                            valAES2(9),
                            valAES3(10),
                            valAES4(11),
                            valAES5(12),
                            valAES6(13),
                            valAES7(14),
                            valAES8(15)
                            }
        MAX-ACCESS        read-write
        STATUS            current
        DESCRIPTION
                "CMNT: - 
                 TYPE: - RadiobuttonList
                 PAGE: - Dolby Setup
                    Encoder Source 4  cmdID= 10460
                    Embedded 1  value= 0
                    Embedded 2  value= 1
                    Embedded 3  value= 2
                    Embedded 4  value= 3
                    Embedded 5  value= 4
                    Embedded 6  value= 5
                    Embedded 7  value= 6
                    Embedded 8  value= 7
                    AES 1  value= 8
                    AES 2  value= 9
                    AES 3  value= 10
                    AES 4  value= 11
                    AES 5  value= 12
                    AES 6  value= 13
                    AES 7  value= 14
                    AES 8  value= 15  "
        ::= { lC350CtrlEntries 10460 }


    iDolbySetupDolbyCh1EncoderFormat OBJECT-TYPE
        SYNTAX            INTEGER {
                            val1(0),
                            val2(1),
                            val3(2),
                            val4(3),
                            val5(4),
                            val6(5),
                            val7(6),
                            val8(7)
                            }
        MAX-ACCESS        read-write
        STATUS            current
        DESCRIPTION
                "CMNT: - 
                 TYPE: - RadiobuttonList
                 PAGE: - Dolby Setup
                    Encoder Format  cmdID= 10461
                    1  value= 0
                    2  value= 1
                    3  value= 2
                    4  value= 3
                    5  value= 4
                    6  value= 5
                    7  value= 6
                    8  value= 7  "
        ::= { lC350CtrlEntries 10461 }


    iDolbySetupDolbyCh1EncoderFormatED OBJECT-TYPE
        SYNTAX            INTEGER {
                            val1(0),
                            val2(1),
                            val3(2),
                            val4(3),
                            val5(4),
                            val6(5),
                            val7(6),
                            val8(7)
                            }
        MAX-ACCESS        read-write
        STATUS            current
        DESCRIPTION
                "CMNT: - 
                 TYPE: - RadiobuttonList
                 PAGE: - Dolby Setup
                    Encoder Format E D  cmdID= 10462
                    1  value= 0
                    2  value= 1
                    3  value= 2
                    4  value= 3
                    5  value= 4
                    6  value= 5
                    7  value= 6
                    8  value= 7  "
        ::= { lC350CtrlEntries 10462 }


    iDolbySetupDolbyCh1EncoderRate OBJECT-TYPE
        SYNTAX            INTEGER {
                            val1(0),
                            val2(1),
                            val3(2),
                            val4(3),
                            val5(4),
                            val6(5),
                            val7(6),
                            val8(7)
                            }
        MAX-ACCESS        read-write
        STATUS            current
        DESCRIPTION
                "CMNT: - 
                 TYPE: - RadiobuttonList
                 PAGE: - Dolby Setup
                    Encoder Rate  cmdID= 10463
                    1  value= 0
                    2  value= 1
                    3  value= 2
                    4  value= 3
                    5  value= 4
                    6  value= 5
                    7  value= 6
                    8  value= 7  "
        ::= { lC350CtrlEntries 10463 }


    iDolbySetupDolbyCh1EncoderBitDepth OBJECT-TYPE
        SYNTAX            INTEGER {
                            val1(0),
                            val2(1),
                            val3(2),
                            val4(3),
                            val5(4),
                            val6(5),
                            val7(6),
                            val8(7)
                            }
        MAX-ACCESS        read-write
        STATUS            current
        DESCRIPTION
                "CMNT: - 
                 TYPE: - RadiobuttonList
                 PAGE: - Dolby Setup
                    Encoder Bit Depth  cmdID= 10464
                    1  value= 0
                    2  value= 1
                    3  value= 2
                    4  value= 3
                    5  value= 4
                    6  value= 5
                    7  value= 6
                    8  value= 7  "
        ::= { lC350CtrlEntries 10464 }


    iDolbySetupDolbyCh1EncoderConfig OBJECT-TYPE
        SYNTAX            INTEGER {
                            val1(0),
                            val2(1),
                            val3(2),
                            val4(3),
                            val5(4),
                            val6(5),
                            val7(6),
                            val8(7)
                            }
        MAX-ACCESS        read-write
        STATUS            current
        DESCRIPTION
                "CMNT: - 
                 TYPE: - RadiobuttonList
                 PAGE: - Dolby Setup
                    Encoder Config  cmdID= 10465
                    1  value= 0
                    2  value= 1
                    3  value= 2
                    4  value= 3
                    5  value= 4
                    6  value= 5
                    7  value= 6
                    8  value= 7  "
        ::= { lC350CtrlEntries 10465 }


    iDolbySetupDolbyCh1InputStatus OBJECT-TYPE
        SYNTAX            RollCallString
        MAX-ACCESS        read-only
        STATUS            current
        DESCRIPTION
                "CMNT: - 
                 TYPE: - Display
                 PAGE: - Dolby Setup
                    Input Status  cmdID= 10448  "
        ::= { lC350CtrlEntries 10448 }


    iDolbySetupDolbyCh1DecoderRate OBJECT-TYPE
        SYNTAX            RollCallString
        MAX-ACCESS        read-only
        STATUS            current
        DESCRIPTION
                "CMNT: - 
                 TYPE: - Display
                 PAGE: - Dolby Setup
                    Decoder Rate  cmdID= 10450  "
        ::= { lC350CtrlEntries 10450 }


    iDolbySetupDolbyCh1DecoderFormat OBJECT-TYPE
        SYNTAX            RollCallString
        MAX-ACCESS        read-only
        STATUS            current
        DESCRIPTION
                "CMNT: - 
                 TYPE: - Display
                 PAGE: - Dolby Setup
                    Decoder Format  cmdID= 10449  "
        ::= { lC350CtrlEntries 10449 }


    iDolbySetupDolbyCh1DecoderVersion OBJECT-TYPE
        SYNTAX            RollCallString
        MAX-ACCESS        read-only
        STATUS            current
        DESCRIPTION
                "CMNT: - 
                 TYPE: - Display
                 PAGE: - Dolby Setup
                    Decoder Version  cmdID= 10451  "
        ::= { lC350CtrlEntries 10451 }


    iDolbySetupDolbyCh1EncoderVersion OBJECT-TYPE
        SYNTAX            RollCallString
        MAX-ACCESS        read-only
        STATUS            current
        DESCRIPTION
                "CMNT: - 
                 TYPE: - Display
                 PAGE: - Dolby Setup
                    Encoder Version  cmdID= 10454  "
        ::= { lC350CtrlEntries 10454 }


    iDolbySetupNewDisplay OBJECT-TYPE
        SYNTAX            RollCallString
        MAX-ACCESS        read-only
        STATUS            current
        DESCRIPTION
                "CMNT: - Hide CH2 Controls
                 TYPE: - Display
                 PAGE: - Dolby Setup
                    New Display  cmdID= 10513  "
        ::= { lC350CtrlEntries 10513 }


    iGenlockSource OBJECT-TYPE
        SYNTAX            INTEGER {
                            valRefLock(0),
                            valInput(1),
                            valFreeRun(2)
                            }
        MAX-ACCESS        read-write
        STATUS            current
        DESCRIPTION
                "CMNT: - 
                 TYPE: - RadiobuttonList
                 PAGE: - Genlock
                    Source  cmdID= 10308
                    Ref Lock  value= 0
                    Input  value= 1
                    Free Run  value= 2  "
        ::= { lC350CtrlEntries 10308 }


    iGenlockCurrentReferenceStandard OBJECT-TYPE
        SYNTAX            RollCallString
        MAX-ACCESS        read-only
        STATUS            current
        DESCRIPTION
                "CMNT: - 
                 TYPE: - Display
                 PAGE: - Genlock
                    Current Reference Standard  cmdID= 10311  "
        ::= { lC350CtrlEntries 10311 }


    iGenlockTimingVerticalTiming OBJECT-TYPE
        SYNTAX            INTEGER
        MAX-ACCESS        read-write
        STATUS            current
        DESCRIPTION
                "CMNT: - 
                 TYPE: - Number
                 PAGE: - Genlock
                    Vertical Timing  cmdID= 10309
                    min= -1125  max= 1125  step= 1  format= %0.0f lines  div_scale= 1  preset= 0
                    Min = -1125 lines  Max = 1125 lines  Step = 1 lines  Preset = 0 lines  "
        ::= { lC350CtrlEntries 10309 }


    iGenlockTimingHorizontalTiming OBJECT-TYPE
        SYNTAX            INTEGER
        MAX-ACCESS        read-write
        STATUS            current
        DESCRIPTION
                "CMNT: - 
                 TYPE: - Number
                 PAGE: - Genlock
                    Horizontal Timing  cmdID= 10310
                    min= -2640  max= 2640  step= 1  format= %0.0f pixels  div_scale= 1  preset= 0
                    Min = -2640 pixels  Max = 2640 pixels  Step = 1 pixels  Preset = 0 pixels  "
        ::= { lC350CtrlEntries 10310 }


    iGenlockTimingStatus OBJECT-TYPE
        SYNTAX            RollCallString
        MAX-ACCESS        read-only
        STATUS            current
        DESCRIPTION
                "CMNT: - 
                 TYPE: - Display
                 PAGE: - Genlock
                    Status  cmdID= 10505  "
        ::= { lC350CtrlEntries 10505 }


    iTimecodeSourceHD OBJECT-TYPE
        SYNTAX            INTEGER {
                            valLTC(0),
                            valVITC(1)
                            }
        MAX-ACCESS        read-write
        STATUS            current
        DESCRIPTION
                "CMNT: - 
                 TYPE: - RadiobuttonList
                 PAGE: - Timecode
                    Source (HD)  cmdID= 10312
                    LTC  value= 0
                    VITC  value= 1  "
        ::= { lC350CtrlEntries 10312 }


    iTimecodeSourceSD OBJECT-TYPE
        SYNTAX            INTEGER {
                            valVITC(0),
                            valATCLTC(1),
                            valATCVITC(2)
                            }
        MAX-ACCESS        read-write
        STATUS            current
        DESCRIPTION
                "CMNT: - 
                 TYPE: - RadiobuttonList
                 PAGE: - Timecode
                    Source (SD)  cmdID= 10313
                    VITC  value= 0
                    ATC LTC  value= 1
                    ATC VITC  value= 2  "
        ::= { lC350CtrlEntries 10313 }


    iTimecodeStatus OBJECT-TYPE
        SYNTAX            RollCallString
        MAX-ACCESS        read-only
        STATUS            current
        DESCRIPTION
                "CMNT: - 
                 TYPE: - Display
                 PAGE: - Timecode
                    Status  cmdID= 10322  "
        ::= { lC350CtrlEntries 10322 }


    iTimecodeMode OBJECT-TYPE
        SYNTAX            INTEGER {
                            valFollowInput(0),
                            valGenerate(1),
                            valInputTrigger(2)
                            }
        MAX-ACCESS        read-write
        STATUS            current
        DESCRIPTION
                "CMNT: - 
                 TYPE: - RadiobuttonList
                 PAGE: - Timecode
                    Mode  cmdID= 10314
                    Follow Input  value= 0
                    Generate  value= 1
                    Input Trigger  value= 2  "
        ::= { lC350CtrlEntries 10314 }


    iTimecodeOnTimecodeLoss OBJECT-TYPE
        SYNTAX            INTEGER {
                            valFreeze(0),
                            valFreeRun(1)
                            }
        MAX-ACCESS        read-write
        STATUS            current
        DESCRIPTION
                "CMNT: - 
                 TYPE: - RadiobuttonList
                 PAGE: - Timecode
                    On Timecode Loss  cmdID= 10318
                    Freeze  value= 0
                    Free Run  value= 1  "
        ::= { lC350CtrlEntries 10318 }


    iTimecodeInputTriggerEntry OBJECT-TYPE
        SYNTAX            RollCallString
        MAX-ACCESS        read-write
        STATUS            current
        DESCRIPTION
                "CMNT: - 
                 TYPE: - Editstring
                 PAGE: - Timecode
                    Input Trigger Entry  cmdID= 10323
                    preset= 00:00:00:00"
        ::= { lC350CtrlEntries 10323 }


    iTimecodeOutputTimecodeEntry OBJECT-TYPE
        SYNTAX            RollCallString
        MAX-ACCESS        read-write
        STATUS            current
        DESCRIPTION
                "CMNT: - 
                 TYPE: - Editstring
                 PAGE: - Timecode
                    Output Timecode Entry  cmdID= 10324
                    preset= 00:00:00:00"
        ::= { lC350CtrlEntries 10324 }


    iTimecodeEntry OBJECT-TYPE
        SYNTAX            RollCallString
        MAX-ACCESS        read-write
        STATUS            current
        DESCRIPTION
                "CMNT: - 
                 TYPE: - Editstring
                 PAGE: - Timecode
                    Timecode Entry  cmdID= 10320
                    preset= 00:00:00:00"
        ::= { lC350CtrlEntries 10320 }


    iTimecodeLoad OBJECT-TYPE
        SYNTAX            INTEGER { noAction(0),valTimecodeLoad(1) }
        MAX-ACCESS        read-write
        STATUS            current
        DESCRIPTION
                "CMNT: - 
                 TYPE: - Button
                 PAGE: - Timecode
                    Timecode Load  cmdID= 10325
                    value= 1  "
        ::= { lC350CtrlEntries 10325 }


    iTimecodeNondropFrame OBJECT-TYPE
        SYNTAX            INTEGER { disable(0), enable(1)  }
        MAX-ACCESS        read-write
        STATUS            current
        DESCRIPTION
                "CMNT: - 
                 TYPE: - Checkbox
                 PAGE: - Timecode
                    Non-drop Frame  cmdID= 10319  "
        ::= { lC350CtrlEntries 10319 }


    iTimecodeVITCEnable OBJECT-TYPE
        SYNTAX            INTEGER { disable(0), enable(1)  }
        MAX-ACCESS        read-write
        STATUS            current
        DESCRIPTION
                "CMNT: - 
                 TYPE: - Checkbox
                 PAGE: - Timecode
                    VITC Enable  cmdID= 10321  "
        ::= { lC350CtrlEntries 10321 }


    iTimecodeOutputLine525 OBJECT-TYPE
        SYNTAX            INTEGER
        MAX-ACCESS        read-write
        STATUS            current
        DESCRIPTION
                "CMNT: - 
                 TYPE: - Number
                 PAGE: - Timecode
                    Output Line (525)  cmdID= 10315
                    min= 11  max= 17  step= 1  format= %0.0f  div_scale= 1  preset= 14
                    Min = 11  Max = 17  Step = 1  Preset = 14  "
        ::= { lC350CtrlEntries 10315 }


    iTimecodeOutputLine625 OBJECT-TYPE
        SYNTAX            INTEGER
        MAX-ACCESS        read-write
        STATUS            current
        DESCRIPTION
                "CMNT: - 
                 TYPE: - Number
                 PAGE: - Timecode
                    Output Line (625)  cmdID= 10316
                    min= 7  max= 20  step= 1  format= %0.0f  div_scale= 1  preset= 19
                    Min = 7  Max = 20  Step = 1  Preset = 19  "
        ::= { lC350CtrlEntries 10316 }


    iTimecodeOutputLineStatus OBJECT-TYPE
        SYNTAX            RollCallString
        MAX-ACCESS        read-only
        STATUS            current
        DESCRIPTION
                "CMNT: - 
                 TYPE: - Display
                 PAGE: - Timecode
                    Output Line Status  cmdID= 10317  "
        ::= { lC350CtrlEntries 10317 }


    iTimecodeNewDisplay OBJECT-TYPE
        SYNTAX            RollCallString
        MAX-ACCESS        read-only
        STATUS            current
        DESCRIPTION
                "CMNT: - Hide CH2 Controls
                 TYPE: - Display
                 PAGE: - Timecode
                    New Display  cmdID= 10511  "
        ::= { lC350CtrlEntries 10511 }


    iMetadataClosedCaptionsInputStatus OBJECT-TYPE
        SYNTAX            RollCallString
        MAX-ACCESS        read-only
        STATUS            current
        DESCRIPTION
                "CMNT: - 
                 TYPE: - Display
                 PAGE: - Metadata
                    Input Status  cmdID= 10330  "
        ::= { lC350CtrlEntries 10330 }


    iMetadataClosedCaptionsCEA608OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-608 Output Enable  cmdID= 10326
                    Off  value= 0
                    On  value= 1  "
        ::= { lC350CtrlEntries 10326 }


    iMetadataClosedCaptionsCEA708OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-708 Output Enable  cmdID= 10327
                    Off  value= 0
                    On  value= 1  "
        ::= { lC350CtrlEntries 10327 }


    iMetadataClosedCaptionsCEA708OutputLine OBJECT-TYPE
        SYNTAX            INTEGER
        MAX-ACCESS        read-write
        STATUS            current
        DESCRIPTION
                "CMNT: - 
                 TYPE: - Number
                 PAGE: - Metadata
                    CEA-708 Output Line  cmdID= 10328
                    min= 8  max= 20  step= 1  format= %0.0f  div_scale= 1  preset= 10
                    Min = 8  Max = 20  Step = 1  Preset = 10  "
        ::= { lC350CtrlEntries 10328 }


    iMetadataClosedCaptionsCEA708OutputLineStatus OBJECT-TYPE
        SYNTAX            RollCallString
        MAX-ACCESS        read-only
        STATUS            current
        DESCRIPTION
                "CMNT: - 
                 TYPE: - Display
                 PAGE: - Metadata
                    CEA-708 Output Line Status  cmdID= 10329  "
        ::= { lC350CtrlEntries 10329 }


    iMetadataTeletext625CaptionsSource OBJECT-TYPE
        SYNTAX            INTEGER {
                            valWST(0),
                            valCEAn608(1)
                            }
        MAX-ACCESS        read-write
        STATUS            current
        DESCRIPTION
                "CMNT: - 
                 TYPE: - RadiobuttonList
                 PAGE: - Metadata
                    625 Captions Source  cmdID= 10338
                    WST  value= 0
                    CEA-608  value= 1  "
        ::= { lC350CtrlEntries 10338 }


    iMetadataTeletextPresentStatus OBJECT-TYPE
        SYNTAX            RollCallString
        MAX-ACCESS        read-only
        STATUS            current
        DESCRIPTION
                "CMNT: - 
                 TYPE: - Display
                 PAGE: - Metadata
                    Teletext Present Status  cmdID= 10331  "
        ::= { lC350CtrlEntries 10331 }


    iMetadataTeletextWSTInputLine OBJECT-TYPE
        SYNTAX            INTEGER
        MAX-ACCESS        read-write
        STATUS            current
        DESCRIPTION
                "CMNT: - 
                 TYPE: - Number
                 PAGE: - Metadata
                    WST Input Line  cmdID= 10332
                    min= 7  max= 22  step= 1  format= %0.0f  div_scale= 1  preset= 20
                    Min = 7  Max = 22  Step = 1  Preset = 20  "
        ::= { lC350CtrlEntries 10332 }


    iMetadataTeletextWSTOutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    WST Output Enable  cmdID= 10333
                    Off  value= 0
                    On  value= 1  "
        ::= { lC350CtrlEntries 10333 }


    iMetadataTeletextWSTOutputLine OBJECT-TYPE
        SYNTAX            INTEGER
        MAX-ACCESS        read-write
        STATUS            current
        DESCRIPTION
                "CMNT: - 
                 TYPE: - Number
                 PAGE: - Metadata
                    WST Output Line  cmdID= 10334
                    min= 7  max= 22  step= 1  format= %0.0f  div_scale= 1  preset= 20
                    Min = 7  Max = 22  Step = 1  Preset = 20  "
        ::= { lC350CtrlEntries 10334 }


    iMetadataTeletextWSTOutputLineStatus OBJECT-TYPE
        SYNTAX            RollCallString
        MAX-ACCESS        read-only
        STATUS            current
        DESCRIPTION
                "CMNT: - 
                 TYPE: - Display
                 PAGE: - Metadata
                    WST Output Line Status  cmdID= 10340  "
        ::= { lC350CtrlEntries 10340 }


    iMetadataTeletextWSTSourceLine OBJECT-TYPE
        SYNTAX            INTEGER
        MAX-ACCESS        read-write
        STATUS            current
        DESCRIPTION
                "CMNT: - 
                 TYPE: - Number
                 PAGE: - Metadata
                    WST Source Line  cmdID= 10335
                    min= 7  max= 22  step= 1  format= %0.0f  div_scale= 1  preset= 20
                    Min = 7  Max = 22  Step = 1  Preset = 20  "
        ::= { lC350CtrlEntries 10335 }


    iMetadataTeletextRDD08OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    RDD-08 Output Enable  cmdID= 10336
                    Off  value= 0
                    On  value= 1  "
        ::= { lC350CtrlEntries 10336 }


    iMetadataTeletextRDD08OutputLine OBJECT-TYPE
        SYNTAX            INTEGER
        MAX-ACCESS        read-write
        STATUS            current
        DESCRIPTION
                "CMNT: - 
                 TYPE: - Number
                 PAGE: - Metadata
                    RDD-08 Output Line  cmdID= 10337
                    min= 8  max= 20  step= 1  format= %0.0f  div_scale= 1  preset= 10
                    Min = 8  Max = 20  Step = 1  Preset = 10  "
        ::= { lC350CtrlEntries 10337 }


    iMetadataTeletextRDD08OutputLineStatus OBJECT-TYPE
        SYNTAX            RollCallString
        MAX-ACCESS        read-only
        STATUS            current
        DESCRIPTION
                "CMNT: - 
                 TYPE: - Display
                 PAGE: - Metadata
                    RDD-08 Output Line Status  cmdID= 10339  "
        ::= { lC350CtrlEntries 10339 }


    iMetadataNewDisplay OBJECT-TYPE
        SYNTAX            RollCallString
        MAX-ACCESS        read-only
        STATUS            current
        DESCRIPTION
                "CMNT: - Hide CH2 Controls
                 TYPE: - Display
                 PAGE: - Metadata
                    New Display  cmdID= 10512  "
        ::= { lC350CtrlEntries 10512 }


    iNetworkEthernetCurrentIPAddress OBJECT-TYPE
        SYNTAX            RollCallString
        MAX-ACCESS        read-only
        STATUS            current
        DESCRIPTION
                "CMNT: - 
                 TYPE: - Display
                 PAGE: - Network
                    Current IP Address  cmdID= 10295  "
        ::= { lC350CtrlEntries 10295 }


    iNetworkEthernetCurrentIPNetmask OBJECT-TYPE
        SYNTAX            RollCallString
        MAX-ACCESS        read-only
        STATUS            current
        DESCRIPTION
                "CMNT: - 
                 TYPE: - Display
                 PAGE: - Network
                    Current IP Netmask  cmdID= 10297  "
        ::= { lC350CtrlEntries 10297 }


    iNetworkEthernetCurrentIPGateway OBJECT-TYPE
        SYNTAX            RollCallString
        MAX-ACCESS        read-only
        STATUS            current
        DESCRIPTION
                "CMNT: - 
                 TYPE: - Display
                 PAGE: - Network
                    Current IP Gateway  cmdID= 10296  "
        ::= { lC350CtrlEntries 10296 }


    iNetworkEthernetMACAddress OBJECT-TYPE
        SYNTAX            RollCallString
        MAX-ACCESS        read-only
        STATUS            current
        DESCRIPTION
                "CMNT: - 
                 TYPE: - Display
                 PAGE: - Network
                    MAC Address  cmdID= 10298  "
        ::= { lC350CtrlEntries 10298 }


    iNetworkEthernetIPConfiguration OBJECT-TYPE
        SYNTAX            INTEGER {
                            valFixedAddress(0),
                            valDHCP(1)
                            }
        MAX-ACCESS        read-write
        STATUS            current
        DESCRIPTION
                "CMNT: - 
                 TYPE: - RadiobuttonList
                 PAGE: - Network
                    IP Configuration  cmdID= 10290
                    Fixed Address  value= 0
                    DHCP  value= 1  "
        ::= { lC350CtrlEntries 10290 }


    iNetworkEthernetIPAddress OBJECT-TYPE
        SYNTAX            RollCallString
        MAX-ACCESS        read-write
        STATUS            current
        DESCRIPTION
                "CMNT: - 
                 TYPE: - Editstring
                 PAGE: - Network
                    IP Address  cmdID= 10291
                    preset= 192.168.151.1"
        ::= { lC350CtrlEntries 10291 }


    iNetworkEthernetIPGateway OBJECT-TYPE
        SYNTAX            RollCallString
        MAX-ACCESS        read-write
        STATUS            current
        DESCRIPTION
                "CMNT: - 
                 TYPE: - Editstring
                 PAGE: - Network
                    IP Gateway  cmdID= 10292
                    preset= 192.168.151.200"
        ::= { lC350CtrlEntries 10292 }


    iNetworkEthernetIPNetmask OBJECT-TYPE
        SYNTAX            RollCallString
        MAX-ACCESS        read-write
        STATUS            current
        DESCRIPTION
                "CMNT: - 
                 TYPE: - Editstring
                 PAGE: - Network
                    IP Netmask  cmdID= 10293
                    preset= 255.255.255.0"
        ::= { lC350CtrlEntries 10293 }


    iNetworkEthernetApplyIPChanges OBJECT-TYPE
        SYNTAX            INTEGER { noAction(0),valApplyIPChanges(1) }
        MAX-ACCESS        read-write
        STATUS            current
        DESCRIPTION
                "CMNT: - 
                 TYPE: - Button
                 PAGE: - Network
                    Apply IP Changes  cmdID= 10294
                    value= 1  "
        ::= { lC350CtrlEntries 10294 }


    iNetworkEthernetIPConfigurationStatus OBJECT-TYPE
        SYNTAX            RollCallString
        MAX-ACCESS        read-only
        STATUS            current
        DESCRIPTION
                "CMNT: - 
                 TYPE: - Display
                 PAGE: - Network
                    IP Configuration Status  cmdID= 10509  "
        ::= { lC350CtrlEntries 10509 }


    iNetworkEthernetInterfaceStatus OBJECT-TYPE
        SYNTAX            RollCallString
        MAX-ACCESS        read-only
        STATUS            current
        DESCRIPTION
                "CMNT: - 
                 TYPE: - Display
                 PAGE: - Network
                    Interface Status  cmdID= 10299  "
        ::= { lC350CtrlEntries 10299 }


    iNetworkRollCallUnitName OBJECT-TYPE
        SYNTAX            RollCallString
        MAX-ACCESS        read-write
        STATUS            current
        DESCRIPTION
                "CMNT: - 
                 TYPE: - Editstring
                 PAGE: - Network
                    Unit Name  cmdID= 10300
                    preset= IQP"
        ::= { lC350CtrlEntries 10300 }


    iNetworkRollCallLogServerName OBJECT-TYPE
        SYNTAX            RollCallString
        MAX-ACCESS        read-write
        STATUS            current
        DESCRIPTION
                "CMNT: - 
                 TYPE: - Editstring
                 PAGE: - Network
                    Log Server Name  cmdID= 10301
                    preset= "
        ::= { lC350CtrlEntries 10301 }


    iNetworkRollCallServerName OBJECT-TYPE
        SYNTAX            RollCallString
        MAX-ACCESS        read-only
        STATUS            current
        DESCRIPTION
                "CMNT: - 
                 TYPE: - Display
                 PAGE: - Network
                    Server Name  cmdID= 10302  "
        ::= { lC350CtrlEntries 10302 }


    iNetworkRollCallServerAddress OBJECT-TYPE
        SYNTAX            RollCallString
        MAX-ACCESS        read-only
        STATUS            current
        DESCRIPTION
                "CMNT: - 
                 TYPE: - Display
                 PAGE: - Network
                    Server Address  cmdID= 10303  "
        ::= { lC350CtrlEntries 10303 }


    iNetworkRollCallIPSharePort OBJECT-TYPE
        SYNTAX            INTEGER
        MAX-ACCESS        read-write
        STATUS            current
        DESCRIPTION
                "CMNT: - 
                 TYPE: - Number
                 PAGE: - Network
                    IP Share Port  cmdID= 10304
                    min= 1024  max= 65535  step= 1  format= %d  div_scale= 1  preset= 2050
                    Min = 1024  Max = 65535  Step = 1  Preset = 2050  "
        ::= { lC350CtrlEntries 10304 }


    iNetworkRollCallIPBridgingPort OBJECT-TYPE
        SYNTAX            INTEGER
        MAX-ACCESS        read-write
        STATUS            current
        DESCRIPTION
                "CMNT: - 
                 TYPE: - Number
                 PAGE: - Network
                    IP Bridging Port  cmdID= 10305
                    min= 1024  max= 65535  step= 1  format= %d  div_scale= 1  preset= 2600
                    Min = 1024  Max = 65535  Step = 1  Preset = 2600  "
        ::= { lC350CtrlEntries 10305 }


    iFrontPanelLockFrontPanel OBJECT-TYPE
        SYNTAX            INTEGER {
                            valNormal(0),
                            valLocked(1)
                            }
        MAX-ACCESS        read-write
        STATUS            current
        DESCRIPTION
                "CMNT: - 
                 TYPE: - RadiobuttonList
                 PAGE: - Front Panel
                    Lock Front Panel  cmdID= 10306
                    Normal  value= 0
                    Locked  value= 1  "
        ::= { lC350CtrlEntries 10306 }


    iFrontPanelBrightness OBJECT-TYPE
        SYNTAX            INTEGER
        MAX-ACCESS        read-write
        STATUS            current
        DESCRIPTION
                "CMNT: - 
                 TYPE: - Number
                 PAGE: - Front Panel
                    Brightness  cmdID= 10307
                    min= 1  max= 63  step= 1  format= %d  div_scale= 1  preset= 48
                    Min = 1  Max = 63  Step = 1  Preset = 48  "
        ::= { lC350CtrlEntries 10307 }


    iGPIOGPI1GPI1ipSelect OBJECT-TYPE
        SYNTAX            INTEGER {
                            valUnused(255),
                            valFreeze(0),
                            valBlack(1),
                            valPattern(2),
                            valUserMemory1(3),
                            valUserMemory2(4),
                            valUserMemory3(5),
                            valUserMemory4(6),
                            valUserMemory5(7),
                            valUserMemory6(8),
                            valUserMemory7(9),
                            valUserMemory8(10),
                            valUserMemory9(11),
                            valUserMemory10(12),
                            valUserMemory11(13),
                            valUserMemory12(14),
                            valUserMemory13(15),
                            valUserMemory14(16),
                            valUserMemory15(17),
                            valUserMemory16(18)
                            }
        MAX-ACCESS        read-write
        STATUS            current
        DESCRIPTION
                "CMNT: - 
                 TYPE: - RadiobuttonList
                 PAGE: - GPIO
                    GPI 1-i/p Select  cmdID= 10343
                    Unused  value= 255
                    Freeze  value= 0
                    Black  value= 1
                    Pattern  value= 2
                    User Memory 1  value= 3
                    User Memory 2  value= 4
                    User Memory 3  value= 5
                    User Memory 4  value= 6
                    User Memory 5  value= 7
                    User Memory 6  value= 8
                    User Memory 7  value= 9
                    User Memory 8  value= 10
                    User Memory 9  value= 11
                    User Memory 10  value= 12
                    User Memory 11  value= 13
                    User Memory 12  value= 14
                    User Memory 13  value= 15
                    User Memory 14  value= 16
                    User Memory 15  value= 17
                    User Memory 16  value= 18  "
        ::= { lC350CtrlEntries 10343 }


    iGPIOGPI1GPO1opSelect OBJECT-TYPE
        SYNTAX            INTEGER {
                            valUnused(255),
                            valFreeze(0),
                            valBlack(1),
                            valPattern(2),
                            valCurrentInputOK(3),
                            valSDIInput1OK(4),
                            valSDIInput2OK(5),
                            valCVBSInputOK(6)
                            }
        MAX-ACCESS        read-write
        STATUS            current
        DESCRIPTION
                "CMNT: - 
                 TYPE: - RadiobuttonList
                 PAGE: - GPIO
                    GPO 1-o/p Select  cmdID= 10347
                    Unused  value= 255
                    Freeze  value= 0
                    Black  value= 1
                    Pattern  value= 2
                    Current Input OK  value= 3
                    SDI Input 1 OK  value= 4
                    SDI Input 2 OK  value= 5
                    CVBS Input OK  value= 6  "
        ::= { lC350CtrlEntries 10347 }


    iGPIOGPI2GPI2ipSelect OBJECT-TYPE
        SYNTAX            INTEGER {
                            valUnused(255),
                            valFreeze(0),
                            valBlack(1),
                            valPattern(2),
                            valUserMemory1(3),
                            valUserMemory2(4),
                            valUserMemory3(5),
                            valUserMemory4(6),
                            valUserMemory5(7),
                            valUserMemory6(8),
                            valUserMemory7(9),
                            valUserMemory8(10),
                            valUserMemory9(11),
                            valUserMemory10(12),
                            valUserMemory11(13),
                            valUserMemory12(14),
                            valUserMemory13(15),
                            valUserMemory14(16),
                            valUserMemory15(17),
                            valUserMemory16(18)
                            }
        MAX-ACCESS        read-write
        STATUS            current
        DESCRIPTION
                "CMNT: - 
                 TYPE: - RadiobuttonList
                 PAGE: - GPIO
                    GPI 2-i/p Select  cmdID= 10344
                    Unused  value= 255
                    Freeze  value= 0
                    Black  value= 1
                    Pattern  value= 2
                    User Memory 1  value= 3
                    User Memory 2  value= 4
                    User Memory 3  value= 5
                    User Memory 4  value= 6
                    User Memory 5  value= 7
                    User Memory 6  value= 8
                    User Memory 7  value= 9
                    User Memory 8  value= 10
                    User Memory 9  value= 11
                    User Memory 10  value= 12
                    User Memory 11  value= 13
                    User Memory 12  value= 14
                    User Memory 13  value= 15
                    User Memory 14  value= 16
                    User Memory 15  value= 17
                    User Memory 16  value= 18  "
        ::= { lC350CtrlEntries 10344 }


    iGPIOGPI2GPO2opSelect OBJECT-TYPE
        SYNTAX            INTEGER {
                            valUnused(255),
                            valFreeze(0),
                            valBlack(1),
                            valPattern(2),
                            valCurrentInputOK(3),
                            valSDIInput1OK(4),
                            valSDIInput2OK(5),
                            valCVBSInputOK(6)
                            }
        MAX-ACCESS        read-write
        STATUS            current
        DESCRIPTION
                "CMNT: - 
                 TYPE: - RadiobuttonList
                 PAGE: - GPIO
                    GPO 2-o/p Select  cmdID= 10348
                    Unused  value= 255
                    Freeze  value= 0
                    Black  value= 1
                    Pattern  value= 2
                    Current Input OK  value= 3
                    SDI Input 1 OK  value= 4
                    SDI Input 2 OK  value= 5
                    CVBS Input OK  value= 6  "
        ::= { lC350CtrlEntries 10348 }


    iGPIOGPI3GPI3ipSelect OBJECT-TYPE
        SYNTAX            INTEGER {
                            valUnused(255),
                            valFreeze(0),
                            valBlack(1),
                            valPattern(2),
                            valUserMemory1(3),
                            valUserMemory2(4),
                            valUserMemory3(5),
                            valUserMemory4(6),
                            valUserMemory5(7),
                            valUserMemory6(8),
                            valUserMemory7(9),
                            valUserMemory8(10),
                            valUserMemory9(11),
                            valUserMemory10(12),
                            valUserMemory11(13),
                            valUserMemory12(14),
                            valUserMemory13(15),
                            valUserMemory14(16),
                            valUserMemory15(17),
                            valUserMemory16(18)
                            }
        MAX-ACCESS        read-write
        STATUS            current
        DESCRIPTION
                "CMNT: - 
                 TYPE: - RadiobuttonList
                 PAGE: - GPIO
                    GPI 3-i/p Select  cmdID= 10345
                    Unused  value= 255
                    Freeze  value= 0
                    Black  value= 1
                    Pattern  value= 2
                    User Memory 1  value= 3
                    User Memory 2  value= 4
                    User Memory 3  value= 5
                    User Memory 4  value= 6
                    User Memory 5  value= 7
                    User Memory 6  value= 8
                    User Memory 7  value= 9
                    User Memory 8  value= 10
                    User Memory 9  value= 11
                    User Memory 10  value= 12
                    User Memory 11  value= 13
                    User Memory 12  value= 14
                    User Memory 13  value= 15
                    User Memory 14  value= 16
                    User Memory 15  value= 17
                    User Memory 16  value= 18  "
        ::= { lC350CtrlEntries 10345 }


    iGPIOGPI3GPO3opSelect OBJECT-TYPE
        SYNTAX            INTEGER {
                            valUnused(255),
                            valFreeze(0),
                            valBlack(1),
                            valPattern(2),
                            valCurrentInputOK(3),
                            valSDIInput1OK(4),
                            valSDIInput2OK(5),
                            valCVBSInputOK(6)
                            }
        MAX-ACCESS        read-write
        STATUS            current
        DESCRIPTION
                "CMNT: - 
                 TYPE: - RadiobuttonList
                 PAGE: - GPIO
                    GPO 3-o/p Select  cmdID= 10349
                    Unused  value= 255
                    Freeze  value= 0
                    Black  value= 1
                    Pattern  value= 2
                    Current Input OK  value= 3
                    SDI Input 1 OK  value= 4
                    SDI Input 2 OK  value= 5
                    CVBS Input OK  value= 6  "
        ::= { lC350CtrlEntries 10349 }


    iGPIOGPI4GPI4ipSelect OBJECT-TYPE
        SYNTAX            INTEGER {
                            valUnused(255),
                            valFreeze(0),
                            valBlack(1),
                            valPattern(2),
                            valUserMemory1(3),
                            valUserMemory2(4),
                            valUserMemory3(5),
                            valUserMemory4(6),
                            valUserMemory5(7),
                            valUserMemory6(8),
                            valUserMemory7(9),
                            valUserMemory8(10),
                            valUserMemory9(11),
                            valUserMemory10(12),
                            valUserMemory11(13),
                            valUserMemory12(14),
                            valUserMemory13(15),
                            valUserMemory14(16),
                            valUserMemory15(17),
                            valUserMemory16(18)
                            }
        MAX-ACCESS        read-write
        STATUS            current
        DESCRIPTION
                "CMNT: - 
                 TYPE: - RadiobuttonList
                 PAGE: - GPIO
                    GPI 4-i/p Select  cmdID= 10346
                    Unused  value= 255
                    Freeze  value= 0
                    Black  value= 1
                    Pattern  value= 2
                    User Memory 1  value= 3
                    User Memory 2  value= 4
                    User Memory 3  value= 5
                    User Memory 4  value= 6
                    User Memory 5  value= 7
                    User Memory 6  value= 8
                    User Memory 7  value= 9
                    User Memory 8  value= 10
                    User Memory 9  value= 11
                    User Memory 10  value= 12
                    User Memory 11  value= 13
                    User Memory 12  value= 14
                    User Memory 13  value= 15
                    User Memory 14  value= 16
                    User Memory 15  value= 17
                    User Memory 16  value= 18  "
        ::= { lC350CtrlEntries 10346 }


    iGPIOGPI4GPO4opSelect OBJECT-TYPE
        SYNTAX            INTEGER {
                            valUnused(255),
                            valFreeze(0),
                            valBlack(1),
                            valPattern(2),
                            valCurrentInputOK(3),
                            valSDIInput1OK(4),
                            valSDIInput2OK(5),
                            valCVBSInputOK(6)
                            }
        MAX-ACCESS        read-write
        STATUS            current
        DESCRIPTION
                "CMNT: - 
                 TYPE: - RadiobuttonList
                 PAGE: - GPIO
                    GPO 4-o/p Select  cmdID= 10350
                    Unused  value= 255
                    Freeze  value= 0
                    Black  value= 1
                    Pattern  value= 2
                    Current Input OK  value= 3
                    SDI Input 1 OK  value= 4
                    SDI Input 2 OK  value= 5
                    CVBS Input OK  value= 6  "
        ::= { lC350CtrlEntries 10350 }


    iGPIONewDisplay OBJECT-TYPE
        SYNTAX            RollCallString
        MAX-ACCESS        read-only
        STATUS            current
        DESCRIPTION
                "CMNT: - Hide GPIO controls
                 TYPE: - Display
                 PAGE: - GPIO
                    New Display  cmdID= 10510  "
        ::= { lC350CtrlEntries 10510 }


    iMemoriesRecallMemory OBJECT-TYPE
        SYNTAX            INTEGER {
                            valNoneSelected(0),
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Recall Memory  cmdID= 10353
                    None Selected  value= 0
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { lC350CtrlEntries 10353 }


    iMemoriesSelMemory OBJECT-TYPE
        SYNTAX            INTEGER {
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Sel Memory  cmdID= 10351
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { lC350CtrlEntries 10351 }


    iMemoriesSaveMemory OBJECT-TYPE
        SYNTAX            INTEGER { noAction(0),valSaveMemory(1) }
        MAX-ACCESS        read-write
        STATUS            current
        DESCRIPTION
                "CMNT: - 
                 TYPE: - Button
                 PAGE: - Memories
                    Save Memory  cmdID= 10352
                    value= 1  "
        ::= { lC350CtrlEntries 10352 }


    iMemoriesClearMemory OBJECT-TYPE
        SYNTAX            INTEGER { noAction(0),valClearMemory(1) }
        MAX-ACCESS        read-write
        STATUS            current
        DESCRIPTION
                "CMNT: - 
                 TYPE: - Button
                 PAGE: - Memories
                    Clear Memory  cmdID= 10356
                    value= 1  "
        ::= { lC350CtrlEntries 10356 }


    iMemoriesMemoryNameChangeName OBJECT-TYPE
        SYNTAX            RollCallString
        MAX-ACCESS        read-write
        STATUS            current
        DESCRIPTION
                "CMNT: - 
                 TYPE: - Editstring
                 PAGE: - Memories
                    Change Name  cmdID= 10354
                    preset= Preset Identifier"
        ::= { lC350CtrlEntries 10354 }


    iMemoriesLastDisplayMemory OBJECT-TYPE
        SYNTAX            RollCallString
        MAX-ACCESS        read-only
        STATUS            current
        DESCRIPTION
                "CMNT: - 
                 TYPE: - Display
                 PAGE: - Memories
                    Last Display Memory  cmdID= 10355  "
        ::= { lC350CtrlEntries 10355 }


    iMiscLoggingSerialNumberEnable OBJECT-TYPE
        SYNTAX            INTEGER { disable(0), enable(1)  }
        MAX-ACCESS        read-write
        STATUS            current
        DESCRIPTION
                "CMNT: - 
                 TYPE: - Checkbox
                 PAGE: - Misc. Logging
                    Serial Number Enable  cmdID= 10359  "
        ::= { lC350CtrlEntries 10359 }


    iMiscLoggingSerialNumberStatus OBJECT-TYPE
        SYNTAX            RollCallString
        MAX-ACCESS        read-only
        STATUS            current
        DESCRIPTION
                "CMNT: - 
                 TYPE: - Display
                 PAGE: - Misc. Logging
                    Serial Number Status  cmdID= 10360  "
        ::= { lC350CtrlEntries 10360 }


    iMiscLoggingUpTimeEnable OBJECT-TYPE
        SYNTAX            INTEGER { disable(0), enable(1)  }
        MAX-ACCESS        read-write
        STATUS            current
        DESCRIPTION
                "CMNT: - 
                 TYPE: - Checkbox
                 PAGE: - Misc. Logging
                    Up Time Enable  cmdID= 10361  "
        ::= { lC350CtrlEntries 10361 }


    iMiscLoggingUpTimeStatus OBJECT-TYPE
        SYNTAX            RollCallString
        MAX-ACCESS        read-only
        STATUS            current
        DESCRIPTION
                "CMNT: - 
                 TYPE: - Display
                 PAGE: - Misc. Logging
                    Up Time Status  cmdID= 10362  "
        ::= { lC350CtrlEntries 10362 }


    iMiscLoggingPowerUsageStateEnable OBJECT-TYPE
        SYNTAX            INTEGER { disable(0), enable(1)  }
        MAX-ACCESS        read-write
        STATUS            current
        DESCRIPTION
                "CMNT: - 
                 TYPE: - Checkbox
                 PAGE: - Misc. Logging
                    Power Usage State Enable  cmdID= 10363  "
        ::= { lC350CtrlEntries 10363 }


    iMiscLoggingPowerUsageStateStatus OBJECT-TYPE
        SYNTAX            RollCallString
        MAX-ACCESS        read-only
        STATUS            current
        DESCRIPTION
                "CMNT: - 
                 TYPE: - Display
                 PAGE: - Misc. Logging
                    Power Usage State Status  cmdID= 10364  "
        ::= { lC350CtrlEntries 10364 }


    iMiscLoggingPowerUsage2StateEnable OBJECT-TYPE
        SYNTAX            INTEGER { disable(0), enable(1)  }
        MAX-ACCESS        read-write
        STATUS            current
        DESCRIPTION
                "CMNT: - 
                 TYPE: - Checkbox
                 PAGE: - Misc. Logging
                    Power Usage 2 State Enable  cmdID= 10365  "
        ::= { lC350CtrlEntries 10365 }


    iMiscLoggingPowerUsageState2Status OBJECT-TYPE
        SYNTAX            RollCallString
        MAX-ACCESS        read-only
        STATUS            current
        DESCRIPTION
                "CMNT: - 
                 TYPE: - Display
                 PAGE: - Misc. Logging
                    Power Usage State 2 Status  cmdID= 10366  "
        ::= { lC350CtrlEntries 10366 }


    iMiscLoggingBuild OBJECT-TYPE
        SYNTAX            INTEGER { disable(0), enable(1)  }
        MAX-ACCESS        read-write
        STATUS            current
        DESCRIPTION
                "CMNT: - 
                 TYPE: - Checkbox
                 PAGE: - Misc. Logging
                    Build  cmdID= 10370  "
        ::= { lC350CtrlEntries 10370 }


    iMiscLoggingBuildEnable OBJECT-TYPE
        SYNTAX            RollCallString
        MAX-ACCESS        read-only
        STATUS            current
        DESCRIPTION
                "CMNT: - 
                 TYPE: - Display
                 PAGE: - Misc. Logging
                    Build Enable  cmdID= 10369  "
        ::= { lC350CtrlEntries 10369 }


    iVideoLoggingVideoInput1TypeEnable OBJECT-TYPE
        SYNTAX            INTEGER { disable(0), enable(1)  }
        MAX-ACCESS        read-write
        STATUS            current
        DESCRIPTION
                "CMNT: - 
                 TYPE: - Checkbox
                 PAGE: - Video Logging
                    Video Input 1 Type Enable  cmdID= 10371  "
        ::= { lC350CtrlEntries 10371 }


    iVideoLoggingVideoInput1Type OBJECT-TYPE
        SYNTAX            RollCallString
        MAX-ACCESS        read-only
        STATUS            current
        DESCRIPTION
                "CMNT: - 
                 TYPE: - Display
                 PAGE: - Video Logging
                    Video Input 1 Type  cmdID= 10372  "
        ::= { lC350CtrlEntries 10372 }


    iVideoLoggingVideoInput1StateEnable OBJECT-TYPE
        SYNTAX            INTEGER { disable(0), enable(1)  }
        MAX-ACCESS        read-write
        STATUS            current
        DESCRIPTION
                "CMNT: - 
                 TYPE: - Checkbox
                 PAGE: - Video Logging
                    Video Input 1 State Enable  cmdID= 10373  "
        ::= { lC350CtrlEntries 10373 }


    iVideoLoggingVideoInput1State OBJECT-TYPE
        SYNTAX            RollCallString
        MAX-ACCESS        read-only
        STATUS            current
        DESCRIPTION
                "CMNT: - 
                 TYPE: - Display
                 PAGE: - Video Logging
                    Video Input 1 State  cmdID= 10374  "
        ::= { lC350CtrlEntries 10374 }


    iVideoLoggingVideoInput1StdEnable OBJECT-TYPE
        SYNTAX            INTEGER { disable(0), enable(1)  }
        MAX-ACCESS        read-write
        STATUS            current
        DESCRIPTION
                "CMNT: - 
                 TYPE: - Checkbox
                 PAGE: - Video Logging
                    Video Input 1 Std Enable  cmdID= 10375  "
        ::= { lC350CtrlEntries 10375 }


    iVideoLoggingVideoInput1Std OBJECT-TYPE
        SYNTAX            RollCallString
        MAX-ACCESS        read-only
        STATUS            current
        DESCRIPTION
                "CMNT: - 
                 TYPE: - Display
                 PAGE: - Video Logging
                    Video Input 1 Std  cmdID= 10376  "
        ::= { lC350CtrlEntries 10376 }


    iVideoLoggingVideoInput2TypeEnable OBJECT-TYPE
        SYNTAX            INTEGER { disable(0), enable(1)  }
        MAX-ACCESS        read-write
        STATUS            current
        DESCRIPTION
                "CMNT: - 
                 TYPE: - Checkbox
                 PAGE: - Video Logging
                    Video Input 2 Type Enable  cmdID= 10377  "
        ::= { lC350CtrlEntries 10377 }


    iVideoLoggingVideoInput2Type OBJECT-TYPE
        SYNTAX            RollCallString
        MAX-ACCESS        read-only
        STATUS            current
        DESCRIPTION
                "CMNT: - 
                 TYPE: - Display
                 PAGE: - Video Logging
                    Video Input 2 Type  cmdID= 10378  "
        ::= { lC350CtrlEntries 10378 }


    iVideoLoggingVideoInput2StateEnable OBJECT-TYPE
        SYNTAX            INTEGER { disable(0), enable(1)  }
        MAX-ACCESS        read-write
        STATUS            current
        DESCRIPTION
                "CMNT: - 
                 TYPE: - Checkbox
                 PAGE: - Video Logging
                    Video Input 2 State Enable  cmdID= 10379  "
        ::= { lC350CtrlEntries 10379 }


    iVideoLoggingVideoInput2State OBJECT-TYPE
        SYNTAX            RollCallString
        MAX-ACCESS        read-only
        STATUS            current
        DESCRIPTION
                "CMNT: - 
                 TYPE: - Display
                 PAGE: - Video Logging
                    Video Input 2 State  cmdID= 10380  "
        ::= { lC350CtrlEntries 10380 }


    iVideoLoggingVideoInput2StdEnable OBJECT-TYPE
        SYNTAX            INTEGER { disable(0), enable(1)  }
        MAX-ACCESS        read-write
        STATUS            current
        DESCRIPTION
                "CMNT: - 
                 TYPE: - Checkbox
                 PAGE: - Video Logging
                    Video Input 2 Std Enable  cmdID= 10381  "
        ::= { lC350CtrlEntries 10381 }


    iVideoLoggingVideoInput2Std OBJECT-TYPE
        SYNTAX            RollCallString
        MAX-ACCESS        read-only
        STATUS            current
        DESCRIPTION
                "CMNT: - 
                 TYPE: - Display
                 PAGE: - Video Logging
                    Video Input 2 Std  cmdID= 10382  "
        ::= { lC350CtrlEntries 10382 }


    iVideoLoggingVideoInput3TypeEnable OBJECT-TYPE
        SYNTAX            INTEGER { disable(0), enable(1)  }
        MAX-ACCESS        read-write
        STATUS            current
        DESCRIPTION
                "CMNT: - 
                 TYPE: - Checkbox
                 PAGE: - Video Logging
                    Video Input 3 Type Enable  cmdID= 10383  "
        ::= { lC350CtrlEntries 10383 }


    iVideoLoggingVideoInput3Type OBJECT-TYPE
        SYNTAX            RollCallString
        MAX-ACCESS        read-only
        STATUS            current
        DESCRIPTION
                "CMNT: - 
                 TYPE: - Display
                 PAGE: - Video Logging
                    Video Input 3 Type  cmdID= 10384  "
        ::= { lC350CtrlEntries 10384 }


    iVideoLoggingVideoInput3StateEnable OBJECT-TYPE
        SYNTAX            INTEGER { disable(0), enable(1)  }
        MAX-ACCESS        read-write
        STATUS            current
        DESCRIPTION
                "CMNT: - 
                 TYPE: - Checkbox
                 PAGE: - Video Logging
                    Video Input 3 State Enable  cmdID= 10385  "
        ::= { lC350CtrlEntries 10385 }


    iVideoLoggingVideoInput3State OBJECT-TYPE
        SYNTAX            RollCallString
        MAX-ACCESS        read-only
        STATUS            current
        DESCRIPTION
                "CMNT: - 
                 TYPE: - Display
                 PAGE: - Video Logging
                    Video Input 3 State  cmdID= 10386  "
        ::= { lC350CtrlEntries 10386 }


    iVideoLoggingVideoInput3StdEnable OBJECT-TYPE
        SYNTAX            INTEGER { disable(0), enable(1)  }
        MAX-ACCESS        read-write
        STATUS            current
        DESCRIPTION
                "CMNT: - 
                 TYPE: - Checkbox
                 PAGE: - Video Logging
                    Video Input 3 Std Enable  cmdID= 10387  "
        ::= { lC350CtrlEntries 10387 }


    iVideoLoggingVideoInput3Std OBJECT-TYPE
        SYNTAX            RollCallString
        MAX-ACCESS        read-only
        STATUS            current
        DESCRIPTION
                "CMNT: - 
                 TYPE: - Display
                 PAGE: - Video Logging
                    Video Input 3 Std  cmdID= 10388  "
        ::= { lC350CtrlEntries 10388 }


    iVideoLoggingVideoInput4TypeEnable OBJECT-TYPE
        SYNTAX            INTEGER { disable(0), enable(1)  }
        MAX-ACCESS        read-write
        STATUS            current
        DESCRIPTION
                "CMNT: - 
                 TYPE: - Checkbox
                 PAGE: - Video Logging
                    Video Input 4 Type Enable  cmdID= 10389  "
        ::= { lC350CtrlEntries 10389 }


    iVideoLoggingVideoInput4Type OBJECT-TYPE
        SYNTAX            RollCallString
        MAX-ACCESS        read-only
        STATUS            current
        DESCRIPTION
                "CMNT: - 
                 TYPE: - Display
                 PAGE: - Video Logging
                    Video Input 4 Type  cmdID= 10390  "
        ::= { lC350CtrlEntries 10390 }


    iVideoLoggingVideoInput4StateEnable OBJECT-TYPE
        SYNTAX            INTEGER { disable(0), enable(1)  }
        MAX-ACCESS        read-write
        STATUS            current
        DESCRIPTION
                "CMNT: - 
                 TYPE: - Checkbox
                 PAGE: - Video Logging
                    Video Input 4 State Enable  cmdID= 10391  "
        ::= { lC350CtrlEntries 10391 }


    iVideoLoggingVideoInput4State OBJECT-TYPE
        SYNTAX            RollCallString
        MAX-ACCESS        read-only
        STATUS            current
        DESCRIPTION
                "CMNT: - 
                 TYPE: - Display
                 PAGE: - Video Logging
                    Video Input 4 State  cmdID= 10392  "
        ::= { lC350CtrlEntries 10392 }


    iVideoLoggingVideoInput4StdEnable OBJECT-TYPE
        SYNTAX            INTEGER { disable(0), enable(1)  }
        MAX-ACCESS        read-write
        STATUS            current
        DESCRIPTION
                "CMNT: - 
                 TYPE: - Checkbox
                 PAGE: - Video Logging
                    Video Input 4 Std Enable  cmdID= 10393  "
        ::= { lC350CtrlEntries 10393 }


    iVideoLoggingVideoInput4Std OBJECT-TYPE
        SYNTAX            RollCallString
        MAX-ACCESS        read-only
        STATUS            current
        DESCRIPTION
                "CMNT: - 
                 TYPE: - Display
                 PAGE: - Video Logging
                    Video Input 4 Std  cmdID= 10394  "
        ::= { lC350CtrlEntries 10394 }


    iVideoLoggingVideoInput5TypeEnable OBJECT-TYPE
        SYNTAX            INTEGER { disable(0), enable(1)  }
        MAX-ACCESS        read-write
        STATUS            current
        DESCRIPTION
                "CMNT: - 
                 TYPE: - Checkbox
                 PAGE: - Video Logging
                    Video Input 5 Type Enable  cmdID= 10395  "
        ::= { lC350CtrlEntries 10395 }


    iVideoLoggingVideoInput5Type OBJECT-TYPE
        SYNTAX            RollCallString
        MAX-ACCESS        read-only
        STATUS            current
        DESCRIPTION
                "CMNT: - 
                 TYPE: - Display
                 PAGE: - Video Logging
                    Video Input 5 Type  cmdID= 10396  "
        ::= { lC350CtrlEntries 10396 }


    iVideoLoggingVideoInput5StateEnable OBJECT-TYPE
        SYNTAX            INTEGER { disable(0), enable(1)  }
        MAX-ACCESS        read-write
        STATUS            current
        DESCRIPTION
                "CMNT: - 
                 TYPE: - Checkbox
                 PAGE: - Video Logging
                    Video Input 5 State Enable  cmdID= 10397  "
        ::= { lC350CtrlEntries 10397 }


    iVideoLoggingVideoInput5State OBJECT-TYPE
        SYNTAX            RollCallString
        MAX-ACCESS        read-only
        STATUS            current
        DESCRIPTION
                "CMNT: - 
                 TYPE: - Display
                 PAGE: - Video Logging
                    Video Input 5 State  cmdID= 10398  "
        ::= { lC350CtrlEntries 10398 }


    iVideoLoggingVideoInput5StdEnable OBJECT-TYPE
        SYNTAX            INTEGER { disable(0), enable(1)  }
        MAX-ACCESS        read-write
        STATUS            current
        DESCRIPTION
                "CMNT: - 
                 TYPE: - Checkbox
                 PAGE: - Video Logging
                    Video Input 5 Std Enable  cmdID= 10399  "
        ::= { lC350CtrlEntries 10399 }


    iVideoLoggingVideoInput5Std OBJECT-TYPE
        SYNTAX            RollCallString
        MAX-ACCESS        read-only
        STATUS            current
        DESCRIPTION
                "CMNT: - 
                 TYPE: - Display
                 PAGE: - Video Logging
                    Video Input 5 Std  cmdID= 10400  "
        ::= { lC350CtrlEntries 10400 }


    iVideoLoggingVideoOutput1TypeEnable OBJECT-TYPE
        SYNTAX            INTEGER { disable(0), enable(1)  }
        MAX-ACCESS        read-write
        STATUS            current
        DESCRIPTION
                "CMNT: - 
                 TYPE: - Checkbox
                 PAGE: - Video Logging
                    Video Output 1 Type Enable  cmdID= 10401  "
        ::= { lC350CtrlEntries 10401 }


    iVideoLoggingVideoOutput1Type OBJECT-TYPE
        SYNTAX            RollCallString
        MAX-ACCESS        read-only
        STATUS            current
        DESCRIPTION
                "CMNT: - 
                 TYPE: - Display
                 PAGE: - Video Logging
                    Video Output 1 Type  cmdID= 10402  "
        ::= { lC350CtrlEntries 10402 }


    iVideoLoggingVideoOutput1StateEnable OBJECT-TYPE
        SYNTAX            INTEGER { disable(0), enable(1)  }
        MAX-ACCESS        read-write
        STATUS            current
        DESCRIPTION
                "CMNT: - 
                 TYPE: - Checkbox
                 PAGE: - Video Logging
                    Video Output 1 State Enable  cmdID= 10403  "
        ::= { lC350CtrlEntries 10403 }


    iVideoLoggingVideoOutput1State OBJECT-TYPE
        SYNTAX            RollCallString
        MAX-ACCESS        read-only
        STATUS            current
        DESCRIPTION
                "CMNT: - 
                 TYPE: - Display
                 PAGE: - Video Logging
                    Video Output 1 State  cmdID= 10404  "
        ::= { lC350CtrlEntries 10404 }


    iVideoLoggingVideoOutput1StdEnable OBJECT-TYPE
        SYNTAX            INTEGER { disable(0), enable(1)  }
        MAX-ACCESS        read-write
        STATUS            current
        DESCRIPTION
                "CMNT: - 
                 TYPE: - Checkbox
                 PAGE: - Video Logging
                    Video Output 1 Std Enable  cmdID= 10405  "
        ::= { lC350CtrlEntries 10405 }


    iVideoLoggingVideoOutput1Std OBJECT-TYPE
        SYNTAX            RollCallString
        MAX-ACCESS        read-only
        STATUS            current
        DESCRIPTION
                "CMNT: - 
                 TYPE: - Display
                 PAGE: - Video Logging
                    Video Output 1 Std  cmdID= 10406  "
        ::= { lC350CtrlEntries 10406 }


    iAudioLoggingAudioOutputEmbPair1typeEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 1 type Enable  cmdID= 10431  "
        ::= { lC350CtrlEntries 10431 }


    iAudioLoggingAudioOutputEmbPair1type OBJECT-TYPE
        SYNTAX            RollCallString
        MAX-ACCESS        read-only
        STATUS            current
        DESCRIPTION
                "CMNT: - 
                 TYPE: - Display
                 PAGE: - Audio Logging
                    Audio Output Emb.Pair 1 type  cmdID= 10432  "
        ::= { lC350CtrlEntries 10432 }


    iAudioLoggingAudioOutputEmbPair2typeEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 2 type Enable  cmdID= 10433  "
        ::= { lC350CtrlEntries 10433 }


    iAudioLoggingAudioOutputEmbPair2type OBJECT-TYPE
        SYNTAX            RollCallString
        MAX-ACCESS        read-only
        STATUS            current
        DESCRIPTION
                "CMNT: - 
                 TYPE: - Display
                 PAGE: - Audio Logging
                    Audio Output Emb.Pair 2 type  cmdID= 10434  "
        ::= { lC350CtrlEntries 10434 }


    iAudioLoggingAudioOutputEmbPair3typeEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 3 type Enable  cmdID= 10435  "
        ::= { lC350CtrlEntries 10435 }


    iAudioLoggingAudioOutputEmbPair3type OBJECT-TYPE
        SYNTAX            RollCallString
        MAX-ACCESS        read-only
        STATUS            current
        DESCRIPTION
                "CMNT: - 
                 TYPE: - Display
                 PAGE: - Audio Logging
                    Audio Output Emb.Pair 3 type  cmdID= 10436  "
        ::= { lC350CtrlEntries 10436 }


    iAudioLoggingAudioOutputEmbPair4typeEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 4 type Enable  cmdID= 10437  "
        ::= { lC350CtrlEntries 10437 }


    iAudioLoggingAudioOutputEmbPair4type OBJECT-TYPE
        SYNTAX            RollCallString
        MAX-ACCESS        read-only
        STATUS            current
        DESCRIPTION
                "CMNT: - 
                 TYPE: - Display
                 PAGE: - Audio Logging
                    Audio Output Emb.Pair 4 type  cmdID= 10438  "
        ::= { lC350CtrlEntries 10438 }


    iAudioLoggingAudioOutputEmbPair5typeEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 5 type Enable  cmdID= 10439  "
        ::= { lC350CtrlEntries 10439 }


    iAudioLoggingAudioOutputEmbPair5type OBJECT-TYPE
        SYNTAX            RollCallString
        MAX-ACCESS        read-only
        STATUS            current
        DESCRIPTION
                "CMNT: - 
                 TYPE: - Display
                 PAGE: - Audio Logging
                    Audio Output Emb.Pair 5 type  cmdID= 10440  "
        ::= { lC350CtrlEntries 10440 }


    iAudioLoggingAudioOutputEmbPair6typeEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 6 type Enable  cmdID= 10441  "
        ::= { lC350CtrlEntries 10441 }


    iAudioLoggingAudioOutputEmbPair6type OBJECT-TYPE
        SYNTAX            RollCallString
        MAX-ACCESS        read-only
        STATUS            current
        DESCRIPTION
                "CMNT: - 
                 TYPE: - Display
                 PAGE: - Audio Logging
                    Audio Output Emb.Pair 6 type  cmdID= 10442  "
        ::= { lC350CtrlEntries 10442 }


    iAudioLoggingAudioOutputEmbPair7typeEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 7 type Enable  cmdID= 10443  "
        ::= { lC350CtrlEntries 10443 }


    iAudioLoggingAudioOutputEmbPair7type OBJECT-TYPE
        SYNTAX            RollCallString
        MAX-ACCESS        read-only
        STATUS            current
        DESCRIPTION
                "CMNT: - 
                 TYPE: - Display
                 PAGE: - Audio Logging
                    Audio Output Emb.Pair 7 type  cmdID= 10444  "
        ::= { lC350CtrlEntries 10444 }


    iAudioLoggingAudioOutputEmbPair8typeEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 8 type Enable  cmdID= 10445  "
        ::= { lC350CtrlEntries 10445 }


    iAudioLoggingAudioOutputEmbPair8type OBJECT-TYPE
        SYNTAX            RollCallString
        MAX-ACCESS        read-only
        STATUS            current
        DESCRIPTION
                "CMNT: - 
                 TYPE: - Display
                 PAGE: - Audio Logging
                    Audio Output Emb.Pair 8 type  cmdID= 10446  "
        ::= { lC350CtrlEntries 10446 }


    iAudioLoggingAudioOutputEmbPair1stateEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 1 state Enable  cmdID= 10415  "
        ::= { lC350CtrlEntries 10415 }


    iAudioLoggingAudioOutputEmbPair1state OBJECT-TYPE
        SYNTAX            RollCallString
        MAX-ACCESS        read-only
        STATUS            current
        DESCRIPTION
                "CMNT: - 
                 TYPE: - Display
                 PAGE: - Audio Logging
                    Audio Output Emb.Pair 1 state  cmdID= 10416  "
        ::= { lC350CtrlEntries 10416 }


    iAudioLoggingAudioOutputEmbPair2stateEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 2 state Enable  cmdID= 10417  "
        ::= { lC350CtrlEntries 10417 }


    iAudioLoggingAudioOutputEmbPair2state OBJECT-TYPE
        SYNTAX            RollCallString
        MAX-ACCESS        read-only
        STATUS            current
        DESCRIPTION
                "CMNT: - 
                 TYPE: - Display
                 PAGE: - Audio Logging
                    Audio Output Emb.Pair 2 state  cmdID= 10418  "
        ::= { lC350CtrlEntries 10418 }


    iAudioLoggingAudioOutputEmbPair3stateEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 3 state Enable  cmdID= 10419  "
        ::= { lC350CtrlEntries 10419 }


    iAudioLoggingAudioOutputEmbPair3state OBJECT-TYPE
        SYNTAX            RollCallString
        MAX-ACCESS        read-only
        STATUS            current
        DESCRIPTION
                "CMNT: - 
                 TYPE: - Display
                 PAGE: - Audio Logging
                    Audio Output Emb.Pair 3 state  cmdID= 10420  "
        ::= { lC350CtrlEntries 10420 }


    iAudioLoggingAudioOutputEmbPair4stateEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 4 state Enable  cmdID= 10421  "
        ::= { lC350CtrlEntries 10421 }


    iAudioLoggingAudioOutputEmbPair4state OBJECT-TYPE
        SYNTAX            RollCallString
        MAX-ACCESS        read-only
        STATUS            current
        DESCRIPTION
                "CMNT: - 
                 TYPE: - Display
                 PAGE: - Audio Logging
                    Audio Output Emb.Pair 4 state  cmdID= 10422  "
        ::= { lC350CtrlEntries 10422 }


    iAudioLoggingAudioOutputEmbPair5stateEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 5 state Enable  cmdID= 10423  "
        ::= { lC350CtrlEntries 10423 }


    iAudioLoggingAudioOutputEmbPair5state OBJECT-TYPE
        SYNTAX            RollCallString
        MAX-ACCESS        read-only
        STATUS            current
        DESCRIPTION
                "CMNT: - 
                 TYPE: - Display
                 PAGE: - Audio Logging
                    Audio Output Emb.Pair 5 state  cmdID= 10424  "
        ::= { lC350CtrlEntries 10424 }


    iAudioLoggingAudioOutputEmbPair6stateEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 6 state Enable  cmdID= 10425  "
        ::= { lC350CtrlEntries 10425 }


    iAudioLoggingAudioOutputEmbPair6state OBJECT-TYPE
        SYNTAX            RollCallString
        MAX-ACCESS        read-only
        STATUS            current
        DESCRIPTION
                "CMNT: - 
                 TYPE: - Display
                 PAGE: - Audio Logging
                    Audio Output Emb.Pair 6 state  cmdID= 10426  "
        ::= { lC350CtrlEntries 10426 }


    iAudioLoggingAudioOutputEmbPair7stateEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 7 state Enable  cmdID= 10427  "
        ::= { lC350CtrlEntries 10427 }


    iAudioLoggingAudioOutputEmbPair7state OBJECT-TYPE
        SYNTAX            RollCallString
        MAX-ACCESS        read-only
        STATUS            current
        DESCRIPTION
                "CMNT: - 
                 TYPE: - Display
                 PAGE: - Audio Logging
                    Audio Output Emb.Pair 7 state  cmdID= 10428  "
        ::= { lC350CtrlEntries 10428 }


    iAudioLoggingAudioOutputEmbPair8stateEnable OBJECT-TYPE
        SYNTAX            INTEGER { disable(0), enable(1)  }
        MAX-ACCESS        read-write
        STATUS            current
        DESCRIPTION
                "CMNT: - 
                 TYPE: - Checkbox
                 PAGE: - Audio Logging
                    Audio Output Emb.Pair 8 state Enable  cmdID= 10429  "
        ::= { lC350CtrlEntries 10429 }


    iAudioLoggingAudioOutputEmbPair8state OBJECT-TYPE
        SYNTAX            RollCallString
        MAX-ACCESS        read-only
        STATUS            current
        DESCRIPTION
                "CMNT: - 
                 TYPE: - Display
                 PAGE: - Audio Logging
                    Audio Output Emb.Pair 8 state  cmdID= 10430  "
        ::= { lC350CtrlEntries 10430 }


    iSetupSoftwareVersion OBJECT-TYPE
        SYNTAX            RollCallString
        MAX-ACCESS        read-only
        STATUS            current
        DESCRIPTION
                "CMNT: - 
                 TYPE: - Display
                 PAGE: - Setup
                    Software Version  cmdID= 10518  "
        ::= { lC350CtrlEntries 10518 }


    iSetupSerialNumber OBJECT-TYPE
        SYNTAX            RollCallString
        MAX-ACCESS        read-only
        STATUS            current
        DESCRIPTION
                "CMNT: - 
                 TYPE: - Display
                 PAGE: - Setup
                    Serial Number  cmdID= 10517  "
        ::= { lC350CtrlEntries 10517 }


    iSetupFanSpeed OBJECT-TYPE
        SYNTAX            RollCallString
        MAX-ACCESS        read-only
        STATUS            current
        DESCRIPTION
                "CMNT: - 
                 TYPE: - Display
                 PAGE: - Setup
                    Fan Speed  cmdID= 10502  "
        ::= { lC350CtrlEntries 10502 }


    iSetupLC3OPTNR OBJECT-TYPE
        SYNTAX            RollCallString
        MAX-ACCESS        read-only
        STATUS            current
        DESCRIPTION
                "CMNT: - 
                 TYPE: - Display
                 PAGE: - Setup
                    LC3OPT-NR  cmdID= 10496  "
        ::= { lC350CtrlEntries 10496 }


    iSetupLC3OPTSBK OBJECT-TYPE
        SYNTAX            RollCallString
        MAX-ACCESS        read-only
        STATUS            current
        DESCRIPTION
                "CMNT: - 
                 TYPE: - Display
                 PAGE: - Setup
                    LC3OPT-SBK  cmdID= 10497  "
        ::= { lC350CtrlEntries 10497 }


    iSetupLC3OPTLOG OBJECT-TYPE
        SYNTAX            RollCallString
        MAX-ACCESS        read-only
        STATUS            current
        DESCRIPTION
                "CMNT: - 
                 TYPE: - Display
                 PAGE: - Setup
                    LC3OPT-LOG  cmdID= 10498  "
        ::= { lC350CtrlEntries 10498 }


    iSetupBuild OBJECT-TYPE
        SYNTAX            RollCallString
        MAX-ACCESS        read-only
        STATUS            current
        DESCRIPTION
                "CMNT: - 
                 TYPE: - Display
                 PAGE: - Setup
                    Build  cmdID= 10499  "
        ::= { lC350CtrlEntries 10499 }


    iSetupFactoryDefaults OBJECT-TYPE
        SYNTAX            INTEGER { noAction(0),valFactoryDefaults(1) }
        MAX-ACCESS        read-write
        STATUS            current
        DESCRIPTION
                "CMNT: - 
                 TYPE: - Button
                 PAGE: - Setup
                    Factory Defaults  cmdID= 10358
                    value= 1  "
        ::= { lC350CtrlEntries 10358 }


    iSetupDefaultSettings OBJECT-TYPE
        SYNTAX            INTEGER { noAction(0),valDefaultSettings(1) }
        MAX-ACCESS        read-write
        STATUS            current
        DESCRIPTION
                "CMNT: - 
                 TYPE: - Button
                 PAGE: - Setup
                    Default Settings  cmdID= 10357
                    value= 1  "
        ::= { lC350CtrlEntries 10357 }


    iSetupRestart OBJECT-TYPE
        SYNTAX            INTEGER { noAction(0),valRestart(1) }
        MAX-ACCESS        read-write
        STATUS            current
        DESCRIPTION
                "CMNT: - Restart unit
                 TYPE: - Button
                 PAGE: - Setup
                    Restart  cmdID= 10519
                    value= 1  "
        ::= { lC350CtrlEntries 10519 }


    iSetupNewLogo OBJECT-TYPE
        SYNTAX            RollCallString
        MAX-ACCESS        read-write
        STATUS            current
        DESCRIPTION
                "CMNT: - 
                 TYPE: - Editstring
                 PAGE: - Setup
                    New Logo  cmdID= 15000
                    preset= startupqwerty"
        ::= { lC350CtrlEntries 15000 }


    iSetupLogoStatus OBJECT-TYPE
        SYNTAX            RollCallString
        MAX-ACCESS        read-only
        STATUS            current
        DESCRIPTION
                "CMNT: - 
                 TYPE: - Display
                 PAGE: - Setup
                    Logo Status  cmdID= 15001  "
        ::= { lC350CtrlEntries 15001 }


    iDisplaymenuDisplay OBJECT-TYPE
        SYNTAX            INTEGER {
                            valUnitInfo(0),
                            valVideoStatus(1),
                            valAudioStatus(2),
                            valMetadataStatus(3)
                            }
        MAX-ACCESS        read-write
        STATUS            current
        DESCRIPTION
                "CMNT: - Select Info display to show
                 TYPE: - RadiobuttonList
                 PAGE: - Displaymenu
                    Display  cmdID= 10495
                    Unit Info  value= 0
                    Video Status  value= 1
                    Audio Status  value= 2
                    Metadata Status  value= 3  "
        ::= { lC350CtrlEntries 10495 }
    lC350ConfEntries OBJECT IDENTIFIER ::= { lC350 2 }


    iSNMPMIB2sysContact OBJECT-TYPE
        SYNTAX            RollCallString
        MAX-ACCESS        read-write
        STATUS            current
        DESCRIPTION
                "CMNT: - 
                 TYPE: - Editstring
                 PAGE: - SNMP
                    MIB2 sysContact  cmdID= 10470
                    preset= www.snellgroup.com"
        ::= { lC350ConfEntries 10470 }


    iSNMPMIB2sysName OBJECT-TYPE
        SYNTAX            RollCallString
        MAX-ACCESS        read-write
        STATUS            current
        DESCRIPTION
                "CMNT: - 
                 TYPE: - Editstring
                 PAGE: - SNMP
                    MIB2 sysName  cmdID= 10471
                    preset= System Name"
        ::= { lC350ConfEntries 10471 }


    iSNMPMIB2sysLocation OBJECT-TYPE
        SYNTAX            RollCallString
        MAX-ACCESS        read-write
        STATUS            current
        DESCRIPTION
                "CMNT: - 
                 TYPE: - Editstring
                 PAGE: - SNMP
                    MIB2 sysLocation  cmdID= 10472
                    preset= Location Name"
        ::= { lC350ConfEntries 10472 }


    iSNMPReadWritePort OBJECT-TYPE
        SYNTAX            RollCallString
        MAX-ACCESS        read-write
        STATUS            current
        DESCRIPTION
                "CMNT: - 
                 TYPE: - Editstring
                 PAGE: - SNMP
                    Read Write Port  cmdID= 10473
                    preset= 161"
        ::= { lC350ConfEntries 10473 }


    iSNMPResendTraps OBJECT-TYPE
        SYNTAX            INTEGER { noAction(0),valResendTraps(1) }
        MAX-ACCESS        read-write
        STATUS            current
        DESCRIPTION
                "CMNT: - 
                 TYPE: - Button
                 PAGE: - SNMP
                    Resend Traps  cmdID= 10492
                    value= 1  "
        ::= { lC350ConfEntries 10492 }


    iSNMPControlEnable OBJECT-TYPE
        SYNTAX            INTEGER { disable(0), enable(1)  }
        MAX-ACCESS        read-write
        STATUS            current
        DESCRIPTION
                "CMNT: - 
                 TYPE: - Checkbox
                 PAGE: - SNMP
                    Control Enable  cmdID= 10493  "
        ::= { lC350ConfEntries 10493 }


    iSNMPTrapsEnable OBJECT-TYPE
        SYNTAX            INTEGER { disable(0), enable(1)  }
        MAX-ACCESS        read-write
        STATUS            current
        DESCRIPTION
                "CMNT: - 
                 TYPE: - Checkbox
                 PAGE: - SNMP
                    Traps Enable  cmdID= 10494  "
        ::= { lC350ConfEntries 10494 }


    iSNMPTrapDest1TrapdestIPaddr OBJECT-TYPE
        SYNTAX            RollCallString
        MAX-ACCESS        read-write
        STATUS            current
        DESCRIPTION
                "CMNT: - 
                 TYPE: - Editstring
                 PAGE: - SNMP
                    Trap dest IP addr  cmdID= 10474
                    preset= 0.0.0.0"
        ::= { lC350ConfEntries 10474 }


    iSNMPTrapDest1Trapdestport OBJECT-TYPE
        SYNTAX            RollCallString
        MAX-ACCESS        read-write
        STATUS            current
        DESCRIPTION
                "CMNT: - 
                 TYPE: - Editstring
                 PAGE: - SNMP
                    Trap dest port  cmdID= 10475
                    preset= 162"
        ::= { lC350ConfEntries 10475 }


    iSNMPTrapDest1Trapcommunity OBJECT-TYPE
        SYNTAX            RollCallString
        MAX-ACCESS        read-write
        STATUS            current
        DESCRIPTION
                "CMNT: - 
                 TYPE: - Editstring
                 PAGE: - SNMP
                    Trap community  cmdID= 10476
                    preset= public"
        ::= { lC350ConfEntries 10476 }


    iSNMPTrapDest2TrapdestIPaddr OBJECT-TYPE
        SYNTAX            RollCallString
        MAX-ACCESS        read-write
        STATUS            current
        DESCRIPTION
                "CMNT: - 
                 TYPE: - Editstring
                 PAGE: - SNMP
                    Trap dest IP addr  cmdID= 10477
                    preset= 0.0.0.0"
        ::= { lC350ConfEntries 10477 }


    iSNMPTrapDest2Trapdestport OBJECT-TYPE
        SYNTAX            RollCallString
        MAX-ACCESS        read-write
        STATUS            current
        DESCRIPTION
                "CMNT: - 
                 TYPE: - Editstring
                 PAGE: - SNMP
                    Trap dest port  cmdID= 10478
                    preset= 162"
        ::= { lC350ConfEntries 10478 }


    iSNMPTrapDest2Trapcommunity OBJECT-TYPE
        SYNTAX            RollCallString
        MAX-ACCESS        read-write
        STATUS            current
        DESCRIPTION
                "CMNT: - 
                 TYPE: - Editstring
                 PAGE: - SNMP
                    Trap community  cmdID= 10479
                    preset= public"
        ::= { lC350ConfEntries 10479 }


    iSNMPTrapDest2EnableTrap OBJECT-TYPE
        SYNTAX            INTEGER { disable(0), enable(1)  }
        MAX-ACCESS        read-write
        STATUS            current
        DESCRIPTION
                "CMNT: - 
                 TYPE: - Checkbox
                 PAGE: - SNMP
                    Enable Trap  cmdID= 10480  "
        ::= { lC350ConfEntries 10480 }


    iSNMPTrapDest3TrapdestIPaddr OBJECT-TYPE
        SYNTAX            RollCallString
        MAX-ACCESS        read-write
        STATUS            current
        DESCRIPTION
                "CMNT: - 
                 TYPE: - Editstring
                 PAGE: - SNMP
                    Trap dest IP addr  cmdID= 10481
                    preset= 0.0.0.0"
        ::= { lC350ConfEntries 10481 }


    iSNMPTrapDest3Trapdestport OBJECT-TYPE
        SYNTAX            RollCallString
        MAX-ACCESS        read-write
        STATUS            current
        DESCRIPTION
                "CMNT: - 
                 TYPE: - Editstring
                 PAGE: - SNMP
                    Trap dest port  cmdID= 10482
                    preset= 162"
        ::= { lC350ConfEntries 10482 }


    iSNMPTrapDest3Trapcommunity OBJECT-TYPE
        SYNTAX            RollCallString
        MAX-ACCESS        read-write
        STATUS            current
        DESCRIPTION
                "CMNT: - 
                 TYPE: - Editstring
                 PAGE: - SNMP
                    Trap community  cmdID= 10483
                    preset= public"
        ::= { lC350ConfEntries 10483 }


    iSNMPTrapDest3EnableTrap OBJECT-TYPE
        SYNTAX            INTEGER { disable(0), enable(1)  }
        MAX-ACCESS        read-write
        STATUS            current
        DESCRIPTION
                "CMNT: - 
                 TYPE: - Checkbox
                 PAGE: - SNMP
                    Enable Trap  cmdID= 10484  "
        ::= { lC350ConfEntries 10484 }


    iSNMPTrapDest4TrapdestIPaddr OBJECT-TYPE
        SYNTAX            RollCallString
        MAX-ACCESS        read-write
        STATUS            current
        DESCRIPTION
                "CMNT: - 
                 TYPE: - Editstring
                 PAGE: - SNMP
                    Trap dest IP addr  cmdID= 10485
                    preset= 0.0.0.0"
        ::= { lC350ConfEntries 10485 }


    iSNMPTrapDest4Trapdestport OBJECT-TYPE
        SYNTAX            RollCallString
        MAX-ACCESS        read-write
        STATUS            current
        DESCRIPTION
                "CMNT: - 
                 TYPE: - Editstring
                 PAGE: - SNMP
                    Trap dest port  cmdID= 10486
                    preset= 162"
        ::= { lC350ConfEntries 10486 }


    iSNMPTrapDest4Trapcommunity OBJECT-TYPE
        SYNTAX            RollCallString
        MAX-ACCESS        read-write
        STATUS            current
        DESCRIPTION
                "CMNT: - 
                 TYPE: - Editstring
                 PAGE: - SNMP
                    Trap community  cmdID= 10487
                    preset= public"
        ::= { lC350ConfEntries 10487 }


    iSNMPTrapDest4EnableTrap OBJECT-TYPE
        SYNTAX            INTEGER { disable(0), enable(1)  }
        MAX-ACCESS        read-write
        STATUS            current
        DESCRIPTION
                "CMNT: - 
                 TYPE: - Checkbox
                 PAGE: - SNMP
                    Enable Trap  cmdID= 10488  "
        ::= { lC350ConfEntries 10488 }

END
