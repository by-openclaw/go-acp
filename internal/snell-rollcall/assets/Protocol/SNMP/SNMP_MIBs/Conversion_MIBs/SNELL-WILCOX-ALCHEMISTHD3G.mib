-- Generated file, do not edit
--
-- (c) 2005 Snell and Wilcox Ltd, all rights reserved.
-- Format: MIBv2
-- Product: Alchemist HD 3G
-- ProductID: 582
-- CommandSet: 17
-- Software: V17.0.0
-- CreatedBy: mibgen
-- CreationDate: Wed Nov 16 15:53:35 2011

SNELL-AlchemistHd3G-CMD DEFINITIONS ::= BEGIN

IMPORTS
	OBJECT-TYPE, NOTIFICATION-TYPE, MODULE-IDENTITY, OBJECT-IDENTITY,
	Counter32, Gauge32, IpAddress, Unsigned32, Integer32
		FROM SNMPv2-SMI

	OBJECT-GROUP, MODULE-COMPLIANCE, AGENT-CAPABILITIES
		FROM SNMPv2-CONF

	RollCallString
		FROM SNELL-WILCOX-TC

	conversionAlchemistHd3G, conversionAlchemistHd3GMib
		FROM SNELL-WILCOX-PRODUCT-REG;

conversionAlchemistHd3GMi MODULE-IDENTITY
	LAST-UPDATED "201109141458Z"
	ORGANIZATION "Snell & Wilcox Ltd"
	CONTACT-INFO
		"Primary Author: Generated by mibgen

		post:	Southleigh Park House
			Eastleigh Road
			Havant, Hants
			PO9 2PE
		phone:	+44 (0)23 92489000
		email:	snmp.support@snellwilcox.com"
	DESCRIPTION "Command logging and trap interface for Alchemist HD 3G"

	REVISION "201109141458Z"
	DESCRIPTION	"Sole revision, this file generated on each release"
		::= { conversionAlchemistHd3GMib 1 }

-- ********************************
-- Notifications

	alchemistHd3GNoteEntries OBJECT IDENTIFIER ::= { conversionAlchemistHd3G 0 }

	input1Standard NOTIFICATION-TYPE
		OBJECTS		{ logInpStdStat }
		STATUS		current
		DESCRIPTION	"
			style='ReadOnly string'
			path='/System/input_status'
		"
		::= { alchemistHd3GNoteEntries 6000 }

	output1Standard NOTIFICATION-TYPE
		OBJECTS		{ logOutAStdStat }
		STATUS		current
		DESCRIPTION	"
			style='ReadOnly string'
			path='/System/output_a_status'
		"
		::= { alchemistHd3GNoteEntries 6001 }

	extRef NOTIFICATION-TYPE
		OBJECTS		{ logRefStdStat }
		STATUS		current
		DESCRIPTION	"
			style='ReadOnly string'
			path='/System/reference_status'
		"
		::= { alchemistHd3GNoteEntries 6002 }

	systemStatus NOTIFICATION-TYPE
		OBJECTS		{ logStatusStat }
		STATUS		current
		DESCRIPTION	"
			style='ReadOnly numeric'
			path='/System/status_string'
		"
		::= { alchemistHd3GNoteEntries 6006 }

	output2Standard NOTIFICATION-TYPE
		OBJECTS		{ logOutBStdStat }
		STATUS		current
		DESCRIPTION	"
			style='ReadOnly string'
			path='/System/output_b_status'
		"
		::= { alchemistHd3GNoteEntries 6011 }

	input NOTIFICATION-TYPE
		OBJECTS		{ logInpLossStat }
		STATUS		current
		DESCRIPTION	"
			style='Radiobutton list'
			preset='ok'
			path='/System/input_state'
		"
		::= { alchemistHd3GNoteEntries 6665 }



-- ********************************
-- Control

	alchemistHd3GCtrlEntries OBJECT IDENTIFIER ::= { conversionAlchemistHd3G 1 }

	aliasSuppressionHorizA OBJECT-TYPE
		SYNTAX		Integer32 (-50..50)
		MAX-ACCESS	read-write
		STATUS		current
		DESCRIPTION	"
			style='Numeric control'
			range='-50..50'
			path='/Enhancements/Alias Suppression/Horizontal A'
		"
		::= { alchemistHd3GCtrlEntries 4197 }

	aliasSuppressionHorizB OBJECT-TYPE
		SYNTAX		Integer32 (-50..50)
		MAX-ACCESS	read-write
		STATUS		current
		DESCRIPTION	"
			style='Numeric control'
			range='-50..50'
			path='/Enhancements/Alias Suppression/Horizontal B'
		"
		::= { alchemistHd3GCtrlEntries 4198 }

	aliasSuppressionVertA OBJECT-TYPE
		SYNTAX		Integer32 (-50..50)
		MAX-ACCESS	read-write
		STATUS		current
		DESCRIPTION	"
			style='Numeric control'
			range='-50..50'
			path='/Enhancements/Alias Suppression/Vertical A'
		"
		::= { alchemistHd3GCtrlEntries 4297 }

	aliasSuppressionVertB OBJECT-TYPE
		SYNTAX		Integer32 (-50..50)
		MAX-ACCESS	read-write
		STATUS		current
		DESCRIPTION	"
			style='Numeric control'
			range='-50..50'
			path='/Enhancements/Alias Suppression/Vertical B'
		"
		::= { alchemistHd3GCtrlEntries 4298 }

	aliasSuppressionHoriz OBJECT-TYPE
		SYNTAX		Integer32 (-50..50)
		MAX-ACCESS	read-write
		STATUS		current
		DESCRIPTION	"
			style='Numeric control'
			range='-50..50'
			path='/Enhancements/Alias Suppression/Horizontal'
		"
		::= { alchemistHd3GCtrlEntries 4496 }

	aliasSuppressionVert OBJECT-TYPE
		SYNTAX		Integer32 (-50..50)
		MAX-ACCESS	read-write
		STATUS		current
		DESCRIPTION	"
			style='Numeric control'
			range='-50..50'
			path='/Enhancements/Alias Suppression/Vertical'
		"
		::= { alchemistHd3GCtrlEntries 4497 }

	inpBlankValInputBlankLeft OBJECT-TYPE
		SYNTAX		Integer32 (1..1920)
		MAX-ACCESS	read-write
		STATUS		current
		DESCRIPTION	"
			style='Numeric control'
			range='1..1920'
			preset='1'
			path='/Input/Input/Blanking/Left'
		"
		::= { alchemistHd3GCtrlEntries 5010 }

	inpBlankValInputBlankRight OBJECT-TYPE
		SYNTAX		Integer32 (1..1920)
		MAX-ACCESS	read-write
		STATUS		current
		DESCRIPTION	"
			style='Numeric control'
			range='1..1920'
			preset='720'
			path='/Input/Input/Blanking/Right'
		"
		::= { alchemistHd3GCtrlEntries 5011 }

	inpBlankValInputBlankTop OBJECT-TYPE
		SYNTAX		Integer32 (1..1080)
		MAX-ACCESS	read-write
		STATUS		current
		DESCRIPTION	"
			style='Numeric control'
			range='1..1080'
			preset='1'
			path='/Input/Input/Blanking/Top'
		"
		::= { alchemistHd3GCtrlEntries 5012 }

	inpBlankValInputBlankBottom OBJECT-TYPE
		SYNTAX		Integer32 (1..1080)
		MAX-ACCESS	read-write
		STATUS		current
		DESCRIPTION	"
			style='Numeric control'
			range='1..1080'
			preset='576'
			path='/Input/Input/Blanking/Bottom'
		"
		::= { alchemistHd3GCtrlEntries 5013 }

	loss OBJECT-TYPE
		SYNTAX		INTEGER {
					input(0),
					freeze(1),
					black(2)
				}
		MAX-ACCESS	read-write
		STATUS		current
		DESCRIPTION	"
			style='Radiobutton list'
			preset='input'
			path='/Input/Input/On loss'
		"
		::= { alchemistHd3GCtrlEntries 5020 }

	source OBJECT-TYPE
		SYNTAX		INTEGER {
					sdiA(0),
					sdiB(1)
				}
		MAX-ACCESS	read-write
		STATUS		current
		DESCRIPTION	"
			style='Radiobutton list'
			preset='sdiA'
			path='/Input/Input/Source'
		"
		::= { alchemistHd3GCtrlEntries 5030 }

	sourceString OBJECT-TYPE
		SYNTAX		Integer32
		MAX-ACCESS	read-only
		STATUS		current
		DESCRIPTION	"
			style='ReadOnly numeric'
			path='/System/source'
		"
		::= { alchemistHd3GCtrlEntries 5031 }

	matrixA OBJECT-TYPE
		SYNTAX		INTEGER {
					auto(0),
					rec601(1),
					smpte240(3),
					bt709(4)
				}
		MAX-ACCESS	read-write
		STATUS		current
		DESCRIPTION	"
			style='Radiobutton list'
			preset='auto'
			path='/output/Output A/Colorimetry'
		"
		::= { alchemistHd3GCtrlEntries 5050 }

	matrixB OBJECT-TYPE
		SYNTAX		INTEGER {
					auto(0),
					rec601(1),
					smpte240(3),
					bt709(4)
				}
		MAX-ACCESS	read-write
		STATUS		current
		DESCRIPTION	"
			style='Radiobutton list'
			preset='auto'
			path='/output/Output B/Colorimetry'
		"
		::= { alchemistHd3GCtrlEntries 5051 }

	inputMatrix OBJECT-TYPE
		SYNTAX		INTEGER {
					auto(0),
					rec601(1),
					smpte240(3),
					bt709(4)
				}
		MAX-ACCESS	read-write
		STATUS		current
		DESCRIPTION	"
			style='Radiobutton list'
			preset='auto'
			path='/Input/Input/Colorimetry'
		"
		::= { alchemistHd3GCtrlEntries 5052 }

	vancOutAEnable OBJECT-TYPE
		SYNTAX		INTEGER {
					disabled(0),
					enabled(1)
				}
		MAX-ACCESS	read-write
		STATUS		current
		DESCRIPTION	"
			style='Radiobutton list'
			preset='enabled'
			path='/output/Output A/VANC Output'
		"
		::= { alchemistHd3GCtrlEntries 5053 }

	vancOutBEnable OBJECT-TYPE
		SYNTAX		INTEGER {
					disabled(0),
					enabled(1)
				}
		MAX-ACCESS	read-write
		STATUS		current
		DESCRIPTION	"
			style='Radiobutton list'
			preset='enabled'
			path='/output/Output B/VANC Output'
		"
		::= { alchemistHd3GCtrlEntries 5054 }

	closedCaptionAEnable OBJECT-TYPE
		SYNTAX		INTEGER {
					disabled(0),
					enabled(1)
				}
		MAX-ACCESS	read-write
		STATUS		current
		DESCRIPTION	"
			style='Radiobutton list'
			preset='enabled'
			path='/output/Output A/C-Caption Output'
		"
		::= { alchemistHd3GCtrlEntries 5055 }

	closedCaptionBEnable OBJECT-TYPE
		SYNTAX		INTEGER {
					disabled(0),
					enabled(1)
				}
		MAX-ACCESS	read-write
		STATUS		current
		DESCRIPTION	"
			style='Radiobutton list'
			preset='enabled'
			path='/output/Output B/C-Caption Output'
		"
		::= { alchemistHd3GCtrlEntries 5056 }

	dlInCrossover OBJECT-TYPE
		SYNTAX		INTEGER {
					auto(0),
					off(1),
					on(2)
				}
		MAX-ACCESS	read-write
		STATUS		current
		DESCRIPTION	"
			style='Radiobutton list'
			preset='auto'
			path='/Input/Input/Dual Link In Crossover'
		"
		::= { alchemistHd3GCtrlEntries 5060 }

	dlOut0 OBJECT-TYPE
		SYNTAX		INTEGER {
					v3gLevelA(0),
					v3gLevelB(1),
					dualLink(2)
				}
		MAX-ACCESS	read-write
		STATUS		current
		DESCRIPTION	"
			style='Radiobutton list'
			preset='v3gLevelA'
			path='/output/Output A/1080P Outputs'
		"
		::= { alchemistHd3GCtrlEntries 5070 }

	dlOut1 OBJECT-TYPE
		SYNTAX		INTEGER {
					v3gLevelA(0),
					v3gLevelB(1),
					dualLink(2)
				}
		MAX-ACCESS	read-write
		STATUS		current
		DESCRIPTION	"
			style='Radiobutton list'
			preset='v3gLevelA'
			path='/output/Output B/1080P Outputs'
		"
		::= { alchemistHd3GCtrlEntries 5071 }

	stdOutB OBJECT-TYPE
		SYNTAX		INTEGER {
					v525i59(19),
					v720p59(17),
					v1080i59(7),
					v1080p59(4),
					v625i50(20),
					v720p50(30),
					v1080i50(8),
					v1080p50(5),
					v625psf2398(28),
					v1080psf2398(24),
					v625psf24(27),
					v1080psf24(23),
					v625psf25(1020),
					v1080psf25(36),
					v525psf2998(1019),
					v1080psf2998(35),
					v1080psf30(34),
					v625i4795(1028),
					v1080i4795(1024),
					v625i48(1027),
					v1080i48(1023),
					v720p60(16),
					v1080i60(6),
					v1080p60(3),
					v720p23(41),
					v720p24(40),
					v720p25(39),
					v720p29(38),
					v720p30(37)
				}
		MAX-ACCESS	read-write
		STATUS		current
		DESCRIPTION	"
			style='Radiobutton list'
			preset='v625i50'
			path='/output/Output B/Output Standard'
		"
		::= { alchemistHd3GCtrlEntries 5101 }

	outABlankValOutputABlankLeft OBJECT-TYPE
		SYNTAX		Integer32 (1..1920)
		MAX-ACCESS	read-write
		STATUS		current
		DESCRIPTION	"
			style='Numeric control'
			range='1..1920'
			preset='1'
			path='/output/Output A/Blanking/Left'
		"
		::= { alchemistHd3GCtrlEntries 5110 }

	outABlankValOutputABlankRight OBJECT-TYPE
		SYNTAX		Integer32 (1..1920)
		MAX-ACCESS	read-write
		STATUS		current
		DESCRIPTION	"
			style='Numeric control'
			range='1..1920'
			preset='720'
			path='/output/Output A/Blanking/Right'
		"
		::= { alchemistHd3GCtrlEntries 5111 }

	outABlankValOutputABlankTop OBJECT-TYPE
		SYNTAX		Integer32 (1..1080)
		MAX-ACCESS	read-write
		STATUS		current
		DESCRIPTION	"
			style='Numeric control'
			range='1..1080'
			preset='1'
			path='/output/Output A/Blanking/Top'
		"
		::= { alchemistHd3GCtrlEntries 5112 }

	outABlankValOutputABlankBottom OBJECT-TYPE
		SYNTAX		Integer32 (1..1080)
		MAX-ACCESS	read-write
		STATUS		current
		DESCRIPTION	"
			style='Numeric control'
			range='1..1080'
			preset='576'
			path='/output/Output A/Blanking/Bottom'
		"
		::= { alchemistHd3GCtrlEntries 5113 }

	outBBlankValOutputBBlankLeft OBJECT-TYPE
		SYNTAX		Integer32 (1..1920)
		MAX-ACCESS	read-write
		STATUS		current
		DESCRIPTION	"
			style='Numeric control'
			range='1..1920'
			preset='1'
			path='/output/Output B/Blanking/Left'
		"
		::= { alchemistHd3GCtrlEntries 5114 }

	outBBlankValOutputBBlankRight OBJECT-TYPE
		SYNTAX		Integer32 (1..1920)
		MAX-ACCESS	read-write
		STATUS		current
		DESCRIPTION	"
			style='Numeric control'
			range='1..1920'
			preset='720'
			path='/output/Output B/Blanking/Right'
		"
		::= { alchemistHd3GCtrlEntries 5115 }

	outBBlankValOutputBBlankTop OBJECT-TYPE
		SYNTAX		Integer32 (1..1080)
		MAX-ACCESS	read-write
		STATUS		current
		DESCRIPTION	"
			style='Numeric control'
			range='1..1080'
			preset='1'
			path='/output/Output B/Blanking/Top'
		"
		::= { alchemistHd3GCtrlEntries 5116 }

	outBBlankValOutputBBlankBottom OBJECT-TYPE
		SYNTAX		Integer32 (1..1080)
		MAX-ACCESS	read-write
		STATUS		current
		DESCRIPTION	"
			style='Numeric control'
			range='1..1080'
			preset='576'
			path='/output/Output B/Blanking/Bottom'
		"
		::= { alchemistHd3GCtrlEntries 5117 }

	borderAEnable OBJECT-TYPE
		SYNTAX		INTEGER { disable(0), enable(1) }
		MAX-ACCESS	read-write
		STATUS		current
		DESCRIPTION	"
			style='Checkbox'
			path='/output/Output A/Border/Enable'
		"
		::= { alchemistHd3GCtrlEntries 5120 }

	borderAR OBJECT-TYPE
		SYNTAX		Integer32 (64..940)
		MAX-ACCESS	read-write
		STATUS		current
		DESCRIPTION	"
			style='Numeric control'
			range='64..940'
			preset='64'
			path='/output/Output A/Border/Red'
		"
		::= { alchemistHd3GCtrlEntries 5121 }

	borderAG OBJECT-TYPE
		SYNTAX		Integer32 (64..940)
		MAX-ACCESS	read-write
		STATUS		current
		DESCRIPTION	"
			style='Numeric control'
			range='64..940'
			preset='64'
			path='/output/Output A/Border/Green'
		"
		::= { alchemistHd3GCtrlEntries 5122 }

	borderAB OBJECT-TYPE
		SYNTAX		Integer32 (64..940)
		MAX-ACCESS	read-write
		STATUS		current
		DESCRIPTION	"
			style='Numeric control'
			range='64..940'
			preset='64'
			path='/output/Output A/Border/Blue'
		"
		::= { alchemistHd3GCtrlEntries 5123 }

	borderBEnable OBJECT-TYPE
		SYNTAX		INTEGER { disable(0), enable(1) }
		MAX-ACCESS	read-write
		STATUS		current
		DESCRIPTION	"
			style='Checkbox'
			path='/output/Output B/Border/Enable'
		"
		::= { alchemistHd3GCtrlEntries 5124 }

	borderBR OBJECT-TYPE
		SYNTAX		Integer32 (64..940)
		MAX-ACCESS	read-write
		STATUS		current
		DESCRIPTION	"
			style='Numeric control'
			range='64..940'
			preset='64'
			path='/output/Output B/Border/Red'
		"
		::= { alchemistHd3GCtrlEntries 5125 }

	borderBG OBJECT-TYPE
		SYNTAX		Integer32 (64..940)
		MAX-ACCESS	read-write
		STATUS		current
		DESCRIPTION	"
			style='Numeric control'
			range='64..940'
			preset='64'
			path='/output/Output B/Border/Green'
		"
		::= { alchemistHd3GCtrlEntries 5126 }

	borderBB OBJECT-TYPE
		SYNTAX		Integer32 (64..940)
		MAX-ACCESS	read-write
		STATUS		current
		DESCRIPTION	"
			style='Numeric control'
			range='64..940'
			preset='64'
			path='/output/Output B/Border/Blue'
		"
		::= { alchemistHd3GCtrlEntries 5127 }

	procBlack OBJECT-TYPE
		SYNTAX		Integer32 (-101..101)
		MAX-ACCESS	read-write
		STATUS		current
		DESCRIPTION	"
			style='Numeric control'
			range='-101.0..101.0'
			path='/Proc Amp/Gain/Black Level'
		"
		::= { alchemistHd3GCtrlEntries 5150 }

	procGainY OBJECT-TYPE
		SYNTAX		Integer32 (-60..60)
		MAX-ACCESS	read-write
		STATUS		current
		DESCRIPTION	"
			style='Numeric control'
			range='-6.00dB..6.00dB'
			stepsize='0.1'
			path='/Proc Amp/Gain/Luma Gain'
		"
		::= { alchemistHd3GCtrlEntries 5160 }

	procGainC OBJECT-TYPE
		SYNTAX		Integer32 (-60..60)
		MAX-ACCESS	read-write
		STATUS		current
		DESCRIPTION	"
			style='Numeric control'
			range='-6.00dB..6.00dB'
			stepsize='0.1'
			path='/Proc Amp/Gain/Chroma Gain'
		"
		::= { alchemistHd3GCtrlEntries 5161 }

	procEnhanceVertA OBJECT-TYPE
		SYNTAX		Integer32 (0..100)
		MAX-ACCESS	read-write
		STATUS		current
		DESCRIPTION	"
			style='Numeric control'
			range='0%..100%'
			path='/Enhancements/Enhancer/Vertical A'
		"
		::= { alchemistHd3GCtrlEntries 5172 }

	procEnhanceVert OBJECT-TYPE
		SYNTAX		Integer32 (0..100)
		MAX-ACCESS	read-write
		STATUS		current
		DESCRIPTION	"
			style='Numeric control'
			range='0..100'
			path='/Enhancements/Enhancer/Vertical'
		"
		::= { alchemistHd3GCtrlEntries 5173 }

	procEnhanceHoriz OBJECT-TYPE
		SYNTAX		Integer32 (0..100)
		MAX-ACCESS	read-write
		STATUS		current
		DESCRIPTION	"
			style='Numeric control'
			range='0..100'
			path='/Enhancements/Enhancer/Horizontal'
		"
		::= { alchemistHd3GCtrlEntries 5174 }

	procEnhanceHorizA OBJECT-TYPE
		SYNTAX		Integer32 (0..100)
		MAX-ACCESS	read-write
		STATUS		current
		DESCRIPTION	"
			style='Numeric control'
			range='0%..100%'
			path='/Enhancements/Enhancer/Horizontal A'
		"
		::= { alchemistHd3GCtrlEntries 5175 }

	gamutA OBJECT-TYPE
		SYNTAX		INTEGER {
					off(0),
					v721mv(1),
					v700mv(2),
					v735mv(3)
				}
		MAX-ACCESS	read-write
		STATUS		current
		DESCRIPTION	"
			style='Radiobutton list'
			preset='off'
			path='/utils/Channel A/Legaliser/Gamut/Gamut Legaliser'
		"
		::= { alchemistHd3GCtrlEntries 5183 }

	gamutB OBJECT-TYPE
		SYNTAX		INTEGER {
					off(0),
					v721mv(1),
					v700mv(2),
					v735mv(3)
				}
		MAX-ACCESS	read-write
		STATUS		current
		DESCRIPTION	"
			style='Radiobutton list'
			preset='off'
			path='/utils/Channel B/Legaliser/Gamut/Gamut Legaliser'
		"
		::= { alchemistHd3GCtrlEntries 5184 }

	phcEnable OBJECT-TYPE
		SYNTAX		INTEGER {
					off(0),
					on(1)
				}
		MAX-ACCESS	read-write
		STATUS		current
		DESCRIPTION	"
			style='Radiobutton list'
			preset='on'
			path='/Convert/Convert/Ph.C'
		"
		::= { alchemistHd3GCtrlEntries 5190 }

	apertureA OBJECT-TYPE
		SYNTAX		INTEGER {
					sharp(0),
					normal(1),
					antiAlias(2)
				}
		MAX-ACCESS	read-write
		STATUS		current
		DESCRIPTION	"
			style='Radiobutton list'
			preset='normal'
			path='/Convert/Convert/Aperture A'
		"
		::= { alchemistHd3GCtrlEntries 5191 }

	cleanCut OBJECT-TYPE
		SYNTAX		INTEGER {
					off(0),
					on(1)
				}
		MAX-ACCESS	read-write
		STATUS		current
		DESCRIPTION	"
			style='Radiobutton list'
			preset='on'
			path='/Convert/Convert/Clean Cut'
		"
		::= { alchemistHd3GCtrlEntries 5192 }

	cleanCutType OBJECT-TYPE
		SYNTAX		INTEGER {
					anyField(0),
					field1Only(1),
					field2Only(2)
				}
		MAX-ACCESS	read-write
		STATUS		current
		DESCRIPTION	"
			style='Radiobutton list'
			preset='anyField'
			path='/Convert/Convert/Clean Cut Type'
		"
		::= { alchemistHd3GCtrlEntries 5193 }

	apertureB OBJECT-TYPE
		SYNTAX		INTEGER {
					sharp(0),
					normal(1),
					antiAlias(2)
				}
		MAX-ACCESS	read-write
		STATUS		current
		DESCRIPTION	"
			style='Radiobutton list'
			preset='normal'
			path='/Convert/Convert/Aperture B'
		"
		::= { alchemistHd3GCtrlEntries 5194 }

	activeAreaKey1ValAaKey1Left OBJECT-TYPE
		SYNTAX		Integer32 (1..720)
		MAX-ACCESS	read-write
		STATUS		current
		DESCRIPTION	"
			style='Numeric control'
			range='1..720'
			preset='1'
			path='/Convert/Convert/Ph.C Area/Active Area 1/Left'
		"
		::= { alchemistHd3GCtrlEntries 5200 }

	activeAreaKey1ValAaKey1Right OBJECT-TYPE
		SYNTAX		Integer32 (1..720)
		MAX-ACCESS	read-write
		STATUS		current
		DESCRIPTION	"
			style='Numeric control'
			range='1..720'
			preset='720'
			path='/Convert/Convert/Ph.C Area/Active Area 1/Right'
		"
		::= { alchemistHd3GCtrlEntries 5201 }

	activeAreaKey1ValAaKey1Top OBJECT-TYPE
		SYNTAX		Integer32 (1..576)
		MAX-ACCESS	read-write
		STATUS		current
		DESCRIPTION	"
			style='Numeric control'
			range='1..576'
			preset='1'
			path='/Convert/Convert/Ph.C Area/Active Area 1/Top'
		"
		::= { alchemistHd3GCtrlEntries 5202 }

	activeAreaKey1ValAaKey1Bottom OBJECT-TYPE
		SYNTAX		Integer32 (1..576)
		MAX-ACCESS	read-write
		STATUS		current
		DESCRIPTION	"
			style='Numeric control'
			range='1..576'
			preset='576'
			path='/Convert/Convert/Ph.C Area/Active Area 1/Bottom'
		"
		::= { alchemistHd3GCtrlEntries 5203 }

	activeAreaKey1Enable OBJECT-TYPE
		SYNTAX		INTEGER { disable(0), enable(1) }
		MAX-ACCESS	read-write
		STATUS		current
		DESCRIPTION	"
			style='Checkbox'
			path='/Convert/Convert/Ph.C Area/Active Area 1/Enable'
		"
		::= { alchemistHd3GCtrlEntries 5204 }

	activeAreaKey1Active OBJECT-TYPE
		SYNTAX		INTEGER { disable(0), enable(1) }
		MAX-ACCESS	read-write
		STATUS		current
		DESCRIPTION	"
			style='Checkbox'
			path='/Convert/Convert/Ph.C Area/Active Area 1/Active'
		"
		::= { alchemistHd3GCtrlEntries 5205 }

	activeAreaKey2ValAaKey2Left OBJECT-TYPE
		SYNTAX		Integer32 (1..720)
		MAX-ACCESS	read-write
		STATUS		current
		DESCRIPTION	"
			style='Numeric control'
			range='1..720'
			preset='1'
			path='/Convert/Convert/Ph.C Area/Active Area 2/Left'
		"
		::= { alchemistHd3GCtrlEntries 5206 }

	activeAreaKey2ValAaKey2Right OBJECT-TYPE
		SYNTAX		Integer32 (1..720)
		MAX-ACCESS	read-write
		STATUS		current
		DESCRIPTION	"
			style='Numeric control'
			range='1..720'
			preset='720'
			path='/Convert/Convert/Ph.C Area/Active Area 2/Right'
		"
		::= { alchemistHd3GCtrlEntries 5207 }

	activeAreaKey2ValAaKey2Top OBJECT-TYPE
		SYNTAX		Integer32 (1..576)
		MAX-ACCESS	read-write
		STATUS		current
		DESCRIPTION	"
			style='Numeric control'
			range='1..576'
			preset='1'
			path='/Convert/Convert/Ph.C Area/Active Area 2/Top'
		"
		::= { alchemistHd3GCtrlEntries 5208 }

	activeAreaKey2ValAaKey2Bottom OBJECT-TYPE
		SYNTAX		Integer32 (1..576)
		MAX-ACCESS	read-write
		STATUS		current
		DESCRIPTION	"
			style='Numeric control'
			range='1..576'
			preset='576'
			path='/Convert/Convert/Ph.C Area/Active Area 2/Bottom'
		"
		::= { alchemistHd3GCtrlEntries 5209 }

	activeAreaKey2Enable OBJECT-TYPE
		SYNTAX		INTEGER { disable(0), enable(1) }
		MAX-ACCESS	read-write
		STATUS		current
		DESCRIPTION	"
			style='Checkbox'
			path='/Convert/Convert/Ph.C Area/Active Area 2/Enable'
		"
		::= { alchemistHd3GCtrlEntries 5210 }

	activeAreaKey2Active OBJECT-TYPE
		SYNTAX		INTEGER { disable(0), enable(1) }
		MAX-ACCESS	read-write
		STATUS		current
		DESCRIPTION	"
			style='Checkbox'
			path='/Convert/Convert/Ph.C Area/Active Area 2/Active'
		"
		::= { alchemistHd3GCtrlEntries 5211 }

	activeAreaKey3ValAaKey3Left OBJECT-TYPE
		SYNTAX		Integer32 (1..720)
		MAX-ACCESS	read-write
		STATUS		current
		DESCRIPTION	"
			style='Numeric control'
			range='1..720'
			preset='1'
			path='/Convert/Convert/Ph.C Area/Active Area 3/Left'
		"
		::= { alchemistHd3GCtrlEntries 5212 }

	activeAreaKey3ValAaKey3Right OBJECT-TYPE
		SYNTAX		Integer32 (1..720)
		MAX-ACCESS	read-write
		STATUS		current
		DESCRIPTION	"
			style='Numeric control'
			range='1..720'
			preset='720'
			path='/Convert/Convert/Ph.C Area/Active Area 3/Right'
		"
		::= { alchemistHd3GCtrlEntries 5213 }

	activeAreaKey3ValAaKey3Top OBJECT-TYPE
		SYNTAX		Integer32 (1..576)
		MAX-ACCESS	read-write
		STATUS		current
		DESCRIPTION	"
			style='Numeric control'
			range='1..576'
			preset='1'
			path='/Convert/Convert/Ph.C Area/Active Area 3/Top'
		"
		::= { alchemistHd3GCtrlEntries 5214 }

	activeAreaKey3ValAaKey3Bottom OBJECT-TYPE
		SYNTAX		Integer32 (1..576)
		MAX-ACCESS	read-write
		STATUS		current
		DESCRIPTION	"
			style='Numeric control'
			range='1..576'
			preset='576'
			path='/Convert/Convert/Ph.C Area/Active Area 3/Bottom'
		"
		::= { alchemistHd3GCtrlEntries 5215 }

	activeAreaKey3Enable OBJECT-TYPE
		SYNTAX		INTEGER { disable(0), enable(1) }
		MAX-ACCESS	read-write
		STATUS		current
		DESCRIPTION	"
			style='Checkbox'
			path='/Convert/Convert/Ph.C Area/Active Area 3/Enable'
		"
		::= { alchemistHd3GCtrlEntries 5216 }

	activeAreaKey3Active OBJECT-TYPE
		SYNTAX		INTEGER { disable(0), enable(1) }
		MAX-ACCESS	read-write
		STATUS		current
		DESCRIPTION	"
			style='Checkbox'
			path='/Convert/Convert/Ph.C Area/Active Area 3/Active'
		"
		::= { alchemistHd3GCtrlEntries 5217 }

	activeAreaKey4ValAaKey4Left OBJECT-TYPE
		SYNTAX		Integer32 (1..720)
		MAX-ACCESS	read-write
		STATUS		current
		DESCRIPTION	"
			style='Numeric control'
			range='1..720'
			preset='1'
			path='/Convert/Convert/Ph.C Area/Active Area 4/Left'
		"
		::= { alchemistHd3GCtrlEntries 5218 }

	activeAreaKey4ValAaKey4Right OBJECT-TYPE
		SYNTAX		Integer32 (1..720)
		MAX-ACCESS	read-write
		STATUS		current
		DESCRIPTION	"
			style='Numeric control'
			range='1..720'
			preset='720'
			path='/Convert/Convert/Ph.C Area/Active Area 4/Right'
		"
		::= { alchemistHd3GCtrlEntries 5219 }

	activeAreaKey4ValAaKey4Top OBJECT-TYPE
		SYNTAX		Integer32 (1..576)
		MAX-ACCESS	read-write
		STATUS		current
		DESCRIPTION	"
			style='Numeric control'
			range='1..576'
			preset='1'
			path='/Convert/Convert/Ph.C Area/Active Area 4/Top'
		"
		::= { alchemistHd3GCtrlEntries 5220 }

	activeAreaKey4ValAaKey4Bottom OBJECT-TYPE
		SYNTAX		Integer32 (1..576)
		MAX-ACCESS	read-write
		STATUS		current
		DESCRIPTION	"
			style='Numeric control'
			range='1..576'
			preset='576'
			path='/Convert/Convert/Ph.C Area/Active Area 4/Bottom'
		"
		::= { alchemistHd3GCtrlEntries 5221 }

	activeAreaKey4Enable OBJECT-TYPE
		SYNTAX		INTEGER { disable(0), enable(1) }
		MAX-ACCESS	read-write
		STATUS		current
		DESCRIPTION	"
			style='Checkbox'
			path='/Convert/Convert/Ph.C Area/Active Area 4/Enable'
		"
		::= { alchemistHd3GCtrlEntries 5222 }

	activeAreaKey4Active OBJECT-TYPE
		SYNTAX		INTEGER { disable(0), enable(1) }
		MAX-ACCESS	read-write
		STATUS		current
		DESCRIPTION	"
			style='Checkbox'
			path='/Convert/Convert/Ph.C Area/Active Area 4/Active'
		"
		::= { alchemistHd3GCtrlEntries 5223 }

	activeAreaKey5ValAaKey5Left OBJECT-TYPE
		SYNTAX		Integer32 (1..720)
		MAX-ACCESS	read-write
		STATUS		current
		DESCRIPTION	"
			style='Numeric control'
			range='1..720'
			preset='1'
			path='/Convert/Convert/Ph.C Area/Active Area 5/Left'
		"
		::= { alchemistHd3GCtrlEntries 5224 }

	activeAreaKey5ValAaKey5Right OBJECT-TYPE
		SYNTAX		Integer32 (1..720)
		MAX-ACCESS	read-write
		STATUS		current
		DESCRIPTION	"
			style='Numeric control'
			range='1..720'
			preset='720'
			path='/Convert/Convert/Ph.C Area/Active Area 5/Right'
		"
		::= { alchemistHd3GCtrlEntries 5225 }

	activeAreaKey5ValAaKey5Top OBJECT-TYPE
		SYNTAX		Integer32 (1..576)
		MAX-ACCESS	read-write
		STATUS		current
		DESCRIPTION	"
			style='Numeric control'
			range='1..576'
			preset='1'
			path='/Convert/Convert/Ph.C Area/Active Area 5/Top'
		"
		::= { alchemistHd3GCtrlEntries 5226 }

	activeAreaKey5ValAaKey5Bottom OBJECT-TYPE
		SYNTAX		Integer32 (1..576)
		MAX-ACCESS	read-write
		STATUS		current
		DESCRIPTION	"
			style='Numeric control'
			range='1..576'
			preset='576'
			path='/Convert/Convert/Ph.C Area/Active Area 5/Bottom'
		"
		::= { alchemistHd3GCtrlEntries 5227 }

	activeAreaKey5Enable OBJECT-TYPE
		SYNTAX		INTEGER { disable(0), enable(1) }
		MAX-ACCESS	read-write
		STATUS		current
		DESCRIPTION	"
			style='Checkbox'
			path='/Convert/Convert/Ph.C Area/Active Area 5/Enable'
		"
		::= { alchemistHd3GCtrlEntries 5228 }

	activeAreaKey5Active OBJECT-TYPE
		SYNTAX		INTEGER { disable(0), enable(1) }
		MAX-ACCESS	read-write
		STATUS		current
		DESCRIPTION	"
			style='Checkbox'
			path='/Convert/Convert/Ph.C Area/Active Area 5/Active'
		"
		::= { alchemistHd3GCtrlEntries 5229 }

	activeAreaBgndActive OBJECT-TYPE
		SYNTAX		INTEGER { disable(0), enable(1) }
		MAX-ACCESS	read-write
		STATUS		current
		DESCRIPTION	"
			style='Checkbox'
			range='0..1'
			path='/Convert/Convert/Ph.C Area/Active Area Control/Bgnd Active'
		"
		::= { alchemistHd3GCtrlEntries 5230 }

	activeAreaOverlayKeys OBJECT-TYPE
		SYNTAX		INTEGER { disable(0), enable(1) }
		MAX-ACCESS	read-write
		STATUS		current
		DESCRIPTION	"
			style='Checkbox'
			range='0..1'
			path='/Convert/Convert/Ph.C Area/Active Area Control/Overlay Keys'
		"
		::= { alchemistHd3GCtrlEntries 5231 }

	activeAreaOverlayPhc OBJECT-TYPE
		SYNTAX		INTEGER { disable(0), enable(1) }
		MAX-ACCESS	read-write
		STATUS		current
		DESCRIPTION	"
			style='Checkbox'
			range='0..1'
			path='/Convert/Convert/Ph.C Area/Active Area Control/Overlay Ph.C'
		"
		::= { alchemistHd3GCtrlEntries 5232 }

	activeAreaResetall OBJECT-TYPE
		SYNTAX		INTEGER { ready(0), trigger(1) }
		MAX-ACCESS	read-write
		STATUS		current
		DESCRIPTION	"
			style='Event button'
			path='/Convert/Convert/Ph.C Area/Active Area Control/Reset All'
		"
		::= { alchemistHd3GCtrlEntries 5234 }

	procEnhanceVertB OBJECT-TYPE
		SYNTAX		Integer32 (0..100)
		MAX-ACCESS	read-write
		STATUS		current
		DESCRIPTION	"
			style='Numeric control'
			range='0%..100%'
			path='/Enhancements/Enhancer/Vertical B'
		"
		::= { alchemistHd3GCtrlEntries 5272 }

	procEnhanceHorizB OBJECT-TYPE
		SYNTAX		Integer32 (0..100)
		MAX-ACCESS	read-write
		STATUS		current
		DESCRIPTION	"
			style='Numeric control'
			range='0%..100%'
			path='/Enhancements/Enhancer/Horizontal B'
		"
		::= { alchemistHd3GCtrlEntries 5275 }

	inputAspect OBJECT-TYPE
		SYNTAX		INTEGER {
					v4x3(1),
					v14x9lb(2),
					v16x9lb(3),
					anamorphic(4),
					none(5)
				}
		MAX-ACCESS	read-write
		STATUS		current
		DESCRIPTION	"
			style='Radiobutton list'
			preset='v4x3'
			path='/display/Input/Aspect'
		"
		::= { alchemistHd3GCtrlEntries 5317 }

	aspectControlA OBJECT-TYPE
		SYNTAX		INTEGER {
					v16x9(1),
					v4x3fh(2),
					v14x9fh(3),
					v4x3fw(4),
					v14x9fw(5),
					none(6)
				}
		MAX-ACCESS	read-write
		STATUS		current
		DESCRIPTION	"
			style='Radiobutton list'
			preset='v16x9'
			path='/display/Output A/Aspect'
		"
		::= { alchemistHd3GCtrlEntries 5318 }

	aspectControlB OBJECT-TYPE
		SYNTAX		INTEGER {
					v16x9(1),
					v4x3fh(2),
					v14x9fh(3),
					v4x3fw(4),
					v14x9fw(5),
					none(6)
				}
		MAX-ACCESS	read-write
		STATUS		current
		DESCRIPTION	"
			style='Radiobutton list'
			preset='v16x9'
			path='/display/Output B/Aspect'
		"
		::= { alchemistHd3GCtrlEntries 5319 }

	displaySizeA OBJECT-TYPE
		SYNTAX		Integer32 (4000..20000)
		MAX-ACCESS	read-write
		STATUS		current
		DESCRIPTION	"
			style='Numeric control'
			range='40.00%..200.00%'
			stepsize='0.001'
			preset='100.00%'
			path='/display/Output A/Size'
		"
		::= { alchemistHd3GCtrlEntries 5320 }

	displayAspA OBJECT-TYPE
		SYNTAX		Integer32 (4000..20000)
		MAX-ACCESS	read-write
		STATUS		current
		DESCRIPTION	"
			style='Numeric control'
			range='40.00%..200.00%'
			stepsize='0.001'
			preset='100.00%'
			path='/display/Output A/Asp'
		"
		::= { alchemistHd3GCtrlEntries 5321 }

	displayPanA OBJECT-TYPE
		SYNTAX		Integer32 (-3750..3750)
		MAX-ACCESS	read-write
		STATUS		current
		DESCRIPTION	"
			style='Numeric control'
			range='-75.00%..75.00%'
			stepsize='0.002'
			path='/display/Output A/Pan'
		"
		::= { alchemistHd3GCtrlEntries 5322 }

	displayPosA OBJECT-TYPE
		SYNTAX		Integer32 (-3750..3750)
		MAX-ACCESS	read-write
		STATUS		current
		DESCRIPTION	"
			style='Numeric control'
			range='-75.00%..75.00%'
			stepsize='0.002'
			path='/display/Output A/Tilt'
		"
		::= { alchemistHd3GCtrlEntries 5323 }

	displaySizeB OBJECT-TYPE
		SYNTAX		Integer32 (4000..20000)
		MAX-ACCESS	read-write
		STATUS		current
		DESCRIPTION	"
			style='Numeric control'
			range='40.00%..200.00%'
			stepsize='0.001'
			preset='100.00%'
			path='/display/Output B/Size'
		"
		::= { alchemistHd3GCtrlEntries 5324 }

	displayAspB OBJECT-TYPE
		SYNTAX		Integer32 (4000..20000)
		MAX-ACCESS	read-write
		STATUS		current
		DESCRIPTION	"
			style='Numeric control'
			range='40.00%..200.00%'
			stepsize='0.001'
			preset='100.00%'
			path='/display/Output B/Asp'
		"
		::= { alchemistHd3GCtrlEntries 5325 }

	displayPanB OBJECT-TYPE
		SYNTAX		Integer32 (-3750..3750)
		MAX-ACCESS	read-write
		STATUS		current
		DESCRIPTION	"
			style='Numeric control'
			range='-75.00%..75.00%'
			stepsize='0.002'
			path='/display/Output B/Pan'
		"
		::= { alchemistHd3GCtrlEntries 5326 }

	displayPosB OBJECT-TYPE
		SYNTAX		Integer32 (-3750..3750)
		MAX-ACCESS	read-write
		STATUS		current
		DESCRIPTION	"
			style='Numeric control'
			range='-75.00%..75.00%'
			stepsize='0.002'
			path='/display/Output B/Tilt'
		"
		::= { alchemistHd3GCtrlEntries 5327 }

	aspectControlBLock OBJECT-TYPE
		SYNTAX		INTEGER { disable(0), enable(1) }
		MAX-ACCESS	read-write
		STATUS		current
		DESCRIPTION	"
			style='Checkbox'
			path='/display/Output B/Lock to A'
		"
		::= { alchemistHd3GCtrlEntries 5328 }

	slewEnable OBJECT-TYPE
		SYNTAX		INTEGER {
					off(0),
					on(1)
				}
		MAX-ACCESS	read-write
		STATUS		current
		DESCRIPTION	"
			style='Radiobutton list'
			preset='on'
			path='/display/Transition/Slew'
		"
		::= { alchemistHd3GCtrlEntries 5329 }

	slewProfile OBJECT-TYPE
		SYNTAX		INTEGER {
					vSlowOut(2),
					vLinear(0),
					vStdSCurve(4),
					vSCurve(3),
					vSlowIn(1)
				}
		MAX-ACCESS	read-write
		STATUS		current
		DESCRIPTION	"
			style='Radiobutton list'
			preset='vStdSCurve'
			path='/display/Transition/Profile'
		"
		::= { alchemistHd3GCtrlEntries 5330 }

	slewDurationMode OBJECT-TYPE
		SYNTAX		INTEGER {
					absolute(0),
					proportional(1)
				}
		MAX-ACCESS	read-write
		STATUS		current
		DESCRIPTION	"
			style='Radiobutton list'
			preset='proportional'
			path='/display/Transition/Slew Duration Mode'
		"
		::= { alchemistHd3GCtrlEntries 5331 }

	slewDurationUnit OBJECT-TYPE
		SYNTAX		INTEGER {
					fields(0),
					seconds(1)
				}
		MAX-ACCESS	read-write
		STATUS		current
		DESCRIPTION	"
			style='Radiobutton list'
			preset='fields'
			path='/display/Transition/Slew Duration Unit'
		"
		::= { alchemistHd3GCtrlEntries 5332 }

	slewDuration OBJECT-TYPE
		SYNTAX		Integer32 (20..20000)
		MAX-ACCESS	read-write
		STATUS		current
		DESCRIPTION	"
			style='Numeric control'
			range='0.00Sec..20.00Sec'
			stepsize='0.002'
			preset='1.00Sec'
			path='/display/Transition/Slew Duration'
		"
		::= { alchemistHd3GCtrlEntries 5333 }

	slewUpdate OBJECT-TYPE
		SYNTAX		INTEGER {
					anyField(0),
					field1Only(1),
					field2Only(2)
				}
		MAX-ACCESS	read-write
		STATUS		current
		DESCRIPTION	"
			style='Radiobutton list'
			preset='anyField'
			path='/display/Transition/Transition Update'
		"
		::= { alchemistHd3GCtrlEntries 5334 }

	slewDurationFields OBJECT-TYPE
		SYNTAX		Integer32 (2..1000)
		MAX-ACCESS	read-write
		STATUS		current
		DESCRIPTION	"
			style='Numeric control'
			range='2Flds..1000Flds'
			preset='50Flds'
			path='/display/Transition/Slew Duration'
		"
		::= { alchemistHd3GCtrlEntries 5335 }

	displayControlModeA OBJECT-TYPE
		SYNTAX		INTEGER {
					manual(0),
					forced(1),
					autoFormat(2)
				}
		MAX-ACCESS	read-write
		STATUS		current
		DESCRIPTION	"
			style='Radiobutton list'
			preset='manual'
			path='/display/Control/Output A Mode'
		"
		::= { alchemistHd3GCtrlEntries 5350 }

	displayControlModeB OBJECT-TYPE
		SYNTAX		INTEGER {
					manual(0),
					forced(1),
					autoFormat(2)
				}
		MAX-ACCESS	read-write
		STATUS		current
		DESCRIPTION	"
			style='Radiobutton list'
			preset='manual'
			path='/display/Control/Output B Mode'
		"
		::= { alchemistHd3GCtrlEntries 5351 }

	dispSizeEntry OBJECT-TYPE
		SYNTAX		Integer32 (4000..20000)
		MAX-ACCESS	read-write
		STATUS		current
		DESCRIPTION	"
			style='Numeric control'
			range='40.00%..200.00%'
			stepsize='0.001'
			preset='100.00%'
			path='/display/Control/Display Memory Setup/Size'
		"
		::= { alchemistHd3GCtrlEntries 5353 }

	dispAspEntry OBJECT-TYPE
		SYNTAX		Integer32 (4000..20000)
		MAX-ACCESS	read-write
		STATUS		current
		DESCRIPTION	"
			style='Numeric control'
			range='40.00%..200.00%'
			stepsize='0.001'
			preset='100.00%'
			path='/display/Control/Display Memory Setup/Asp'
		"
		::= { alchemistHd3GCtrlEntries 5354 }

	dispPanEntry OBJECT-TYPE
		SYNTAX		Integer32 (-3750..3750)
		MAX-ACCESS	read-write
		STATUS		current
		DESCRIPTION	"
			style='Numeric control'
			range='-75.00%..75.00%'
			stepsize='0.002'
			path='/display/Control/Display Memory Setup/Pan'
		"
		::= { alchemistHd3GCtrlEntries 5355 }

	dispPosEntry OBJECT-TYPE
		SYNTAX		Integer32 (-3750..3750)
		MAX-ACCESS	read-write
		STATUS		current
		DESCRIPTION	"
			style='Numeric control'
			range='-75.00%..75.00%'
			stepsize='0.002'
			path='/display/Control/Display Memory Setup/Tilt'
		"
		::= { alchemistHd3GCtrlEntries 5356 }

	dispEntryPreset OBJECT-TYPE
		SYNTAX		INTEGER { ready(0), trigger(1) }
		MAX-ACCESS	read-write
		STATUS		current
		DESCRIPTION	"
			style='Event button'
			path='/display/Control/Display Memory Setup/Preset'
		"
		::= { alchemistHd3GCtrlEntries 5357 }

	dispEntryCurrent OBJECT-TYPE
		SYNTAX		INTEGER { ready(0), trigger(1) }
		MAX-ACCESS	read-write
		STATUS		current
		DESCRIPTION	"
			style='Event button'
			path='/display/Control/Display Memory Setup/Current'
		"
		::= { alchemistHd3GCtrlEntries 5358 }

	dispEntryAccept OBJECT-TYPE
		SYNTAX		INTEGER { ready(0), trigger(1) }
		MAX-ACCESS	read-write
		STATUS		current
		DESCRIPTION	"
			style='Event button'
			path='/display/Control/Display Memory Setup/Accept Changes'
		"
		::= { alchemistHd3GCtrlEntries 5359 }

	dispEntryPreview OBJECT-TYPE
		SYNTAX		INTEGER { disable(0), enable(1) }
		MAX-ACCESS	read-write
		STATUS		current
		DESCRIPTION	"
			style='Checkbox'
			range='0..1'
			path='/display/Control/Display Memory Setup/Preview'
		"
		::= { alchemistHd3GCtrlEntries 5360 }

	dispMemSetupSel OBJECT-TYPE
		SYNTAX		INTEGER {
					sdToSd(1),
					sdToHd(2),
					hdToSd(3),
					hdToHd(4)
				}
		MAX-ACCESS	read-write
		STATUS		current
		DESCRIPTION	"
			style='Radiobutton list'
			preset='sdToSd'
			path='/display/Control/Display Memory Setup/Memory Select'
		"
		::= { alchemistHd3GCtrlEntries 5361 }

	dispMemSetupGrp OBJECT-TYPE
		SYNTAX		INTEGER {
					format(0),
					group0(1),
					group1(2),
					group2(3),
					group3(4)
				}
		MAX-ACCESS	read-write
		STATUS		current
		DESCRIPTION	"
			style='Radiobutton list'
			preset='format'
			path='/display/Control/Display Memory Setup/Memory Group Select'
		"
		::= { alchemistHd3GCtrlEntries 5362 }

	dispEntryAfdCode OBJECT-TYPE
		SYNTAX		INTEGER {
					v00000(0),
					v00011(1),
					v00102(2),
					v00113(3),
					v01004(4),
					v01015(5),
					v01106(6),
					v01117(7),
					v10008(8),
					v10019(9),
					v101010(10),
					v101111(11),
					v110012(12),
					v110113(13),
					v111014(14),
					v111115(15)
				}
		MAX-ACCESS	read-write
		STATUS		current
		DESCRIPTION	"
			style='Radiobutton list'
			preset='v00000'
			path='/display/Control/Display Memory Setup/AFD Code'
		"
		::= { alchemistHd3GCtrlEntries 5363 }

	dispEntryDefault OBJECT-TYPE
		SYNTAX		INTEGER { ready(0), trigger(1) }
		MAX-ACCESS	read-write
		STATUS		current
		DESCRIPTION	"
			style='Event button'
			path='/display/Control/Display Memory Setup/Default'
		"
		::= { alchemistHd3GCtrlEntries 5364 }

	dispEntryCodedFrame4X3 OBJECT-TYPE
		SYNTAX		INTEGER { disable(0), enable(1) }
		MAX-ACCESS	read-write
		STATUS		current
		DESCRIPTION	"
			style='Checkbox'
			range='0..1'
			path='/display/Control/Display Memory Setup/   4:3   '
		"
		::= { alchemistHd3GCtrlEntries 5365 }

	dispEntryCodedFrame16X9 OBJECT-TYPE
		SYNTAX		INTEGER { disable(0), enable(1) }
		MAX-ACCESS	read-write
		STATUS		current
		DESCRIPTION	"
			style='Checkbox'
			range='0..1'
			path='/display/Control/Display Memory Setup/  16:9   '
		"
		::= { alchemistHd3GCtrlEntries 5366 }

	dispForcedMemSelA OBJECT-TYPE
		SYNTAX		INTEGER {
					sdToSd(1),
					sdToHd(2),
					hdToSd(3),
					hdToHd(4)
				}
		MAX-ACCESS	read-write
		STATUS		current
		DESCRIPTION	"
			style='Radiobutton list'
			path='/display/Control/Display Memory Setup/Output A Forced Mem'
		"
		::= { alchemistHd3GCtrlEntries 5367 }

	dispForcedMemSelB OBJECT-TYPE
		SYNTAX		INTEGER {
					sdToSd(1),
					sdToHd(2),
					hdToSd(3),
					hdToHd(4)
				}
		MAX-ACCESS	read-write
		STATUS		current
		DESCRIPTION	"
			style='Radiobutton list'
			path='/display/Control/Display Memory Setup/Output B Forced Mem'
		"
		::= { alchemistHd3GCtrlEntries 5368 }

	procEnhanceVertLock OBJECT-TYPE
		SYNTAX		INTEGER { disable(0), enable(1) }
		MAX-ACCESS	read-write
		STATUS		current
		DESCRIPTION	"
			style='Checkbox'
			path='/Enhancements/Enhancer/Vertical lock'
		"
		::= { alchemistHd3GCtrlEntries 5372 }

	procEnhanceHorizLock OBJECT-TYPE
		SYNTAX		INTEGER { disable(0), enable(1) }
		MAX-ACCESS	read-write
		STATUS		current
		DESCRIPTION	"
			style='Checkbox'
			path='/Enhancements/Enhancer/Horizontal lock'
		"
		::= { alchemistHd3GCtrlEntries 5375 }

	aliasSuppressionVertLock OBJECT-TYPE
		SYNTAX		INTEGER { disable(0), enable(1) }
		MAX-ACCESS	read-write
		STATUS		current
		DESCRIPTION	"
			style='Checkbox'
			path='/Enhancements/Alias Suppression/Vertical lock'
		"
		::= { alchemistHd3GCtrlEntries 5376 }

	aliasSuppressionHorizLock OBJECT-TYPE
		SYNTAX		INTEGER { disable(0), enable(1) }
		MAX-ACCESS	read-write
		STATUS		current
		DESCRIPTION	"
			style='Checkbox'
			path='/Enhancements/Alias Suppression/Horizontal lock'
		"
		::= { alchemistHd3GCtrlEntries 5377 }

	referenceEnable OBJECT-TYPE
		SYNTAX		INTEGER { disable(0), enable(1) }
		MAX-ACCESS	read-write
		STATUS		current
		DESCRIPTION	"
			style='Checkbox'
			path='/Reference/  Reference Enable'
		"
		::= { alchemistHd3GCtrlEntries 5400 }

	referenceSrc OBJECT-TYPE
		SYNTAX		INTEGER {
					auto(0),
					refA(1),
					refB(2),
					input(3)
				}
		MAX-ACCESS	read-write
		STATUS		current
		DESCRIPTION	"
			style='Radiobutton list'
			preset='input'
			path='/Reference/Reference Source'
		"
		::= { alchemistHd3GCtrlEntries 5410 }

	referenceOffsetHoriz OBJECT-TYPE
		SYNTAX		Integer32 (-2640..2640)
		MAX-ACCESS	read-write
		STATUS		current
		DESCRIPTION	"
			style='Numeric control'
			range='-2640..2640'
			path='/output/Output B/Offset/Ref Offset Horiz'
		"
		::= { alchemistHd3GCtrlEntries 5432 }

	referenceOffsetVert OBJECT-TYPE
		SYNTAX		Integer32 (-10..10)
		MAX-ACCESS	read-write
		STATUS		current
		DESCRIPTION	"
			style='Numeric control'
			range='-10..10'
			path='/output/Output B/Offset/Ref Offset Vert'
		"
		::= { alchemistHd3GCtrlEntries 5433 }

	referenceTimingHoriz OBJECT-TYPE
		SYNTAX		Integer32 (-2640..2640)
		MAX-ACCESS	read-write
		STATUS		current
		DESCRIPTION	"
			style='Numeric control'
			range='-2640pixels..2640pixels'
			path='/Reference/Horizontal timing'
		"
		::= { alchemistHd3GCtrlEntries 5437 }

	referenceTimingVert OBJECT-TYPE
		SYNTAX		Integer32 (-1249..1249)
		MAX-ACCESS	read-write
		STATUS		current
		DESCRIPTION	"
			style='Numeric control'
			range='-1249lines..1249lines'
			path='/Reference/Vertical timing'
		"
		::= { alchemistHd3GCtrlEntries 5438 }

	nvrLoad OBJECT-TYPE
		SYNTAX		INTEGER { ready(0), trigger(1) }
		MAX-ACCESS	read-write
		STATUS		current
		DESCRIPTION	"
			style='Event button'
			path='/Memory/Global Memories/Recall'
		"
		::= { alchemistHd3GCtrlEntries 5500 }

	nvrSave OBJECT-TYPE
		SYNTAX		INTEGER { ready(0), trigger(1) }
		MAX-ACCESS	read-write
		STATUS		current
		DESCRIPTION	"
			style='Event button'
			path='/Memory/Global Memories/Store'
		"
		::= { alchemistHd3GCtrlEntries 5501 }

	nvrSelect OBJECT-TYPE
		SYNTAX		INTEGER {
					memory1(1),
					memory2(2),
					memory3(3),
					memory4(4),
					memory5(5),
					memory6(6),
					factory(7),
					default(8),
					fileflow(9)
				}
		MAX-ACCESS	read-write
		STATUS		current
		DESCRIPTION	"
			style='Radiobutton list'
			path='/Memory/Global Memories/Select'
		"
		::= { alchemistHd3GCtrlEntries 5510 }

	nvrRename OBJECT-TYPE
		SYNTAX		RollCallString
		MAX-ACCESS	read-write
		STATUS		current
		DESCRIPTION	"
			style='Editable string'
			path='/Memory/Global Memories/Memory Rename'
		"
		::= { alchemistHd3GCtrlEntries 5530 }

	monoEnableA OBJECT-TYPE
		SYNTAX		INTEGER { disable(0), enable(1) }
		MAX-ACCESS	read-write
		STATUS		current
		DESCRIPTION	"
			style='Checkbox'
			path='/utils/Channel A/Mono'
		"
		::= { alchemistHd3GCtrlEntries 5601 }

	monoEnableB OBJECT-TYPE
		SYNTAX		INTEGER { disable(0), enable(1) }
		MAX-ACCESS	read-write
		STATUS		current
		DESCRIPTION	"
			style='Checkbox'
			path='/utils/Channel B/Mono'
		"
		::= { alchemistHd3GCtrlEntries 5602 }

	cutToBlackA OBJECT-TYPE
		SYNTAX		INTEGER { disable(0), enable(1) }
		MAX-ACCESS	read-write
		STATUS		current
		DESCRIPTION	"
			style='Checkbox'
			path='/utils/Channel A/Input Loss/Cut to black'
		"
		::= { alchemistHd3GCtrlEntries 5603 }

	cutToBlackB OBJECT-TYPE
		SYNTAX		INTEGER { disable(0), enable(1) }
		MAX-ACCESS	read-write
		STATUS		current
		DESCRIPTION	"
			style='Checkbox'
			path='/utils/Channel B/Input Loss/Cut to black'
		"
		::= { alchemistHd3GCtrlEntries 5604 }

	freezeControl OBJECT-TYPE
		SYNTAX		INTEGER {
					off(0),
					frame(3)
				}
		MAX-ACCESS	read-write
		STATUS		current
		DESCRIPTION	"
			style='Radiobutton list'
			preset='off'
			path='/utils/Channel A/Input Loss/Freeze'
		"
		::= { alchemistHd3GCtrlEntries 5611 }

	patternEnableA OBJECT-TYPE
		SYNTAX		INTEGER { disable(0), enable(1) }
		MAX-ACCESS	read-write
		STATUS		current
		DESCRIPTION	"
			style='Checkbox'
			path='/utils/Channel A/Patterns/Pattern Enable'
		"
		::= { alchemistHd3GCtrlEntries 5620 }

	patternTypeA OBJECT-TYPE
		SYNTAX		INTEGER {
					v100PctBars(0),
					v75PctBars(1),
					smpteBars(2),
					tartan(3),
					pluge(4),
					ramp(5),
					sweep(6),
					pulseAndBar(7),
					burst(8)
				}
		MAX-ACCESS	read-write
		STATUS		current
		DESCRIPTION	"
			style='Radiobutton list'
			preset='v100PctBars'
			path='/utils/Channel A/Patterns/Pattern Type'
		"
		::= { alchemistHd3GCtrlEntries 5621 }

	patternEnableB OBJECT-TYPE
		SYNTAX		INTEGER { disable(0), enable(1) }
		MAX-ACCESS	read-write
		STATUS		current
		DESCRIPTION	"
			style='Checkbox'
			path='/utils/Channel B/Patterns/Pattern Enable'
		"
		::= { alchemistHd3GCtrlEntries 5622 }

	patternTypeB OBJECT-TYPE
		SYNTAX		INTEGER {
					v100PctBars(0),
					v75PctBars(1),
					smpteBars(2),
					tartan(3),
					pluge(4),
					ramp(5),
					sweep(6),
					pulseAndBar(7),
					burst(8)
				}
		MAX-ACCESS	read-write
		STATUS		current
		DESCRIPTION	"
			style='Radiobutton list'
			preset='v100PctBars'
			path='/utils/Channel B/Patterns/Pattern Type'
		"
		::= { alchemistHd3GCtrlEntries 5623 }

	blitsLoop OBJECT-TYPE
		SYNTAX		INTEGER {
					all(0),
					phase1(1),
					phase2(2),
					phase3(3)
				}
		MAX-ACCESS	read-write
		STATUS		current
		DESCRIPTION	"
			style='Radiobutton list'
			preset='all'
			path='/utils/Blits Control/Blits Loop'
		"
		::= { alchemistHd3GCtrlEntries 5624 }

	globalAudioDelay OBJECT-TYPE
		SYNTAX		Integer32 (-190..250)
		MAX-ACCESS	read-write
		STATUS		current
		DESCRIPTION	"
			style='Numeric control'
			range='-190ms..250ms'
			path='/Audio Control/Global Audio Delay/Global Delay'
		"
		::= { alchemistHd3GCtrlEntries 5790 }

	globalAudioDelayPreset OBJECT-TYPE
		SYNTAX		INTEGER { ready(0), trigger(1) }
		MAX-ACCESS	read-write
		STATUS		current
		DESCRIPTION	"
			style='Event button'
			path='/Audio Control/Audio Delay Offset Preset'
		"
		::= { alchemistHd3GCtrlEntries 5791 }

	dolbyEncDelayOffsetPreset1 OBJECT-TYPE
		SYNTAX		INTEGER { ready(0), trigger(1) }
		MAX-ACCESS	read-write
		STATUS		current
		DESCRIPTION	"
			style='Event button'
			path='/Audio Control/Transcode Delay Preset'
		"
		::= { alchemistHd3GCtrlEntries 5792 }

	dolbyEncDelayOffsetPreset2 OBJECT-TYPE
		SYNTAX		INTEGER { ready(0), trigger(1) }
		MAX-ACCESS	read-write
		STATUS		current
		DESCRIPTION	"
			style='Event button'
			path='/Audio Control/Transcode Delay Preset'
		"
		::= { alchemistHd3GCtrlEntries 5793 }

	filmtoolsOpStd23 OBJECT-TYPE
		SYNTAX		INTEGER {
					v62523Psf(28),
					v108023Psf(24),
					v72023P(41)
				}
		MAX-ACCESS	read-write
		STATUS		current
		DESCRIPTION	"
			style='Radiobutton list'
			path='/output/Output A Std/23.98Hz'
		"
		::= { alchemistHd3GCtrlEntries 5900 }

	filmtoolsOpStd24 OBJECT-TYPE
		SYNTAX		INTEGER {
					v62524Psf(27),
					v108024Psf(23),
					v72024P(40)
				}
		MAX-ACCESS	read-write
		STATUS		current
		DESCRIPTION	"
			style='Radiobutton list'
			path='/output/Output A Std/24Hz'
		"
		::= { alchemistHd3GCtrlEntries 5901 }

	filmtoolsOpStd25 OBJECT-TYPE
		SYNTAX		INTEGER {
					v62525Psf(1020),
					v108025Psf(36),
					v72025P(39)
				}
		MAX-ACCESS	read-write
		STATUS		current
		DESCRIPTION	"
			style='Radiobutton list'
			path='/output/Output A Std/25Hz'
		"
		::= { alchemistHd3GCtrlEntries 5902 }

	filmtoolsOpStd29 OBJECT-TYPE
		SYNTAX		INTEGER {
					v52529Psf(1019),
					v108029Psf(35),
					v72029P(38)
				}
		MAX-ACCESS	read-write
		STATUS		current
		DESCRIPTION	"
			style='Radiobutton list'
			path='/output/Output A Std/29.97Hz'
		"
		::= { alchemistHd3GCtrlEntries 5903 }

	filmtoolsOpStd30 OBJECT-TYPE
		SYNTAX		INTEGER {
					v108030Psf(34),
					v72030P(37)
				}
		MAX-ACCESS	read-write
		STATUS		current
		DESCRIPTION	"
			style='Radiobutton list'
			path='/output/Output A Std/30Hz'
		"
		::= { alchemistHd3GCtrlEntries 5904 }

	filmtoolsOpStd47 OBJECT-TYPE
		SYNTAX		INTEGER {
					v62547I(1028),
					v108047I(1024)
				}
		MAX-ACCESS	read-write
		STATUS		current
		DESCRIPTION	"
			style='Radiobutton list'
			path='/output/Output A Std/47.95Hz'
		"
		::= { alchemistHd3GCtrlEntries 5905 }

	filmtoolsOpStd48 OBJECT-TYPE
		SYNTAX		INTEGER {
					v62548I(1027),
					v108048I(1023)
				}
		MAX-ACCESS	read-write
		STATUS		current
		DESCRIPTION	"
			style='Radiobutton list'
			path='/output/Output A Std/48Hz'
		"
		::= { alchemistHd3GCtrlEntries 5906 }

	filmtoolsOpStd50 OBJECT-TYPE
		SYNTAX		INTEGER {
					v62550I(20),
					v108050I(8),
					v72050P(30),
					v108050P(5)
				}
		MAX-ACCESS	read-write
		STATUS		current
		DESCRIPTION	"
			style='Radiobutton list'
			preset='v62550I'
			path='/output/Output A Std/50Hz'
		"
		::= { alchemistHd3GCtrlEntries 5907 }

	filmtoolsOpStd59 OBJECT-TYPE
		SYNTAX		INTEGER {
					v52559I(19),
					v108059I(7),
					v72059P(17),
					v108059P(4)
				}
		MAX-ACCESS	read-write
		STATUS		current
		DESCRIPTION	"
			style='Radiobutton list'
			path='/output/Output A Std/59.94Hz'
		"
		::= { alchemistHd3GCtrlEntries 5908 }

	filmtoolsOpStd60 OBJECT-TYPE
		SYNTAX		INTEGER {
					v108060I(6),
					v72060P(16),
					v108060P(3)
				}
		MAX-ACCESS	read-write
		STATUS		current
		DESCRIPTION	"
			style='Radiobutton list'
			path='/output/Output A Std/60Hz'
		"
		::= { alchemistHd3GCtrlEntries 5909 }

	filmtoolsOpStdAuto OBJECT-TYPE
		SYNTAX		INTEGER { disable(0), enable(1) }
		MAX-ACCESS	read-write
		STATUS		current
		DESCRIPTION	"
			style='Checkbox'
			range='0..1'
			path='/output/Output A Std/Auto'
		"
		::= { alchemistHd3GCtrlEntries 5910 }

	filmtoolsIpStd23 OBJECT-TYPE
		SYNTAX		INTEGER {
					v62523Psf(28),
					v108023Psf(24),
					v72023P(41)
				}
		MAX-ACCESS	read-write
		STATUS		current
		DESCRIPTION	"
			style='Radiobutton list'
			path='/output/Input Std/23.98Hz'
		"
		::= { alchemistHd3GCtrlEntries 5920 }

	filmtoolsIpStd24 OBJECT-TYPE
		SYNTAX		INTEGER {
					v62524Psf(27),
					v108024Psf(23),
					v72024P(40)
				}
		MAX-ACCESS	read-write
		STATUS		current
		DESCRIPTION	"
			style='Radiobutton list'
			path='/output/Input Std/24Hz'
		"
		::= { alchemistHd3GCtrlEntries 5921 }

	filmtoolsIpStd25 OBJECT-TYPE
		SYNTAX		INTEGER {
					v62525Psf(1020),
					v108025Psf(36),
					v72025P(39)
				}
		MAX-ACCESS	read-write
		STATUS		current
		DESCRIPTION	"
			style='Radiobutton list'
			path='/output/Input Std/25Hz'
		"
		::= { alchemistHd3GCtrlEntries 5922 }

	filmtoolsIpStd29 OBJECT-TYPE
		SYNTAX		INTEGER {
					v52529Psf(1019),
					v108029Psf(35),
					v72029P(38)
				}
		MAX-ACCESS	read-write
		STATUS		current
		DESCRIPTION	"
			style='Radiobutton list'
			path='/output/Input Std/29.97Hz'
		"
		::= { alchemistHd3GCtrlEntries 5923 }

	filmtoolsIpStd30 OBJECT-TYPE
		SYNTAX		INTEGER {
					v108030Psf(34),
					v72030P(37)
				}
		MAX-ACCESS	read-write
		STATUS		current
		DESCRIPTION	"
			style='Radiobutton list'
			path='/output/Input Std/30Hz'
		"
		::= { alchemistHd3GCtrlEntries 5924 }

	filmtoolsIpStd47 OBJECT-TYPE
		SYNTAX		INTEGER {
					v62547I(1028),
					v108047I(1024)
				}
		MAX-ACCESS	read-write
		STATUS		current
		DESCRIPTION	"
			style='Radiobutton list'
			path='/output/Input Std/47.95Hz'
		"
		::= { alchemistHd3GCtrlEntries 5925 }

	filmtoolsIpStd48 OBJECT-TYPE
		SYNTAX		INTEGER {
					v62548I(1027),
					v108048I(1023)
				}
		MAX-ACCESS	read-write
		STATUS		current
		DESCRIPTION	"
			style='Radiobutton list'
			path='/output/Input Std/48Hz'
		"
		::= { alchemistHd3GCtrlEntries 5926 }

	filmtoolsIpStd50 OBJECT-TYPE
		SYNTAX		INTEGER {
					v62550I(20),
					v108050I(8),
					v72050P(30),
					v108050P(5)
				}
		MAX-ACCESS	read-write
		STATUS		current
		DESCRIPTION	"
			style='Radiobutton list'
			path='/output/Input Std/50Hz'
		"
		::= { alchemistHd3GCtrlEntries 5927 }

	filmtoolsIpStd59 OBJECT-TYPE
		SYNTAX		INTEGER {
					v52559I(19),
					v108059I(7),
					v72059P(17),
					v108059P(4)
				}
		MAX-ACCESS	read-write
		STATUS		current
		DESCRIPTION	"
			style='Radiobutton list'
			path='/output/Input Std/59.94Hz'
		"
		::= { alchemistHd3GCtrlEntries 5928 }

	filmtoolsIpStd60 OBJECT-TYPE
		SYNTAX		INTEGER {
					v108060I(6),
					v72060P(16),
					v108060P(3)
				}
		MAX-ACCESS	read-write
		STATUS		current
		DESCRIPTION	"
			style='Radiobutton list'
			path='/output/Input Std/60Hz'
		"
		::= { alchemistHd3GCtrlEntries 5929 }

	filmtoolsIpStdAuto OBJECT-TYPE
		SYNTAX		INTEGER { disable(0), enable(1) }
		MAX-ACCESS	read-write
		STATUS		current
		DESCRIPTION	"
			style='Checkbox'
			range='0..1'
			path='/output/Input Std/Auto'
		"
		::= { alchemistHd3GCtrlEntries 5930 }

	logInp OBJECT-TYPE
		SYNTAX		INTEGER { disable(0), enable(1) }
		MAX-ACCESS	read-write
		STATUS		current
		DESCRIPTION	"
			style='Checkbox'
			path='/System/Log items/Input Status'
		"
		::= { alchemistHd3GCtrlEntries 5960 }

	logInpStd OBJECT-TYPE
		SYNTAX		INTEGER { disable(0), enable(1) }
		MAX-ACCESS	read-write
		STATUS		current
		DESCRIPTION	"
			style='Checkbox'
			path='/System/Log items/Input Standard'
		"
		::= { alchemistHd3GCtrlEntries 5961 }

	logRefStd OBJECT-TYPE
		SYNTAX		INTEGER { disable(0), enable(1) }
		MAX-ACCESS	read-write
		STATUS		current
		DESCRIPTION	"
			style='Checkbox'
			path='/System/Log items/Reference Status'
		"
		::= { alchemistHd3GCtrlEntries 5962 }

	logOutAStd OBJECT-TYPE
		SYNTAX		INTEGER { disable(0), enable(1) }
		MAX-ACCESS	read-write
		STATUS		current
		DESCRIPTION	"
			style='Checkbox'
			path='/System/Log items/Output A Standard'
		"
		::= { alchemistHd3GCtrlEntries 5966 }

	logOutBStd OBJECT-TYPE
		SYNTAX		INTEGER { disable(0), enable(1) }
		MAX-ACCESS	read-write
		STATUS		current
		DESCRIPTION	"
			style='Checkbox'
			path='/System/Log items/Output B Standard'
		"
		::= { alchemistHd3GCtrlEntries 5967 }

	logStatus OBJECT-TYPE
		SYNTAX		INTEGER { disable(0), enable(1) }
		MAX-ACCESS	read-write
		STATUS		current
		DESCRIPTION	"
			style='Checkbox'
			path='/System/Log items/System Status'
		"
		::= { alchemistHd3GCtrlEntries 5971 }

	activeLineLength OBJECT-TYPE
		SYNTAX		INTEGER {
					digital(0),
					analog(1)
				}
		MAX-ACCESS	read-write
		STATUS		current
		DESCRIPTION	"
			style='Radiobutton list'
			preset='digital'
			path='/System/Setup/Active Line Length'
		"
		::= { alchemistHd3GCtrlEntries 5980 }

	shapedBlanking OBJECT-TYPE
		SYNTAX		INTEGER {
					off(0),
					on(1)
				}
		MAX-ACCESS	read-write
		STATUS		current
		DESCRIPTION	"
			style='Radiobutton list'
			preset='off'
			path='/System/Setup/Shaped Horizontal Blanking'
		"
		::= { alchemistHd3GCtrlEntries 5981 }

	blankToAnalogLine OBJECT-TYPE
		SYNTAX		INTEGER {
					off(0),
					on(1)
				}
		MAX-ACCESS	read-write
		STATUS		current
		DESCRIPTION	"
			style='Radiobutton list'
			preset='off'
			path='/System/Setup/Analog Blanking'
		"
		::= { alchemistHd3GCtrlEntries 5982 }

	autoAesRealign OBJECT-TYPE
		SYNTAX		INTEGER {
					automatic(1),
					manual(0)
				}
		MAX-ACCESS	read-write
		STATUS		current
		DESCRIPTION	"
			style='Radiobutton list'
			preset='automatic'
			path='/System/Setup/Audio Alignment'
		"
		::= { alchemistHd3GCtrlEntries 5983 }

	realignAesNow OBJECT-TYPE
		SYNTAX		INTEGER { ready(0), trigger(1) }
		MAX-ACCESS	read-write
		STATUS		current
		DESCRIPTION	"
			style='Event button'
			path='/System/Setup/Align Audio Now'
		"
		::= { alchemistHd3GCtrlEntries 5984 }

	minimumDelay OBJECT-TYPE
		SYNTAX		INTEGER {
					off(0),
					on(1)
				}
		MAX-ACCESS	read-write
		STATUS		current
		DESCRIPTION	"
			style='Radiobutton list'
			preset='on'
			path='/System/Setup/Minimum Delay'
		"
		::= { alchemistHd3GCtrlEntries 5985 }

	audioDelayMode OBJECT-TYPE
		SYNTAX		INTEGER {
					minimum(0),
					nominal(1),
					maximum(2)
				}
		MAX-ACCESS	read-write
		STATUS		current
		DESCRIPTION	"
			style='Radiobutton list'
			preset='maximum'
			path='/System/Setup/Audio Delay Mode'
		"
		::= { alchemistHd3GCtrlEntries 5986 }

	outputAName OBJECT-TYPE
		SYNTAX		RollCallString
		MAX-ACCESS	read-write
		STATUS		current
		DESCRIPTION	"
			style='Editable string'
			path='/output/Output A/Output Name'
		"
		::= { alchemistHd3GCtrlEntries 6007 }

	outputBName OBJECT-TYPE
		SYNTAX		RollCallString
		MAX-ACCESS	read-write
		STATUS		current
		DESCRIPTION	"
			style='Editable string'
			path='/output/Output B/Output Name'
		"
		::= { alchemistHd3GCtrlEntries 6008 }

	inputCadenceStr OBJECT-TYPE
		SYNTAX		Integer32
		MAX-ACCESS	read-only
		STATUS		current
		DESCRIPTION	"
			style='ReadOnly numeric'
			path='/System/Input Cadence Str'
		"
		::= { alchemistHd3GCtrlEntries 6027 }

	ftEnable OBJECT-TYPE
		SYNTAX		INTEGER {
					off(0),
					on(1)
				}
		MAX-ACCESS	read-write
		STATUS		current
		DESCRIPTION	"
			style='Radiobutton list'
			preset='on'
			path='/Convert/Convert/FilmTools'
		"
		::= { alchemistHd3GCtrlEntries 6190 }

	recursiveEnable OBJECT-TYPE
		SYNTAX		INTEGER { disable(0), enable(1) }
		MAX-ACCESS	read-write
		STATUS		current
		DESCRIPTION	"
			style='Checkbox'
			range='0..1'
			path='/Noise Reduction/Noise Reduction/Enable'
		"
		::= { alchemistHd3GCtrlEntries 6200 }

	recursiveStrength OBJECT-TYPE
		SYNTAX		Integer32 (0..30)
		MAX-ACCESS	read-write
		STATUS		current
		DESCRIPTION	"
			style='Numeric control'
			range='0..30'
			path='/Noise Reduction/Noise Reduction/Y Strength'
		"
		::= { alchemistHd3GCtrlEntries 6201 }

	recursiveSplitScreen OBJECT-TYPE
		SYNTAX		INTEGER { disable(0), enable(1) }
		MAX-ACCESS	read-write
		STATUS		current
		DESCRIPTION	"
			style='Checkbox'
			range='0..1'
			path='/Noise Reduction/Noise Reduction/Split Screen'
		"
		::= { alchemistHd3GCtrlEntries 6202 }

	recursiveStrengthC OBJECT-TYPE
		SYNTAX		Integer32 (0..30)
		MAX-ACCESS	read-write
		STATUS		current
		DESCRIPTION	"
			style='Numeric control'
			range='0..30'
			path='/Noise Reduction/Noise Reduction/C Strength'
		"
		::= { alchemistHd3GCtrlEntries 6203 }

	recursiveBias OBJECT-TYPE
		SYNTAX		Integer32 (-15..15)
		MAX-ACCESS	read-write
		STATUS		current
		DESCRIPTION	"
			style='Numeric control'
			range='-15..15'
			path='/Noise Reduction/Noise Reduction/Bias'
		"
		::= { alchemistHd3GCtrlEntries 6204 }

	recursiveWeight OBJECT-TYPE
		SYNTAX		INTEGER {
					uniform(0),
					black(1),
					white(2)
				}
		MAX-ACCESS	read-write
		STATUS		current
		DESCRIPTION	"
			style='Radiobutton list'
			preset='uniform'
			path='/Noise Reduction/Noise Reduction/Weight'
		"
		::= { alchemistHd3GCtrlEntries 6205 }

	recursiveOverlay OBJECT-TYPE
		SYNTAX		INTEGER { disable(0), enable(1) }
		MAX-ACCESS	read-write
		STATUS		current
		DESCRIPTION	"
			style='Checkbox'
			range='0..1'
			path='/Noise Reduction/Noise Reduction/Overlay'
		"
		::= { alchemistHd3GCtrlEntries 6206 }

	audioAesInputStatus OBJECT-TYPE
		SYNTAX		RollCallString
		MAX-ACCESS	read-only
		STATUS		current
		DESCRIPTION	"
			style='ReadOnly string'
			path='/System/audio_aes_input_status'
		"
		::= { alchemistHd3GCtrlEntries 6536 }

	audioEmbInputStatus OBJECT-TYPE
		SYNTAX		RollCallString
		MAX-ACCESS	read-only
		STATUS		current
		DESCRIPTION	"
			style='ReadOnly string'
			path='/System/audio_emb_input_status'
		"
		::= { alchemistHd3GCtrlEntries 6537 }

	referenceState OBJECT-TYPE
		SYNTAX		INTEGER {
					ok(0),
					bad(1)
				}
		MAX-ACCESS	read-only
		STATUS		current
		DESCRIPTION	"
			style='Radiobutton list'
			preset='ok'
			path='/System/reference_state'
		"
		::= { alchemistHd3GCtrlEntries 6667 }

	mapEmbToOutputA OBJECT-TYPE
		SYNTAX		INTEGER { ready(0), trigger(1) }
		MAX-ACCESS	read-write
		STATUS		current
		DESCRIPTION	"
			style='Event button'
			path='/Audio Output EMB A/Map/Map 1-8/EMB 1-8'
		"
		::= { alchemistHd3GCtrlEntries 6770 }

	mapAesToOutputA OBJECT-TYPE
		SYNTAX		INTEGER { ready(0), trigger(1) }
		MAX-ACCESS	read-write
		STATUS		current
		DESCRIPTION	"
			style='Event button'
			path='/Audio Output EMB A/Map/Map 1-8/AES 1-8'
		"
		::= { alchemistHd3GCtrlEntries 6771 }

	mapDec1ToOutputATop OBJECT-TYPE
		SYNTAX		INTEGER { ready(0), trigger(1) }
		MAX-ACCESS	read-write
		STATUS		current
		DESCRIPTION	"
			style='Event button'
			path='/Audio Output EMB A/Map/Map 1-4/DEC 1'
		"
		::= { alchemistHd3GCtrlEntries 6772 }

	mapDec2ToOutputATop OBJECT-TYPE
		SYNTAX		INTEGER { ready(0), trigger(1) }
		MAX-ACCESS	read-write
		STATUS		current
		DESCRIPTION	"
			style='Event button'
			path='/Audio Output EMB A/Map/Map 1-4/DEC 2'
		"
		::= { alchemistHd3GCtrlEntries 6773 }

	mapDec1ToOutputABottom OBJECT-TYPE
		SYNTAX		INTEGER { ready(0), trigger(1) }
		MAX-ACCESS	read-write
		STATUS		current
		DESCRIPTION	"
			style='Event button'
			path='/Audio Output EMB A/Map/Map 4-8/DEC 1'
		"
		::= { alchemistHd3GCtrlEntries 6774 }

	mapDec2ToOutputABottom OBJECT-TYPE
		SYNTAX		INTEGER { ready(0), trigger(1) }
		MAX-ACCESS	read-write
		STATUS		current
		DESCRIPTION	"
			style='Event button'
			path='/Audio Output EMB A/Map/Map 4-8/DEC 2'
		"
		::= { alchemistHd3GCtrlEntries 6775 }

	mapDec1ToEnc1 OBJECT-TYPE
		SYNTAX		INTEGER { ready(0), trigger(1) }
		MAX-ACCESS	read-write
		STATUS		current
		DESCRIPTION	"
			style='Event button'
			path='/Dolby 1 Encoder/Map/DEC 1'
		"
		::= { alchemistHd3GCtrlEntries 6776 }

	mapDec2ToEnc1 OBJECT-TYPE
		SYNTAX		INTEGER { ready(0), trigger(1) }
		MAX-ACCESS	read-write
		STATUS		current
		DESCRIPTION	"
			style='Event button'
			path='/Dolby 1 Encoder/Map/DEC 2'
		"
		::= { alchemistHd3GCtrlEntries 6777 }

	mapEmbTopToEnc1 OBJECT-TYPE
		SYNTAX		INTEGER { ready(0), trigger(1) }
		MAX-ACCESS	read-write
		STATUS		current
		DESCRIPTION	"
			style='Event button'
			path='/Dolby 1 Encoder/Map/EMB 1-4'
		"
		::= { alchemistHd3GCtrlEntries 6778 }

	mapEmbBottomToEnc1 OBJECT-TYPE
		SYNTAX		INTEGER { ready(0), trigger(1) }
		MAX-ACCESS	read-write
		STATUS		current
		DESCRIPTION	"
			style='Event button'
			path='/Dolby 1 Encoder/Map/EMB 5-8'
		"
		::= { alchemistHd3GCtrlEntries 6779 }

	mapAesTopToEnc1 OBJECT-TYPE
		SYNTAX		INTEGER { ready(0), trigger(1) }
		MAX-ACCESS	read-write
		STATUS		current
		DESCRIPTION	"
			style='Event button'
			path='/Dolby 1 Encoder/Map/AES 1-4'
		"
		::= { alchemistHd3GCtrlEntries 6780 }

	mapAesBottomToEnc1 OBJECT-TYPE
		SYNTAX		INTEGER { ready(0), trigger(1) }
		MAX-ACCESS	read-write
		STATUS		current
		DESCRIPTION	"
			style='Event button'
			path='/Dolby 1 Encoder/Map/AES 5-8'
		"
		::= { alchemistHd3GCtrlEntries 6781 }

	mapDec1ToEnc2 OBJECT-TYPE
		SYNTAX		INTEGER { ready(0), trigger(1) }
		MAX-ACCESS	read-write
		STATUS		current
		DESCRIPTION	"
			style='Event button'
			path='/Dolby 2 Encoder/Map/DEC 1'
		"
		::= { alchemistHd3GCtrlEntries 6782 }

	mapDec2ToEnc2 OBJECT-TYPE
		SYNTAX		INTEGER { ready(0), trigger(1) }
		MAX-ACCESS	read-write
		STATUS		current
		DESCRIPTION	"
			style='Event button'
			path='/Dolby 2 Encoder/Map/DEC 2'
		"
		::= { alchemistHd3GCtrlEntries 6783 }

	mapEmbTopToEnc2 OBJECT-TYPE
		SYNTAX		INTEGER { ready(0), trigger(1) }
		MAX-ACCESS	read-write
		STATUS		current
		DESCRIPTION	"
			style='Event button'
			path='/Dolby 2 Encoder/Map/EMB 1-4'
		"
		::= { alchemistHd3GCtrlEntries 6784 }

	mapEmbBottomToEnc2 OBJECT-TYPE
		SYNTAX		INTEGER { ready(0), trigger(1) }
		MAX-ACCESS	read-write
		STATUS		current
		DESCRIPTION	"
			style='Event button'
			path='/Dolby 2 Encoder/Map/EMB 5-8'
		"
		::= { alchemistHd3GCtrlEntries 6785 }

	mapAesTopToEnc2 OBJECT-TYPE
		SYNTAX		INTEGER { ready(0), trigger(1) }
		MAX-ACCESS	read-write
		STATUS		current
		DESCRIPTION	"
			style='Event button'
			path='/Dolby 2 Encoder/Map/AES 1-4'
		"
		::= { alchemistHd3GCtrlEntries 6786 }

	mapAesBottomToEnc2 OBJECT-TYPE
		SYNTAX		INTEGER { ready(0), trigger(1) }
		MAX-ACCESS	read-write
		STATUS		current
		DESCRIPTION	"
			style='Event button'
			path='/Dolby 2 Encoder/Map/AES 5-8'
		"
		::= { alchemistHd3GCtrlEntries 6787 }

	mapEmbToOutputB OBJECT-TYPE
		SYNTAX		INTEGER { ready(0), trigger(1) }
		MAX-ACCESS	read-write
		STATUS		current
		DESCRIPTION	"
			style='Event button'
			path='/Audio Output EMB B/Map/Map 1-8/EMB 1-8'
		"
		::= { alchemistHd3GCtrlEntries 6788 }

	mapAesToOutputB OBJECT-TYPE
		SYNTAX		INTEGER { ready(0), trigger(1) }
		MAX-ACCESS	read-write
		STATUS		current
		DESCRIPTION	"
			style='Event button'
			path='/Audio Output EMB B/Map/Map 1-8/AES 1-8'
		"
		::= { alchemistHd3GCtrlEntries 6789 }

	mapDec1ToOutputBTop OBJECT-TYPE
		SYNTAX		INTEGER { ready(0), trigger(1) }
		MAX-ACCESS	read-write
		STATUS		current
		DESCRIPTION	"
			style='Event button'
			path='/Audio Output EMB B/Map/Map 1-4/DEC 1'
		"
		::= { alchemistHd3GCtrlEntries 6790 }

	mapDec2ToOutputBTop OBJECT-TYPE
		SYNTAX		INTEGER { ready(0), trigger(1) }
		MAX-ACCESS	read-write
		STATUS		current
		DESCRIPTION	"
			style='Event button'
			path='/Audio Output EMB B/Map/Map 1-4/DEC 2'
		"
		::= { alchemistHd3GCtrlEntries 6791 }

	mapDec1ToOutputBBottom OBJECT-TYPE
		SYNTAX		INTEGER { ready(0), trigger(1) }
		MAX-ACCESS	read-write
		STATUS		current
		DESCRIPTION	"
			style='Event button'
			path='/Audio Output EMB B/Map/Map 4-8/DEC 1'
		"
		::= { alchemistHd3GCtrlEntries 6792 }

	mapDec2ToOutputBBottom OBJECT-TYPE
		SYNTAX		INTEGER { ready(0), trigger(1) }
		MAX-ACCESS	read-write
		STATUS		current
		DESCRIPTION	"
			style='Event button'
			path='/Audio Output EMB B/Map/Map 4-8/DEC 2'
		"
		::= { alchemistHd3GCtrlEntries 6793 }

	mapEmbToAes OBJECT-TYPE
		SYNTAX		INTEGER { ready(0), trigger(1) }
		MAX-ACCESS	read-write
		STATUS		current
		DESCRIPTION	"
			style='Event button'
			path='/Audio Output AES/Map/Map 1-8/EMB 1-8'
		"
		::= { alchemistHd3GCtrlEntries 6794 }

	mapAesToAes OBJECT-TYPE
		SYNTAX		INTEGER { ready(0), trigger(1) }
		MAX-ACCESS	read-write
		STATUS		current
		DESCRIPTION	"
			style='Event button'
			path='/Audio Output AES/Map/Map 1-8/AES 1-8'
		"
		::= { alchemistHd3GCtrlEntries 6795 }

	mapDec1ToAesTop OBJECT-TYPE
		SYNTAX		INTEGER { ready(0), trigger(1) }
		MAX-ACCESS	read-write
		STATUS		current
		DESCRIPTION	"
			style='Event button'
			path='/Audio Output AES/Map/Map 1-4/DEC 1'
		"
		::= { alchemistHd3GCtrlEntries 6796 }

	mapDec2ToAesTop OBJECT-TYPE
		SYNTAX		INTEGER { ready(0), trigger(1) }
		MAX-ACCESS	read-write
		STATUS		current
		DESCRIPTION	"
			style='Event button'
			path='/Audio Output AES/Map/Map 1-4/DEC 2'
		"
		::= { alchemistHd3GCtrlEntries 6797 }

	mapDec1ToAesBottom OBJECT-TYPE
		SYNTAX		INTEGER { ready(0), trigger(1) }
		MAX-ACCESS	read-write
		STATUS		current
		DESCRIPTION	"
			style='Event button'
			path='/Audio Output AES/Map/Map 4-8/DEC 1'
		"
		::= { alchemistHd3GCtrlEntries 6798 }

	mapDec2ToAesBottom OBJECT-TYPE
		SYNTAX		INTEGER { ready(0), trigger(1) }
		MAX-ACCESS	read-write
		STATUS		current
		DESCRIPTION	"
			style='Event button'
			path='/Audio Output AES/Map/Map 4-8/DEC 2'
		"
		::= { alchemistHd3GCtrlEntries 6799 }

	cadenceInputOffset OBJECT-TYPE
		SYNTAX		Integer32 (-50..50)
		MAX-ACCESS	read-write
		STATUS		current
		DESCRIPTION	"
			style='Numeric control'
			range='-50..50'
			path='/FilmTools/Input/Cadence Offset'
		"
		::= { alchemistHd3GCtrlEntries 6827 }

	cadenceOutputOffset OBJECT-TYPE
		SYNTAX		Integer32 (-50..50)
		MAX-ACCESS	read-write
		STATUS		current
		DESCRIPTION	"
			style='Numeric control'
			range='-50..50'
			path='/FilmTools/Output/Cadence Offset'
		"
		::= { alchemistHd3GCtrlEntries 6828 }

	extMetadataOut1 OBJECT-TYPE
		SYNTAX		INTEGER {
					internal1(0),
					internal2(1),
					decoder1(2),
					decoder2(3),
					externalIn1(4),
					externalIn2(5)
				}
		MAX-ACCESS	read-write
		STATUS		current
		DESCRIPTION	"
			style='Radiobutton list'
			preset='internal1'
			path='/External Metadata Output/Ext 1 Source'
		"
		::= { alchemistHd3GCtrlEntries 6850 }

	extMetadataOut2 OBJECT-TYPE
		SYNTAX		INTEGER {
					internal1(0),
					internal2(1),
					decoder1(2),
					decoder2(3),
					externalIn1(4),
					externalIn2(5)
				}
		MAX-ACCESS	read-write
		STATUS		current
		DESCRIPTION	"
			style='Radiobutton list'
			preset='internal2'
			path='/External Metadata Output/Ext 2 Source'
		"
		::= { alchemistHd3GCtrlEntries 6851 }

	ftMode OBJECT-TYPE
		SYNTAX		INTEGER {
					auto(0),
					synchronise(1),
					interpolate(2),
					mcInterpolate(3)
				}
		MAX-ACCESS	read-write
		STATUS		current
		DESCRIPTION	"
			style='Radiobutton list'
			preset='auto'
			path='/FilmTools/Control/Mode'
		"
		::= { alchemistHd3GCtrlEntries 6900 }

	ftAperture OBJECT-TYPE
		SYNTAX		INTEGER {
					normal(0),
					sharp(1),
					safe(2)
				}
		MAX-ACCESS	read-write
		STATUS		current
		DESCRIPTION	"
			style='Radiobutton list'
			preset='normal'
			path='/FilmTools/Control/Film Aperture'
		"
		::= { alchemistHd3GCtrlEntries 6901 }

	ftBlurEnable OBJECT-TYPE
		SYNTAX		INTEGER { disable(0), enable(1) }
		MAX-ACCESS	read-write
		STATUS		current
		DESCRIPTION	"
			style='Checkbox'
			range='0..1'
			path='/FilmTools/Control/Blur Enable'
		"
		::= { alchemistHd3GCtrlEntries 6902 }

	ftBlur OBJECT-TYPE
		SYNTAX		Integer32 (0..8)
		MAX-ACCESS	read-write
		STATUS		current
		DESCRIPTION	"
			style='Numeric control'
			range='0..8'
			preset='8'
			path='/FilmTools/Control/Blur Strength'
		"
		::= { alchemistHd3GCtrlEntries 6903 }

	ftInEditIndTriggerTem OBJECT-TYPE
		SYNTAX		RollCallString
		MAX-ACCESS	read-write
		STATUS		current
		DESCRIPTION	"
			style='Editable string'
			path='/FilmTools/Input/Cadence Datum/Datum TC/Datum Timecode'
		"
		::= { alchemistHd3GCtrlEntries 6909 }

	ftInCadAlignment OBJECT-TYPE
		SYNTAX		INTEGER {
					auto(0),
					detect(1),
					v1x1(2),
					v2x2F12Psf(3),
					v2x2F21(4),
					v2x3TcDatum(5),
					v2x3Tc0And5(6),
					v2x3Freerun(7)
				}
		MAX-ACCESS	read-write
		STATUS		current
		DESCRIPTION	"
			style='Radiobutton list'
			preset='auto'
			path='/FilmTools/Input/Cadence Control'
		"
		::= { alchemistHd3GCtrlEntries 6910 }

	ftUseInTrigger OBJECT-TYPE
		SYNTAX		INTEGER { disable(0), enable(1) }
		MAX-ACCESS	read-write
		STATUS		current
		DESCRIPTION	"
			style='Checkbox'
			range='0..1'
			path='/FilmTools/Input/Cadence Datum/Use Input Trigger TC/   Use   '
		"
		::= { alchemistHd3GCtrlEntries 6915 }

	ftUseIndTrigger OBJECT-TYPE
		SYNTAX		INTEGER { disable(0), enable(1) }
		MAX-ACCESS	read-write
		STATUS		current
		DESCRIPTION	"
			style='Checkbox'
			range='0..1'
			path='/FilmTools/Input/Cadence Datum/Use Datum TC/   Use   '
		"
		::= { alchemistHd3GCtrlEntries 6916 }

	ftInCadence OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Input/2:3 Datum Cadence'
		"
		::= { alchemistHd3GCtrlEntries 6918 }

	ftInCadenceValid OBJECT-TYPE
		SYNTAX		INTEGER {
					atDatumPoint(0),
					onValidTc(1)
				}
		MAX-ACCESS	read-write
		STATUS		current
		DESCRIPTION	"
			style='Radiobutton list'
			preset='onValidTc'
			path='/FilmTools/Input/2:3 Cadence reset'
		"
		::= { alchemistHd3GCtrlEntries 6919 }

	ftInCadencePre OBJECT-TYPE
		SYNTAX		Integer32 (0..23)
		MAX-ACCESS	read-write
		STATUS		current
		DESCRIPTION	"
			style='Numeric control'
			range='0hrs..23hrs'
			preset='12hrs'
			path='/FilmTools/Input/Max time pre-datum'
		"
		::= { alchemistHd3GCtrlEntries 6920 }

	ftDetectVidOn OBJECT-TYPE
		SYNTAX		INTEGER {
					off(0),
					on(1)
				}
		MAX-ACCESS	read-write
		STATUS		current
		DESCRIPTION	"
			style='Radiobutton list'
			preset='on'
			path='/FilmTools/Detection/Video Enable'
		"
		::= { alchemistHd3GCtrlEntries 6930 }

	ftDetectFilmOn OBJECT-TYPE
		SYNTAX		INTEGER {
					any(1),
					off(0),
					v2x2(2),
					v2x3(3),
					animation(4)
				}
		MAX-ACCESS	read-write
		STATUS		current
		DESCRIPTION	"
			style='Radiobutton list'
			preset='any'
			path='/FilmTools/Detection/Film Enable'
		"
		::= { alchemistHd3GCtrlEntries 6931 }

	ftDetectBias OBJECT-TYPE
		SYNTAX		INTEGER {
					video2(0),
					video1(1),
					normal(2),
					film1(3),
					film2(4)
				}
		MAX-ACCESS	read-write
		STATUS		current
		DESCRIPTION	"
			style='Radiobutton list'
			preset='normal'
			path='/FilmTools/Detection/Bias'
		"
		::= { alchemistHd3GCtrlEntries 6932 }

	ftDetectWindow OBJECT-TYPE
		SYNTAX		INTEGER {
					auto(0),
					tracking(1),
					user(2)
				}
		MAX-ACCESS	read-write
		STATUS		current
		DESCRIPTION	"
			style='Radiobutton list'
			preset='auto'
			path='/FilmTools/Detection/Window Mode'
		"
		::= { alchemistHd3GCtrlEntries 6933 }

	ftDetectOverlay OBJECT-TYPE
		SYNTAX		INTEGER {
					off(0),
					darken(1),
					greyed(2)
				}
		MAX-ACCESS	read-write
		STATUS		current
		DESCRIPTION	"
			style='Radiobutton list'
			preset='off'
			path='/FilmTools/Detection/Overlay'
		"
		::= { alchemistHd3GCtrlEntries 6934 }

	ftDetectWinValFtDetectWinLeft OBJECT-TYPE
		SYNTAX		Integer32 (0..1000)
		MAX-ACCESS	read-write
		STATUS		current
		DESCRIPTION	"
			style='Numeric control'
			range='0.0%..100.0%'
			stepsize='0.1'
			preset='2.0%'
			path='/FilmTools/Detection/User Window Left'
		"
		::= { alchemistHd3GCtrlEntries 6935 }

	ftDetectWinValFtDetectWinRight OBJECT-TYPE
		SYNTAX		Integer32 (0..1000)
		MAX-ACCESS	read-write
		STATUS		current
		DESCRIPTION	"
			style='Numeric control'
			range='0.0%..100.0%'
			stepsize='0.1'
			preset='98.0%'
			path='/FilmTools/Detection/User Window Right'
		"
		::= { alchemistHd3GCtrlEntries 6936 }

	ftDetectWinValFtDetectWinTop OBJECT-TYPE
		SYNTAX		Integer32 (0..1000)
		MAX-ACCESS	read-write
		STATUS		current
		DESCRIPTION	"
			style='Numeric control'
			range='0.0%..100.0%'
			stepsize='0.1'
			preset='2.0%'
			path='/FilmTools/Detection/User Window Top'
		"
		::= { alchemistHd3GCtrlEntries 6937 }

	ftDetectWinValFtDetectWinBottom OBJECT-TYPE
		SYNTAX		Integer32 (0..1000)
		MAX-ACCESS	read-write
		STATUS		current
		DESCRIPTION	"
			style='Numeric control'
			range='0.0%..100.0%'
			stepsize='0.1'
			preset='98.0%'
			path='/FilmTools/Detection/User Window Bottom'
		"
		::= { alchemistHd3GCtrlEntries 6938 }

	ftOutEditIndTriggerTem OBJECT-TYPE
		SYNTAX		RollCallString
		MAX-ACCESS	read-write
		STATUS		current
		DESCRIPTION	"
			style='Editable string'
			path='/FilmTools/Output/Cadence Datum/Datum TC/Datum Timecode'
		"
		::= { alchemistHd3GCtrlEntries 6939 }

	ftOutCadAlignment OBJECT-TYPE
		SYNTAX		INTEGER {
					off(2),
					v2x2F12Psf(3),
					v2x2F21(4),
					v2x3TcDatum(5),
					v2x3Tc0And5(6),
					v2x3Freerun(7)
				}
		MAX-ACCESS	read-write
		STATUS		current
		DESCRIPTION	"
			style='Radiobutton list'
			preset='off'
			path='/FilmTools/Output/Cadence Control'
		"
		::= { alchemistHd3GCtrlEntries 6940 }

	ftOutCadOffInc OBJECT-TYPE
		SYNTAX		INTEGER { ready(0), trigger(1) }
		MAX-ACCESS	read-write
		STATUS		current
		DESCRIPTION	"
			style='Event button'
			path='/Cadence Offset/+'
		"
		::= { alchemistHd3GCtrlEntries 6943 }

	ftOutCadOffDec OBJECT-TYPE
		SYNTAX		INTEGER { ready(0), trigger(1) }
		MAX-ACCESS	read-write
		STATUS		current
		DESCRIPTION	"
			style='Event button'
			path='/Cadence Offset/-'
		"
		::= { alchemistHd3GCtrlEntries 6944 }

	ftOutUseOutTrigger OBJECT-TYPE
		SYNTAX		INTEGER { disable(0), enable(1) }
		MAX-ACCESS	read-write
		STATUS		current
		DESCRIPTION	"
			style='Checkbox'
			range='0..1'
			path='/FilmTools/Output/Cadence Datum/Use Input Trigger TC/   Use   '
		"
		::= { alchemistHd3GCtrlEntries 6945 }

	ftOutUseIndTrigger OBJECT-TYPE
		SYNTAX		INTEGER { disable(0), enable(1) }
		MAX-ACCESS	read-write
		STATUS		current
		DESCRIPTION	"
			style='Checkbox'
			range='0..1'
			path='/FilmTools/Output/Cadence Datum/Use Datum Timecode/   Use   '
		"
		::= { alchemistHd3GCtrlEntries 6946 }

	ftOutEditIndTrigger OBJECT-TYPE
		SYNTAX		INTEGER { disable(0), enable(1) }
		MAX-ACCESS	read-write
		STATUS		current
		DESCRIPTION	"
			style='Checkbox'
			range='0..1'
			path='/   Edit   '
		"
		::= { alchemistHd3GCtrlEntries 6947 }

	ftOutCadence OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Output/2:3 Datum Cadence'
		"
		::= { alchemistHd3GCtrlEntries 6948 }

	ftOutCadenceValid OBJECT-TYPE
		SYNTAX		INTEGER {
					atDatumPoint(0),
					onValidTc(1)
				}
		MAX-ACCESS	read-write
		STATUS		current
		DESCRIPTION	"
			style='Radiobutton list'
			preset='onValidTc'
			path='/FilmTools/Output/2:3 Cadence reset'
		"
		::= { alchemistHd3GCtrlEntries 6949 }

	ftOutCadencePre OBJECT-TYPE
		SYNTAX		Integer32 (0..23)
		MAX-ACCESS	read-write
		STATUS		current
		DESCRIPTION	"
			style='Numeric control'
			range='0hrs..23hrs'
			preset='12hrs'
			path='/FilmTools/Output/Max time pre-datum'
		"
		::= { alchemistHd3GCtrlEntries 6950 }

	ftIn05Cadence OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Input/0 and 5 Cadence'
		"
		::= { alchemistHd3GCtrlEntries 6951 }

	ftOut05Cadence OBJECT-TYPE
		SYNTAX		INTEGER {
					aa(0),
					bb(1),
					bc(2),
					cd(3),
					dd(4)
				}
		MAX-ACCESS	read-write
		STATUS		current
		DESCRIPTION	"
			style='Radiobutton list'
			preset='aa'
			path='/FilmTools/Output/0 and 5 Cadence'
		"
		::= { alchemistHd3GCtrlEntries 6952 }

	tcSdSource OBJECT-TYPE
		SYNTAX		INTEGER {
					vitc(0),
					ltc(1)
				}
		MAX-ACCESS	read-write
		STATUS		current
		DESCRIPTION	"
			style='Radiobutton list'
			preset='vitc'
			path='/Timecode/Timecode In/SD Source'
		"
		::= { alchemistHd3GCtrlEntries 7000 }

	tcHdSource OBJECT-TYPE
		SYNTAX		INTEGER {
					embeddedVitc(0),
					embeddedLtc(1),
					ltc(2)
				}
		MAX-ACCESS	read-write
		STATUS		current
		DESCRIPTION	"
			style='Radiobutton list'
			preset='embeddedVitc'
			path='/Timecode/Timecode In/HD Source'
		"
		::= { alchemistHd3GCtrlEntries 7001 }

	tcSdVitcOutEn OBJECT-TYPE
		SYNTAX		INTEGER { disable(0), enable(1) }
		MAX-ACCESS	read-write
		STATUS		current
		DESCRIPTION	"
			style='Checkbox'
			path='/Timecode/Timecode Out/  VITC  '
		"
		::= { alchemistHd3GCtrlEntries 7010 }

	tcSdVitcOut2NdLineEn OBJECT-TYPE
		SYNTAX		INTEGER { disable(0), enable(1) }
		MAX-ACCESS	read-write
		STATUS		current
		DESCRIPTION	"
			style='Checkbox'
			path='/Timecode/Timecode Out/Repeat line'
		"
		::= { alchemistHd3GCtrlEntries 7011 }

	tcSdVitcOutLineVitcOutLine525 OBJECT-TYPE
		SYNTAX		Integer32 (10..17)
		MAX-ACCESS	read-write
		STATUS		current
		DESCRIPTION	"
			style='Numeric control'
			range='10..17'
			preset='14'
			path='/Timecode/Timecode Out/VITC Insertion 525'
		"
		::= { alchemistHd3GCtrlEntries 7012 }

	tcSdVitcOutLineVitcOutLine625 OBJECT-TYPE
		SYNTAX		Integer32 (6..20)
		MAX-ACCESS	read-write
		STATUS		current
		DESCRIPTION	"
			style='Numeric control'
			range='6..20'
			preset='19'
			path='/Timecode/Timecode Out/VITC Insertion 625'
		"
		::= { alchemistHd3GCtrlEntries 7013 }

	tcHdVitcOutEn OBJECT-TYPE
		SYNTAX		INTEGER { disable(0), enable(1) }
		MAX-ACCESS	read-write
		STATUS		current
		DESCRIPTION	"
			style='Checkbox'
			path='/Timecode/Timecode Out/Emb VITC'
		"
		::= { alchemistHd3GCtrlEntries 7020 }

	tcHdLtcOutEn OBJECT-TYPE
		SYNTAX		INTEGER { disable(0), enable(1) }
		MAX-ACCESS	read-write
		STATUS		current
		DESCRIPTION	"
			style='Checkbox'
			path='/Timecode/Timecode Out/Emb LTC'
		"
		::= { alchemistHd3GCtrlEntries 7021 }

	tcDropFrameOuta OBJECT-TYPE
		SYNTAX		INTEGER {
					nonDropFrame(0),
					dropFrame(1)
				}
		MAX-ACCESS	read-write
		STATUS		current
		DESCRIPTION	"
			style='Radiobutton list'
			preset='dropFrame'
			path='/Timecode/Timecode Out/Frame Mode A'
		"
		::= { alchemistHd3GCtrlEntries 7030 }

	tcDropFrameOutb OBJECT-TYPE
		SYNTAX		INTEGER {
					nonDropFrame(0),
					dropFrame(1)
				}
		MAX-ACCESS	read-write
		STATUS		current
		DESCRIPTION	"
			style='Radiobutton list'
			preset='dropFrame'
			path='/Timecode/Timecode Out/Frame Mode B'
		"
		::= { alchemistHd3GCtrlEntries 7031 }

	tcInMaxFrames OBJECT-TYPE
		SYNTAX		INTEGER {
					detect(0),
					format(1),
					v24(2),
					v25(3),
					v30(4)
				}
		MAX-ACCESS	read-write
		STATUS		current
		DESCRIPTION	"
			style='Radiobutton list'
			preset='detect'
			path='/Timecode/Timecode In/Frame Count'
		"
		::= { alchemistHd3GCtrlEntries 7032 }

	tcOutMaxFramesOuta OBJECT-TYPE
		SYNTAX		INTEGER {
					auto(0),
					v24(1),
					v25(2),
					v30(3)
				}
		MAX-ACCESS	read-write
		STATUS		current
		DESCRIPTION	"
			style='Radiobutton list'
			preset='auto'
			path='/Timecode/Timecode Out/Frame Count A'
		"
		::= { alchemistHd3GCtrlEntries 7033 }

	tcOutMaxFramesOutb OBJECT-TYPE
		SYNTAX		INTEGER {
					auto(0),
					v24(1),
					v25(2),
					v30(3)
				}
		MAX-ACCESS	read-write
		STATUS		current
		DESCRIPTION	"
			style='Radiobutton list'
			preset='auto'
			path='/Timecode/Timecode Out/Frame Count B'
		"
		::= { alchemistHd3GCtrlEntries 7034 }

	tcMode OBJECT-TYPE
		SYNTAX		INTEGER {
					freeRun(0),
					syncAuto(1),
					syncManual(2),
					syncPrerun(3),
					eE(4),
					eERegen(5),
					triggerLoad(6)
				}
		MAX-ACCESS	read-write
		STATUS		current
		DESCRIPTION	"
			style='Radiobutton list'
			preset='freeRun'
			path='/Timecode/Timecode Conversion/Timecode Mode'
		"
		::= { alchemistHd3GCtrlEntries 7035 }

	tcLoadNow OBJECT-TYPE
		SYNTAX		INTEGER { ready(0), trigger(1) }
		MAX-ACCESS	read-write
		STATUS		current
		DESCRIPTION	"
			style='Event button'
			path='/Timecode/Timecode Conversion/Load Now'
		"
		::= { alchemistHd3GCtrlEntries 7036 }

	tcTrigger OBJECT-TYPE
		SYNTAX		Integer32
		MAX-ACCESS	read-only
		STATUS		current
		DESCRIPTION	"
			style='ReadOnly numeric'
			path='/Timecode/Timecode Status/Input trigger value'
		"
		::= { alchemistHd3GCtrlEntries 7040 }

	tcLoadOuta OBJECT-TYPE
		SYNTAX		Integer32
		MAX-ACCESS	read-only
		STATUS		current
		DESCRIPTION	"
			style='ReadOnly numeric'
			path='/Timecode/Timecode Status/Output A load value'
		"
		::= { alchemistHd3GCtrlEntries 7041 }

	tcLoadOutb OBJECT-TYPE
		SYNTAX		Integer32
		MAX-ACCESS	read-only
		STATUS		current
		DESCRIPTION	"
			style='ReadOnly numeric'
			path='/Timecode/Timecode Status/Output B load value'
		"
		::= { alchemistHd3GCtrlEntries 7042 }

	tcSynchroPrerun OBJECT-TYPE
		SYNTAX		Integer32
		MAX-ACCESS	read-only
		STATUS		current
		DESCRIPTION	"
			style='ReadOnly numeric'
			path='/Timecode/Timecode Status/Auto Synchro Pre-run'
		"
		::= { alchemistHd3GCtrlEntries 7043 }

	tcSynchroStatusA OBJECT-TYPE
		SYNTAX		Integer32
		MAX-ACCESS	read-only
		STATUS		current
		DESCRIPTION	"
			style='ReadOnly numeric'
			path='/Timecode/Timecode Status/Synchro Status A'
		"
		::= { alchemistHd3GCtrlEntries 7044 }

	tcSynchroLastTrigger OBJECT-TYPE
		SYNTAX		RollCallString
		MAX-ACCESS	read-only
		STATUS		current
		DESCRIPTION	"
			style='ReadOnly string'
			path='/Timecode/Timecode Status/Synchro Last Trigger'
		"
		::= { alchemistHd3GCtrlEntries 7045 }

	tcInputTc OBJECT-TYPE
		SYNTAX		Integer32
		MAX-ACCESS	read-only
		STATUS		current
		DESCRIPTION	"
			style='ReadOnly numeric'
			path='/Timecode/Timecode Status/Input Timecode'
		"
		::= { alchemistHd3GCtrlEntries 7046 }

	tcOutputaTc OBJECT-TYPE
		SYNTAX		Integer32
		MAX-ACCESS	read-only
		STATUS		current
		DESCRIPTION	"
			style='ReadOnly numeric'
			path='/Timecode/Timecode Status/Output A Timecode'
		"
		::= { alchemistHd3GCtrlEntries 7047 }

	tcOutputbTc OBJECT-TYPE
		SYNTAX		Integer32
		MAX-ACCESS	read-only
		STATUS		current
		DESCRIPTION	"
			style='ReadOnly numeric'
			path='/Timecode/Timecode Status/Output B Timecode'
		"
		::= { alchemistHd3GCtrlEntries 7048 }

	tcIpOverlay OBJECT-TYPE
		SYNTAX		INTEGER { disable(0), enable(1) }
		MAX-ACCESS	read-write
		STATUS		current
		DESCRIPTION	"
			style='Checkbox'
			range='0..1'
			path='/Timecode/Timecode Overlay/Input TC Overlay'
		"
		::= { alchemistHd3GCtrlEntries 7050 }

	tcOpaOverlay OBJECT-TYPE
		SYNTAX		INTEGER { disable(0), enable(1) }
		MAX-ACCESS	read-write
		STATUS		current
		DESCRIPTION	"
			style='Checkbox'
			range='0..1'
			path='/Timecode/Timecode Overlay/Output A TC Overlay'
		"
		::= { alchemistHd3GCtrlEntries 7051 }

	tcOpbOverlay OBJECT-TYPE
		SYNTAX		INTEGER { disable(0), enable(1) }
		MAX-ACCESS	read-write
		STATUS		current
		DESCRIPTION	"
			style='Checkbox'
			range='0..1'
			path='/Timecode/Timecode Overlay/Output B TC Overlay'
		"
		::= { alchemistHd3GCtrlEntries 7052 }

	templateTcEntry OBJECT-TYPE
		SYNTAX		RollCallString
		MAX-ACCESS	read-write
		STATUS		current
		DESCRIPTION	"
			style='Editable string'
			path='/Timecode/Timecode Conversion/TC Entry'
		"
		::= { alchemistHd3GCtrlEntries 7053 }

	tcE2eWindow OBJECT-TYPE
		SYNTAX		INTEGER {
					minimum(0),
					v05S(1),
					v1s(2),
					v2s(3),
					v5s(4)
				}
		MAX-ACCESS	read-write
		STATUS		current
		DESCRIPTION	"
			style='Radiobutton list'
			preset='minimum'
			path='/Timecode/Timecode Conversion/E-E Error Window'
		"
		::= { alchemistHd3GCtrlEntries 7060 }

	tcTriggerSet OBJECT-TYPE
		SYNTAX		INTEGER { ready(0), trigger(1) }
		MAX-ACCESS	read-write
		STATUS		current
		DESCRIPTION	"
			style='Event button'
			path='/Timecode/Timecode Conversion/Trigger Set'
		"
		::= { alchemistHd3GCtrlEntries 7070 }

	tcLoadOutaSet OBJECT-TYPE
		SYNTAX		INTEGER { ready(0), trigger(1) }
		MAX-ACCESS	read-write
		STATUS		current
		DESCRIPTION	"
			style='Event button'
			path='/Timecode/Timecode Conversion/Output A Set'
		"
		::= { alchemistHd3GCtrlEntries 7071 }

	tcLoadOutbSet OBJECT-TYPE
		SYNTAX		INTEGER { ready(0), trigger(1) }
		MAX-ACCESS	read-write
		STATUS		current
		DESCRIPTION	"
			style='Event button'
			path='/Timecode/Timecode Conversion/Output B Set'
		"
		::= { alchemistHd3GCtrlEntries 7072 }

	tcSynchroPrerunSet OBJECT-TYPE
		SYNTAX		INTEGER { ready(0), trigger(1) }
		MAX-ACCESS	read-write
		STATUS		current
		DESCRIPTION	"
			style='Event button'
			path='/Timecode/Timecode Conversion/Prerun Set'
		"
		::= { alchemistHd3GCtrlEntries 7073 }

	tcTriggerGrab OBJECT-TYPE
		SYNTAX		INTEGER { ready(0), trigger(1) }
		MAX-ACCESS	read-write
		STATUS		current
		DESCRIPTION	"
			style='Event button'
			path='/Timecode/Timecode Conversion/Trigger Grab'
		"
		::= { alchemistHd3GCtrlEntries 7074 }

	tcLoadOutaGrab OBJECT-TYPE
		SYNTAX		INTEGER { ready(0), trigger(1) }
		MAX-ACCESS	read-write
		STATUS		current
		DESCRIPTION	"
			style='Event button'
			path='/Timecode/Timecode Conversion/Output A Grab'
		"
		::= { alchemistHd3GCtrlEntries 7075 }

	tcLoadOutbGrab OBJECT-TYPE
		SYNTAX		INTEGER { ready(0), trigger(1) }
		MAX-ACCESS	read-write
		STATUS		current
		DESCRIPTION	"
			style='Event button'
			path='/Timecode/Timecode Conversion/Output B Grab'
		"
		::= { alchemistHd3GCtrlEntries 7076 }

	tcSynchroPrerunPreset OBJECT-TYPE
		SYNTAX		INTEGER { ready(0), trigger(1) }
		MAX-ACCESS	read-write
		STATUS		current
		DESCRIPTION	"
			style='Event button'
			path='/Timecode/Timecode Conversion/Prerun Preset'
		"
		::= { alchemistHd3GCtrlEntries 7077 }

	triggerMemory OBJECT-TYPE
		SYNTAX		RollCallString
		MAX-ACCESS	read-write
		STATUS		current
		DESCRIPTION	"
			style='Editable string'
			path='/System/Trigger Memory'
		"
		::= { alchemistHd3GCtrlEntries 7120 }

	loadAMemory OBJECT-TYPE
		SYNTAX		RollCallString
		MAX-ACCESS	read-write
		STATUS		current
		DESCRIPTION	"
			style='Editable string'
			path='/System/Load A Memory'
		"
		::= { alchemistHd3GCtrlEntries 7121 }

	loadBMemory OBJECT-TYPE
		SYNTAX		RollCallString
		MAX-ACCESS	read-write
		STATUS		current
		DESCRIPTION	"
			style='Editable string'
			path='/System/Load B Memory'
		"
		::= { alchemistHd3GCtrlEntries 7122 }

	prerunMemory OBJECT-TYPE
		SYNTAX		RollCallString
		MAX-ACCESS	read-write
		STATUS		current
		DESCRIPTION	"
			style='Editable string'
			path='/System/Prerun Memory'
		"
		::= { alchemistHd3GCtrlEntries 7123 }

	tcCadenceInMemory OBJECT-TYPE
		SYNTAX		RollCallString
		MAX-ACCESS	read-write
		STATUS		current
		DESCRIPTION	"
			style='Editable string'
			path='/System/TC Cadence In Memory'
		"
		::= { alchemistHd3GCtrlEntries 7124 }

	tcCadenceOutMemory OBJECT-TYPE
		SYNTAX		RollCallString
		MAX-ACCESS	read-write
		STATUS		current
		DESCRIPTION	"
			style='Editable string'
			path='/System/TC Cadence Out Memory'
		"
		::= { alchemistHd3GCtrlEntries 7125 }

	tcSynchroStatusB OBJECT-TYPE
		SYNTAX		Integer32
		MAX-ACCESS	read-only
		STATUS		current
		DESCRIPTION	"
			style='ReadOnly numeric'
			path='/Timecode/Timecode Status/Synchro Status B'
		"
		::= { alchemistHd3GCtrlEntries 7144 }

	tcSynchroTriggerElapse OBJECT-TYPE
		SYNTAX		Integer32
		MAX-ACCESS	read-only
		STATUS		current
		DESCRIPTION	"
			style='ReadOnly numeric'
			path='/Timecode/Timecode Status/Synchro Trigger Elapse'
		"
		::= { alchemistHd3GCtrlEntries 7146 }

	lumaClipperAEnable OBJECT-TYPE
		SYNTAX		INTEGER { disable(0), enable(1) }
		MAX-ACCESS	read-write
		STATUS		current
		DESCRIPTION	"
			style='Checkbox'
			range='0..1'
			path='/utils/Channel A/Legaliser/Luma Clipper/Enable'
		"
		::= { alchemistHd3GCtrlEntries 7170 }

	whiteMaxA OBJECT-TYPE
		SYNTAX		Integer32 (900..1090)
		MAX-ACCESS	read-write
		STATUS		current
		DESCRIPTION	"
			style='Numeric control'
			range='90.0%..109.0%'
			stepsize='0.1'
			preset='103.0%'
			path='/utils/Channel A/Legaliser/Luma Clipper/White Max'
		"
		::= { alchemistHd3GCtrlEntries 7171 }

	whiteKneeA OBJECT-TYPE
		SYNTAX		Integer32 (600..1090)
		MAX-ACCESS	read-write
		STATUS		current
		DESCRIPTION	"
			style='Numeric control'
			range='60.0%..109.0%'
			stepsize='0.1'
			preset='100.0%'
			path='/utils/Channel A/Legaliser/Luma Clipper/White Knee'
		"
		::= { alchemistHd3GCtrlEntries 7172 }

	blackMinA OBJECT-TYPE
		SYNTAX		Integer32 (-70..100)
		MAX-ACCESS	read-write
		STATUS		current
		DESCRIPTION	"
			style='Numeric control'
			range='-7.0%..10.0%'
			stepsize='0.1'
			preset='-1.0%'
			path='/utils/Channel A/Legaliser/Luma Clipper/Black Min'
		"
		::= { alchemistHd3GCtrlEntries 7173 }

	blackKneeA OBJECT-TYPE
		SYNTAX		Integer32 (-70..600)
		MAX-ACCESS	read-write
		STATUS		current
		DESCRIPTION	"
			style='Numeric control'
			range='-7.0%..60.0%'
			stepsize='0.1'
			path='/utils/Channel A/Legaliser/Luma Clipper/Black Knee'
		"
		::= { alchemistHd3GCtrlEntries 7174 }

	lumaClipperBEnable OBJECT-TYPE
		SYNTAX		INTEGER { disable(0), enable(1) }
		MAX-ACCESS	read-write
		STATUS		current
		DESCRIPTION	"
			style='Checkbox'
			range='0..10'
			path='/utils/Channel B/Legaliser/Luma Clipper/Enable'
		"
		::= { alchemistHd3GCtrlEntries 7180 }

	whiteMaxB OBJECT-TYPE
		SYNTAX		Integer32 (900..1090)
		MAX-ACCESS	read-write
		STATUS		current
		DESCRIPTION	"
			style='Numeric control'
			range='90.0%..109.0%'
			stepsize='0.1'
			preset='103.0%'
			path='/utils/Channel B/Legaliser/Luma Clipper/White Max'
		"
		::= { alchemistHd3GCtrlEntries 7181 }

	whiteKneeB OBJECT-TYPE
		SYNTAX		Integer32 (600..1090)
		MAX-ACCESS	read-write
		STATUS		current
		DESCRIPTION	"
			style='Numeric control'
			range='60.0%..109.0%'
			stepsize='0.1'
			preset='100.0%'
			path='/utils/Channel B/Legaliser/Luma Clipper/White Knee'
		"
		::= { alchemistHd3GCtrlEntries 7182 }

	blackMinB OBJECT-TYPE
		SYNTAX		Integer32 (-70..100)
		MAX-ACCESS	read-write
		STATUS		current
		DESCRIPTION	"
			style='Numeric control'
			range='-7.0%..10.0%'
			stepsize='0.1'
			preset='-1.0%'
			path='/utils/Channel B/Legaliser/Luma Clipper/Black Min'
		"
		::= { alchemistHd3GCtrlEntries 7183 }

	blackKneeB OBJECT-TYPE
		SYNTAX		Integer32 (-70..600)
		MAX-ACCESS	read-write
		STATUS		current
		DESCRIPTION	"
			style='Numeric control'
			range='-7.0%..60.0%'
			stepsize='0.1'
			path='/utils/Channel B/Legaliser/Luma Clipper/Black Knee'
		"
		::= { alchemistHd3GCtrlEntries 7184 }

	dolbyEncToneType2 OBJECT-TYPE
		SYNTAX		INTEGER {
					off(9),
					v1khz20Dbfs(0),
					v4khz20Dbfs(1),
					v1khz18Dbfs(2),
					v4khz18Dbfs(3),
					blits(4)
				}
		MAX-ACCESS	read-write
		STATUS		current
		DESCRIPTION	"
			style='Radiobutton list'
			preset='off'
			path='/Dolby 2 Encoder/Dolby 2 Encoder/Tone'
		"
		::= { alchemistHd3GCtrlEntries 7282 }

	dolbyEncMute2 OBJECT-TYPE
		SYNTAX		INTEGER { disable(0), enable(1) }
		MAX-ACCESS	read-write
		STATUS		current
		DESCRIPTION	"
			style='Checkbox'
			range='0..1'
			path='/Dolby 2 Encoder/Dolby 2 Encoder/      Mute      '
		"
		::= { alchemistHd3GCtrlEntries 7283 }

	dolbyEncDelayOffset2 OBJECT-TYPE
		SYNTAX		Integer32 (0..250)
		MAX-ACCESS	read-write
		STATUS		current
		DESCRIPTION	"
			style='Numeric control'
			range='0mS..250mS'
			path='/Dolby 2 Encoder/Dolby 2 Encoder/Transcode Delay Offset'
		"
		::= { alchemistHd3GCtrlEntries 7284 }

	dolbyEncToneType1 OBJECT-TYPE
		SYNTAX		INTEGER {
					off(9),
					v1khz20Dbfs(0),
					v4khz20Dbfs(1),
					v1khz18Dbfs(2),
					v4khz18Dbfs(3),
					blits(4)
				}
		MAX-ACCESS	read-write
		STATUS		current
		DESCRIPTION	"
			style='Radiobutton list'
			preset='off'
			path='/Dolby 1 Encoder/Dolby 1 Encoder/Tone'
		"
		::= { alchemistHd3GCtrlEntries 7286 }

	dolbyEncMute1 OBJECT-TYPE
		SYNTAX		INTEGER { disable(0), enable(1) }
		MAX-ACCESS	read-write
		STATUS		current
		DESCRIPTION	"
			style='Checkbox'
			range='0..1'
			path='/Dolby 1 Encoder/Dolby 1 Encoder/      Mute      '
		"
		::= { alchemistHd3GCtrlEntries 7287 }

	aesFollowsEmba OBJECT-TYPE
		SYNTAX		INTEGER { disable(0), enable(1) }
		MAX-ACCESS	read-write
		STATUS		current
		DESCRIPTION	"
			style='Checkbox'
			range='0..1'
			path='/Audio Output EMB A/AES Out/Emb B/AES follows EMBA'
		"
		::= { alchemistHd3GCtrlEntries 9880 }

	dolbyDecFrameDelay1 OBJECT-TYPE
		SYNTAX		INTEGER {
					advanced(1),
					coTimed(0),
					delayed(2)
				}
		MAX-ACCESS	read-write
		STATUS		current
		DESCRIPTION	"
			style='Radiobutton list'
			preset='coTimed'
			path='/Dolby Decoder/Dolby Decoder/IP Alignment'
		"
		::= { alchemistHd3GCtrlEntries 9881 }

	dolbyEncFrameAdvance1 OBJECT-TYPE
		SYNTAX		INTEGER {
					advanced(1),
					coTimed(0),
					delayed(2)
				}
		MAX-ACCESS	read-write
		STATUS		current
		DESCRIPTION	"
			style='Radiobutton list'
			preset='coTimed'
			path='/Dolby 1 Encoder/Dolby 1 Encoder/OP Alignment'
		"
		::= { alchemistHd3GCtrlEntries 9882 }

	dolbyDecMonitorDecode1 OBJECT-TYPE
		SYNTAX		INTEGER { disable(0), enable(1) }
		MAX-ACCESS	read-write
		STATUS		current
		DESCRIPTION	"
			style='Checkbox'
			range='0..1'
			path='/Dolby Decoder/Dolby Decoder/Monitor Decode'
		"
		::= { alchemistHd3GCtrlEntries 9884 }

	dolbyDecMetadataSource1 OBJECT-TYPE
		SYNTAX		INTEGER {
					dolbyDecoder1(0),
					externalIn1(2)
				}
		MAX-ACCESS	read-write
		STATUS		current
		DESCRIPTION	"
			style='Radiobutton list'
			preset='dolbyDecoder1'
			path='/Decoded Metadata 1/Decoded Metadata 1/Metadata Decoder source'
		"
		::= { alchemistHd3GCtrlEntries 9885 }

	dolbyDecProgramConfig1 OBJECT-TYPE
		SYNTAX		RollCallString
		MAX-ACCESS	read-only
		STATUS		current
		DESCRIPTION	"
			style='ReadOnly string'
			path='/Dolby Decoder/Dolby Decoder/Program Config'
		"
		::= { alchemistHd3GCtrlEntries 9887 }

	embbFollowsEmba OBJECT-TYPE
		SYNTAX		INTEGER { disable(0), enable(1) }
		MAX-ACCESS	read-write
		STATUS		current
		DESCRIPTION	"
			style='Checkbox'
			range='0..1'
			path='/Audio Output EMB A/AES Out/Emb B/EMBB follows EMBA'
		"
		::= { alchemistHd3GCtrlEntries 9889 }

	dolbyDecFrameDelay2 OBJECT-TYPE
		SYNTAX		INTEGER {
					advanced(1),
					coTimed(0),
					delayed(2)
				}
		MAX-ACCESS	read-write
		STATUS		current
		DESCRIPTION	"
			style='Radiobutton list'
			preset='coTimed'
			path='/Dolby 2 Decoder/Dolby 2 Decoder/IP Alignment'
		"
		::= { alchemistHd3GCtrlEntries 9891 }

	dolbyEncFrameAdvance2 OBJECT-TYPE
		SYNTAX		INTEGER {
					advanced(1),
					coTimed(0),
					delayed(2)
				}
		MAX-ACCESS	read-write
		STATUS		current
		DESCRIPTION	"
			style='Radiobutton list'
			preset='coTimed'
			path='/Dolby 2 Encoder/Dolby 2 Encoder/OP Alignment'
		"
		::= { alchemistHd3GCtrlEntries 9892 }

	dolbyDecMonitorDecode2 OBJECT-TYPE
		SYNTAX		INTEGER { disable(0), enable(1) }
		MAX-ACCESS	read-write
		STATUS		current
		DESCRIPTION	"
			style='Checkbox'
			range='0..1'
			path='/Dolby 2 Decoder/Dolby 2 Decoder/Monitor Decode'
		"
		::= { alchemistHd3GCtrlEntries 9894 }

	dolbyDecMetadataSource2 OBJECT-TYPE
		SYNTAX		INTEGER {
					dolbyDecoder2(1),
					externalIn2(3)
				}
		MAX-ACCESS	read-write
		STATUS		current
		DESCRIPTION	"
			style='Radiobutton list'
			preset='dolbyDecoder2'
			path='/Decoded Metadata 2/Decoded Metadata 2/Metadata Decoder source'
		"
		::= { alchemistHd3GCtrlEntries 9895 }

	dolbyDecProgramConfig2 OBJECT-TYPE
		SYNTAX		RollCallString
		MAX-ACCESS	read-only
		STATUS		current
		DESCRIPTION	"
			style='ReadOnly string'
			path='/Dolby 2 Decoder/Dolby 2 Decoder/Program Config...2'
		"
		::= { alchemistHd3GCtrlEntries 9897 }

	audioInputSrc10 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb1Ch1'
			path='/Audio Output EMB A/partial_audio_routing_1/Audio Pair 1/Output A EMB 1 Ch 1'
		"
		::= { alchemistHd3GCtrlEntries 13300 }

	audioInputSrc11 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb1Ch2'
			path='/Audio Output EMB A/partial_audio_routing_1/Audio Pair 1/Output A EMB 1 Ch 2'
		"
		::= { alchemistHd3GCtrlEntries 13301 }

	audioPairInputType1 OBJECT-TYPE
		SYNTAX		INTEGER { disable(0), enable(1) }
		MAX-ACCESS	read-write
		STATUS		current
		DESCRIPTION	"
			style='Checkbox'
			path='/Audio Inputs/Embedded Audio Inputs/Emb In Pair 1 Data Mode'
		"
		::= { alchemistHd3GCtrlEntries 13302 }

	audioInputSrc20 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb2Ch1'
			path='/Audio Output EMB A/partial_audio_routing_2/Audio Pair 2/Output A EMB 2 Ch 1'
		"
		::= { alchemistHd3GCtrlEntries 13303 }

	audioInputSrc21 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb2Ch2'
			path='/Audio Output EMB A/partial_audio_routing_2/Audio Pair 2/Output A EMB 2 Ch 2'
		"
		::= { alchemistHd3GCtrlEntries 13304 }

	audioPairInputType2 OBJECT-TYPE
		SYNTAX		INTEGER { disable(0), enable(1) }
		MAX-ACCESS	read-write
		STATUS		current
		DESCRIPTION	"
			style='Checkbox'
			path='/Audio Inputs/Embedded Audio Inputs/Emb In Pair 2 Data Mode'
		"
		::= { alchemistHd3GCtrlEntries 13305 }

	audioInputSrc30 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb3Ch1'
			path='/Audio Output EMB A/partial_audio_routing_3/Audio Pair 3/Output A EMB 3 Ch 1'
		"
		::= { alchemistHd3GCtrlEntries 13306 }

	audioInputSrc31 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb3Ch2'
			path='/Audio Output EMB A/partial_audio_routing_3/Audio Pair 3/Output A EMB 3 Ch 2'
		"
		::= { alchemistHd3GCtrlEntries 13307 }

	audioPairInputType3 OBJECT-TYPE
		SYNTAX		INTEGER { disable(0), enable(1) }
		MAX-ACCESS	read-write
		STATUS		current
		DESCRIPTION	"
			style='Checkbox'
			path='/Audio Inputs/Embedded Audio Inputs/Emb In Pair 3 Data Mode'
		"
		::= { alchemistHd3GCtrlEntries 13308 }

	audioInputSrc40 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb4Ch1'
			path='/Audio Output EMB A/partial_audio_routing_4/Audio Pair 4/Output A EMB 4 Ch 1'
		"
		::= { alchemistHd3GCtrlEntries 13309 }

	audioInputSrc41 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb4Ch2'
			path='/Audio Output EMB A/partial_audio_routing_4/Audio Pair 4/Output A EMB 4 Ch 2'
		"
		::= { alchemistHd3GCtrlEntries 13310 }

	audioPairInputType4 OBJECT-TYPE
		SYNTAX		INTEGER { disable(0), enable(1) }
		MAX-ACCESS	read-write
		STATUS		current
		DESCRIPTION	"
			style='Checkbox'
			path='/Audio Inputs/Embedded Audio Inputs/Emb In Pair 4 Data Mode'
		"
		::= { alchemistHd3GCtrlEntries 13311 }

	audioInputSrc50 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb5Ch1'
			path='/Audio Output EMB A/partial_audio_routing_5/Audio Pair 5/Output A EMB 5 Ch 1'
		"
		::= { alchemistHd3GCtrlEntries 13312 }

	audioInputSrc51 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb5Ch2'
			path='/Audio Output EMB A/partial_audio_routing_5/Audio Pair 5/Output A EMB 5 Ch 2'
		"
		::= { alchemistHd3GCtrlEntries 13313 }

	audioPairInputType5 OBJECT-TYPE
		SYNTAX		INTEGER { disable(0), enable(1) }
		MAX-ACCESS	read-write
		STATUS		current
		DESCRIPTION	"
			style='Checkbox'
			path='/Audio Inputs/Embedded Audio Inputs/Emb In Pair 5 Data Mode'
		"
		::= { alchemistHd3GCtrlEntries 13314 }

	audioInputSrc60 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb6Ch1'
			path='/Audio Output EMB A/partial_audio_routing_6/Audio Pair 6/Output A EMB 6 Ch 1'
		"
		::= { alchemistHd3GCtrlEntries 13315 }

	audioInputSrc61 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb6Ch2'
			path='/Audio Output EMB A/partial_audio_routing_6/Audio Pair 6/Output A EMB 6 Ch 2'
		"
		::= { alchemistHd3GCtrlEntries 13316 }

	audioPairInputType6 OBJECT-TYPE
		SYNTAX		INTEGER { disable(0), enable(1) }
		MAX-ACCESS	read-write
		STATUS		current
		DESCRIPTION	"
			style='Checkbox'
			path='/Audio Inputs/Embedded Audio Inputs/Emb In Pair 6 Data Mode'
		"
		::= { alchemistHd3GCtrlEntries 13317 }

	audioInputSrc70 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb7Ch1'
			path='/Audio Output EMB A/partial_audio_routing_7/Audio Pair 7/Output A EMB 7 Ch 1'
		"
		::= { alchemistHd3GCtrlEntries 13318 }

	audioInputSrc71 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb7Ch2'
			path='/Audio Output EMB A/partial_audio_routing_7/Audio Pair 7/Output A EMB 7 Ch 2'
		"
		::= { alchemistHd3GCtrlEntries 13319 }

	audioPairInputType7 OBJECT-TYPE
		SYNTAX		INTEGER { disable(0), enable(1) }
		MAX-ACCESS	read-write
		STATUS		current
		DESCRIPTION	"
			style='Checkbox'
			path='/Audio Inputs/Embedded Audio Inputs/Emb In Pair 7 Data Mode'
		"
		::= { alchemistHd3GCtrlEntries 13320 }

	audioInputSrc80 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb8Ch1'
			path='/Audio Output EMB A/partial_audio_routing_8/Audio Pair 8/Output A EMB 8 Ch 1'
		"
		::= { alchemistHd3GCtrlEntries 13321 }

	audioInputSrc81 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb8Ch2'
			path='/Audio Output EMB A/partial_audio_routing_8/Audio Pair 8/Output A EMB 8 Ch 2'
		"
		::= { alchemistHd3GCtrlEntries 13322 }

	audioPairInputType8 OBJECT-TYPE
		SYNTAX		INTEGER { disable(0), enable(1) }
		MAX-ACCESS	read-write
		STATUS		current
		DESCRIPTION	"
			style='Checkbox'
			path='/Audio Inputs/Embedded Audio Inputs/Emb In Pair 8 Data Mode'
		"
		::= { alchemistHd3GCtrlEntries 13323 }

	audioInputSrc90 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb1Ch1'
			path='/Audio Output EMB B/partial_audio_routing_9/Audio Pair 1/Output B EMB 1 Ch 1'
		"
		::= { alchemistHd3GCtrlEntries 13400 }

	audioInputSrc91 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb1Ch2'
			path='/Audio Output EMB B/partial_audio_routing_9/Audio Pair 1/Output B EMB 1 Ch 2'
		"
		::= { alchemistHd3GCtrlEntries 13401 }

	audioPairInputType9 OBJECT-TYPE
		SYNTAX		INTEGER { disable(0), enable(1) }
		MAX-ACCESS	read-write
		STATUS		current
		DESCRIPTION	"
			style='Checkbox'
			path='/Audio Inputs/AES Audio Inputs/AES In Pair 1 Data Mode'
		"
		::= { alchemistHd3GCtrlEntries 13402 }

	audioInputSrc100 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb2Ch1'
			path='/Audio Output EMB B/partial_audio_routing_10/Audio Pair 2/Output B EMB 2 Ch 1'
		"
		::= { alchemistHd3GCtrlEntries 13403 }

	audioInputSrc101 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb2Ch2'
			path='/Audio Output EMB B/partial_audio_routing_10/Audio Pair 2/Output B EMB 2 Ch 2'
		"
		::= { alchemistHd3GCtrlEntries 13404 }

	audioPairInputType10 OBJECT-TYPE
		SYNTAX		INTEGER { disable(0), enable(1) }
		MAX-ACCESS	read-write
		STATUS		current
		DESCRIPTION	"
			style='Checkbox'
			path='/Audio Inputs/AES Audio Inputs/AES In Pair 2 Data Mode'
		"
		::= { alchemistHd3GCtrlEntries 13405 }

	audioInputSrc110 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb3Ch1'
			path='/Audio Output EMB B/partial_audio_routing_11/Audio Pair 3/Output B EMB 3 Ch 1'
		"
		::= { alchemistHd3GCtrlEntries 13406 }

	audioInputSrc111 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb3Ch2'
			path='/Audio Output EMB B/partial_audio_routing_11/Audio Pair 3/Output B EMB 3 Ch 2'
		"
		::= { alchemistHd3GCtrlEntries 13407 }

	audioPairInputType11 OBJECT-TYPE
		SYNTAX		INTEGER { disable(0), enable(1) }
		MAX-ACCESS	read-write
		STATUS		current
		DESCRIPTION	"
			style='Checkbox'
			path='/Audio Inputs/AES Audio Inputs/AES In Pair 3 Data Mode'
		"
		::= { alchemistHd3GCtrlEntries 13408 }

	audioInputSrc120 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb4Ch1'
			path='/Audio Output EMB B/partial_audio_routing_12/Audio Pair 4/Output B EMB 4 Ch 1'
		"
		::= { alchemistHd3GCtrlEntries 13409 }

	audioInputSrc121 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb4Ch2'
			path='/Audio Output EMB B/partial_audio_routing_12/Audio Pair 4/Output B EMB 4 Ch 2'
		"
		::= { alchemistHd3GCtrlEntries 13410 }

	audioPairInputType12 OBJECT-TYPE
		SYNTAX		INTEGER { disable(0), enable(1) }
		MAX-ACCESS	read-write
		STATUS		current
		DESCRIPTION	"
			style='Checkbox'
			path='/Audio Inputs/AES Audio Inputs/AES In Pair 4 Data Mode'
		"
		::= { alchemistHd3GCtrlEntries 13411 }

	audioInputSrc130 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb5Ch1'
			path='/Audio Output EMB B/partial_audio_routing_13/Audio Pair 5/Output B EMB 5 Ch 1'
		"
		::= { alchemistHd3GCtrlEntries 13412 }

	audioInputSrc131 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb5Ch2'
			path='/Audio Output EMB B/partial_audio_routing_13/Audio Pair 5/Output B EMB 5 Ch 2'
		"
		::= { alchemistHd3GCtrlEntries 13413 }

	audioPairInputType13 OBJECT-TYPE
		SYNTAX		INTEGER { disable(0), enable(1) }
		MAX-ACCESS	read-write
		STATUS		current
		DESCRIPTION	"
			style='Checkbox'
			path='/Audio Inputs/AES Audio Inputs/AES In Pair 5 Data Mode'
		"
		::= { alchemistHd3GCtrlEntries 13414 }

	audioInputSrc140 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb6Ch1'
			path='/Audio Output EMB B/partial_audio_routing_14/Audio Pair 6/Output B EMB 6 Ch 1'
		"
		::= { alchemistHd3GCtrlEntries 13415 }

	audioInputSrc141 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb6Ch2'
			path='/Audio Output EMB B/partial_audio_routing_14/Audio Pair 6/Output B EMB 6 Ch 2'
		"
		::= { alchemistHd3GCtrlEntries 13416 }

	audioPairInputType14 OBJECT-TYPE
		SYNTAX		INTEGER { disable(0), enable(1) }
		MAX-ACCESS	read-write
		STATUS		current
		DESCRIPTION	"
			style='Checkbox'
			path='/Audio Inputs/AES Audio Inputs/AES In Pair 6 Data Mode'
		"
		::= { alchemistHd3GCtrlEntries 13417 }

	audioInputSrc150 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb7Ch1'
			path='/Audio Output EMB B/partial_audio_routing_15/Audio Pair 7/Output B EMB 7 Ch 1'
		"
		::= { alchemistHd3GCtrlEntries 13418 }

	audioInputSrc151 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb7Ch2'
			path='/Audio Output EMB B/partial_audio_routing_15/Audio Pair 7/Output B EMB 7 Ch 2'
		"
		::= { alchemistHd3GCtrlEntries 13419 }

	audioPairInputType15 OBJECT-TYPE
		SYNTAX		INTEGER { disable(0), enable(1) }
		MAX-ACCESS	read-write
		STATUS		current
		DESCRIPTION	"
			style='Checkbox'
			path='/Audio Inputs/AES Audio Inputs/AES In Pair 7 Data Mode'
		"
		::= { alchemistHd3GCtrlEntries 13420 }

	audioInputSrc160 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb8Ch1'
			path='/Audio Output EMB B/partial_audio_routing_16/Audio Pair 8/Output B EMB 8 Ch 1'
		"
		::= { alchemistHd3GCtrlEntries 13421 }

	audioInputSrc161 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb8Ch2'
			path='/Audio Output EMB B/partial_audio_routing_16/Audio Pair 8/Output B EMB 8 Ch 2'
		"
		::= { alchemistHd3GCtrlEntries 13422 }

	audioPairInputType16 OBJECT-TYPE
		SYNTAX		INTEGER { disable(0), enable(1) }
		MAX-ACCESS	read-write
		STATUS		current
		DESCRIPTION	"
			style='Checkbox'
			path='/Audio Inputs/AES Audio Inputs/AES In Pair 8 Data Mode'
		"
		::= { alchemistHd3GCtrlEntries 13423 }

	audioInputSrc170 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes1Ch1'
			path='/Audio Output AES/partial_audio_routing_17/Audio Pair 1/Output AES 1 Ch 1'
		"
		::= { alchemistHd3GCtrlEntries 13500 }

	audioInputSrc171 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes1Ch2'
			path='/Audio Output AES/partial_audio_routing_17/Audio Pair 1/Output AES 1 Ch 2'
		"
		::= { alchemistHd3GCtrlEntries 13501 }

	audioInputSrc180 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes2Ch1'
			path='/Audio Output AES/partial_audio_routing_18/Audio Pair 2/Output AES 2 Ch 1'
		"
		::= { alchemistHd3GCtrlEntries 13503 }

	audioInputSrc181 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes2Ch2'
			path='/Audio Output AES/partial_audio_routing_18/Audio Pair 2/Output AES 2 Ch 2'
		"
		::= { alchemistHd3GCtrlEntries 13504 }

	audioInputSrc190 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes3Ch1'
			path='/Audio Output AES/partial_audio_routing_19/Audio Pair 3/Output AES 3 Ch 1'
		"
		::= { alchemistHd3GCtrlEntries 13506 }

	audioInputSrc191 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes3Ch2'
			path='/Audio Output AES/partial_audio_routing_19/Audio Pair 3/Output AES 3 Ch 2'
		"
		::= { alchemistHd3GCtrlEntries 13507 }

	audioInputSrc200 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes4Ch1'
			path='/Audio Output AES/partial_audio_routing_20/Audio Pair 4/Output AES 4 Ch 1'
		"
		::= { alchemistHd3GCtrlEntries 13509 }

	audioInputSrc201 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes4Ch2'
			path='/Audio Output AES/partial_audio_routing_20/Audio Pair 4/Output AES 4 Ch 2'
		"
		::= { alchemistHd3GCtrlEntries 13510 }

	audioInputSrc210 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes5Ch1'
			path='/Audio Output AES/partial_audio_routing_21/Audio Pair 5/Output AES Ch 1'
		"
		::= { alchemistHd3GCtrlEntries 13512 }

	audioInputSrc211 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes5Ch2'
			path='/Audio Output AES/partial_audio_routing_21/Audio Pair 5/Output AES 5 Ch 2'
		"
		::= { alchemistHd3GCtrlEntries 13513 }

	audioInputSrc220 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes6Ch1'
			path='/Audio Output AES/partial_audio_routing_22/Audio Pair 6/Output AES 6 Ch 1'
		"
		::= { alchemistHd3GCtrlEntries 13515 }

	audioInputSrc221 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes6Ch2'
			path='/Audio Output AES/partial_audio_routing_22/Audio Pair 6/Output AES 6 Ch 2'
		"
		::= { alchemistHd3GCtrlEntries 13516 }

	audioInputSrc230 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes7Ch1'
			path='/Audio Output AES/partial_audio_routing_23/Audio Pair 7/Output AES 7 Ch 1'
		"
		::= { alchemistHd3GCtrlEntries 13518 }

	audioInputSrc231 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes7Ch2'
			path='/Audio Output AES/partial_audio_routing_23/Audio Pair 7/Output AES 7 Ch 2'
		"
		::= { alchemistHd3GCtrlEntries 13519 }

	audioInputSrc240 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes8Ch1'
			path='/Audio Output AES/partial_audio_routing_24/Audio Pair 8/Output AES 8 Ch 1'
		"
		::= { alchemistHd3GCtrlEntries 13521 }

	audioInputSrc241 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='aes8Ch2'
			path='/Audio Output AES/partial_audio_routing_24/Audio Pair 8/Output AES 8 Ch 2'
		"
		::= { alchemistHd3GCtrlEntries 13522 }

	audioGain10 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 1/Channel 1/Gain'
		"
		::= { alchemistHd3GCtrlEntries 15700 }

	audioGain20 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 2/Channel 1/Gain'
		"
		::= { alchemistHd3GCtrlEntries 15701 }

	audioGain30 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 3/Channel 1/Gain'
		"
		::= { alchemistHd3GCtrlEntries 15702 }

	audioGain40 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 4/Channel 1/Gain'
		"
		::= { alchemistHd3GCtrlEntries 15703 }

	audioGain50 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 5/Channel 1/Gain'
		"
		::= { alchemistHd3GCtrlEntries 15704 }

	audioGain60 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 6/Channel 1/Gain'
		"
		::= { alchemistHd3GCtrlEntries 15705 }

	audioGain70 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 7/Channel 1/Gain'
		"
		::= { alchemistHd3GCtrlEntries 15706 }

	audioGain80 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 8/Channel 1/Gain'
		"
		::= { alchemistHd3GCtrlEntries 15707 }

	audioGain90 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 1/Channel 1/Gain'
		"
		::= { alchemistHd3GCtrlEntries 15708 }

	audioGain100 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 2/Channel 1/Gain'
		"
		::= { alchemistHd3GCtrlEntries 15709 }

	audioGain110 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 3/Channel 1/Gain'
		"
		::= { alchemistHd3GCtrlEntries 15710 }

	audioGain120 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 4/Channel 1/Gain'
		"
		::= { alchemistHd3GCtrlEntries 15711 }

	audioGain130 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 5/Channel 1/Gain'
		"
		::= { alchemistHd3GCtrlEntries 15712 }

	audioGain140 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 6/Channel 1/Gain'
		"
		::= { alchemistHd3GCtrlEntries 15713 }

	audioGain150 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 7/Channel 1/Gain'
		"
		::= { alchemistHd3GCtrlEntries 15714 }

	audioGain160 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 8/Channel 1/Gain'
		"
		::= { alchemistHd3GCtrlEntries 15715 }

	audioGain170 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 1/Channel 1/Gain'
		"
		::= { alchemistHd3GCtrlEntries 15716 }

	audioGain180 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 2/Channel 1/Gain'
		"
		::= { alchemistHd3GCtrlEntries 15717 }

	audioGain190 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 3/Channel 1/Gain'
		"
		::= { alchemistHd3GCtrlEntries 15718 }

	audioGain200 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 4/Channel 1/Gain'
		"
		::= { alchemistHd3GCtrlEntries 15719 }

	audioGain210 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 5/Channel 1/Gain'
		"
		::= { alchemistHd3GCtrlEntries 15720 }

	audioGain220 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 6/Channel 1/Gain'
		"
		::= { alchemistHd3GCtrlEntries 15721 }

	audioGain230 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 7/Channel 1/Gain'
		"
		::= { alchemistHd3GCtrlEntries 15722 }

	audioGain240 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 8/Channel 1/Gain'
		"
		::= { alchemistHd3GCtrlEntries 15723 }

	audioGain11 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 1/Channel 2/Gain'
		"
		::= { alchemistHd3GCtrlEntries 15730 }

	audioGain21 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 2/Channel 1/Gain'
		"
		::= { alchemistHd3GCtrlEntries 15731 }

	audioGain31 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 3/Channel 2/Gain'
		"
		::= { alchemistHd3GCtrlEntries 15732 }

	audioGain41 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 4/Channel 2/Gain'
		"
		::= { alchemistHd3GCtrlEntries 15733 }

	audioGain51 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 5/Channel 2/Gain'
		"
		::= { alchemistHd3GCtrlEntries 15734 }

	audioGain61 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 6/Channel 2/Gain'
		"
		::= { alchemistHd3GCtrlEntries 15735 }

	audioGain71 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 7/Channel 2/Gain'
		"
		::= { alchemistHd3GCtrlEntries 15736 }

	audioGain81 OBJECT-TYPE
		SYNTAX		Integer32 (-120..120)
		MAX-ACCESS	read-write
		STATUS		current
		DESCRIPTION	"
			style='Numeric control'
			range='-12.0dB..12.0dB'
			stepsize='0.1'
			path='/Audio Control/Audio Control A/Output A EMB 8/Channel 2/Gain'
		"
		::= { alchemistHd3GCtrlEntries 15737 }

	audioGain91 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 1/Channel 2/Gain'
		"
		::= { alchemistHd3GCtrlEntries 15738 }

	audioGain101 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 2/Channel 1/Gain'
		"
		::= { alchemistHd3GCtrlEntries 15739 }

	audioGain111 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 3/Channel 2/Gain'
		"
		::= { alchemistHd3GCtrlEntries 15740 }

	audioGain121 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 4/Channel 2/Gain'
		"
		::= { alchemistHd3GCtrlEntries 15741 }

	audioGain131 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 5/Channel 2/Gain'
		"
		::= { alchemistHd3GCtrlEntries 15742 }

	audioGain141 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 6/Channel 2/Gain'
		"
		::= { alchemistHd3GCtrlEntries 15743 }

	audioGain151 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 7/Channel 2/Gain'
		"
		::= { alchemistHd3GCtrlEntries 15744 }

	audioGain161 OBJECT-TYPE
		SYNTAX		Integer32 (-120..120)
		MAX-ACCESS	read-write
		STATUS		current
		DESCRIPTION	"
			style='Numeric control'
			range='-12.0dB..12.0dB'
			stepsize='0.1'
			path='/Audio Control/Audio Control B/Output B EMB 8/Channel 2/Gain'
		"
		::= { alchemistHd3GCtrlEntries 15745 }

	audioGain171 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 1/Channel 2/Gain'
		"
		::= { alchemistHd3GCtrlEntries 15746 }

	audioGain181 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 2/Channel 1/Gain'
		"
		::= { alchemistHd3GCtrlEntries 15747 }

	audioGain191 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 3/Channel 2/Gain'
		"
		::= { alchemistHd3GCtrlEntries 15748 }

	audioGain201 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 4/Channel 2/Gain'
		"
		::= { alchemistHd3GCtrlEntries 15749 }

	audioGain211 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 5/Channel 2/Gain'
		"
		::= { alchemistHd3GCtrlEntries 15750 }

	audioGain221 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 6/Channel 2/Gain'
		"
		::= { alchemistHd3GCtrlEntries 15751 }

	audioGain231 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 7/Channel 2/Gain'
		"
		::= { alchemistHd3GCtrlEntries 15752 }

	audioGain241 OBJECT-TYPE
		SYNTAX		Integer32 (-120..120)
		MAX-ACCESS	read-write
		STATUS		current
		DESCRIPTION	"
			style='Numeric control'
			range='-12.0dB..12.0dB'
			stepsize='0.1'
			path='/Audio Control/Audio Control AES/AES Output 8/Channel 2/Gain'
		"
		::= { alchemistHd3GCtrlEntries 15753 }

	audioGainPreset10 OBJECT-TYPE
		SYNTAX		INTEGER { ready(0), trigger(1) }
		MAX-ACCESS	read-write
		STATUS		current
		DESCRIPTION	"
			style='Event button'
			path='/Audio Control/Audio Control A/Output A EMB 1/Preset'
		"
		::= { alchemistHd3GCtrlEntries 15760 }

	audioGainPreset20 OBJECT-TYPE
		SYNTAX		INTEGER { ready(0), trigger(1) }
		MAX-ACCESS	read-write
		STATUS		current
		DESCRIPTION	"
			style='Event button'
			path='/Audio Control/Audio Control A/Output A EMB 2/Preset'
		"
		::= { alchemistHd3GCtrlEntries 15761 }

	audioGainPreset30 OBJECT-TYPE
		SYNTAX		INTEGER { ready(0), trigger(1) }
		MAX-ACCESS	read-write
		STATUS		current
		DESCRIPTION	"
			style='Event button'
			path='/Audio Control/Audio Control A/Output A EMB 3/Preset'
		"
		::= { alchemistHd3GCtrlEntries 15762 }

	audioGainPreset40 OBJECT-TYPE
		SYNTAX		INTEGER { ready(0), trigger(1) }
		MAX-ACCESS	read-write
		STATUS		current
		DESCRIPTION	"
			style='Event button'
			path='/Audio Control/Audio Control A/Output A EMB 4/Preset'
		"
		::= { alchemistHd3GCtrlEntries 15763 }

	audioGainPreset50 OBJECT-TYPE
		SYNTAX		INTEGER { ready(0), trigger(1) }
		MAX-ACCESS	read-write
		STATUS		current
		DESCRIPTION	"
			style='Event button'
			path='/Audio Control/Audio Control A/Output A EMB 5/Preset'
		"
		::= { alchemistHd3GCtrlEntries 15764 }

	audioGainPreset60 OBJECT-TYPE
		SYNTAX		INTEGER { ready(0), trigger(1) }
		MAX-ACCESS	read-write
		STATUS		current
		DESCRIPTION	"
			style='Event button'
			path='/Audio Control/Audio Control A/Output A EMB 6/Preset'
		"
		::= { alchemistHd3GCtrlEntries 15765 }

	audioGainPreset70 OBJECT-TYPE
		SYNTAX		INTEGER { ready(0), trigger(1) }
		MAX-ACCESS	read-write
		STATUS		current
		DESCRIPTION	"
			style='Event button'
			path='/Audio Control/Audio Control A/Output A EMB 7/Preset'
		"
		::= { alchemistHd3GCtrlEntries 15766 }

	audioGainPreset80 OBJECT-TYPE
		SYNTAX		INTEGER { ready(0), trigger(1) }
		MAX-ACCESS	read-write
		STATUS		current
		DESCRIPTION	"
			style='Event button'
			path='/Audio Control/Audio Control A/Output A EMB 8/Preset'
		"
		::= { alchemistHd3GCtrlEntries 15767 }

	audioGainPreset90 OBJECT-TYPE
		SYNTAX		INTEGER { ready(0), trigger(1) }
		MAX-ACCESS	read-write
		STATUS		current
		DESCRIPTION	"
			style='Event button'
			path='/Audio Control/Audio Control B/Output B EMB 1/Preset'
		"
		::= { alchemistHd3GCtrlEntries 15768 }

	audioGainPreset100 OBJECT-TYPE
		SYNTAX		INTEGER { ready(0), trigger(1) }
		MAX-ACCESS	read-write
		STATUS		current
		DESCRIPTION	"
			style='Event button'
			path='/Audio Control/Audio Control B/Output B EMB 2/Preset'
		"
		::= { alchemistHd3GCtrlEntries 15769 }

	audioGainPreset110 OBJECT-TYPE
		SYNTAX		INTEGER { ready(0), trigger(1) }
		MAX-ACCESS	read-write
		STATUS		current
		DESCRIPTION	"
			style='Event button'
			path='/Audio Control/Audio Control B/Output B EMB 3/Preset'
		"
		::= { alchemistHd3GCtrlEntries 15770 }

	audioGainPreset120 OBJECT-TYPE
		SYNTAX		INTEGER { ready(0), trigger(1) }
		MAX-ACCESS	read-write
		STATUS		current
		DESCRIPTION	"
			style='Event button'
			path='/Audio Control/Audio Control B/Output B EMB 4/Preset'
		"
		::= { alchemistHd3GCtrlEntries 15771 }

	audioGainPreset130 OBJECT-TYPE
		SYNTAX		INTEGER { ready(0), trigger(1) }
		MAX-ACCESS	read-write
		STATUS		current
		DESCRIPTION	"
			style='Event button'
			path='/Audio Control/Audio Control B/Output B EMB 5/Preset'
		"
		::= { alchemistHd3GCtrlEntries 15772 }

	audioGainPreset140 OBJECT-TYPE
		SYNTAX		INTEGER { ready(0), trigger(1) }
		MAX-ACCESS	read-write
		STATUS		current
		DESCRIPTION	"
			style='Event button'
			path='/Audio Control/Audio Control B/Output B EMB 6/Preset'
		"
		::= { alchemistHd3GCtrlEntries 15773 }

	audioGainPreset150 OBJECT-TYPE
		SYNTAX		INTEGER { ready(0), trigger(1) }
		MAX-ACCESS	read-write
		STATUS		current
		DESCRIPTION	"
			style='Event button'
			path='/Audio Control/Audio Control B/Output B EMB 7/Preset'
		"
		::= { alchemistHd3GCtrlEntries 15774 }

	audioGainPreset160 OBJECT-TYPE
		SYNTAX		INTEGER { ready(0), trigger(1) }
		MAX-ACCESS	read-write
		STATUS		current
		DESCRIPTION	"
			style='Event button'
			path='/Audio Control/Audio Control B/Output B EMB 8/Preset'
		"
		::= { alchemistHd3GCtrlEntries 15775 }

	audioGainPreset170 OBJECT-TYPE
		SYNTAX		INTEGER { ready(0), trigger(1) }
		MAX-ACCESS	read-write
		STATUS		current
		DESCRIPTION	"
			style='Event button'
			path='/Audio Control/Audio Control AES/AES Output 1/Preset'
		"
		::= { alchemistHd3GCtrlEntries 15776 }

	audioGainPreset180 OBJECT-TYPE
		SYNTAX		INTEGER { ready(0), trigger(1) }
		MAX-ACCESS	read-write
		STATUS		current
		DESCRIPTION	"
			style='Event button'
			path='/Audio Control/Audio Control AES/AES Output 2/Preset'
		"
		::= { alchemistHd3GCtrlEntries 15777 }

	audioGainPreset190 OBJECT-TYPE
		SYNTAX		INTEGER { ready(0), trigger(1) }
		MAX-ACCESS	read-write
		STATUS		current
		DESCRIPTION	"
			style='Event button'
			path='/Audio Control/Audio Control AES/AES Output 3/Preset'
		"
		::= { alchemistHd3GCtrlEntries 15778 }

	audioGainPreset200 OBJECT-TYPE
		SYNTAX		INTEGER { ready(0), trigger(1) }
		MAX-ACCESS	read-write
		STATUS		current
		DESCRIPTION	"
			style='Event button'
			path='/Audio Control/Audio Control AES/AES Output 4/Preset'
		"
		::= { alchemistHd3GCtrlEntries 15779 }

	audioGainPreset210 OBJECT-TYPE
		SYNTAX		INTEGER { ready(0), trigger(1) }
		MAX-ACCESS	read-write
		STATUS		current
		DESCRIPTION	"
			style='Event button'
			path='/Audio Control/Audio Control AES/AES Output 5/Preset'
		"
		::= { alchemistHd3GCtrlEntries 15780 }

	audioGainPreset220 OBJECT-TYPE
		SYNTAX		INTEGER { ready(0), trigger(1) }
		MAX-ACCESS	read-write
		STATUS		current
		DESCRIPTION	"
			style='Event button'
			path='/Audio Control/Audio Control AES/AES Output 6/Preset'
		"
		::= { alchemistHd3GCtrlEntries 15781 }

	audioGainPreset230 OBJECT-TYPE
		SYNTAX		INTEGER { ready(0), trigger(1) }
		MAX-ACCESS	read-write
		STATUS		current
		DESCRIPTION	"
			style='Event button'
			path='/Audio Control/Audio Control AES/AES Output 7/Preset'
		"
		::= { alchemistHd3GCtrlEntries 15782 }

	audioGainPreset240 OBJECT-TYPE
		SYNTAX		INTEGER { ready(0), trigger(1) }
		MAX-ACCESS	read-write
		STATUS		current
		DESCRIPTION	"
			style='Event button'
			path='/Audio Control/Audio Control AES/AES Output 8/Preset'
		"
		::= { alchemistHd3GCtrlEntries 15783 }

	audioGainPreset11 OBJECT-TYPE
		SYNTAX		INTEGER { ready(0), trigger(1) }
		MAX-ACCESS	read-write
		STATUS		current
		DESCRIPTION	"
			style='Event button'
			path='/Audio Control/Audio Control A/Output A EMB 1/Preset'
		"
		::= { alchemistHd3GCtrlEntries 15790 }

	audioGainPreset21 OBJECT-TYPE
		SYNTAX		INTEGER { ready(0), trigger(1) }
		MAX-ACCESS	read-write
		STATUS		current
		DESCRIPTION	"
			style='Event button'
			path='/Audio Control/Audio Control A/Output A EMB 2/Preset'
		"
		::= { alchemistHd3GCtrlEntries 15791 }

	audioGainPreset31 OBJECT-TYPE
		SYNTAX		INTEGER { ready(0), trigger(1) }
		MAX-ACCESS	read-write
		STATUS		current
		DESCRIPTION	"
			style='Event button'
			path='/Audio Control/Audio Control A/Output A EMB 3/Preset'
		"
		::= { alchemistHd3GCtrlEntries 15792 }

	audioGainPreset41 OBJECT-TYPE
		SYNTAX		INTEGER { ready(0), trigger(1) }
		MAX-ACCESS	read-write
		STATUS		current
		DESCRIPTION	"
			style='Event button'
			path='/Audio Control/Audio Control A/Output A EMB 4/Preset'
		"
		::= { alchemistHd3GCtrlEntries 15793 }

	audioGainPreset51 OBJECT-TYPE
		SYNTAX		INTEGER { ready(0), trigger(1) }
		MAX-ACCESS	read-write
		STATUS		current
		DESCRIPTION	"
			style='Event button'
			path='/Audio Control/Audio Control A/Output A EMB 5/Preset'
		"
		::= { alchemistHd3GCtrlEntries 15794 }

	audioGainPreset61 OBJECT-TYPE
		SYNTAX		INTEGER { ready(0), trigger(1) }
		MAX-ACCESS	read-write
		STATUS		current
		DESCRIPTION	"
			style='Event button'
			path='/Audio Control/Audio Control A/Output A EMB 6/Preset'
		"
		::= { alchemistHd3GCtrlEntries 15795 }

	audioGainPreset71 OBJECT-TYPE
		SYNTAX		INTEGER { ready(0), trigger(1) }
		MAX-ACCESS	read-write
		STATUS		current
		DESCRIPTION	"
			style='Event button'
			path='/Audio Control/Audio Control A/Output A EMB 7/Preset'
		"
		::= { alchemistHd3GCtrlEntries 15796 }

	audioGainPreset81 OBJECT-TYPE
		SYNTAX		INTEGER { ready(0), trigger(1) }
		MAX-ACCESS	read-write
		STATUS		current
		DESCRIPTION	"
			style='Event button'
			path='/Audio Control/Audio Control A/Output A EMB 8/Preset'
		"
		::= { alchemistHd3GCtrlEntries 15797 }

	audioGainPreset91 OBJECT-TYPE
		SYNTAX		INTEGER { ready(0), trigger(1) }
		MAX-ACCESS	read-write
		STATUS		current
		DESCRIPTION	"
			style='Event button'
			path='/Audio Control/Audio Control B/Output B EMB 1/Preset'
		"
		::= { alchemistHd3GCtrlEntries 15798 }

	audioGainPreset101 OBJECT-TYPE
		SYNTAX		INTEGER { ready(0), trigger(1) }
		MAX-ACCESS	read-write
		STATUS		current
		DESCRIPTION	"
			style='Event button'
			path='/Audio Control/Audio Control B/Output B EMB 2/Preset'
		"
		::= { alchemistHd3GCtrlEntries 15799 }

	audioGainPreset111 OBJECT-TYPE
		SYNTAX		INTEGER { ready(0), trigger(1) }
		MAX-ACCESS	read-write
		STATUS		current
		DESCRIPTION	"
			style='Event button'
			path='/Audio Control/Audio Control B/Output B EMB 3/Preset'
		"
		::= { alchemistHd3GCtrlEntries 15800 }

	audioGainPreset121 OBJECT-TYPE
		SYNTAX		INTEGER { ready(0), trigger(1) }
		MAX-ACCESS	read-write
		STATUS		current
		DESCRIPTION	"
			style='Event button'
			path='/Audio Control/Audio Control B/Output B EMB 4/Preset'
		"
		::= { alchemistHd3GCtrlEntries 15801 }

	audioGainPreset131 OBJECT-TYPE
		SYNTAX		INTEGER { ready(0), trigger(1) }
		MAX-ACCESS	read-write
		STATUS		current
		DESCRIPTION	"
			style='Event button'
			path='/Audio Control/Audio Control B/Output B EMB 5/Preset'
		"
		::= { alchemistHd3GCtrlEntries 15802 }

	audioGainPreset141 OBJECT-TYPE
		SYNTAX		INTEGER { ready(0), trigger(1) }
		MAX-ACCESS	read-write
		STATUS		current
		DESCRIPTION	"
			style='Event button'
			path='/Audio Control/Audio Control B/Output B EMB 6/Preset'
		"
		::= { alchemistHd3GCtrlEntries 15803 }

	audioGainPreset151 OBJECT-TYPE
		SYNTAX		INTEGER { ready(0), trigger(1) }
		MAX-ACCESS	read-write
		STATUS		current
		DESCRIPTION	"
			style='Event button'
			path='/Audio Control/Audio Control B/Output B EMB 7/Preset'
		"
		::= { alchemistHd3GCtrlEntries 15804 }

	audioGainPreset161 OBJECT-TYPE
		SYNTAX		INTEGER { ready(0), trigger(1) }
		MAX-ACCESS	read-write
		STATUS		current
		DESCRIPTION	"
			style='Event button'
			path='/Audio Control/Audio Control B/Output B EMB 8/Preset'
		"
		::= { alchemistHd3GCtrlEntries 15805 }

	audioGainPreset171 OBJECT-TYPE
		SYNTAX		INTEGER { ready(0), trigger(1) }
		MAX-ACCESS	read-write
		STATUS		current
		DESCRIPTION	"
			style='Event button'
			path='/Audio Control/Audio Control AES/AES Output 1/Preset'
		"
		::= { alchemistHd3GCtrlEntries 15806 }

	audioGainPreset181 OBJECT-TYPE
		SYNTAX		INTEGER { ready(0), trigger(1) }
		MAX-ACCESS	read-write
		STATUS		current
		DESCRIPTION	"
			style='Event button'
			path='/Audio Control/Audio Control AES/AES Output 2/Preset'
		"
		::= { alchemistHd3GCtrlEntries 15807 }

	audioGainPreset191 OBJECT-TYPE
		SYNTAX		INTEGER { ready(0), trigger(1) }
		MAX-ACCESS	read-write
		STATUS		current
		DESCRIPTION	"
			style='Event button'
			path='/Audio Control/Audio Control AES/AES Output 3/Preset'
		"
		::= { alchemistHd3GCtrlEntries 15808 }

	audioGainPreset201 OBJECT-TYPE
		SYNTAX		INTEGER { ready(0), trigger(1) }
		MAX-ACCESS	read-write
		STATUS		current
		DESCRIPTION	"
			style='Event button'
			path='/Audio Control/Audio Control AES/AES Output 4/Preset'
		"
		::= { alchemistHd3GCtrlEntries 15809 }

	audioGainPreset211 OBJECT-TYPE
		SYNTAX		INTEGER { ready(0), trigger(1) }
		MAX-ACCESS	read-write
		STATUS		current
		DESCRIPTION	"
			style='Event button'
			path='/Audio Control/Audio Control AES/AES Output 5/Preset'
		"
		::= { alchemistHd3GCtrlEntries 15810 }

	audioGainPreset221 OBJECT-TYPE
		SYNTAX		INTEGER { ready(0), trigger(1) }
		MAX-ACCESS	read-write
		STATUS		current
		DESCRIPTION	"
			style='Event button'
			path='/Audio Control/Audio Control AES/AES Output 6/Preset'
		"
		::= { alchemistHd3GCtrlEntries 15811 }

	audioGainPreset231 OBJECT-TYPE
		SYNTAX		INTEGER { ready(0), trigger(1) }
		MAX-ACCESS	read-write
		STATUS		current
		DESCRIPTION	"
			style='Event button'
			path='/Audio Control/Audio Control AES/AES Output 7/Preset'
		"
		::= { alchemistHd3GCtrlEntries 15812 }

	audioGainPreset241 OBJECT-TYPE
		SYNTAX		INTEGER { ready(0), trigger(1) }
		MAX-ACCESS	read-write
		STATUS		current
		DESCRIPTION	"
			style='Event button'
			path='/Audio Control/Audio Control AES/AES Output 8/Preset'
		"
		::= { alchemistHd3GCtrlEntries 15813 }

	audioGainTrack10 OBJECT-TYPE
		SYNTAX		INTEGER { disable(0), enable(1) }
		MAX-ACCESS	read-write
		STATUS		current
		DESCRIPTION	"
			style='Checkbox'
			range='0..1'
			path='/Audio Control/Audio Control A/Output A EMB 1/Channel 1/Gain Track'
		"
		::= { alchemistHd3GCtrlEntries 15850 }

	audioGainTrack20 OBJECT-TYPE
		SYNTAX		INTEGER { disable(0), enable(1) }
		MAX-ACCESS	read-write
		STATUS		current
		DESCRIPTION	"
			style='Checkbox'
			range='0..1'
			path='/Audio Control/Audio Control A/Output A EMB 2/Channel 1/Gain Track'
		"
		::= { alchemistHd3GCtrlEntries 15851 }

	audioGainTrack30 OBJECT-TYPE
		SYNTAX		INTEGER { disable(0), enable(1) }
		MAX-ACCESS	read-write
		STATUS		current
		DESCRIPTION	"
			style='Checkbox'
			range='0..1'
			path='/Audio Control/Audio Control A/Output A EMB 3/Channel 1/Gain Track'
		"
		::= { alchemistHd3GCtrlEntries 15852 }

	audioGainTrack40 OBJECT-TYPE
		SYNTAX		INTEGER { disable(0), enable(1) }
		MAX-ACCESS	read-write
		STATUS		current
		DESCRIPTION	"
			style='Checkbox'
			range='0..1'
			path='/Audio Control/Audio Control A/Output A EMB 4/Channel 1/Gain Track'
		"
		::= { alchemistHd3GCtrlEntries 15853 }

	audioGainTrack50 OBJECT-TYPE
		SYNTAX		INTEGER { disable(0), enable(1) }
		MAX-ACCESS	read-write
		STATUS		current
		DESCRIPTION	"
			style='Checkbox'
			range='0..1'
			path='/Audio Control/Audio Control A/Output A EMB 5/Channel 1/Gain Track'
		"
		::= { alchemistHd3GCtrlEntries 15854 }

	audioGainTrack60 OBJECT-TYPE
		SYNTAX		INTEGER { disable(0), enable(1) }
		MAX-ACCESS	read-write
		STATUS		current
		DESCRIPTION	"
			style='Checkbox'
			range='0..1'
			path='/Audio Control/Audio Control A/Output A EMB 6/Channel 1/Gain Track'
		"
		::= { alchemistHd3GCtrlEntries 15855 }

	audioGainTrack70 OBJECT-TYPE
		SYNTAX		INTEGER { disable(0), enable(1) }
		MAX-ACCESS	read-write
		STATUS		current
		DESCRIPTION	"
			style='Checkbox'
			range='0..1'
			path='/Audio Control/Audio Control A/Output A EMB 7/Channel 1/Gain Track'
		"
		::= { alchemistHd3GCtrlEntries 15856 }

	audioGainTrack80 OBJECT-TYPE
		SYNTAX		INTEGER { disable(0), enable(1) }
		MAX-ACCESS	read-write
		STATUS		current
		DESCRIPTION	"
			style='Checkbox'
			range='0..1'
			path='/Audio Control/Audio Control A/Output A EMB 8/Channel 1/Gain Track'
		"
		::= { alchemistHd3GCtrlEntries 15857 }

	audioGainTrack90 OBJECT-TYPE
		SYNTAX		INTEGER { disable(0), enable(1) }
		MAX-ACCESS	read-write
		STATUS		current
		DESCRIPTION	"
			style='Checkbox'
			range='0..1'
			path='/Audio Control/Audio Control B/Output B EMB 1/Channel 1/Gain Track'
		"
		::= { alchemistHd3GCtrlEntries 15858 }

	audioGainTrack100 OBJECT-TYPE
		SYNTAX		INTEGER { disable(0), enable(1) }
		MAX-ACCESS	read-write
		STATUS		current
		DESCRIPTION	"
			style='Checkbox'
			range='0..1'
			path='/Audio Control/Audio Control B/Output B EMB 2/Channel 1/Gain Track'
		"
		::= { alchemistHd3GCtrlEntries 15859 }

	audioGainTrack110 OBJECT-TYPE
		SYNTAX		INTEGER { disable(0), enable(1) }
		MAX-ACCESS	read-write
		STATUS		current
		DESCRIPTION	"
			style='Checkbox'
			range='0..1'
			path='/Audio Control/Audio Control B/Output B EMB 3/Channel 1/Gain Track'
		"
		::= { alchemistHd3GCtrlEntries 15860 }

	audioGainTrack120 OBJECT-TYPE
		SYNTAX		INTEGER { disable(0), enable(1) }
		MAX-ACCESS	read-write
		STATUS		current
		DESCRIPTION	"
			style='Checkbox'
			range='0..1'
			path='/Audio Control/Audio Control B/Output B EMB 4/Channel 1/Gain Track'
		"
		::= { alchemistHd3GCtrlEntries 15861 }

	audioGainTrack130 OBJECT-TYPE
		SYNTAX		INTEGER { disable(0), enable(1) }
		MAX-ACCESS	read-write
		STATUS		current
		DESCRIPTION	"
			style='Checkbox'
			range='0..1'
			path='/Audio Control/Audio Control B/Output B EMB 5/Channel 1/Gain Track'
		"
		::= { alchemistHd3GCtrlEntries 15862 }

	audioGainTrack140 OBJECT-TYPE
		SYNTAX		INTEGER { disable(0), enable(1) }
		MAX-ACCESS	read-write
		STATUS		current
		DESCRIPTION	"
			style='Checkbox'
			range='0..1'
			path='/Audio Control/Audio Control B/Output B EMB 6/Channel 1/Gain Track'
		"
		::= { alchemistHd3GCtrlEntries 15863 }

	audioGainTrack150 OBJECT-TYPE
		SYNTAX		INTEGER { disable(0), enable(1) }
		MAX-ACCESS	read-write
		STATUS		current
		DESCRIPTION	"
			style='Checkbox'
			range='0..1'
			path='/Audio Control/Audio Control B/Output B EMB 7/Channel 1/Gain Track'
		"
		::= { alchemistHd3GCtrlEntries 15864 }

	audioGainTrack160 OBJECT-TYPE
		SYNTAX		INTEGER { disable(0), enable(1) }
		MAX-ACCESS	read-write
		STATUS		current
		DESCRIPTION	"
			style='Checkbox'
			range='0..1'
			path='/Audio Control/Audio Control B/Output B EMB 8/Channel 1/Gain Track'
		"
		::= { alchemistHd3GCtrlEntries 15865 }

	audioGainTrack170 OBJECT-TYPE
		SYNTAX		INTEGER { disable(0), enable(1) }
		MAX-ACCESS	read-write
		STATUS		current
		DESCRIPTION	"
			style='Checkbox'
			range='0..1'
			path='/Audio Control/Audio Control AES/AES Output 1/Channel 1/Gain Track'
		"
		::= { alchemistHd3GCtrlEntries 15866 }

	audioGainTrack180 OBJECT-TYPE
		SYNTAX		INTEGER { disable(0), enable(1) }
		MAX-ACCESS	read-write
		STATUS		current
		DESCRIPTION	"
			style='Checkbox'
			range='0..1'
			path='/Audio Control/Audio Control AES/AES Output 2/Channel 1/Gain Track'
		"
		::= { alchemistHd3GCtrlEntries 15867 }

	audioGainTrack190 OBJECT-TYPE
		SYNTAX		INTEGER { disable(0), enable(1) }
		MAX-ACCESS	read-write
		STATUS		current
		DESCRIPTION	"
			style='Checkbox'
			range='0..1'
			path='/Audio Control/Audio Control AES/AES Output 3/Channel 1/Gain Track'
		"
		::= { alchemistHd3GCtrlEntries 15868 }

	audioGainTrack200 OBJECT-TYPE
		SYNTAX		INTEGER { disable(0), enable(1) }
		MAX-ACCESS	read-write
		STATUS		current
		DESCRIPTION	"
			style='Checkbox'
			range='0..1'
			path='/Audio Control/Audio Control AES/AES Output 4/Channel 1/Gain Track'
		"
		::= { alchemistHd3GCtrlEntries 15869 }

	audioGainTrack210 OBJECT-TYPE
		SYNTAX		INTEGER { disable(0), enable(1) }
		MAX-ACCESS	read-write
		STATUS		current
		DESCRIPTION	"
			style='Checkbox'
			range='0..1'
			path='/Audio Control/Audio Control AES/AES Output 5/Channel 1/Gain Track'
		"
		::= { alchemistHd3GCtrlEntries 15870 }

	audioGainTrack220 OBJECT-TYPE
		SYNTAX		INTEGER { disable(0), enable(1) }
		MAX-ACCESS	read-write
		STATUS		current
		DESCRIPTION	"
			style='Checkbox'
			range='0..1'
			path='/Audio Control/Audio Control AES/AES Output 6/Channel 1/Gain Track'
		"
		::= { alchemistHd3GCtrlEntries 15871 }

	audioGainTrack230 OBJECT-TYPE
		SYNTAX		INTEGER { disable(0), enable(1) }
		MAX-ACCESS	read-write
		STATUS		current
		DESCRIPTION	"
			style='Checkbox'
			range='0..1'
			path='/Audio Control/Audio Control AES/AES Output 7/Channel 1/Gain Track'
		"
		::= { alchemistHd3GCtrlEntries 15872 }

	audioGainTrack240 OBJECT-TYPE
		SYNTAX		INTEGER { disable(0), enable(1) }
		MAX-ACCESS	read-write
		STATUS		current
		DESCRIPTION	"
			style='Checkbox'
			range='0..1'
			path='/Audio Control/Audio Control AES/AES Output 8/Channel 1/Gain Track'
		"
		::= { alchemistHd3GCtrlEntries 15873 }

	audioGainTrack11 OBJECT-TYPE
		SYNTAX		INTEGER { disable(0), enable(1) }
		MAX-ACCESS	read-write
		STATUS		current
		DESCRIPTION	"
			style='Checkbox'
			range='0..1'
			path='/Audio Control/Audio Control A/Output A EMB 1/Channel 2/Gain Track'
		"
		::= { alchemistHd3GCtrlEntries 15874 }

	audioGainTrack21 OBJECT-TYPE
		SYNTAX		INTEGER { disable(0), enable(1) }
		MAX-ACCESS	read-write
		STATUS		current
		DESCRIPTION	"
			style='Checkbox'
			range='0..1'
			path='/Audio Control/Audio Control A/Output A EMB 2/Channel 1/Gain Track'
		"
		::= { alchemistHd3GCtrlEntries 15875 }

	audioGainTrack31 OBJECT-TYPE
		SYNTAX		INTEGER { disable(0), enable(1) }
		MAX-ACCESS	read-write
		STATUS		current
		DESCRIPTION	"
			style='Checkbox'
			range='0..1'
			path='/Audio Control/Audio Control A/Output A EMB 3/Channel 2/Gain Track'
		"
		::= { alchemistHd3GCtrlEntries 15876 }

	audioGainTrack41 OBJECT-TYPE
		SYNTAX		INTEGER { disable(0), enable(1) }
		MAX-ACCESS	read-write
		STATUS		current
		DESCRIPTION	"
			style='Checkbox'
			range='0..1'
			path='/Audio Control/Audio Control A/Output A EMB 4/Channel 2/Gain Track'
		"
		::= { alchemistHd3GCtrlEntries 15877 }

	audioGainTrack51 OBJECT-TYPE
		SYNTAX		INTEGER { disable(0), enable(1) }
		MAX-ACCESS	read-write
		STATUS		current
		DESCRIPTION	"
			style='Checkbox'
			range='0..1'
			path='/Audio Control/Audio Control A/Output A EMB 5/Channel 2/Gain Track'
		"
		::= { alchemistHd3GCtrlEntries 15878 }

	audioGainTrack61 OBJECT-TYPE
		SYNTAX		INTEGER { disable(0), enable(1) }
		MAX-ACCESS	read-write
		STATUS		current
		DESCRIPTION	"
			style='Checkbox'
			range='0..1'
			path='/Audio Control/Audio Control A/Output A EMB 6/Channel 2/Gain Track'
		"
		::= { alchemistHd3GCtrlEntries 15879 }

	audioGainTrack71 OBJECT-TYPE
		SYNTAX		INTEGER { disable(0), enable(1) }
		MAX-ACCESS	read-write
		STATUS		current
		DESCRIPTION	"
			style='Checkbox'
			range='0..1'
			path='/Audio Control/Audio Control A/Output A EMB 7/Channel 2/Gain Track'
		"
		::= { alchemistHd3GCtrlEntries 15880 }

	audioGainTrack81 OBJECT-TYPE
		SYNTAX		INTEGER { disable(0), enable(1) }
		MAX-ACCESS	read-write
		STATUS		current
		DESCRIPTION	"
			style='Checkbox'
			range='0..1'
			path='/Audio Control/Audio Control A/Output A EMB 8/Channel 2/Gain Track'
		"
		::= { alchemistHd3GCtrlEntries 15881 }

	audioGainTrack91 OBJECT-TYPE
		SYNTAX		INTEGER { disable(0), enable(1) }
		MAX-ACCESS	read-write
		STATUS		current
		DESCRIPTION	"
			style='Checkbox'
			range='0..1'
			path='/Audio Control/Audio Control B/Output B EMB 1/Channel 2/Gain Track'
		"
		::= { alchemistHd3GCtrlEntries 15882 }

	audioGainTrack101 OBJECT-TYPE
		SYNTAX		INTEGER { disable(0), enable(1) }
		MAX-ACCESS	read-write
		STATUS		current
		DESCRIPTION	"
			style='Checkbox'
			range='0..1'
			path='/Audio Control/Audio Control B/Output B EMB 2/Channel 1/Gain Track'
		"
		::= { alchemistHd3GCtrlEntries 15883 }

	audioGainTrack111 OBJECT-TYPE
		SYNTAX		INTEGER { disable(0), enable(1) }
		MAX-ACCESS	read-write
		STATUS		current
		DESCRIPTION	"
			style='Checkbox'
			range='0..1'
			path='/Audio Control/Audio Control B/Output B EMB 3/Channel 2/Gain Track'
		"
		::= { alchemistHd3GCtrlEntries 15884 }

	audioGainTrack121 OBJECT-TYPE
		SYNTAX		INTEGER { disable(0), enable(1) }
		MAX-ACCESS	read-write
		STATUS		current
		DESCRIPTION	"
			style='Checkbox'
			range='0..1'
			path='/Audio Control/Audio Control B/Output B EMB 4/Channel 2/Gain Track'
		"
		::= { alchemistHd3GCtrlEntries 15885 }

	audioGainTrack131 OBJECT-TYPE
		SYNTAX		INTEGER { disable(0), enable(1) }
		MAX-ACCESS	read-write
		STATUS		current
		DESCRIPTION	"
			style='Checkbox'
			range='0..1'
			path='/Audio Control/Audio Control B/Output B EMB 5/Channel 2/Gain Track'
		"
		::= { alchemistHd3GCtrlEntries 15886 }

	audioGainTrack141 OBJECT-TYPE
		SYNTAX		INTEGER { disable(0), enable(1) }
		MAX-ACCESS	read-write
		STATUS		current
		DESCRIPTION	"
			style='Checkbox'
			range='0..1'
			path='/Audio Control/Audio Control B/Output B EMB 6/Channel 2/Gain Track'
		"
		::= { alchemistHd3GCtrlEntries 15887 }

	audioGainTrack151 OBJECT-TYPE
		SYNTAX		INTEGER { disable(0), enable(1) }
		MAX-ACCESS	read-write
		STATUS		current
		DESCRIPTION	"
			style='Checkbox'
			range='0..1'
			path='/Audio Control/Audio Control B/Output B EMB 7/Channel 2/Gain Track'
		"
		::= { alchemistHd3GCtrlEntries 15888 }

	audioGainTrack161 OBJECT-TYPE
		SYNTAX		INTEGER { disable(0), enable(1) }
		MAX-ACCESS	read-write
		STATUS		current
		DESCRIPTION	"
			style='Checkbox'
			range='0..1'
			path='/Audio Control/Audio Control B/Output B EMB 8/Channel 2/Gain Track'
		"
		::= { alchemistHd3GCtrlEntries 15889 }

	audioGainTrack171 OBJECT-TYPE
		SYNTAX		INTEGER { disable(0), enable(1) }
		MAX-ACCESS	read-write
		STATUS		current
		DESCRIPTION	"
			style='Checkbox'
			range='0..1'
			path='/Audio Control/Audio Control AES/AES Output 1/Channel 2/Gain Track'
		"
		::= { alchemistHd3GCtrlEntries 15890 }

	audioGainTrack181 OBJECT-TYPE
		SYNTAX		INTEGER { disable(0), enable(1) }
		MAX-ACCESS	read-write
		STATUS		current
		DESCRIPTION	"
			style='Checkbox'
			range='0..1'
			path='/Audio Control/Audio Control AES/AES Output 2/Channel 1/Gain Track'
		"
		::= { alchemistHd3GCtrlEntries 15891 }

	audioGainTrack191 OBJECT-TYPE
		SYNTAX		INTEGER { disable(0), enable(1) }
		MAX-ACCESS	read-write
		STATUS		current
		DESCRIPTION	"
			style='Checkbox'
			range='0..1'
			path='/Audio Control/Audio Control AES/AES Output 3/Channel 2/Gain Track'
		"
		::= { alchemistHd3GCtrlEntries 15892 }

	audioGainTrack201 OBJECT-TYPE
		SYNTAX		INTEGER { disable(0), enable(1) }
		MAX-ACCESS	read-write
		STATUS		current
		DESCRIPTION	"
			style='Checkbox'
			range='0..1'
			path='/Audio Control/Audio Control AES/AES Output 4/Channel 2/Gain Track'
		"
		::= { alchemistHd3GCtrlEntries 15893 }

	audioGainTrack211 OBJECT-TYPE
		SYNTAX		INTEGER { disable(0), enable(1) }
		MAX-ACCESS	read-write
		STATUS		current
		DESCRIPTION	"
			style='Checkbox'
			range='0..1'
			path='/Audio Control/Audio Control AES/AES Output 5/Channel 2/Gain Track'
		"
		::= { alchemistHd3GCtrlEntries 15894 }

	audioGainTrack221 OBJECT-TYPE
		SYNTAX		INTEGER { disable(0), enable(1) }
		MAX-ACCESS	read-write
		STATUS		current
		DESCRIPTION	"
			style='Checkbox'
			range='0..1'
			path='/Audio Control/Audio Control AES/AES Output 6/Channel 2/Gain Track'
		"
		::= { alchemistHd3GCtrlEntries 15895 }

	audioGainTrack231 OBJECT-TYPE
		SYNTAX		INTEGER { disable(0), enable(1) }
		MAX-ACCESS	read-write
		STATUS		current
		DESCRIPTION	"
			style='Checkbox'
			range='0..1'
			path='/Audio Control/Audio Control AES/AES Output 7/Channel 2/Gain Track'
		"
		::= { alchemistHd3GCtrlEntries 15896 }

	audioGainTrack241 OBJECT-TYPE
		SYNTAX		INTEGER { disable(0), enable(1) }
		MAX-ACCESS	read-write
		STATUS		current
		DESCRIPTION	"
			style='Checkbox'
			range='0..1'
			path='/Audio Control/Audio Control AES/AES Output 8/Channel 2/Gain Track'
		"
		::= { alchemistHd3GCtrlEntries 15897 }

	dolbyMode11 OBJECT-TYPE
		SYNTAX		INTEGER {
					transcoding(0),
					authoring(1)
				}
		MAX-ACCESS	read-write
		STATUS		current
		DESCRIPTION	"
			style='Radiobutton list'
			preset='transcoding'
			path='/Dolby 1 Encoder/Dolby 1 Encoder/Encoder 1 Mode'
		"
		::= { alchemistHd3GCtrlEntries 15918 }

	dolbyMode22 OBJECT-TYPE
		SYNTAX		INTEGER {
					transcoding(0),
					authoring(1)
				}
		MAX-ACCESS	read-write
		STATUS		current
		DESCRIPTION	"
			style='Radiobutton list'
			preset='transcoding'
			path='/Dolby 2 Encoder/Dolby 2 Encoder/Encoder 2 Mode'
		"
		::= { alchemistHd3GCtrlEntries 15919 }

	audioTotal10 OBJECT-TYPE
		SYNTAX		Integer32 (0..1000)
		MAX-ACCESS	read-only
		STATUS		current
		DESCRIPTION	"
			style='ReadOnly numeric'
			range='0..1000'
			path='/Audio Control/Audio Control A/Output A EMB 1/Channel 1/Delay Total'
		"
		::= { alchemistHd3GCtrlEntries 16100 }

	audioTotal20 OBJECT-TYPE
		SYNTAX		Integer32 (0..1000)
		MAX-ACCESS	read-only
		STATUS		current
		DESCRIPTION	"
			style='ReadOnly numeric'
			range='0..1000'
			path='/Audio Control/Audio Control A/Output A EMB 2/Channel 1/Delay Total'
		"
		::= { alchemistHd3GCtrlEntries 16101 }

	audioTotal30 OBJECT-TYPE
		SYNTAX		Integer32 (0..1000)
		MAX-ACCESS	read-only
		STATUS		current
		DESCRIPTION	"
			style='ReadOnly numeric'
			range='0..1000'
			path='/Audio Control/Audio Control A/Output A EMB 3/Channel 1/Total'
		"
		::= { alchemistHd3GCtrlEntries 16102 }

	audioTotal40 OBJECT-TYPE
		SYNTAX		Integer32 (0..1000)
		MAX-ACCESS	read-only
		STATUS		current
		DESCRIPTION	"
			style='ReadOnly numeric'
			range='0..1000'
			path='/Audio Control/Audio Control A/Output A EMB 4/Channel 1/Total'
		"
		::= { alchemistHd3GCtrlEntries 16103 }

	audioTotal50 OBJECT-TYPE
		SYNTAX		Integer32 (0..1000)
		MAX-ACCESS	read-only
		STATUS		current
		DESCRIPTION	"
			style='ReadOnly numeric'
			range='0..1000'
			path='/Audio Control/Audio Control A/Output A EMB 5/Channel 1/Total'
		"
		::= { alchemistHd3GCtrlEntries 16104 }

	audioTotal60 OBJECT-TYPE
		SYNTAX		Integer32 (0..1000)
		MAX-ACCESS	read-only
		STATUS		current
		DESCRIPTION	"
			style='ReadOnly numeric'
			range='0..1000'
			path='/Audio Control/Audio Control A/Output A EMB 6/Channel 1/Total'
		"
		::= { alchemistHd3GCtrlEntries 16105 }

	audioTotal70 OBJECT-TYPE
		SYNTAX		Integer32 (0..1000)
		MAX-ACCESS	read-only
		STATUS		current
		DESCRIPTION	"
			style='ReadOnly numeric'
			range='0..1000'
			path='/Audio Control/Audio Control A/Output A EMB 7/Channel 1/Total'
		"
		::= { alchemistHd3GCtrlEntries 16106 }

	audioTotal80 OBJECT-TYPE
		SYNTAX		Integer32 (0..1000)
		MAX-ACCESS	read-only
		STATUS		current
		DESCRIPTION	"
			style='ReadOnly numeric'
			range='0..1000'
			path='/Audio Control/Audio Control A/Output A EMB 8/Channel 1/Total'
		"
		::= { alchemistHd3GCtrlEntries 16107 }

	audioTotal90 OBJECT-TYPE
		SYNTAX		Integer32 (0..1000)
		MAX-ACCESS	read-only
		STATUS		current
		DESCRIPTION	"
			style='ReadOnly numeric'
			range='0..1000'
			path='/Audio Control/Audio Control B/Output B EMB 1/Channel 1/Total'
		"
		::= { alchemistHd3GCtrlEntries 16108 }

	audioTotal100 OBJECT-TYPE
		SYNTAX		Integer32 (0..1000)
		MAX-ACCESS	read-only
		STATUS		current
		DESCRIPTION	"
			style='ReadOnly numeric'
			range='0..1000'
			path='/Audio Control/Audio Control B/Output B EMB 2/Channel 1/Total'
		"
		::= { alchemistHd3GCtrlEntries 16109 }

	audioTotal110 OBJECT-TYPE
		SYNTAX		Integer32 (0..1000)
		MAX-ACCESS	read-only
		STATUS		current
		DESCRIPTION	"
			style='ReadOnly numeric'
			range='0..1000'
			path='/Audio Control/Audio Control B/Output B EMB 3/Channel 1/Total'
		"
		::= { alchemistHd3GCtrlEntries 16110 }

	audioTotal120 OBJECT-TYPE
		SYNTAX		Integer32 (0..1000)
		MAX-ACCESS	read-only
		STATUS		current
		DESCRIPTION	"
			style='ReadOnly numeric'
			range='0..1000'
			path='/Audio Control/Audio Control B/Output B EMB 4/Channel 1/Total'
		"
		::= { alchemistHd3GCtrlEntries 16111 }

	audioTotal130 OBJECT-TYPE
		SYNTAX		Integer32 (0..1000)
		MAX-ACCESS	read-only
		STATUS		current
		DESCRIPTION	"
			style='ReadOnly numeric'
			range='0..1000'
			path='/Audio Control/Audio Control B/Output B EMB 5/Channel 1/Total'
		"
		::= { alchemistHd3GCtrlEntries 16112 }

	audioTotal140 OBJECT-TYPE
		SYNTAX		Integer32 (0..1000)
		MAX-ACCESS	read-only
		STATUS		current
		DESCRIPTION	"
			style='ReadOnly numeric'
			range='0..1000'
			path='/Audio Control/Audio Control B/Output B EMB 6/Channel 1/Total'
		"
		::= { alchemistHd3GCtrlEntries 16113 }

	audioTotal150 OBJECT-TYPE
		SYNTAX		Integer32 (0..1000)
		MAX-ACCESS	read-only
		STATUS		current
		DESCRIPTION	"
			style='ReadOnly numeric'
			range='0..1000'
			path='/Audio Control/Audio Control B/Output B EMB 7/Channel 1/Total'
		"
		::= { alchemistHd3GCtrlEntries 16114 }

	audioTotal160 OBJECT-TYPE
		SYNTAX		Integer32 (0..1000)
		MAX-ACCESS	read-only
		STATUS		current
		DESCRIPTION	"
			style='ReadOnly numeric'
			range='0..1000'
			path='/Audio Control/Audio Control B/Output B EMB 8/Channel 1/Total'
		"
		::= { alchemistHd3GCtrlEntries 16115 }

	audioTotal170 OBJECT-TYPE
		SYNTAX		Integer32 (0..1000)
		MAX-ACCESS	read-only
		STATUS		current
		DESCRIPTION	"
			style='ReadOnly numeric'
			range='0..1000'
			path='/Audio Control/Audio Control AES/AES Output 1/Channel 1/Total'
		"
		::= { alchemistHd3GCtrlEntries 16116 }

	audioTotal180 OBJECT-TYPE
		SYNTAX		Integer32 (0..1000)
		MAX-ACCESS	read-only
		STATUS		current
		DESCRIPTION	"
			style='ReadOnly numeric'
			range='0..1000'
			path='/Audio Control/Audio Control AES/AES Output 2/Channel 1/Total'
		"
		::= { alchemistHd3GCtrlEntries 16117 }

	audioTotal190 OBJECT-TYPE
		SYNTAX		Integer32 (0..1000)
		MAX-ACCESS	read-only
		STATUS		current
		DESCRIPTION	"
			style='ReadOnly numeric'
			range='0..1000'
			path='/Audio Control/Audio Control AES/AES Output 3/Channel 1/Total'
		"
		::= { alchemistHd3GCtrlEntries 16118 }

	audioTotal200 OBJECT-TYPE
		SYNTAX		Integer32 (0..1000)
		MAX-ACCESS	read-only
		STATUS		current
		DESCRIPTION	"
			style='ReadOnly numeric'
			range='0..1000'
			path='/Audio Control/Audio Control AES/AES Output 4/Channel 1/Total'
		"
		::= { alchemistHd3GCtrlEntries 16119 }

	audioTotal210 OBJECT-TYPE
		SYNTAX		Integer32 (0..1000)
		MAX-ACCESS	read-only
		STATUS		current
		DESCRIPTION	"
			style='ReadOnly numeric'
			range='0..1000'
			path='/Audio Control/Audio Control AES/AES Output 5/Channel 1/Total'
		"
		::= { alchemistHd3GCtrlEntries 16120 }

	audioTotal220 OBJECT-TYPE
		SYNTAX		Integer32 (0..1000)
		MAX-ACCESS	read-only
		STATUS		current
		DESCRIPTION	"
			style='ReadOnly numeric'
			range='0..1000'
			path='/Audio Control/Audio Control AES/AES Output 6/Channel 1/Total'
		"
		::= { alchemistHd3GCtrlEntries 16121 }

	audioTotal230 OBJECT-TYPE
		SYNTAX		Integer32 (0..1000)
		MAX-ACCESS	read-only
		STATUS		current
		DESCRIPTION	"
			style='ReadOnly numeric'
			range='0..1000'
			path='/Audio Control/Audio Control AES/AES Output 7/Channel 1/Total'
		"
		::= { alchemistHd3GCtrlEntries 16122 }

	audioTotal240 OBJECT-TYPE
		SYNTAX		Integer32 (0..1000)
		MAX-ACCESS	read-only
		STATUS		current
		DESCRIPTION	"
			style='ReadOnly numeric'
			range='0..1000'
			path='/Audio Control/Audio Control AES/AES Output 8/Channel 1/Total'
		"
		::= { alchemistHd3GCtrlEntries 16123 }

	audioTotal11 OBJECT-TYPE
		SYNTAX		Integer32 (0..1000)
		MAX-ACCESS	read-only
		STATUS		current
		DESCRIPTION	"
			style='ReadOnly numeric'
			range='0..1000'
			path='/Audio Control/Audio Control A/Output A EMB 1/Channel 2/Delay Total'
		"
		::= { alchemistHd3GCtrlEntries 16130 }

	audioTotal21 OBJECT-TYPE
		SYNTAX		Integer32 (0..1000)
		MAX-ACCESS	read-only
		STATUS		current
		DESCRIPTION	"
			style='ReadOnly numeric'
			range='0..1000'
			path='/Audio Control/Audio Control A/Output A EMB 2/Channel 1/Delay Total'
		"
		::= { alchemistHd3GCtrlEntries 16131 }

	audioTotal31 OBJECT-TYPE
		SYNTAX		Integer32 (0..1000)
		MAX-ACCESS	read-only
		STATUS		current
		DESCRIPTION	"
			style='ReadOnly numeric'
			range='0..1000'
			path='/Audio Control/Audio Control A/Output A EMB 3/Channel 2/Total'
		"
		::= { alchemistHd3GCtrlEntries 16132 }

	audioTotal41 OBJECT-TYPE
		SYNTAX		Integer32 (0..1000)
		MAX-ACCESS	read-only
		STATUS		current
		DESCRIPTION	"
			style='ReadOnly numeric'
			range='0..1000'
			path='/Audio Control/Audio Control A/Output A EMB 4/Channel 2/Total'
		"
		::= { alchemistHd3GCtrlEntries 16133 }

	audioTotal51 OBJECT-TYPE
		SYNTAX		Integer32 (0..1000)
		MAX-ACCESS	read-only
		STATUS		current
		DESCRIPTION	"
			style='ReadOnly numeric'
			range='0..1000'
			path='/Audio Control/Audio Control A/Output A EMB 5/Channel 2/Total'
		"
		::= { alchemistHd3GCtrlEntries 16134 }

	audioTotal61 OBJECT-TYPE
		SYNTAX		Integer32 (0..1000)
		MAX-ACCESS	read-only
		STATUS		current
		DESCRIPTION	"
			style='ReadOnly numeric'
			range='0..1000'
			path='/Audio Control/Audio Control A/Output A EMB 6/Channel 2/Total'
		"
		::= { alchemistHd3GCtrlEntries 16135 }

	audioTotal71 OBJECT-TYPE
		SYNTAX		Integer32 (0..1000)
		MAX-ACCESS	read-only
		STATUS		current
		DESCRIPTION	"
			style='ReadOnly numeric'
			range='0..1000'
			path='/Audio Control/Audio Control A/Output A EMB 7/Channel 2/Total'
		"
		::= { alchemistHd3GCtrlEntries 16136 }

	audioTotal81 OBJECT-TYPE
		SYNTAX		Integer32 (0..1000)
		MAX-ACCESS	read-only
		STATUS		current
		DESCRIPTION	"
			style='ReadOnly numeric'
			range='0..1000'
			path='/Audio Control/Audio Control A/Output A EMB 8/Channel 2/Total'
		"
		::= { alchemistHd3GCtrlEntries 16137 }

	audioTotal91 OBJECT-TYPE
		SYNTAX		Integer32 (0..1000)
		MAX-ACCESS	read-only
		STATUS		current
		DESCRIPTION	"
			style='ReadOnly numeric'
			range='0..1000'
			path='/Audio Control/Audio Control B/Output B EMB 1/Channel 2/Total'
		"
		::= { alchemistHd3GCtrlEntries 16138 }

	audioTotal101 OBJECT-TYPE
		SYNTAX		Integer32 (0..1000)
		MAX-ACCESS	read-only
		STATUS		current
		DESCRIPTION	"
			style='ReadOnly numeric'
			range='0..1000'
			path='/Audio Control/Audio Control B/Output B EMB 2/Channel 1/Total'
		"
		::= { alchemistHd3GCtrlEntries 16139 }

	audioTotal111 OBJECT-TYPE
		SYNTAX		Integer32 (0..1000)
		MAX-ACCESS	read-only
		STATUS		current
		DESCRIPTION	"
			style='ReadOnly numeric'
			range='0..1000'
			path='/Audio Control/Audio Control B/Output B EMB 3/Channel 2/Total'
		"
		::= { alchemistHd3GCtrlEntries 16140 }

	audioTotal121 OBJECT-TYPE
		SYNTAX		Integer32 (0..1000)
		MAX-ACCESS	read-only
		STATUS		current
		DESCRIPTION	"
			style='ReadOnly numeric'
			range='0..1000'
			path='/Audio Control/Audio Control B/Output B EMB 4/Channel 2/Total'
		"
		::= { alchemistHd3GCtrlEntries 16141 }

	audioTotal131 OBJECT-TYPE
		SYNTAX		Integer32 (0..1000)
		MAX-ACCESS	read-only
		STATUS		current
		DESCRIPTION	"
			style='ReadOnly numeric'
			range='0..1000'
			path='/Audio Control/Audio Control B/Output B EMB 5/Channel 2/Total'
		"
		::= { alchemistHd3GCtrlEntries 16142 }

	audioTotal141 OBJECT-TYPE
		SYNTAX		Integer32 (0..1000)
		MAX-ACCESS	read-only
		STATUS		current
		DESCRIPTION	"
			style='ReadOnly numeric'
			range='0..1000'
			path='/Audio Control/Audio Control B/Output B EMB 6/Channel 2/Total'
		"
		::= { alchemistHd3GCtrlEntries 16143 }

	audioTotal151 OBJECT-TYPE
		SYNTAX		Integer32 (0..1000)
		MAX-ACCESS	read-only
		STATUS		current
		DESCRIPTION	"
			style='ReadOnly numeric'
			range='0..1000'
			path='/Audio Control/Audio Control B/Output B EMB 7/Channel 2/Total'
		"
		::= { alchemistHd3GCtrlEntries 16144 }

	audioTotal161 OBJECT-TYPE
		SYNTAX		Integer32 (0..1000)
		MAX-ACCESS	read-only
		STATUS		current
		DESCRIPTION	"
			style='ReadOnly numeric'
			range='0..1000'
			path='/Audio Control/Audio Control B/Output B EMB 8/Channel 2/Total'
		"
		::= { alchemistHd3GCtrlEntries 16145 }

	audioTotal171 OBJECT-TYPE
		SYNTAX		Integer32 (0..1000)
		MAX-ACCESS	read-only
		STATUS		current
		DESCRIPTION	"
			style='ReadOnly numeric'
			range='0..1000'
			path='/Audio Control/Audio Control AES/AES Output 1/Channel 2/Total'
		"
		::= { alchemistHd3GCtrlEntries 16146 }

	audioTotal181 OBJECT-TYPE
		SYNTAX		Integer32 (0..1000)
		MAX-ACCESS	read-only
		STATUS		current
		DESCRIPTION	"
			style='ReadOnly numeric'
			range='0..1000'
			path='/Audio Control/Audio Control AES/AES Output 2/Channel 1/Total'
		"
		::= { alchemistHd3GCtrlEntries 16147 }

	audioTotal191 OBJECT-TYPE
		SYNTAX		Integer32 (0..1000)
		MAX-ACCESS	read-only
		STATUS		current
		DESCRIPTION	"
			style='ReadOnly numeric'
			range='0..1000'
			path='/Audio Control/Audio Control AES/AES Output 3/Channel 2/Total'
		"
		::= { alchemistHd3GCtrlEntries 16148 }

	audioTotal201 OBJECT-TYPE
		SYNTAX		Integer32 (0..1000)
		MAX-ACCESS	read-only
		STATUS		current
		DESCRIPTION	"
			style='ReadOnly numeric'
			range='0..1000'
			path='/Audio Control/Audio Control AES/AES Output 4/Channel 2/Total'
		"
		::= { alchemistHd3GCtrlEntries 16149 }

	audioTotal211 OBJECT-TYPE
		SYNTAX		Integer32 (0..1000)
		MAX-ACCESS	read-only
		STATUS		current
		DESCRIPTION	"
			style='ReadOnly numeric'
			range='0..1000'
			path='/Audio Control/Audio Control AES/AES Output 5/Channel 2/Total'
		"
		::= { alchemistHd3GCtrlEntries 16150 }

	audioTotal221 OBJECT-TYPE
		SYNTAX		Integer32 (0..1000)
		MAX-ACCESS	read-only
		STATUS		current
		DESCRIPTION	"
			style='ReadOnly numeric'
			range='0..1000'
			path='/Audio Control/Audio Control AES/AES Output 6/Channel 2/Total'
		"
		::= { alchemistHd3GCtrlEntries 16151 }

	audioTotal231 OBJECT-TYPE
		SYNTAX		Integer32 (0..1000)
		MAX-ACCESS	read-only
		STATUS		current
		DESCRIPTION	"
			style='ReadOnly numeric'
			range='0..1000'
			path='/Audio Control/Audio Control AES/AES Output 7/Channel 2/Total'
		"
		::= { alchemistHd3GCtrlEntries 16152 }

	audioTotal241 OBJECT-TYPE
		SYNTAX		Integer32 (0..1000)
		MAX-ACCESS	read-only
		STATUS		current
		DESCRIPTION	"
			style='ReadOnly numeric'
			range='0..1000'
			path='/Audio Control/Audio Control AES/AES Output 8/Channel 2/Total'
		"
		::= { alchemistHd3GCtrlEntries 16153 }

	encoderSourceSelection11 OBJECT-TYPE
		SYNTAX		INTEGER {
					emb(1),
					aes(2),
					dec1(3),
					dec2(4)
				}
		MAX-ACCESS	read-write
		STATUS		current
		DESCRIPTION	"
			style='Radiobutton list'
			path='/Audio Source Select ENC 1/Encoder Source Selection/Select Source Type'
		"
		::= { alchemistHd3GCtrlEntries 16801 }

	encoderSourceSelectionAes11 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 1/Encoder Source Selection/Select Source'
		"
		::= { alchemistHd3GCtrlEntries 16803 }

	encoderSourceSelectionEmb11 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 1/Encoder Source Selection/Select Source'
		"
		::= { alchemistHd3GCtrlEntries 16804 }

	encoderSourceSelectionDlbDec111 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 1/Encoder Source Selection/Select Source'
		"
		::= { alchemistHd3GCtrlEntries 16805 }

	encoderSourceSelectionDlbDec211 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 1/Encoder Source Selection/Select Source'
		"
		::= { alchemistHd3GCtrlEntries 16806 }

	encoderSourceSelectionChannel11 OBJECT-TYPE
		SYNTAX		INTEGER {
					ch1(1),
					ch2(2)
				}
		MAX-ACCESS	read-write
		STATUS		current
		DESCRIPTION	"
			style='Radiobutton list'
			path='/Audio Source Select ENC 1/Encoder Source Selection/Select Channel'
		"
		::= { alchemistHd3GCtrlEntries 16808 }

	encoderSourceSelection12 OBJECT-TYPE
		SYNTAX		INTEGER {
					emb(1),
					aes(2),
					dec1(3),
					dec2(4)
				}
		MAX-ACCESS	read-write
		STATUS		current
		DESCRIPTION	"
			style='Radiobutton list'
			path='/Audio Source Select ENC 1/Encoder Source Selection/Select Source Type'
		"
		::= { alchemistHd3GCtrlEntries 16811 }

	encoderSourceSelectionAes12 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 1/Encoder Source Selection/Select Source'
		"
		::= { alchemistHd3GCtrlEntries 16813 }

	encoderSourceSelectionEmb12 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 1/Encoder Source Selection/Select Source'
		"
		::= { alchemistHd3GCtrlEntries 16814 }

	encoderSourceSelectionDlbDec112 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 1/Encoder Source Selection/Select Source'
		"
		::= { alchemistHd3GCtrlEntries 16815 }

	encoderSourceSelectionDlbDec212 OBJECT-TYPE
		SYNTAX		INTEGER {
					dec21(1),
					dec22(2),
					dec23(3),
					dec24(4),
					aux(5)
				}
		MAX-ACCESS	read-write
		STATUS		current
		DESCRIPTION	"
			style='Radiobutton list'
			path='/Audio Source Select ENC 1/Encoder Source Selection/Select Source'
		"
		::= { alchemistHd3GCtrlEntries 16816 }

	encoderSourceSelectionChannel12 OBJECT-TYPE
		SYNTAX		INTEGER {
					ch1(1),
					ch2(2)
				}
		MAX-ACCESS	read-write
		STATUS		current
		DESCRIPTION	"
			style='Radiobutton list'
			path='/Audio Source Select ENC 1/Encoder Source Selection/Select Channel'
		"
		::= { alchemistHd3GCtrlEntries 16818 }

	encoderSourceSelection13 OBJECT-TYPE
		SYNTAX		INTEGER {
					emb(1),
					aes(2),
					dec1(3),
					dec2(4)
				}
		MAX-ACCESS	read-write
		STATUS		current
		DESCRIPTION	"
			style='Radiobutton list'
			path='/Audio Source Select ENC 1/Encoder Source Selection/Select Source Type'
		"
		::= { alchemistHd3GCtrlEntries 16821 }

	encoderSourceSelectionAes13 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 1/Encoder Source Selection/Select Source'
		"
		::= { alchemistHd3GCtrlEntries 16823 }

	encoderSourceSelectionEmb13 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 1/Encoder Source Selection/Select Source'
		"
		::= { alchemistHd3GCtrlEntries 16824 }

	encoderSourceSelectionDlbDec113 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 1/Encoder Source Selection/Select Source'
		"
		::= { alchemistHd3GCtrlEntries 16825 }

	encoderSourceSelectionDlbDec213 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 1/Encoder Source Selection/Select Source'
		"
		::= { alchemistHd3GCtrlEntries 16826 }

	encoderSourceSelectionChannel13 OBJECT-TYPE
		SYNTAX		INTEGER {
					ch1(1),
					ch2(2)
				}
		MAX-ACCESS	read-write
		STATUS		current
		DESCRIPTION	"
			style='Radiobutton list'
			path='/Audio Source Select ENC 1/Encoder Source Selection/Select Channel'
		"
		::= { alchemistHd3GCtrlEntries 16828 }

	encoderSourceSelection14 OBJECT-TYPE
		SYNTAX		INTEGER {
					emb(1),
					aes(2),
					dec1(3),
					dec2(4)
				}
		MAX-ACCESS	read-write
		STATUS		current
		DESCRIPTION	"
			style='Radiobutton list'
			path='/Audio Source Select ENC 1/Encoder Source Selection/Select Source Type'
		"
		::= { alchemistHd3GCtrlEntries 16831 }

	encoderSourceSelectionAes14 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 1/Encoder Source Selection/Select Source'
		"
		::= { alchemistHd3GCtrlEntries 16833 }

	encoderSourceSelectionEmb14 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 1/Encoder Source Selection/Select Source'
		"
		::= { alchemistHd3GCtrlEntries 16834 }

	encoderSourceSelectionDlbDec114 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 1/Encoder Source Selection/Select Source'
		"
		::= { alchemistHd3GCtrlEntries 16835 }

	encoderSourceSelectionDlbDec214 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 1/Encoder Source Selection/Select Source'
		"
		::= { alchemistHd3GCtrlEntries 16836 }

	encoderSourceSelectionChannel14 OBJECT-TYPE
		SYNTAX		INTEGER {
					ch1(1),
					ch2(2)
				}
		MAX-ACCESS	read-write
		STATUS		current
		DESCRIPTION	"
			style='Radiobutton list'
			path='/Audio Source Select ENC 1/Encoder Source Selection/Select Channel'
		"
		::= { alchemistHd3GCtrlEntries 16838 }

	encoderSourceSelection15 OBJECT-TYPE
		SYNTAX		INTEGER {
					emb(1),
					aes(2),
					dec1(3),
					dec2(4)
				}
		MAX-ACCESS	read-write
		STATUS		current
		DESCRIPTION	"
			style='Radiobutton list'
			path='/Audio Source Select ENC 1/Encoder Source Selection/Select Source Type'
		"
		::= { alchemistHd3GCtrlEntries 16841 }

	encoderSourceSelectionAes15 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 1/Encoder Source Selection/Select Source'
		"
		::= { alchemistHd3GCtrlEntries 16843 }

	encoderSourceSelectionEmb15 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 1/Encoder Source Selection/Select Source'
		"
		::= { alchemistHd3GCtrlEntries 16844 }

	encoderSourceSelectionDlbDec115 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 1/Encoder Source Selection/Select Source'
		"
		::= { alchemistHd3GCtrlEntries 16845 }

	encoderSourceSelectionDlbDec215 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 1/Encoder Source Selection/Select Source'
		"
		::= { alchemistHd3GCtrlEntries 16846 }

	encoderSourceSelectionChannel15 OBJECT-TYPE
		SYNTAX		INTEGER {
					ch1(1),
					ch2(2)
				}
		MAX-ACCESS	read-write
		STATUS		current
		DESCRIPTION	"
			style='Radiobutton list'
			path='/Audio Source Select ENC 1/Encoder Source Selection/Select Channel'
		"
		::= { alchemistHd3GCtrlEntries 16848 }

	encoderSourceSelection16 OBJECT-TYPE
		SYNTAX		INTEGER {
					emb(1),
					aes(2),
					dec1(3),
					dec2(4)
				}
		MAX-ACCESS	read-write
		STATUS		current
		DESCRIPTION	"
			style='Radiobutton list'
			path='/Audio Source Select ENC 1/Encoder Source Selection/Select Source Type'
		"
		::= { alchemistHd3GCtrlEntries 16851 }

	encoderSourceSelectionAes16 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 1/Encoder Source Selection/Select Source'
		"
		::= { alchemistHd3GCtrlEntries 16853 }

	encoderSourceSelectionEmb16 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 1/Encoder Source Selection/Select Source'
		"
		::= { alchemistHd3GCtrlEntries 16854 }

	encoderSourceSelectionDlbDec116 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 1/Encoder Source Selection/Select Source'
		"
		::= { alchemistHd3GCtrlEntries 16855 }

	encoderSourceSelectionDlbDec216 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 1/Encoder Source Selection/Select Source'
		"
		::= { alchemistHd3GCtrlEntries 16856 }

	encoderSourceSelectionChannel16 OBJECT-TYPE
		SYNTAX		INTEGER {
					ch1(1),
					ch2(2)
				}
		MAX-ACCESS	read-write
		STATUS		current
		DESCRIPTION	"
			style='Radiobutton list'
			path='/Audio Source Select ENC 1/Encoder Source Selection/Select Channel'
		"
		::= { alchemistHd3GCtrlEntries 16858 }

	encoderSourceSelection17 OBJECT-TYPE
		SYNTAX		INTEGER {
					emb(1),
					aes(2),
					dec1(3),
					dec2(4)
				}
		MAX-ACCESS	read-write
		STATUS		current
		DESCRIPTION	"
			style='Radiobutton list'
			path='/Audio Source Select ENC 1/Encoder Source Selection/Select Source Type'
		"
		::= { alchemistHd3GCtrlEntries 16861 }

	encoderSourceSelectionAes17 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 1/Encoder Source Selection/Select Source'
		"
		::= { alchemistHd3GCtrlEntries 16863 }

	encoderSourceSelectionEmb17 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 1/Encoder Source Selection/Select Source'
		"
		::= { alchemistHd3GCtrlEntries 16864 }

	encoderSourceSelectionDlbDec117 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 1/Encoder Source Selection/Select Source'
		"
		::= { alchemistHd3GCtrlEntries 16865 }

	encoderSourceSelectionDlbDec217 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 1/Encoder Source Selection/Select Source'
		"
		::= { alchemistHd3GCtrlEntries 16866 }

	encoderSourceSelectionChannel17 OBJECT-TYPE
		SYNTAX		INTEGER {
					ch1(1),
					ch2(2)
				}
		MAX-ACCESS	read-write
		STATUS		current
		DESCRIPTION	"
			style='Radiobutton list'
			path='/Audio Source Select ENC 1/Encoder Source Selection/Select Channel'
		"
		::= { alchemistHd3GCtrlEntries 16868 }

	encoderSourceSelection18 OBJECT-TYPE
		SYNTAX		INTEGER {
					emb(1),
					aes(2),
					dec1(3),
					dec2(4)
				}
		MAX-ACCESS	read-write
		STATUS		current
		DESCRIPTION	"
			style='Radiobutton list'
			path='/Audio Source Select ENC 1/Encoder Source Selection/Select Source Type'
		"
		::= { alchemistHd3GCtrlEntries 16871 }

	encoderSourceSelectionAes18 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 1/Encoder Source Selection/Select Source'
		"
		::= { alchemistHd3GCtrlEntries 16873 }

	encoderSourceSelectionEmb18 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 1/Encoder Source Selection/Select Source'
		"
		::= { alchemistHd3GCtrlEntries 16874 }

	encoderSourceSelectionDlbDec118 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 1/Encoder Source Selection/Select Source'
		"
		::= { alchemistHd3GCtrlEntries 16875 }

	encoderSourceSelectionDlbDec218 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 1/Encoder Source Selection/Select Source'
		"
		::= { alchemistHd3GCtrlEntries 16876 }

	encoderSourceSelectionChannel18 OBJECT-TYPE
		SYNTAX		INTEGER {
					ch1(1),
					ch2(2)
				}
		MAX-ACCESS	read-write
		STATUS		current
		DESCRIPTION	"
			style='Radiobutton list'
			path='/Audio Source Select ENC 1/Encoder Source Selection/Select Channel'
		"
		::= { alchemistHd3GCtrlEntries 16878 }

	encoderSourceSelection21 OBJECT-TYPE
		SYNTAX		INTEGER {
					emb(1),
					aes(2),
					dec1(3),
					dec2(4)
				}
		MAX-ACCESS	read-write
		STATUS		current
		DESCRIPTION	"
			style='Radiobutton list'
			path='/Audio Source Select ENC 2/Encoder Source Selection/Select Source Type'
		"
		::= { alchemistHd3GCtrlEntries 16879 }

	encoderSourceSelectionAes21 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 2/Encoder Source Selection/Select Source'
		"
		::= { alchemistHd3GCtrlEntries 16880 }

	encoderSourceSelectionEmb21 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 2/Encoder Source Selection/Select Source'
		"
		::= { alchemistHd3GCtrlEntries 16881 }

	encoderSourceSelectionDlbDec121 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 2/Encoder Source Selection/Select Source'
		"
		::= { alchemistHd3GCtrlEntries 16882 }

	encoderSourceSelectionDlbDec221 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 2/Encoder Source Selection/Select Source'
		"
		::= { alchemistHd3GCtrlEntries 16883 }

	encoderSourceSelectionChannel21 OBJECT-TYPE
		SYNTAX		INTEGER {
					ch1(1),
					ch2(2)
				}
		MAX-ACCESS	read-write
		STATUS		current
		DESCRIPTION	"
			style='Radiobutton list'
			path='/Audio Source Select ENC 2/Encoder Source Selection/Select Channel'
		"
		::= { alchemistHd3GCtrlEntries 16884 }

	encoderSourceSelection22 OBJECT-TYPE
		SYNTAX		INTEGER {
					emb(1),
					aes(2),
					dec1(3),
					dec2(4)
				}
		MAX-ACCESS	read-write
		STATUS		current
		DESCRIPTION	"
			style='Radiobutton list'
			path='/Audio Source Select ENC 2/Encoder Source Selection/Select Source Type'
		"
		::= { alchemistHd3GCtrlEntries 16885 }

	encoderSourceSelectionAes22 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 2/Encoder Source Selection/Select Source'
		"
		::= { alchemistHd3GCtrlEntries 16886 }

	encoderSourceSelectionEmb22 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 2/Encoder Source Selection/Select Source'
		"
		::= { alchemistHd3GCtrlEntries 16887 }

	encoderSourceSelectionDlbDec122 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 2/Encoder Source Selection/Select Source'
		"
		::= { alchemistHd3GCtrlEntries 16888 }

	encoderSourceSelectionDlbDec222 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 2/Encoder Source Selection/Select Source'
		"
		::= { alchemistHd3GCtrlEntries 16889 }

	encoderSourceSelectionChannel22 OBJECT-TYPE
		SYNTAX		INTEGER {
					ch1(1),
					ch2(2)
				}
		MAX-ACCESS	read-write
		STATUS		current
		DESCRIPTION	"
			style='Radiobutton list'
			path='/Audio Source Select ENC 2/Encoder Source Selection/Select Channel'
		"
		::= { alchemistHd3GCtrlEntries 16890 }

	encoderSourceSelection23 OBJECT-TYPE
		SYNTAX		INTEGER {
					emb(1),
					aes(2),
					dec1(3),
					dec2(4)
				}
		MAX-ACCESS	read-write
		STATUS		current
		DESCRIPTION	"
			style='Radiobutton list'
			path='/Audio Source Select ENC 2/Encoder Source Selection/Select Source Type'
		"
		::= { alchemistHd3GCtrlEntries 16891 }

	encoderSourceSelectionAes23 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 2/Encoder Source Selection/Select Source'
		"
		::= { alchemistHd3GCtrlEntries 16892 }

	encoderSourceSelectionEmb23 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 2/Encoder Source Selection/Select Source'
		"
		::= { alchemistHd3GCtrlEntries 16893 }

	encoderSourceSelectionDlbDec123 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 2/Encoder Source Selection/Select Source'
		"
		::= { alchemistHd3GCtrlEntries 16894 }

	encoderSourceSelectionDlbDec223 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 2/Encoder Source Selection/Select Source'
		"
		::= { alchemistHd3GCtrlEntries 16895 }

	encoderSourceSelectionChannel23 OBJECT-TYPE
		SYNTAX		INTEGER {
					ch1(1),
					ch2(2)
				}
		MAX-ACCESS	read-write
		STATUS		current
		DESCRIPTION	"
			style='Radiobutton list'
			path='/Audio Source Select ENC 2/Encoder Source Selection/Select Channel'
		"
		::= { alchemistHd3GCtrlEntries 16896 }

	encoderSourceSelection24 OBJECT-TYPE
		SYNTAX		INTEGER {
					emb(1),
					aes(2),
					dec1(3),
					dec2(4)
				}
		MAX-ACCESS	read-write
		STATUS		current
		DESCRIPTION	"
			style='Radiobutton list'
			path='/Audio Source Select ENC 2/Encoder Source Selection/Select Source Type'
		"
		::= { alchemistHd3GCtrlEntries 16897 }

	encoderSourceSelectionAes24 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 2/Encoder Source Selection/Select Source'
		"
		::= { alchemistHd3GCtrlEntries 16898 }

	encoderSourceSelectionEmb24 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 2/Encoder Source Selection/Select Source'
		"
		::= { alchemistHd3GCtrlEntries 16899 }

	encoderSourceSelectionDlbDec124 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 2/Encoder Source Selection/Select Source'
		"
		::= { alchemistHd3GCtrlEntries 16900 }

	encoderSourceSelectionDlbDec224 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 2/Encoder Source Selection/Select Source'
		"
		::= { alchemistHd3GCtrlEntries 16901 }

	encoderSourceSelectionChannel24 OBJECT-TYPE
		SYNTAX		INTEGER {
					ch1(1),
					ch2(2)
				}
		MAX-ACCESS	read-write
		STATUS		current
		DESCRIPTION	"
			style='Radiobutton list'
			path='/Audio Source Select ENC 2/Encoder Source Selection/Select Channel'
		"
		::= { alchemistHd3GCtrlEntries 16902 }

	encoderSourceSelection25 OBJECT-TYPE
		SYNTAX		INTEGER {
					emb(1),
					aes(2),
					dec1(3),
					dec2(4)
				}
		MAX-ACCESS	read-write
		STATUS		current
		DESCRIPTION	"
			style='Radiobutton list'
			path='/Audio Source Select ENC 2/Encoder Source Selection/Select Source Type'
		"
		::= { alchemistHd3GCtrlEntries 16903 }

	encoderSourceSelectionAes25 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 2/Encoder Source Selection/Select Source'
		"
		::= { alchemistHd3GCtrlEntries 16904 }

	encoderSourceSelectionEmb25 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 2/Encoder Source Selection/Select Source'
		"
		::= { alchemistHd3GCtrlEntries 16905 }

	encoderSourceSelectionDlbDec125 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 2/Encoder Source Selection/Select Source'
		"
		::= { alchemistHd3GCtrlEntries 16906 }

	encoderSourceSelectionDlbDec225 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 2/Encoder Source Selection/Select Source'
		"
		::= { alchemistHd3GCtrlEntries 16907 }

	encoderSourceSelectionChannel25 OBJECT-TYPE
		SYNTAX		INTEGER {
					ch1(1),
					ch2(2)
				}
		MAX-ACCESS	read-write
		STATUS		current
		DESCRIPTION	"
			style='Radiobutton list'
			path='/Audio Source Select ENC 2/Encoder Source Selection/Select Channel'
		"
		::= { alchemistHd3GCtrlEntries 16908 }

	encoderSourceSelection26 OBJECT-TYPE
		SYNTAX		INTEGER {
					emb(1),
					aes(2),
					dec1(3),
					dec2(4)
				}
		MAX-ACCESS	read-write
		STATUS		current
		DESCRIPTION	"
			style='Radiobutton list'
			path='/Audio Source Select ENC 2/Encoder Source Selection/Select Source Type'
		"
		::= { alchemistHd3GCtrlEntries 16909 }

	encoderSourceSelectionAes26 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 2/Encoder Source Selection/Select Source'
		"
		::= { alchemistHd3GCtrlEntries 16910 }

	encoderSourceSelectionEmb26 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 2/Encoder Source Selection/Select Source'
		"
		::= { alchemistHd3GCtrlEntries 16911 }

	encoderSourceSelectionDlbDec126 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 2/Encoder Source Selection/Select Source'
		"
		::= { alchemistHd3GCtrlEntries 16912 }

	encoderSourceSelectionDlbDec226 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 2/Encoder Source Selection/Select Source'
		"
		::= { alchemistHd3GCtrlEntries 16913 }

	encoderSourceSelectionChannel26 OBJECT-TYPE
		SYNTAX		INTEGER {
					ch1(1),
					ch2(2)
				}
		MAX-ACCESS	read-write
		STATUS		current
		DESCRIPTION	"
			style='Radiobutton list'
			path='/Audio Source Select ENC 2/Encoder Source Selection/Select Channel'
		"
		::= { alchemistHd3GCtrlEntries 16914 }

	encoderSourceSelection27 OBJECT-TYPE
		SYNTAX		INTEGER {
					emb(1),
					aes(2),
					dec1(3),
					dec2(4)
				}
		MAX-ACCESS	read-write
		STATUS		current
		DESCRIPTION	"
			style='Radiobutton list'
			path='/Audio Source Select ENC 2/Encoder Source Selection/Select Source Type'
		"
		::= { alchemistHd3GCtrlEntries 16915 }

	encoderSourceSelectionAes27 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 2/Encoder Source Selection/Select Source'
		"
		::= { alchemistHd3GCtrlEntries 16916 }

	encoderSourceSelectionEmb27 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 2/Encoder Source Selection/Select Source'
		"
		::= { alchemistHd3GCtrlEntries 16917 }

	encoderSourceSelectionDlbDec127 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 2/Encoder Source Selection/Select Source'
		"
		::= { alchemistHd3GCtrlEntries 16918 }

	encoderSourceSelectionDlbDec227 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 2/Encoder Source Selection/Select Source'
		"
		::= { alchemistHd3GCtrlEntries 16919 }

	encoderSourceSelectionChannel27 OBJECT-TYPE
		SYNTAX		INTEGER {
					ch1(1),
					ch2(2)
				}
		MAX-ACCESS	read-write
		STATUS		current
		DESCRIPTION	"
			style='Radiobutton list'
			path='/Audio Source Select ENC 2/Encoder Source Selection/Select Channel'
		"
		::= { alchemistHd3GCtrlEntries 16920 }

	encoderSourceSelection28 OBJECT-TYPE
		SYNTAX		INTEGER {
					emb(1),
					aes(2),
					dec1(3),
					dec2(4)
				}
		MAX-ACCESS	read-write
		STATUS		current
		DESCRIPTION	"
			style='Radiobutton list'
			path='/Audio Source Select ENC 2/Encoder Source Selection/Select Source Type'
		"
		::= { alchemistHd3GCtrlEntries 16921 }

	encoderSourceSelectionAes28 OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Audio Source Select ENC 2/Encoder Source Selection/Select Source'
		"
		::= { alchemistHd3GCtrlEntries 16922 }

	encoderSourceSelectionEmb28 OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Audio Source Select ENC 2/Encoder Source Selection/Select Source'
		"
		::= { alchemistHd3GCtrlEntries 16923 }

	encoderSourceSelectionDlbDec128 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Audio Source Select ENC 2/Encoder Source Selection/Select Source'
		"
		::= { alchemistHd3GCtrlEntries 16924 }

	encoderSourceSelectionDlbDec228 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Audio Source Select ENC 2/Encoder Source Selection/Select Source'
		"
		::= { alchemistHd3GCtrlEntries 16925 }

	encoderSourceSelectionChannel28 OBJECT-TYPE
		SYNTAX		INTEGER {
					ch1(1),
					ch2(2)
				}
		MAX-ACCESS	read-write
		STATUS		current
		DESCRIPTION	"
			style='Radiobutton list'
			path='/Audio Source Select ENC 2/Encoder Source Selection/Select Channel'
		"
		::= { alchemistHd3GCtrlEntries 16926 }

	dolbyEncBitDepth11 OBJECT-TYPE
		SYNTAX		INTEGER {
					v20Bit(0),
					v16Bit(1)
				}
		MAX-ACCESS	read-write
		STATUS		current
		DESCRIPTION	"
			style='Radiobutton list'
			preset='v20Bit'
			path='/Dolby 1 Encoder/Dolby 1 Encoder/Bit Depth'
		"
		::= { alchemistHd3GCtrlEntries 16950 }

	dolbyEncProgramConfig1 OBJECT-TYPE
		SYNTAX		INTEGER {
					v51Plus2(0),
					v51Plus2X1(1),
					v4Plus4(2),
					v4Plus2X2(3),
					v4Plus2Plus2X1(4),
					v4Plus4X1(5),
					v4x2(6),
					v3x2Plus2X1(7),
					v2x2Plus4X1(8),
					v2Plus6X1(9),
					v8x1(10),
					v51(11),
					v4Plus2(12),
					v4Plus2X1(13),
					v3x2(14),
					v2x2Plus2X1(15),
					v2Plus4X1(16),
					v6x1(17),
					v4(18),
					v2Plus2(19),
					v2Plus2X1(20),
					v4x1(21),
					v71(22),
					v71Screen(23)
				}
		MAX-ACCESS	read-write
		STATUS		current
		DESCRIPTION	"
			style='Radiobutton list'
			preset='v51Plus2'
			path='/Dolby 1 Encoder/Dolby 1 Encoder/Program Config'
		"
		::= { alchemistHd3GCtrlEntries 16951 }

	dolbyEncBitDepth22 OBJECT-TYPE
		SYNTAX		INTEGER {
					v20Bit(0),
					v16Bit(1)
				}
		MAX-ACCESS	read-write
		STATUS		current
		DESCRIPTION	"
			style='Radiobutton list'
			preset='v20Bit'
			path='/Dolby 2 Encoder/Dolby 2 Encoder/Bit Depth'
		"
		::= { alchemistHd3GCtrlEntries 16952 }

	dolbyEncProgramConfig2 OBJECT-TYPE
		SYNTAX		INTEGER {
					v51Plus2(0),
					v51Plus2X1(1),
					v4Plus4(2),
					v4Plus2X2(3),
					v4Plus2Plus2X1(4),
					v4Plus4X1(5),
					v4x2(6),
					v3x2Plus2X1(7),
					v2x2Plus4X1(8),
					v2Plus6X1(9),
					v8x1(10),
					v51(11),
					v4Plus2(12),
					v4Plus2X1(13),
					v3x2(14),
					v2x2Plus2X1(15),
					v2Plus4X1(16),
					v6x1(17),
					v4(18),
					v2Plus2(19),
					v2Plus2X1(20),
					v4x1(21),
					v71(22),
					v71Screen(23)
				}
		MAX-ACCESS	read-write
		STATUS		current
		DESCRIPTION	"
			style='Radiobutton list'
			preset='v51Plus2'
			path='/Dolby 2 Encoder/Dolby 2 Encoder/Program Config'
		"
		::= { alchemistHd3GCtrlEntries 16953 }

	dolbyEncMetadataSource1 OBJECT-TYPE
		SYNTAX		INTEGER {
					internal1(0),
					decoder1(2),
					decoder2(3),
					externalIn1(4),
					externalIn2(5)
				}
		MAX-ACCESS	read-write
		STATUS		current
		DESCRIPTION	"
			style='Radiobutton list'
			preset='internal1'
			path='/Dolby 1 Encoder/Dolby 1 Encoder/Metadata Source'
		"
		::= { alchemistHd3GCtrlEntries 16954 }

	dolbyEncMetadataSource2 OBJECT-TYPE
		SYNTAX		INTEGER {
					internal2(1),
					decoder1(2),
					decoder2(3),
					externalIn1(4),
					externalIn2(5)
				}
		MAX-ACCESS	read-write
		STATUS		current
		DESCRIPTION	"
			style='Radiobutton list'
			preset='internal2'
			path='/Dolby 2 Encoder/Dolby 2 Encoder/Metadata Source'
		"
		::= { alchemistHd3GCtrlEntries 16955 }

	dolbyEncDelayOffset1 OBJECT-TYPE
		SYNTAX		Integer32 (0..250)
		MAX-ACCESS	read-write
		STATUS		current
		DESCRIPTION	"
			style='Numeric control'
			range='0mS..250mS'
			path='/Dolby 1 Encoder/Dolby 1 Encoder/Transcode Delay Offset'
		"
		::= { alchemistHd3GCtrlEntries 16960 }

	audioMono10 OBJECT-TYPE
		SYNTAX		INTEGER { disable(0), enable(1) }
		MAX-ACCESS	read-write
		STATUS		current
		DESCRIPTION	"
			style='Checkbox'
			path='/Audio Control/Audio Control A/Output A EMB 1/Mono'
		"
		::= { alchemistHd3GCtrlEntries 17200 }

	audioMute10 OBJECT-TYPE
		SYNTAX		INTEGER { disable(0), enable(1) }
		MAX-ACCESS	read-write
		STATUS		current
		DESCRIPTION	"
			style='Checkbox'
			path='/Audio Control/Audio Control A/Output A EMB 1/Mute'
		"
		::= { alchemistHd3GCtrlEntries 17201 }

	audioToneType10 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control A/Output A EMB 1/Tone'
		"
		::= { alchemistHd3GCtrlEntries 17203 }

	audioMono20 OBJECT-TYPE
		SYNTAX		INTEGER { disable(0), enable(1) }
		MAX-ACCESS	read-write
		STATUS		current
		DESCRIPTION	"
			style='Checkbox'
			path='/Audio Control/Audio Control A/Output A EMB 2/Mono'
		"
		::= { alchemistHd3GCtrlEntries 17204 }

	audioMute20 OBJECT-TYPE
		SYNTAX		INTEGER { disable(0), enable(1) }
		MAX-ACCESS	read-write
		STATUS		current
		DESCRIPTION	"
			style='Checkbox'
			path='/Audio Control/Audio Control A/Output A EMB 2/Mute'
		"
		::= { alchemistHd3GCtrlEntries 17205 }

	audioToneType20 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control A/Output A EMB 2/Tone'
		"
		::= { alchemistHd3GCtrlEntries 17207 }

	audioMono30 OBJECT-TYPE
		SYNTAX		INTEGER { disable(0), enable(1) }
		MAX-ACCESS	read-write
		STATUS		current
		DESCRIPTION	"
			style='Checkbox'
			path='/Audio Control/Audio Control A/Output A EMB 3/Mono'
		"
		::= { alchemistHd3GCtrlEntries 17208 }

	audioMute30 OBJECT-TYPE
		SYNTAX		INTEGER { disable(0), enable(1) }
		MAX-ACCESS	read-write
		STATUS		current
		DESCRIPTION	"
			style='Checkbox'
			path='/Audio Control/Audio Control A/Output A EMB 3/Mute'
		"
		::= { alchemistHd3GCtrlEntries 17209 }

	audioToneType30 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control A/Output A EMB 3/Tone'
		"
		::= { alchemistHd3GCtrlEntries 17211 }

	audioMono40 OBJECT-TYPE
		SYNTAX		INTEGER { disable(0), enable(1) }
		MAX-ACCESS	read-write
		STATUS		current
		DESCRIPTION	"
			style='Checkbox'
			path='/Audio Control/Audio Control A/Output A EMB 4/Mono'
		"
		::= { alchemistHd3GCtrlEntries 17212 }

	audioMute40 OBJECT-TYPE
		SYNTAX		INTEGER { disable(0), enable(1) }
		MAX-ACCESS	read-write
		STATUS		current
		DESCRIPTION	"
			style='Checkbox'
			path='/Audio Control/Audio Control A/Output A EMB 4/Mute'
		"
		::= { alchemistHd3GCtrlEntries 17213 }

	audioToneType40 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control A/Output A EMB 4/Tone'
		"
		::= { alchemistHd3GCtrlEntries 17215 }

	audioMono50 OBJECT-TYPE
		SYNTAX		INTEGER { disable(0), enable(1) }
		MAX-ACCESS	read-write
		STATUS		current
		DESCRIPTION	"
			style='Checkbox'
			path='/Audio Control/Audio Control A/Output A EMB 5/Mono'
		"
		::= { alchemistHd3GCtrlEntries 17216 }

	audioMute50 OBJECT-TYPE
		SYNTAX		INTEGER { disable(0), enable(1) }
		MAX-ACCESS	read-write
		STATUS		current
		DESCRIPTION	"
			style='Checkbox'
			path='/Audio Control/Audio Control A/Output A EMB 5/Mute'
		"
		::= { alchemistHd3GCtrlEntries 17217 }

	audioToneType50 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control A/Output A EMB 5/Tone'
		"
		::= { alchemistHd3GCtrlEntries 17219 }

	audioMono60 OBJECT-TYPE
		SYNTAX		INTEGER { disable(0), enable(1) }
		MAX-ACCESS	read-write
		STATUS		current
		DESCRIPTION	"
			style='Checkbox'
			path='/Audio Control/Audio Control A/Output A EMB 6/Mono'
		"
		::= { alchemistHd3GCtrlEntries 17220 }

	audioMute60 OBJECT-TYPE
		SYNTAX		INTEGER { disable(0), enable(1) }
		MAX-ACCESS	read-write
		STATUS		current
		DESCRIPTION	"
			style='Checkbox'
			path='/Audio Control/Audio Control A/Output A EMB 6/Mute'
		"
		::= { alchemistHd3GCtrlEntries 17221 }

	audioToneType60 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control A/Output A EMB 6/Tone'
		"
		::= { alchemistHd3GCtrlEntries 17223 }

	audioMono70 OBJECT-TYPE
		SYNTAX		INTEGER { disable(0), enable(1) }
		MAX-ACCESS	read-write
		STATUS		current
		DESCRIPTION	"
			style='Checkbox'
			path='/Audio Control/Audio Control A/Output A EMB 7/Mono'
		"
		::= { alchemistHd3GCtrlEntries 17224 }

	audioMute70 OBJECT-TYPE
		SYNTAX		INTEGER { disable(0), enable(1) }
		MAX-ACCESS	read-write
		STATUS		current
		DESCRIPTION	"
			style='Checkbox'
			path='/Audio Control/Audio Control A/Output A EMB 7/Mute'
		"
		::= { alchemistHd3GCtrlEntries 17225 }

	audioToneType70 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control A/Output A EMB 7/Tone'
		"
		::= { alchemistHd3GCtrlEntries 17227 }

	audioMono80 OBJECT-TYPE
		SYNTAX		INTEGER { disable(0), enable(1) }
		MAX-ACCESS	read-write
		STATUS		current
		DESCRIPTION	"
			style='Checkbox'
			path='/Audio Control/Audio Control A/Output A EMB 8/Mono'
		"
		::= { alchemistHd3GCtrlEntries 17228 }

	audioMute80 OBJECT-TYPE
		SYNTAX		INTEGER { disable(0), enable(1) }
		MAX-ACCESS	read-write
		STATUS		current
		DESCRIPTION	"
			style='Checkbox'
			path='/Audio Control/Audio Control A/Output A EMB 8/Mute'
		"
		::= { alchemistHd3GCtrlEntries 17229 }

	audioToneType80 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control A/Output A EMB 8/Tone'
		"
		::= { alchemistHd3GCtrlEntries 17231 }

	audioMono90 OBJECT-TYPE
		SYNTAX		INTEGER { disable(0), enable(1) }
		MAX-ACCESS	read-write
		STATUS		current
		DESCRIPTION	"
			style='Checkbox'
			path='/Audio Control/Audio Control B/Output B EMB 1/Mono'
		"
		::= { alchemistHd3GCtrlEntries 17232 }

	audioMute90 OBJECT-TYPE
		SYNTAX		INTEGER { disable(0), enable(1) }
		MAX-ACCESS	read-write
		STATUS		current
		DESCRIPTION	"
			style='Checkbox'
			path='/Audio Control/Audio Control B/Output B EMB 1/Mute'
		"
		::= { alchemistHd3GCtrlEntries 17233 }

	audioToneType90 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control B/Output B EMB 1/Tone'
		"
		::= { alchemistHd3GCtrlEntries 17235 }

	audioMono100 OBJECT-TYPE
		SYNTAX		INTEGER { disable(0), enable(1) }
		MAX-ACCESS	read-write
		STATUS		current
		DESCRIPTION	"
			style='Checkbox'
			path='/Audio Control/Audio Control B/Output B EMB 2/Mono'
		"
		::= { alchemistHd3GCtrlEntries 17236 }

	audioMute100 OBJECT-TYPE
		SYNTAX		INTEGER { disable(0), enable(1) }
		MAX-ACCESS	read-write
		STATUS		current
		DESCRIPTION	"
			style='Checkbox'
			path='/Audio Control/Audio Control B/Output B EMB 2/Mute'
		"
		::= { alchemistHd3GCtrlEntries 17237 }

	audioToneType100 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control B/Output B EMB 2/Tone'
		"
		::= { alchemistHd3GCtrlEntries 17239 }

	audioMono110 OBJECT-TYPE
		SYNTAX		INTEGER { disable(0), enable(1) }
		MAX-ACCESS	read-write
		STATUS		current
		DESCRIPTION	"
			style='Checkbox'
			path='/Audio Control/Audio Control B/Output B EMB 3/Mono'
		"
		::= { alchemistHd3GCtrlEntries 17240 }

	audioMute110 OBJECT-TYPE
		SYNTAX		INTEGER { disable(0), enable(1) }
		MAX-ACCESS	read-write
		STATUS		current
		DESCRIPTION	"
			style='Checkbox'
			path='/Audio Control/Audio Control B/Output B EMB 3/Mute'
		"
		::= { alchemistHd3GCtrlEntries 17241 }

	audioToneType110 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control B/Output B EMB 3/Tone'
		"
		::= { alchemistHd3GCtrlEntries 17243 }

	audioMono120 OBJECT-TYPE
		SYNTAX		INTEGER { disable(0), enable(1) }
		MAX-ACCESS	read-write
		STATUS		current
		DESCRIPTION	"
			style='Checkbox'
			path='/Audio Control/Audio Control B/Output B EMB 4/Mono'
		"
		::= { alchemistHd3GCtrlEntries 17244 }

	audioMute120 OBJECT-TYPE
		SYNTAX		INTEGER { disable(0), enable(1) }
		MAX-ACCESS	read-write
		STATUS		current
		DESCRIPTION	"
			style='Checkbox'
			path='/Audio Control/Audio Control B/Output B EMB 4/Mute'
		"
		::= { alchemistHd3GCtrlEntries 17245 }

	audioToneType120 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control B/Output B EMB 4/Tone'
		"
		::= { alchemistHd3GCtrlEntries 17247 }

	audioMono130 OBJECT-TYPE
		SYNTAX		INTEGER { disable(0), enable(1) }
		MAX-ACCESS	read-write
		STATUS		current
		DESCRIPTION	"
			style='Checkbox'
			path='/Audio Control/Audio Control B/Output B EMB 5/Mono'
		"
		::= { alchemistHd3GCtrlEntries 17248 }

	audioMute130 OBJECT-TYPE
		SYNTAX		INTEGER { disable(0), enable(1) }
		MAX-ACCESS	read-write
		STATUS		current
		DESCRIPTION	"
			style='Checkbox'
			path='/Audio Control/Audio Control B/Output B EMB 5/Mute'
		"
		::= { alchemistHd3GCtrlEntries 17249 }

	audioToneType130 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control B/Output B EMB 5/Tone'
		"
		::= { alchemistHd3GCtrlEntries 17251 }

	audioMono140 OBJECT-TYPE
		SYNTAX		INTEGER { disable(0), enable(1) }
		MAX-ACCESS	read-write
		STATUS		current
		DESCRIPTION	"
			style='Checkbox'
			path='/Audio Control/Audio Control B/Output B EMB 6/Mono'
		"
		::= { alchemistHd3GCtrlEntries 17252 }

	audioMute140 OBJECT-TYPE
		SYNTAX		INTEGER { disable(0), enable(1) }
		MAX-ACCESS	read-write
		STATUS		current
		DESCRIPTION	"
			style='Checkbox'
			path='/Audio Control/Audio Control B/Output B EMB 6/Mute'
		"
		::= { alchemistHd3GCtrlEntries 17253 }

	audioToneType140 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control B/Output B EMB 6/Tone'
		"
		::= { alchemistHd3GCtrlEntries 17255 }

	audioMono150 OBJECT-TYPE
		SYNTAX		INTEGER { disable(0), enable(1) }
		MAX-ACCESS	read-write
		STATUS		current
		DESCRIPTION	"
			style='Checkbox'
			path='/Audio Control/Audio Control B/Output B EMB 7/Mono'
		"
		::= { alchemistHd3GCtrlEntries 17256 }

	audioMute150 OBJECT-TYPE
		SYNTAX		INTEGER { disable(0), enable(1) }
		MAX-ACCESS	read-write
		STATUS		current
		DESCRIPTION	"
			style='Checkbox'
			path='/Audio Control/Audio Control B/Output B EMB 7/Mute'
		"
		::= { alchemistHd3GCtrlEntries 17257 }

	audioToneType150 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control B/Output B EMB 7/Tone'
		"
		::= { alchemistHd3GCtrlEntries 17259 }

	audioMono160 OBJECT-TYPE
		SYNTAX		INTEGER { disable(0), enable(1) }
		MAX-ACCESS	read-write
		STATUS		current
		DESCRIPTION	"
			style='Checkbox'
			path='/Audio Control/Audio Control B/Output B EMB 8/Mono'
		"
		::= { alchemistHd3GCtrlEntries 17260 }

	audioMute160 OBJECT-TYPE
		SYNTAX		INTEGER { disable(0), enable(1) }
		MAX-ACCESS	read-write
		STATUS		current
		DESCRIPTION	"
			style='Checkbox'
			path='/Audio Control/Audio Control B/Output B EMB 8/Mute'
		"
		::= { alchemistHd3GCtrlEntries 17261 }

	audioToneType160 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control B/Output B EMB 8/Tone'
		"
		::= { alchemistHd3GCtrlEntries 17263 }

	audioMono170 OBJECT-TYPE
		SYNTAX		INTEGER { disable(0), enable(1) }
		MAX-ACCESS	read-write
		STATUS		current
		DESCRIPTION	"
			style='Checkbox'
			path='/Audio Control/Audio Control AES/AES Output 1/Mono'
		"
		::= { alchemistHd3GCtrlEntries 17264 }

	audioMute170 OBJECT-TYPE
		SYNTAX		INTEGER { disable(0), enable(1) }
		MAX-ACCESS	read-write
		STATUS		current
		DESCRIPTION	"
			style='Checkbox'
			path='/Audio Control/Audio Control AES/AES Output 1/Mute'
		"
		::= { alchemistHd3GCtrlEntries 17265 }

	audioToneType170 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control AES/AES Output 1/Tone'
		"
		::= { alchemistHd3GCtrlEntries 17267 }

	audioMono180 OBJECT-TYPE
		SYNTAX		INTEGER { disable(0), enable(1) }
		MAX-ACCESS	read-write
		STATUS		current
		DESCRIPTION	"
			style='Checkbox'
			path='/Audio Control/Audio Control AES/AES Output 2/Mono'
		"
		::= { alchemistHd3GCtrlEntries 17268 }

	audioMute180 OBJECT-TYPE
		SYNTAX		INTEGER { disable(0), enable(1) }
		MAX-ACCESS	read-write
		STATUS		current
		DESCRIPTION	"
			style='Checkbox'
			path='/Audio Control/Audio Control AES/AES Output 2/Mute'
		"
		::= { alchemistHd3GCtrlEntries 17269 }

	audioToneType180 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control AES/AES Output 2/Tone'
		"
		::= { alchemistHd3GCtrlEntries 17271 }

	audioMono190 OBJECT-TYPE
		SYNTAX		INTEGER { disable(0), enable(1) }
		MAX-ACCESS	read-write
		STATUS		current
		DESCRIPTION	"
			style='Checkbox'
			path='/Audio Control/Audio Control AES/AES Output 3/Mono'
		"
		::= { alchemistHd3GCtrlEntries 17272 }

	audioMute190 OBJECT-TYPE
		SYNTAX		INTEGER { disable(0), enable(1) }
		MAX-ACCESS	read-write
		STATUS		current
		DESCRIPTION	"
			style='Checkbox'
			path='/Audio Control/Audio Control AES/AES Output 3/Mute'
		"
		::= { alchemistHd3GCtrlEntries 17273 }

	audioToneType190 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control AES/AES Output 3/Tone'
		"
		::= { alchemistHd3GCtrlEntries 17275 }

	audioMono200 OBJECT-TYPE
		SYNTAX		INTEGER { disable(0), enable(1) }
		MAX-ACCESS	read-write
		STATUS		current
		DESCRIPTION	"
			style='Checkbox'
			path='/Audio Control/Audio Control AES/AES Output 4/Mono'
		"
		::= { alchemistHd3GCtrlEntries 17276 }

	audioMute200 OBJECT-TYPE
		SYNTAX		INTEGER { disable(0), enable(1) }
		MAX-ACCESS	read-write
		STATUS		current
		DESCRIPTION	"
			style='Checkbox'
			path='/Audio Control/Audio Control AES/AES Output 4/Mute'
		"
		::= { alchemistHd3GCtrlEntries 17277 }

	audioToneType200 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control AES/AES Output 4/Tone'
		"
		::= { alchemistHd3GCtrlEntries 17279 }

	audioMono210 OBJECT-TYPE
		SYNTAX		INTEGER { disable(0), enable(1) }
		MAX-ACCESS	read-write
		STATUS		current
		DESCRIPTION	"
			style='Checkbox'
			path='/Audio Control/Audio Control AES/AES Output 5/Mono'
		"
		::= { alchemistHd3GCtrlEntries 17280 }

	audioMute210 OBJECT-TYPE
		SYNTAX		INTEGER { disable(0), enable(1) }
		MAX-ACCESS	read-write
		STATUS		current
		DESCRIPTION	"
			style='Checkbox'
			path='/Audio Control/Audio Control AES/AES Output 5/Mute'
		"
		::= { alchemistHd3GCtrlEntries 17281 }

	audioToneType210 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control AES/AES Output 5/Tone'
		"
		::= { alchemistHd3GCtrlEntries 17283 }

	audioMono220 OBJECT-TYPE
		SYNTAX		INTEGER { disable(0), enable(1) }
		MAX-ACCESS	read-write
		STATUS		current
		DESCRIPTION	"
			style='Checkbox'
			path='/Audio Control/Audio Control AES/AES Output 6/Mono'
		"
		::= { alchemistHd3GCtrlEntries 17284 }

	audioMute220 OBJECT-TYPE
		SYNTAX		INTEGER { disable(0), enable(1) }
		MAX-ACCESS	read-write
		STATUS		current
		DESCRIPTION	"
			style='Checkbox'
			path='/Audio Control/Audio Control AES/AES Output 6/Mute'
		"
		::= { alchemistHd3GCtrlEntries 17285 }

	audioToneType220 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control AES/AES Output 6/Tone'
		"
		::= { alchemistHd3GCtrlEntries 17287 }

	audioMono230 OBJECT-TYPE
		SYNTAX		INTEGER { disable(0), enable(1) }
		MAX-ACCESS	read-write
		STATUS		current
		DESCRIPTION	"
			style='Checkbox'
			path='/Audio Control/Audio Control AES/AES Output 7/Mono'
		"
		::= { alchemistHd3GCtrlEntries 17288 }

	audioMute230 OBJECT-TYPE
		SYNTAX		INTEGER { disable(0), enable(1) }
		MAX-ACCESS	read-write
		STATUS		current
		DESCRIPTION	"
			style='Checkbox'
			path='/Audio Control/Audio Control AES/AES Output 7/Mute'
		"
		::= { alchemistHd3GCtrlEntries 17289 }

	audioToneType230 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control AES/AES Output 7/Tone'
		"
		::= { alchemistHd3GCtrlEntries 17291 }

	audioMono240 OBJECT-TYPE
		SYNTAX		INTEGER { disable(0), enable(1) }
		MAX-ACCESS	read-write
		STATUS		current
		DESCRIPTION	"
			style='Checkbox'
			path='/Audio Control/Audio Control AES/AES Output 8/Mono'
		"
		::= { alchemistHd3GCtrlEntries 17292 }

	audioMute240 OBJECT-TYPE
		SYNTAX		INTEGER { disable(0), enable(1) }
		MAX-ACCESS	read-write
		STATUS		current
		DESCRIPTION	"
			style='Checkbox'
			path='/Audio Control/Audio Control AES/AES Output 8/Mute'
		"
		::= { alchemistHd3GCtrlEntries 17293 }

	audioToneType240 OBJECT-TYPE
		SYNTAX		INTEGER {
					off(9),
					v1khz20Dbfs(0),
					v4khz20Dbfs(1),
					v1khz18Dbfs(2),
					v4khz18Dbfs(3)
				}
		MAX-ACCESS	read-write
		STATUS		current
		DESCRIPTION	"
			style='Radiobutton list'
			preset='off'
			path='/Audio Control/Audio Control AES/AES Output 8/Tone'
		"
		::= { alchemistHd3GCtrlEntries 17295 }

	audioGainEnc101 OBJECT-TYPE
		SYNTAX		Integer32 (-120..120)
		MAX-ACCESS	read-write
		STATUS		current
		DESCRIPTION	"
			style='Numeric control'
			range='-12.0dB..12.0dB'
			stepsize='0.1'
			path='/Dolby 1 Encoder/Gain/Channel 1/Gain'
		"
		::= { alchemistHd3GCtrlEntries 17700 }

	audioGainEnc111 OBJECT-TYPE
		SYNTAX		Integer32 (-120..120)
		MAX-ACCESS	read-write
		STATUS		current
		DESCRIPTION	"
			style='Numeric control'
			range='-12.0dB..12.0dB'
			stepsize='0.1'
			path='/Dolby 1 Encoder/Gain/Channel 2/Gain'
		"
		::= { alchemistHd3GCtrlEntries 17701 }

	audioGainEnc201 OBJECT-TYPE
		SYNTAX		Integer32 (-120..120)
		MAX-ACCESS	read-write
		STATUS		current
		DESCRIPTION	"
			style='Numeric control'
			range='-12.0dB..12.0dB'
			stepsize='0.1'
			path='/Dolby 1 Encoder/Gain/Channel 3/Gain'
		"
		::= { alchemistHd3GCtrlEntries 17702 }

	audioGainEnc211 OBJECT-TYPE
		SYNTAX		Integer32 (-120..120)
		MAX-ACCESS	read-write
		STATUS		current
		DESCRIPTION	"
			style='Numeric control'
			range='-12.0dB..12.0dB'
			stepsize='0.1'
			path='/Dolby 1 Encoder/Gain/Channel 4/Gain'
		"
		::= { alchemistHd3GCtrlEntries 17703 }

	audioGainEnc301 OBJECT-TYPE
		SYNTAX		Integer32 (-120..120)
		MAX-ACCESS	read-write
		STATUS		current
		DESCRIPTION	"
			style='Numeric control'
			range='-12.0dB..12.0dB'
			stepsize='0.1'
			path='/Dolby 1 Encoder/Gain/Channel 5/Gain'
		"
		::= { alchemistHd3GCtrlEntries 17704 }

	audioGainEnc311 OBJECT-TYPE
		SYNTAX		Integer32 (-120..120)
		MAX-ACCESS	read-write
		STATUS		current
		DESCRIPTION	"
			style='Numeric control'
			range='-12.0dB..12.0dB'
			stepsize='0.1'
			path='/Dolby 1 Encoder/Gain/Channel 6/Gain'
		"
		::= { alchemistHd3GCtrlEntries 17705 }

	audioGainEnc401 OBJECT-TYPE
		SYNTAX		Integer32 (-120..120)
		MAX-ACCESS	read-write
		STATUS		current
		DESCRIPTION	"
			style='Numeric control'
			range='-12.0dB..12.0dB'
			stepsize='0.1'
			path='/Dolby 1 Encoder/Gain/Channel 7/Gain'
		"
		::= { alchemistHd3GCtrlEntries 17706 }

	audioGainEnc411 OBJECT-TYPE
		SYNTAX		Integer32 (-120..120)
		MAX-ACCESS	read-write
		STATUS		current
		DESCRIPTION	"
			style='Numeric control'
			range='-12.0dB..12.0dB'
			stepsize='0.1'
			path='/Dolby 1 Encoder/Gain/Channel 8/Gain'
		"
		::= { alchemistHd3GCtrlEntries 17707 }

	audioGainEnc102 OBJECT-TYPE
		SYNTAX		Integer32 (-120..120)
		MAX-ACCESS	read-write
		STATUS		current
		DESCRIPTION	"
			style='Numeric control'
			range='-12.0dB..12.0dB'
			stepsize='0.1'
			path='/Dolby 2 Encoder/Gain/Channel 1/Gain'
		"
		::= { alchemistHd3GCtrlEntries 17708 }

	audioGainEnc112 OBJECT-TYPE
		SYNTAX		Integer32 (-120..120)
		MAX-ACCESS	read-write
		STATUS		current
		DESCRIPTION	"
			style='Numeric control'
			range='-12.0dB..12.0dB'
			stepsize='0.1'
			path='/Dolby 2 Encoder/Gain/Channel 2/Gain'
		"
		::= { alchemistHd3GCtrlEntries 17709 }

	audioGainEnc202 OBJECT-TYPE
		SYNTAX		Integer32 (-120..120)
		MAX-ACCESS	read-write
		STATUS		current
		DESCRIPTION	"
			style='Numeric control'
			range='-12.0dB..12.0dB'
			stepsize='0.1'
			path='/Dolby 2 Encoder/Gain/Channel 3/Gain'
		"
		::= { alchemistHd3GCtrlEntries 17710 }

	audioGainEnc212 OBJECT-TYPE
		SYNTAX		Integer32 (-120..120)
		MAX-ACCESS	read-write
		STATUS		current
		DESCRIPTION	"
			style='Numeric control'
			range='-12.0dB..12.0dB'
			stepsize='0.1'
			path='/Dolby 2 Encoder/Gain/Channel 4/Gain'
		"
		::= { alchemistHd3GCtrlEntries 17711 }

	audioGainEnc302 OBJECT-TYPE
		SYNTAX		Integer32 (-120..120)
		MAX-ACCESS	read-write
		STATUS		current
		DESCRIPTION	"
			style='Numeric control'
			range='-12.0dB..12.0dB'
			stepsize='0.1'
			path='/Dolby 2 Encoder/Gain/Channel 5/Gain'
		"
		::= { alchemistHd3GCtrlEntries 17712 }

	audioGainEnc312 OBJECT-TYPE
		SYNTAX		Integer32 (-120..120)
		MAX-ACCESS	read-write
		STATUS		current
		DESCRIPTION	"
			style='Numeric control'
			range='-12.0dB..12.0dB'
			stepsize='0.1'
			path='/Dolby 2 Encoder/Gain/Channel 6/Gain'
		"
		::= { alchemistHd3GCtrlEntries 17713 }

	audioGainEnc402 OBJECT-TYPE
		SYNTAX		Integer32 (-120..120)
		MAX-ACCESS	read-write
		STATUS		current
		DESCRIPTION	"
			style='Numeric control'
			range='-12.0dB..12.0dB'
			stepsize='0.1'
			path='/Dolby 2 Encoder/Gain/Channel 7/Gain'
		"
		::= { alchemistHd3GCtrlEntries 17714 }

	audioGainEnc412 OBJECT-TYPE
		SYNTAX		Integer32 (-120..120)
		MAX-ACCESS	read-write
		STATUS		current
		DESCRIPTION	"
			style='Numeric control'
			range='-12.0dB..12.0dB'
			stepsize='0.1'
			path='/Dolby 2 Encoder/Gain/Channel 8/Gain'
		"
		::= { alchemistHd3GCtrlEntries 17715 }

	headphoneSourceSelectionTypeHss OBJECT-TYPE
		SYNTAX		INTEGER {
					embOrInput(1),
					aesOrInput(2),
					dec1(3),
					dec2(4),
					embOrOutA(5),
					embOrOutB(6),
					aesOrOut(7)
				}
		MAX-ACCESS	read-write
		STATUS		current
		DESCRIPTION	"
			style='Radiobutton list'
			path='/Headphones/Select Source Type'
		"
		::= { alchemistHd3GCtrlEntries 17801 }

	headphoneSourceSelectionHssAesAes OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Headphones/AES In'
		"
		::= { alchemistHd3GCtrlEntries 17803 }

	headphoneSourceSelectionHssEmbEmb OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Headphones/Embedded In'
		"
		::= { alchemistHd3GCtrlEntries 17804 }

	headphoneSourceSelectionHssDec1DlbDec1 OBJECT-TYPE
		SYNTAX		INTEGER {
					decOr11(1),
					decOr12(2),
					decOr13(3),
					decOr14(4),
					aux(5)
				}
		MAX-ACCESS	read-write
		STATUS		current
		DESCRIPTION	"
			style='Radiobutton list'
			path='/Headphones/Decoder 1 Out'
		"
		::= { alchemistHd3GCtrlEntries 17805 }

	headphoneSourceSelectionHssDec2DlbDec2 OBJECT-TYPE
		SYNTAX		INTEGER {
					decOr21(1),
					decOr22(2),
					decOr23(3),
					decOr24(4),
					aux(5)
				}
		MAX-ACCESS	read-write
		STATUS		current
		DESCRIPTION	"
			style='Radiobutton list'
			path='/Headphones/Decoder 2 Out'
		"
		::= { alchemistHd3GCtrlEntries 17806 }

	headphoneSourceSelectionHssOutEmbaOutEmba OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Headphones/Embedder A Out'
		"
		::= { alchemistHd3GCtrlEntries 17807 }

	headphoneSourceSelectionHssOutEmbbOutEmbb OBJECT-TYPE
		SYNTAX		INTEGER {
					embOr1(1),
					embOr2(2),
					embOr3(3),
					embOr4(4),
					embOr5(5),
					embOr6(6),
					embOr7(7),
					embOr8(8)
				}
		MAX-ACCESS	read-write
		STATUS		current
		DESCRIPTION	"
			style='Radiobutton list'
			path='/Headphones/Embedder B Out'
		"
		::= { alchemistHd3GCtrlEntries 17808 }

	headphoneSourceSelectionHssOutAesOutAes OBJECT-TYPE
		SYNTAX		INTEGER {
					aesOr1(1),
					aesOr2(2),
					aesOr3(3),
					aesOr4(4),
					aesOr5(5),
					aesOr6(6),
					aesOr7(7),
					aesOr8(8)
				}
		MAX-ACCESS	read-write
		STATUS		current
		DESCRIPTION	"
			style='Radiobutton list'
			path='/Headphones/AES Out'
		"
		::= { alchemistHd3GCtrlEntries 17809 }

	headphoneLevel OBJECT-TYPE
		SYNTAX		Integer32 (-120..120)
		MAX-ACCESS	read-write
		STATUS		current
		DESCRIPTION	"
			style='Numeric control'
			range='-12.0dB..12.0dB'
			stepsize='0.1'
			path='/Audio Control/Headphones/Headphones/Headphone Level'
		"
		::= { alchemistHd3GCtrlEntries 17810 }

	headphoneSource OBJECT-TYPE
		SYNTAX		INTEGER {
					embIn1(36),
					embIn2(37),
					embIn3(38),
					embIn4(39),
					embIn5(40),
					embIn6(41),
					embIn7(42),
					embIn8(43),
					aesIn1(44),
					aesIn2(45),
					aesIn3(46),
					aesIn4(47),
					aesIn5(48),
					aesIn6(49),
					aesIn7(50),
					aesIn8(51),
					dec11(26),
					dec12(27),
					dec13(28),
					dec14(29),
					dec1Aux(30),
					dec21(31),
					dec22(32),
					dec23(33),
					dec24(34),
					dec2Aux(35),
					embaOut1(0),
					embaOut2(1),
					embaOut3(2),
					embaOut4(3),
					embaOut5(4),
					embaOut6(5),
					embaOut7(6),
					embaOut8(7),
					embbOut1(8),
					embbOut2(9),
					embbOut3(10),
					embbOut4(11),
					embbOut5(12),
					embbOut6(13),
					embbOut7(14),
					embbOut8(15),
					aesOut1(16),
					aesOut2(17),
					aesOut3(18),
					aesOut4(19),
					aesOut5(20),
					aesOut6(21),
					aesOut7(22),
					aesOut8(23),
					enc1(24),
					enc2(25)
				}
		MAX-ACCESS	read-write
		STATUS		current
		DESCRIPTION	"
			style='Radiobutton list'
			preset='embaOut1'
			path='/Audio Control/Headphones/Headphones/Headphones Source'
		"
		::= { alchemistHd3GCtrlEntries 17811 }

	audioGainPresetEnc101 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 17860 }

	audioGainPresetEnc111 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 17861 }

	audioGainPresetEnc201 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 17862 }

	audioGainPresetEnc211 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 17863 }

	audioGainPresetEnc301 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 17864 }

	audioGainPresetEnc311 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 17865 }

	audioGainPresetEnc401 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 17866 }

	audioGainPresetEnc411 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 17867 }

	audioGainPresetEnc102 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 17868 }

	audioGainPresetEnc112 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 17869 }

	audioGainPresetEnc202 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 17870 }

	audioGainPresetEnc212 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 17871 }

	audioGainPresetEnc302 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 17872 }

	audioGainPresetEnc312 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 17873 }

	audioGainPresetEnc402 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 17874 }

	audioGainPresetEnc412 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 17875 }

	audioGainTrackEnc101 OBJECT-TYPE
		SYNTAX		INTEGER { disable(0), enable(1) }
		MAX-ACCESS	read-write
		STATUS		current
		DESCRIPTION	"
			style='Checkbox'
			range='0..1'
			path='/Dolby 1 Encoder/Gain/Channel 1/Track'
		"
		::= { alchemistHd3GCtrlEntries 17880 }

	audioGainTrackEnc111 OBJECT-TYPE
		SYNTAX		INTEGER { disable(0), enable(1) }
		MAX-ACCESS	read-write
		STATUS		current
		DESCRIPTION	"
			style='Checkbox'
			range='0..1'
			path='/Dolby 1 Encoder/Gain/Channel 2/Track'
		"
		::= { alchemistHd3GCtrlEntries 17881 }

	audioGainTrackEnc201 OBJECT-TYPE
		SYNTAX		INTEGER { disable(0), enable(1) }
		MAX-ACCESS	read-write
		STATUS		current
		DESCRIPTION	"
			style='Checkbox'
			range='0..1'
			path='/Dolby 1 Encoder/Gain/Channel 3/Track'
		"
		::= { alchemistHd3GCtrlEntries 17882 }

	audioGainTrackEnc211 OBJECT-TYPE
		SYNTAX		INTEGER { disable(0), enable(1) }
		MAX-ACCESS	read-write
		STATUS		current
		DESCRIPTION	"
			style='Checkbox'
			range='0..1'
			path='/Dolby 1 Encoder/Gain/Channel 4/Track'
		"
		::= { alchemistHd3GCtrlEntries 17883 }

	audioGainTrackEnc301 OBJECT-TYPE
		SYNTAX		INTEGER { disable(0), enable(1) }
		MAX-ACCESS	read-write
		STATUS		current
		DESCRIPTION	"
			style='Checkbox'
			range='0..1'
			path='/Dolby 1 Encoder/Gain/Channel 5/Track'
		"
		::= { alchemistHd3GCtrlEntries 17884 }

	audioGainTrackEnc311 OBJECT-TYPE
		SYNTAX		INTEGER { disable(0), enable(1) }
		MAX-ACCESS	read-write
		STATUS		current
		DESCRIPTION	"
			style='Checkbox'
			range='0..1'
			path='/Dolby 1 Encoder/Gain/Channel 6/Track'
		"
		::= { alchemistHd3GCtrlEntries 17885 }

	audioGainTrackEnc401 OBJECT-TYPE
		SYNTAX		INTEGER { disable(0), enable(1) }
		MAX-ACCESS	read-write
		STATUS		current
		DESCRIPTION	"
			style='Checkbox'
			range='0..1'
			path='/Dolby 1 Encoder/Gain/Channel 7/Track'
		"
		::= { alchemistHd3GCtrlEntries 17886 }

	audioGainTrackEnc411 OBJECT-TYPE
		SYNTAX		INTEGER { disable(0), enable(1) }
		MAX-ACCESS	read-write
		STATUS		current
		DESCRIPTION	"
			style='Checkbox'
			range='0..1'
			path='/Dolby 1 Encoder/Gain/Channel 8/Track'
		"
		::= { alchemistHd3GCtrlEntries 17887 }

	audioGainTrackEnc102 OBJECT-TYPE
		SYNTAX		INTEGER { disable(0), enable(1) }
		MAX-ACCESS	read-write
		STATUS		current
		DESCRIPTION	"
			style='Checkbox'
			range='0..1'
			path='/Dolby 2 Encoder/Gain/Channel 1/Track'
		"
		::= { alchemistHd3GCtrlEntries 17888 }

	audioGainTrackEnc112 OBJECT-TYPE
		SYNTAX		INTEGER { disable(0), enable(1) }
		MAX-ACCESS	read-write
		STATUS		current
		DESCRIPTION	"
			style='Checkbox'
			range='0..1'
			path='/Dolby 2 Encoder/Gain/Channel 2/Track'
		"
		::= { alchemistHd3GCtrlEntries 17889 }

	audioGainTrackEnc202 OBJECT-TYPE
		SYNTAX		INTEGER { disable(0), enable(1) }
		MAX-ACCESS	read-write
		STATUS		current
		DESCRIPTION	"
			style='Checkbox'
			range='0..1'
			path='/Dolby 2 Encoder/Gain/Channel 3/Track'
		"
		::= { alchemistHd3GCtrlEntries 17890 }

	audioGainTrackEnc212 OBJECT-TYPE
		SYNTAX		INTEGER { disable(0), enable(1) }
		MAX-ACCESS	read-write
		STATUS		current
		DESCRIPTION	"
			style='Checkbox'
			range='0..1'
			path='/Dolby 2 Encoder/Gain/Channel 4/Track'
		"
		::= { alchemistHd3GCtrlEntries 17891 }

	audioGainTrackEnc302 OBJECT-TYPE
		SYNTAX		INTEGER { disable(0), enable(1) }
		MAX-ACCESS	read-write
		STATUS		current
		DESCRIPTION	"
			style='Checkbox'
			range='0..1'
			path='/Dolby 2 Encoder/Gain/Channel 5/Track'
		"
		::= { alchemistHd3GCtrlEntries 17892 }

	audioGainTrackEnc312 OBJECT-TYPE
		SYNTAX		INTEGER { disable(0), enable(1) }
		MAX-ACCESS	read-write
		STATUS		current
		DESCRIPTION	"
			style='Checkbox'
			range='0..1'
			path='/Dolby 2 Encoder/Gain/Channel 6/Track'
		"
		::= { alchemistHd3GCtrlEntries 17893 }

	audioGainTrackEnc402 OBJECT-TYPE
		SYNTAX		INTEGER { disable(0), enable(1) }
		MAX-ACCESS	read-write
		STATUS		current
		DESCRIPTION	"
			style='Checkbox'
			range='0..1'
			path='/Dolby 2 Encoder/Gain/Channel 7/Track'
		"
		::= { alchemistHd3GCtrlEntries 17894 }

	audioGainTrackEnc412 OBJECT-TYPE
		SYNTAX		INTEGER { disable(0), enable(1) }
		MAX-ACCESS	read-write
		STATUS		current
		DESCRIPTION	"
			style='Checkbox'
			range='0..1'
			path='/Dolby 2 Encoder/Gain/Channel 8/Track'
		"
		::= { alchemistHd3GCtrlEntries 17895 }

	dolbyDecSrc1 OBJECT-TYPE
		SYNTAX		INTEGER {
					emb1(8),
					emb2(9),
					emb3(10),
					emb4(11),
					emb5(12),
					emb6(13),
					emb7(14),
					emb8(15),
					aes1(0),
					aes2(1),
					aes3(2),
					aes4(3),
					aes5(4),
					aes6(5),
					aes7(6),
					aes8(7),
					enc1(16),
					enc2(17)
				}
		MAX-ACCESS	read-write
		STATUS		current
		DESCRIPTION	"
			style='Radiobutton list'
			preset='aes1'
			path='/Dolby Decoder/Dolby Decoder/Decoder 1 Input'
		"
		::= { alchemistHd3GCtrlEntries 17975 }

	dolbyDecSrcEmb1 OBJECT-TYPE
		SYNTAX		INTEGER {
					embOr1(8),
					embOr2(9),
					embOr3(10),
					embOr4(11),
					embOr5(12),
					embOr6(13),
					embOr7(14),
					embOr8(15)
				}
		MAX-ACCESS	read-write
		STATUS		current
		DESCRIPTION	"
			style='Radiobutton list'
			path='/Audio Source Select DEC 1/Embedded Inputs'
		"
		::= { alchemistHd3GCtrlEntries 17976 }

	dolbyDecSrcAes1 OBJECT-TYPE
		SYNTAX		INTEGER {
					aesOr1(0),
					aesOr2(1),
					aesOr3(2),
					aesOr4(3),
					aesOr5(4),
					aesOr6(5),
					aesOr7(6),
					aesOr8(7)
				}
		MAX-ACCESS	read-write
		STATUS		current
		DESCRIPTION	"
			style='Radiobutton list'
			preset='aesOr1'
			path='/Audio Source Select DEC 1/AES Inputs'
		"
		::= { alchemistHd3GCtrlEntries 17977 }

	dolbyDecSrcEnc1 OBJECT-TYPE
		SYNTAX		INTEGER {
					encOr1(16),
					encOr2(17)
				}
		MAX-ACCESS	read-write
		STATUS		current
		DESCRIPTION	"
			style='Radiobutton list'
			path='/Audio Source Select DEC 1/Encoder'
		"
		::= { alchemistHd3GCtrlEntries 17978 }

	dolbyDecSrc2 OBJECT-TYPE
		SYNTAX		INTEGER {
					emb1(8),
					emb2(9),
					emb3(10),
					emb4(11),
					emb5(12),
					emb6(13),
					emb7(14),
					emb8(15),
					aes1(0),
					aes2(1),
					aes3(2),
					aes4(3),
					aes5(4),
					aes6(5),
					aes7(6),
					aes8(7),
					enc1(16),
					enc2(17)
				}
		MAX-ACCESS	read-write
		STATUS		current
		DESCRIPTION	"
			style='Radiobutton list'
			preset='aes1'
			path='/Dolby 2 Decoder/Dolby 2 Decoder/Decoder 2 Input'
		"
		::= { alchemistHd3GCtrlEntries 17979 }

	dolbyDecSrcEmb2 OBJECT-TYPE
		SYNTAX		INTEGER {
					embOr1(8),
					embOr2(9),
					embOr3(10),
					embOr4(11),
					embOr5(12),
					embOr6(13),
					embOr7(14),
					embOr8(15)
				}
		MAX-ACCESS	read-write
		STATUS		current
		DESCRIPTION	"
			style='Radiobutton list'
			path='/Audio Source Select DEC 2/Embedded Inputs'
		"
		::= { alchemistHd3GCtrlEntries 17980 }

	dolbyDecSrcAes2 OBJECT-TYPE
		SYNTAX		INTEGER {
					aesOr1(0),
					aesOr2(1),
					aesOr3(2),
					aesOr4(3),
					aesOr5(4),
					aesOr6(5),
					aesOr7(6),
					aesOr8(7)
				}
		MAX-ACCESS	read-write
		STATUS		current
		DESCRIPTION	"
			style='Radiobutton list'
			preset='aesOr1'
			path='/Audio Source Select DEC 2/AES Inputs'
		"
		::= { alchemistHd3GCtrlEntries 17981 }

	dolbyDecSrcEnc2 OBJECT-TYPE
		SYNTAX		INTEGER {
					encOr1(16),
					encOr2(17)
				}
		MAX-ACCESS	read-write
		STATUS		current
		DESCRIPTION	"
			style='Radiobutton list'
			path='/Audio Source Select DEC 2/Encoder'
		"
		::= { alchemistHd3GCtrlEntries 17982 }

	audioDelay10 OBJECT-TYPE
		SYNTAX		Integer32 (-250..250)
		MAX-ACCESS	read-write
		STATUS		current
		DESCRIPTION	"
			style='Numeric control'
			range='-250mS..250mS'
			path='/Audio Control/Audio Control A/Output A EMB 1/Channel 1/Delay'
		"
		::= { alchemistHd3GCtrlEntries 18820 }

	audioDelay20 OBJECT-TYPE
		SYNTAX		Integer32 (-250..250)
		MAX-ACCESS	read-write
		STATUS		current
		DESCRIPTION	"
			style='Numeric control'
			range='-250mS..250mS'
			path='/Audio Control/Audio Control A/Output A EMB 2/Channel 1/Delay'
		"
		::= { alchemistHd3GCtrlEntries 18821 }

	audioDelay30 OBJECT-TYPE
		SYNTAX		Integer32 (-250..250)
		MAX-ACCESS	read-write
		STATUS		current
		DESCRIPTION	"
			style='Numeric control'
			range='-250mS..250mS'
			path='/Audio Control/Audio Control A/Output A EMB 3/Channel 1/Delay'
		"
		::= { alchemistHd3GCtrlEntries 18822 }

	audioDelay40 OBJECT-TYPE
		SYNTAX		Integer32 (-250..250)
		MAX-ACCESS	read-write
		STATUS		current
		DESCRIPTION	"
			style='Numeric control'
			range='-250mS..250mS'
			path='/Audio Control/Audio Control A/Output A EMB 4/Channel 1/Delay'
		"
		::= { alchemistHd3GCtrlEntries 18823 }

	audioDelay50 OBJECT-TYPE
		SYNTAX		Integer32 (-250..250)
		MAX-ACCESS	read-write
		STATUS		current
		DESCRIPTION	"
			style='Numeric control'
			range='-250mS..250mS'
			path='/Audio Control/Audio Control A/Output A EMB 5/Channel 1/Delay'
		"
		::= { alchemistHd3GCtrlEntries 18824 }

	audioDelay60 OBJECT-TYPE
		SYNTAX		Integer32 (-250..250)
		MAX-ACCESS	read-write
		STATUS		current
		DESCRIPTION	"
			style='Numeric control'
			range='-250mS..250mS'
			path='/Audio Control/Audio Control A/Output A EMB 6/Channel 1/Delay'
		"
		::= { alchemistHd3GCtrlEntries 18825 }

	audioDelay70 OBJECT-TYPE
		SYNTAX		Integer32 (-250..250)
		MAX-ACCESS	read-write
		STATUS		current
		DESCRIPTION	"
			style='Numeric control'
			range='-250mS..250mS'
			path='/Audio Control/Audio Control A/Output A EMB 7/Channel 1/Delay'
		"
		::= { alchemistHd3GCtrlEntries 18826 }

	audioDelay80 OBJECT-TYPE
		SYNTAX		Integer32 (-250..250)
		MAX-ACCESS	read-write
		STATUS		current
		DESCRIPTION	"
			style='Numeric control'
			range='-250mS..250mS'
			path='/Audio Control/Audio Control A/Output A EMB 8/Channel 1/Delay'
		"
		::= { alchemistHd3GCtrlEntries 18827 }

	audioDelay90 OBJECT-TYPE
		SYNTAX		Integer32 (-250..250)
		MAX-ACCESS	read-write
		STATUS		current
		DESCRIPTION	"
			style='Numeric control'
			range='-250mS..250mS'
			path='/Audio Control/Audio Control B/Output B EMB 1/Channel 1/Delay'
		"
		::= { alchemistHd3GCtrlEntries 18828 }

	audioDelay100 OBJECT-TYPE
		SYNTAX		Integer32 (-250..250)
		MAX-ACCESS	read-write
		STATUS		current
		DESCRIPTION	"
			style='Numeric control'
			range='-250mS..250mS'
			path='/Audio Control/Audio Control B/Output B EMB 2/Channel 1/Delay'
		"
		::= { alchemistHd3GCtrlEntries 18829 }

	audioDelay110 OBJECT-TYPE
		SYNTAX		Integer32 (-250..250)
		MAX-ACCESS	read-write
		STATUS		current
		DESCRIPTION	"
			style='Numeric control'
			range='-250mS..250mS'
			path='/Audio Control/Audio Control B/Output B EMB 3/Channel 1/Delay'
		"
		::= { alchemistHd3GCtrlEntries 18830 }

	audioDelay120 OBJECT-TYPE
		SYNTAX		Integer32 (-250..250)
		MAX-ACCESS	read-write
		STATUS		current
		DESCRIPTION	"
			style='Numeric control'
			range='-250mS..250mS'
			path='/Audio Control/Audio Control B/Output B EMB 4/Channel 1/Delay'
		"
		::= { alchemistHd3GCtrlEntries 18831 }

	audioDelay130 OBJECT-TYPE
		SYNTAX		Integer32 (-250..250)
		MAX-ACCESS	read-write
		STATUS		current
		DESCRIPTION	"
			style='Numeric control'
			range='-250mS..250mS'
			path='/Audio Control/Audio Control B/Output B EMB 5/Channel 1/Delay'
		"
		::= { alchemistHd3GCtrlEntries 18832 }

	audioDelay140 OBJECT-TYPE
		SYNTAX		Integer32 (-250..250)
		MAX-ACCESS	read-write
		STATUS		current
		DESCRIPTION	"
			style='Numeric control'
			range='-250mS..250mS'
			path='/Audio Control/Audio Control B/Output B EMB 6/Channel 1/Delay'
		"
		::= { alchemistHd3GCtrlEntries 18833 }

	audioDelay150 OBJECT-TYPE
		SYNTAX		Integer32 (-250..250)
		MAX-ACCESS	read-write
		STATUS		current
		DESCRIPTION	"
			style='Numeric control'
			range='-250mS..250mS'
			path='/Audio Control/Audio Control B/Output B EMB 7/Channel 1/Delay'
		"
		::= { alchemistHd3GCtrlEntries 18834 }

	audioDelay160 OBJECT-TYPE
		SYNTAX		Integer32 (-250..250)
		MAX-ACCESS	read-write
		STATUS		current
		DESCRIPTION	"
			style='Numeric control'
			range='-250mS..250mS'
			path='/Audio Control/Audio Control B/Output B EMB 8/Channel 1/Delay'
		"
		::= { alchemistHd3GCtrlEntries 18835 }

	audioDelay170 OBJECT-TYPE
		SYNTAX		Integer32 (-250..250)
		MAX-ACCESS	read-write
		STATUS		current
		DESCRIPTION	"
			style='Numeric control'
			range='-250mS..250mS'
			path='/Audio Control/Audio Control AES/AES Output 1/Channel 1/Delay'
		"
		::= { alchemistHd3GCtrlEntries 18836 }

	audioDelay180 OBJECT-TYPE
		SYNTAX		Integer32 (-250..250)
		MAX-ACCESS	read-write
		STATUS		current
		DESCRIPTION	"
			style='Numeric control'
			range='-250mS..250mS'
			path='/Audio Control/Audio Control AES/AES Output 2/Channel 1/Delay'
		"
		::= { alchemistHd3GCtrlEntries 18837 }

	audioDelay190 OBJECT-TYPE
		SYNTAX		Integer32 (-250..250)
		MAX-ACCESS	read-write
		STATUS		current
		DESCRIPTION	"
			style='Numeric control'
			range='-250mS..250mS'
			path='/Audio Control/Audio Control AES/AES Output 3/Channel 1/Delay'
		"
		::= { alchemistHd3GCtrlEntries 18838 }

	audioDelay200 OBJECT-TYPE
		SYNTAX		Integer32 (-250..250)
		MAX-ACCESS	read-write
		STATUS		current
		DESCRIPTION	"
			style='Numeric control'
			range='-250mS..250mS'
			path='/Audio Control/Audio Control AES/AES Output 4/Channel 1/Delay'
		"
		::= { alchemistHd3GCtrlEntries 18839 }

	audioDelay210 OBJECT-TYPE
		SYNTAX		Integer32 (-250..250)
		MAX-ACCESS	read-write
		STATUS		current
		DESCRIPTION	"
			style='Numeric control'
			range='-250mS..250mS'
			path='/Audio Control/Audio Control AES/AES Output 5/Channel 1/Delay'
		"
		::= { alchemistHd3GCtrlEntries 18840 }

	audioDelay220 OBJECT-TYPE
		SYNTAX		Integer32 (-250..250)
		MAX-ACCESS	read-write
		STATUS		current
		DESCRIPTION	"
			style='Numeric control'
			range='-250mS..250mS'
			path='/Audio Control/Audio Control AES/AES Output 6/Channel 1/Delay'
		"
		::= { alchemistHd3GCtrlEntries 18841 }

	audioDelay230 OBJECT-TYPE
		SYNTAX		Integer32 (-250..250)
		MAX-ACCESS	read-write
		STATUS		current
		DESCRIPTION	"
			style='Numeric control'
			range='-250mS..250mS'
			path='/Audio Control/Audio Control AES/AES Output 7/Channel 1/Delay'
		"
		::= { alchemistHd3GCtrlEntries 18842 }

	audioDelay240 OBJECT-TYPE
		SYNTAX		Integer32 (-250..250)
		MAX-ACCESS	read-write
		STATUS		current
		DESCRIPTION	"
			style='Numeric control'
			range='-250mS..250mS'
			path='/Audio Control/Audio Control AES/AES Output 8/Channel 1/Delay'
		"
		::= { alchemistHd3GCtrlEntries 18843 }

	audioDelay11 OBJECT-TYPE
		SYNTAX		Integer32 (-250..250)
		MAX-ACCESS	read-write
		STATUS		current
		DESCRIPTION	"
			style='Numeric control'
			range='-250mS..250mS'
			path='/Audio Control/Audio Control A/Output A EMB 1/Channel 2/Delay'
		"
		::= { alchemistHd3GCtrlEntries 18850 }

	audioDelay21 OBJECT-TYPE
		SYNTAX		Integer32 (-250..250)
		MAX-ACCESS	read-write
		STATUS		current
		DESCRIPTION	"
			style='Numeric control'
			range='-250mS..250mS'
			path='/Audio Control/Audio Control A/Output A EMB 2/Channel 1/Delay'
		"
		::= { alchemistHd3GCtrlEntries 18851 }

	audioDelay31 OBJECT-TYPE
		SYNTAX		Integer32 (-250..250)
		MAX-ACCESS	read-write
		STATUS		current
		DESCRIPTION	"
			style='Numeric control'
			range='-250mS..250mS'
			path='/Audio Control/Audio Control A/Output A EMB 3/Channel 2/Delay'
		"
		::= { alchemistHd3GCtrlEntries 18852 }

	audioDelay41 OBJECT-TYPE
		SYNTAX		Integer32 (-250..250)
		MAX-ACCESS	read-write
		STATUS		current
		DESCRIPTION	"
			style='Numeric control'
			range='-250mS..250mS'
			path='/Audio Control/Audio Control A/Output A EMB 4/Channel 2/Delay'
		"
		::= { alchemistHd3GCtrlEntries 18853 }

	audioDelay51 OBJECT-TYPE
		SYNTAX		Integer32 (-250..250)
		MAX-ACCESS	read-write
		STATUS		current
		DESCRIPTION	"
			style='Numeric control'
			range='-250mS..250mS'
			path='/Audio Control/Audio Control A/Output A EMB 5/Channel 2/Delay'
		"
		::= { alchemistHd3GCtrlEntries 18854 }

	audioDelay61 OBJECT-TYPE
		SYNTAX		Integer32 (-250..250)
		MAX-ACCESS	read-write
		STATUS		current
		DESCRIPTION	"
			style='Numeric control'
			range='-250mS..250mS'
			path='/Audio Control/Audio Control A/Output A EMB 6/Channel 2/Delay'
		"
		::= { alchemistHd3GCtrlEntries 18855 }

	audioDelay71 OBJECT-TYPE
		SYNTAX		Integer32 (-250..250)
		MAX-ACCESS	read-write
		STATUS		current
		DESCRIPTION	"
			style='Numeric control'
			range='-250mS..250mS'
			path='/Audio Control/Audio Control A/Output A EMB 7/Channel 2/Delay'
		"
		::= { alchemistHd3GCtrlEntries 18856 }

	audioDelay81 OBJECT-TYPE
		SYNTAX		Integer32 (-250..250)
		MAX-ACCESS	read-write
		STATUS		current
		DESCRIPTION	"
			style='Numeric control'
			range='-250mS..250mS'
			path='/Audio Control/Audio Control A/Output A EMB 8/Channel 2/Delay'
		"
		::= { alchemistHd3GCtrlEntries 18857 }

	audioDelay91 OBJECT-TYPE
		SYNTAX		Integer32 (-250..250)
		MAX-ACCESS	read-write
		STATUS		current
		DESCRIPTION	"
			style='Numeric control'
			range='-250mS..250mS'
			path='/Audio Control/Audio Control B/Output B EMB 1/Channel 2/Delay'
		"
		::= { alchemistHd3GCtrlEntries 18858 }

	audioDelay101 OBJECT-TYPE
		SYNTAX		Integer32 (-250..250)
		MAX-ACCESS	read-write
		STATUS		current
		DESCRIPTION	"
			style='Numeric control'
			range='-250mS..250mS'
			path='/Audio Control/Audio Control B/Output B EMB 2/Channel 1/Delay'
		"
		::= { alchemistHd3GCtrlEntries 18859 }

	audioDelay111 OBJECT-TYPE
		SYNTAX		Integer32 (-250..250)
		MAX-ACCESS	read-write
		STATUS		current
		DESCRIPTION	"
			style='Numeric control'
			range='-250mS..250mS'
			path='/Audio Control/Audio Control B/Output B EMB 3/Channel 2/Delay'
		"
		::= { alchemistHd3GCtrlEntries 18860 }

	audioDelay121 OBJECT-TYPE
		SYNTAX		Integer32 (-250..250)
		MAX-ACCESS	read-write
		STATUS		current
		DESCRIPTION	"
			style='Numeric control'
			range='-250mS..250mS'
			path='/Audio Control/Audio Control B/Output B EMB 4/Channel 2/Delay'
		"
		::= { alchemistHd3GCtrlEntries 18861 }

	audioDelay131 OBJECT-TYPE
		SYNTAX		Integer32 (-250..250)
		MAX-ACCESS	read-write
		STATUS		current
		DESCRIPTION	"
			style='Numeric control'
			range='-250mS..250mS'
			path='/Audio Control/Audio Control B/Output B EMB 5/Channel 2/Delay'
		"
		::= { alchemistHd3GCtrlEntries 18862 }

	audioDelay141 OBJECT-TYPE
		SYNTAX		Integer32 (-250..250)
		MAX-ACCESS	read-write
		STATUS		current
		DESCRIPTION	"
			style='Numeric control'
			range='-250mS..250mS'
			path='/Audio Control/Audio Control B/Output B EMB 6/Channel 2/Delay'
		"
		::= { alchemistHd3GCtrlEntries 18863 }

	audioDelay151 OBJECT-TYPE
		SYNTAX		Integer32 (-250..250)
		MAX-ACCESS	read-write
		STATUS		current
		DESCRIPTION	"
			style='Numeric control'
			range='-250mS..250mS'
			path='/Audio Control/Audio Control B/Output B EMB 7/Channel 2/Delay'
		"
		::= { alchemistHd3GCtrlEntries 18864 }

	audioDelay161 OBJECT-TYPE
		SYNTAX		Integer32 (-250..250)
		MAX-ACCESS	read-write
		STATUS		current
		DESCRIPTION	"
			style='Numeric control'
			range='-250mS..250mS'
			path='/Audio Control/Audio Control B/Output B EMB 8/Channel 2/Delay'
		"
		::= { alchemistHd3GCtrlEntries 18865 }

	audioDelay171 OBJECT-TYPE
		SYNTAX		Integer32 (-250..250)
		MAX-ACCESS	read-write
		STATUS		current
		DESCRIPTION	"
			style='Numeric control'
			range='-250mS..250mS'
			path='/Audio Control/Audio Control AES/AES Output 1/Channel 2/Delay'
		"
		::= { alchemistHd3GCtrlEntries 18866 }

	audioDelay181 OBJECT-TYPE
		SYNTAX		Integer32 (-250..250)
		MAX-ACCESS	read-write
		STATUS		current
		DESCRIPTION	"
			style='Numeric control'
			range='-250mS..250mS'
			path='/Audio Control/Audio Control AES/AES Output 2/Channel 1/Delay'
		"
		::= { alchemistHd3GCtrlEntries 18867 }

	audioDelay191 OBJECT-TYPE
		SYNTAX		Integer32 (-250..250)
		MAX-ACCESS	read-write
		STATUS		current
		DESCRIPTION	"
			style='Numeric control'
			range='-250mS..250mS'
			path='/Audio Control/Audio Control AES/AES Output 3/Channel 2/Delay'
		"
		::= { alchemistHd3GCtrlEntries 18868 }

	audioDelay201 OBJECT-TYPE
		SYNTAX		Integer32 (-250..250)
		MAX-ACCESS	read-write
		STATUS		current
		DESCRIPTION	"
			style='Numeric control'
			range='-250mS..250mS'
			path='/Audio Control/Audio Control AES/AES Output 4/Channel 2/Delay'
		"
		::= { alchemistHd3GCtrlEntries 18869 }

	audioDelay211 OBJECT-TYPE
		SYNTAX		Integer32 (-250..250)
		MAX-ACCESS	read-write
		STATUS		current
		DESCRIPTION	"
			style='Numeric control'
			range='-250mS..250mS'
			path='/Audio Control/Audio Control AES/AES Output 5/Channel 2/Delay'
		"
		::= { alchemistHd3GCtrlEntries 18870 }

	audioDelay221 OBJECT-TYPE
		SYNTAX		Integer32 (-250..250)
		MAX-ACCESS	read-write
		STATUS		current
		DESCRIPTION	"
			style='Numeric control'
			range='-250mS..250mS'
			path='/Audio Control/Audio Control AES/AES Output 6/Channel 2/Delay'
		"
		::= { alchemistHd3GCtrlEntries 18871 }

	audioDelay231 OBJECT-TYPE
		SYNTAX		Integer32 (-250..250)
		MAX-ACCESS	read-write
		STATUS		current
		DESCRIPTION	"
			style='Numeric control'
			range='-250mS..250mS'
			path='/Audio Control/Audio Control AES/AES Output 7/Channel 2/Delay'
		"
		::= { alchemistHd3GCtrlEntries 18872 }

	audioDelay241 OBJECT-TYPE
		SYNTAX		Integer32 (-250..250)
		MAX-ACCESS	read-write
		STATUS		current
		DESCRIPTION	"
			style='Numeric control'
			range='-250mS..250mS'
			path='/Audio Control/Audio Control AES/AES Output 8/Channel 2/Delay'
		"
		::= { alchemistHd3GCtrlEntries 18873 }

	audioDelayPreset10 OBJECT-TYPE
		SYNTAX		INTEGER { ready(0), trigger(1) }
		MAX-ACCESS	read-write
		STATUS		current
		DESCRIPTION	"
			style='Event button'
			path='/Audio Control/Audio Control A/Output A EMB 1/Preset'
		"
		::= { alchemistHd3GCtrlEntries 18880 }

	audioDelayPreset20 OBJECT-TYPE
		SYNTAX		INTEGER { ready(0), trigger(1) }
		MAX-ACCESS	read-write
		STATUS		current
		DESCRIPTION	"
			style='Event button'
			path='/Audio Control/Audio Control A/Output A EMB 2/Preset'
		"
		::= { alchemistHd3GCtrlEntries 18881 }

	audioDelayPreset30 OBJECT-TYPE
		SYNTAX		INTEGER { ready(0), trigger(1) }
		MAX-ACCESS	read-write
		STATUS		current
		DESCRIPTION	"
			style='Event button'
			path='/Audio Control/Audio Control A/Output A EMB 3/Preset'
		"
		::= { alchemistHd3GCtrlEntries 18882 }

	audioDelayPreset40 OBJECT-TYPE
		SYNTAX		INTEGER { ready(0), trigger(1) }
		MAX-ACCESS	read-write
		STATUS		current
		DESCRIPTION	"
			style='Event button'
			path='/Audio Control/Audio Control A/Output A EMB 4/Preset'
		"
		::= { alchemistHd3GCtrlEntries 18883 }

	audioDelayPreset50 OBJECT-TYPE
		SYNTAX		INTEGER { ready(0), trigger(1) }
		MAX-ACCESS	read-write
		STATUS		current
		DESCRIPTION	"
			style='Event button'
			path='/Audio Control/Audio Control A/Output A EMB 5/Preset'
		"
		::= { alchemistHd3GCtrlEntries 18884 }

	audioDelayPreset60 OBJECT-TYPE
		SYNTAX		INTEGER { ready(0), trigger(1) }
		MAX-ACCESS	read-write
		STATUS		current
		DESCRIPTION	"
			style='Event button'
			path='/Audio Control/Audio Control A/Output A EMB 6/Preset'
		"
		::= { alchemistHd3GCtrlEntries 18885 }

	audioDelayPreset70 OBJECT-TYPE
		SYNTAX		INTEGER { ready(0), trigger(1) }
		MAX-ACCESS	read-write
		STATUS		current
		DESCRIPTION	"
			style='Event button'
			path='/Audio Control/Audio Control A/Output A EMB 7/Preset'
		"
		::= { alchemistHd3GCtrlEntries 18886 }

	audioDelayPreset80 OBJECT-TYPE
		SYNTAX		INTEGER { ready(0), trigger(1) }
		MAX-ACCESS	read-write
		STATUS		current
		DESCRIPTION	"
			style='Event button'
			path='/Audio Control/Audio Control A/Output A EMB 8/Preset'
		"
		::= { alchemistHd3GCtrlEntries 18887 }

	audioDelayPreset90 OBJECT-TYPE
		SYNTAX		INTEGER { ready(0), trigger(1) }
		MAX-ACCESS	read-write
		STATUS		current
		DESCRIPTION	"
			style='Event button'
			path='/Audio Control/Audio Control B/Output B EMB 1/Preset'
		"
		::= { alchemistHd3GCtrlEntries 18888 }

	audioDelayPreset100 OBJECT-TYPE
		SYNTAX		INTEGER { ready(0), trigger(1) }
		MAX-ACCESS	read-write
		STATUS		current
		DESCRIPTION	"
			style='Event button'
			path='/Audio Control/Audio Control B/Output B EMB 2/Preset'
		"
		::= { alchemistHd3GCtrlEntries 18889 }

	audioDelayPreset110 OBJECT-TYPE
		SYNTAX		INTEGER { ready(0), trigger(1) }
		MAX-ACCESS	read-write
		STATUS		current
		DESCRIPTION	"
			style='Event button'
			path='/Audio Control/Audio Control B/Output B EMB 3/Preset'
		"
		::= { alchemistHd3GCtrlEntries 18890 }

	audioDelayPreset120 OBJECT-TYPE
		SYNTAX		INTEGER { ready(0), trigger(1) }
		MAX-ACCESS	read-write
		STATUS		current
		DESCRIPTION	"
			style='Event button'
			path='/Audio Control/Audio Control B/Output B EMB 4/Preset'
		"
		::= { alchemistHd3GCtrlEntries 18891 }

	audioDelayPreset130 OBJECT-TYPE
		SYNTAX		INTEGER { ready(0), trigger(1) }
		MAX-ACCESS	read-write
		STATUS		current
		DESCRIPTION	"
			style='Event button'
			path='/Audio Control/Audio Control B/Output B EMB 5/Preset'
		"
		::= { alchemistHd3GCtrlEntries 18892 }

	audioDelayPreset140 OBJECT-TYPE
		SYNTAX		INTEGER { ready(0), trigger(1) }
		MAX-ACCESS	read-write
		STATUS		current
		DESCRIPTION	"
			style='Event button'
			path='/Audio Control/Audio Control B/Output B EMB 6/Preset'
		"
		::= { alchemistHd3GCtrlEntries 18893 }

	audioDelayPreset150 OBJECT-TYPE
		SYNTAX		INTEGER { ready(0), trigger(1) }
		MAX-ACCESS	read-write
		STATUS		current
		DESCRIPTION	"
			style='Event button'
			path='/Audio Control/Audio Control B/Output B EMB 7/Preset'
		"
		::= { alchemistHd3GCtrlEntries 18894 }

	audioDelayPreset160 OBJECT-TYPE
		SYNTAX		INTEGER { ready(0), trigger(1) }
		MAX-ACCESS	read-write
		STATUS		current
		DESCRIPTION	"
			style='Event button'
			path='/Audio Control/Audio Control B/Output B EMB 8/Preset'
		"
		::= { alchemistHd3GCtrlEntries 18895 }

	audioDelayPreset170 OBJECT-TYPE
		SYNTAX		INTEGER { ready(0), trigger(1) }
		MAX-ACCESS	read-write
		STATUS		current
		DESCRIPTION	"
			style='Event button'
			path='/Audio Control/Audio Control AES/AES Output 1/Preset'
		"
		::= { alchemistHd3GCtrlEntries 18896 }

	audioDelayPreset180 OBJECT-TYPE
		SYNTAX		INTEGER { ready(0), trigger(1) }
		MAX-ACCESS	read-write
		STATUS		current
		DESCRIPTION	"
			style='Event button'
			path='/Audio Control/Audio Control AES/AES Output 2/Preset'
		"
		::= { alchemistHd3GCtrlEntries 18897 }

	audioDelayPreset190 OBJECT-TYPE
		SYNTAX		INTEGER { ready(0), trigger(1) }
		MAX-ACCESS	read-write
		STATUS		current
		DESCRIPTION	"
			style='Event button'
			path='/Audio Control/Audio Control AES/AES Output 3/Preset'
		"
		::= { alchemistHd3GCtrlEntries 18898 }

	audioDelayPreset200 OBJECT-TYPE
		SYNTAX		INTEGER { ready(0), trigger(1) }
		MAX-ACCESS	read-write
		STATUS		current
		DESCRIPTION	"
			style='Event button'
			path='/Audio Control/Audio Control AES/AES Output 4/Preset'
		"
		::= { alchemistHd3GCtrlEntries 18899 }

	audioDelayPreset210 OBJECT-TYPE
		SYNTAX		INTEGER { ready(0), trigger(1) }
		MAX-ACCESS	read-write
		STATUS		current
		DESCRIPTION	"
			style='Event button'
			path='/Audio Control/Audio Control AES/AES Output 5/Preset'
		"
		::= { alchemistHd3GCtrlEntries 18900 }

	audioDelayPreset220 OBJECT-TYPE
		SYNTAX		INTEGER { ready(0), trigger(1) }
		MAX-ACCESS	read-write
		STATUS		current
		DESCRIPTION	"
			style='Event button'
			path='/Audio Control/Audio Control AES/AES Output 6/Preset'
		"
		::= { alchemistHd3GCtrlEntries 18901 }

	audioDelayPreset230 OBJECT-TYPE
		SYNTAX		INTEGER { ready(0), trigger(1) }
		MAX-ACCESS	read-write
		STATUS		current
		DESCRIPTION	"
			style='Event button'
			path='/Audio Control/Audio Control AES/AES Output 7/Preset'
		"
		::= { alchemistHd3GCtrlEntries 18902 }

	audioDelayPreset240 OBJECT-TYPE
		SYNTAX		INTEGER { ready(0), trigger(1) }
		MAX-ACCESS	read-write
		STATUS		current
		DESCRIPTION	"
			style='Event button'
			path='/Audio Control/Audio Control AES/AES Output 8/Preset'
		"
		::= { alchemistHd3GCtrlEntries 18903 }

	audioDelayPreset11 OBJECT-TYPE
		SYNTAX		INTEGER { ready(0), trigger(1) }
		MAX-ACCESS	read-write
		STATUS		current
		DESCRIPTION	"
			style='Event button'
			path='/Audio Control/Audio Control A/Output A EMB 1/Preset'
		"
		::= { alchemistHd3GCtrlEntries 18910 }

	audioDelayPreset21 OBJECT-TYPE
		SYNTAX		INTEGER { ready(0), trigger(1) }
		MAX-ACCESS	read-write
		STATUS		current
		DESCRIPTION	"
			style='Event button'
			path='/Audio Control/Audio Control A/Output A EMB 2/Preset'
		"
		::= { alchemistHd3GCtrlEntries 18911 }

	audioDelayPreset31 OBJECT-TYPE
		SYNTAX		INTEGER { ready(0), trigger(1) }
		MAX-ACCESS	read-write
		STATUS		current
		DESCRIPTION	"
			style='Event button'
			path='/Audio Control/Audio Control A/Output A EMB 3/Preset'
		"
		::= { alchemistHd3GCtrlEntries 18912 }

	audioDelayPreset41 OBJECT-TYPE
		SYNTAX		INTEGER { ready(0), trigger(1) }
		MAX-ACCESS	read-write
		STATUS		current
		DESCRIPTION	"
			style='Event button'
			path='/Audio Control/Audio Control A/Output A EMB 4/Preset'
		"
		::= { alchemistHd3GCtrlEntries 18913 }

	audioDelayPreset51 OBJECT-TYPE
		SYNTAX		INTEGER { ready(0), trigger(1) }
		MAX-ACCESS	read-write
		STATUS		current
		DESCRIPTION	"
			style='Event button'
			path='/Audio Control/Audio Control A/Output A EMB 5/Preset'
		"
		::= { alchemistHd3GCtrlEntries 18914 }

	audioDelayPreset61 OBJECT-TYPE
		SYNTAX		INTEGER { ready(0), trigger(1) }
		MAX-ACCESS	read-write
		STATUS		current
		DESCRIPTION	"
			style='Event button'
			path='/Audio Control/Audio Control A/Output A EMB 6/Preset'
		"
		::= { alchemistHd3GCtrlEntries 18915 }

	audioDelayPreset71 OBJECT-TYPE
		SYNTAX		INTEGER { ready(0), trigger(1) }
		MAX-ACCESS	read-write
		STATUS		current
		DESCRIPTION	"
			style='Event button'
			path='/Audio Control/Audio Control A/Output A EMB 7/Preset'
		"
		::= { alchemistHd3GCtrlEntries 18916 }

	audioDelayPreset81 OBJECT-TYPE
		SYNTAX		INTEGER { ready(0), trigger(1) }
		MAX-ACCESS	read-write
		STATUS		current
		DESCRIPTION	"
			style='Event button'
			path='/Audio Control/Audio Control A/Output A EMB 8/Preset'
		"
		::= { alchemistHd3GCtrlEntries 18917 }

	audioDelayPreset91 OBJECT-TYPE
		SYNTAX		INTEGER { ready(0), trigger(1) }
		MAX-ACCESS	read-write
		STATUS		current
		DESCRIPTION	"
			style='Event button'
			path='/Audio Control/Audio Control B/Output B EMB 1/Preset'
		"
		::= { alchemistHd3GCtrlEntries 18918 }

	audioDelayPreset101 OBJECT-TYPE
		SYNTAX		INTEGER { ready(0), trigger(1) }
		MAX-ACCESS	read-write
		STATUS		current
		DESCRIPTION	"
			style='Event button'
			path='/Audio Control/Audio Control B/Output B EMB 2/Preset'
		"
		::= { alchemistHd3GCtrlEntries 18919 }

	audioDelayPreset111 OBJECT-TYPE
		SYNTAX		INTEGER { ready(0), trigger(1) }
		MAX-ACCESS	read-write
		STATUS		current
		DESCRIPTION	"
			style='Event button'
			path='/Audio Control/Audio Control B/Output B EMB 3/Preset'
		"
		::= { alchemistHd3GCtrlEntries 18920 }

	audioDelayPreset121 OBJECT-TYPE
		SYNTAX		INTEGER { ready(0), trigger(1) }
		MAX-ACCESS	read-write
		STATUS		current
		DESCRIPTION	"
			style='Event button'
			path='/Audio Control/Audio Control B/Output B EMB 4/Preset'
		"
		::= { alchemistHd3GCtrlEntries 18921 }

	audioDelayPreset131 OBJECT-TYPE
		SYNTAX		INTEGER { ready(0), trigger(1) }
		MAX-ACCESS	read-write
		STATUS		current
		DESCRIPTION	"
			style='Event button'
			path='/Audio Control/Audio Control B/Output B EMB 5/Preset'
		"
		::= { alchemistHd3GCtrlEntries 18922 }

	audioDelayPreset141 OBJECT-TYPE
		SYNTAX		INTEGER { ready(0), trigger(1) }
		MAX-ACCESS	read-write
		STATUS		current
		DESCRIPTION	"
			style='Event button'
			path='/Audio Control/Audio Control B/Output B EMB 6/Preset'
		"
		::= { alchemistHd3GCtrlEntries 18923 }

	audioDelayPreset151 OBJECT-TYPE
		SYNTAX		INTEGER { ready(0), trigger(1) }
		MAX-ACCESS	read-write
		STATUS		current
		DESCRIPTION	"
			style='Event button'
			path='/Audio Control/Audio Control B/Output B EMB 7/Preset'
		"
		::= { alchemistHd3GCtrlEntries 18924 }

	audioDelayPreset161 OBJECT-TYPE
		SYNTAX		INTEGER { ready(0), trigger(1) }
		MAX-ACCESS	read-write
		STATUS		current
		DESCRIPTION	"
			style='Event button'
			path='/Audio Control/Audio Control B/Output B EMB 8/Preset'
		"
		::= { alchemistHd3GCtrlEntries 18925 }

	audioDelayPreset171 OBJECT-TYPE
		SYNTAX		INTEGER { ready(0), trigger(1) }
		MAX-ACCESS	read-write
		STATUS		current
		DESCRIPTION	"
			style='Event button'
			path='/Audio Control/Audio Control AES/AES Output 1/Preset'
		"
		::= { alchemistHd3GCtrlEntries 18926 }

	audioDelayPreset181 OBJECT-TYPE
		SYNTAX		INTEGER { ready(0), trigger(1) }
		MAX-ACCESS	read-write
		STATUS		current
		DESCRIPTION	"
			style='Event button'
			path='/Audio Control/Audio Control AES/AES Output 2/Preset'
		"
		::= { alchemistHd3GCtrlEntries 18927 }

	audioDelayPreset191 OBJECT-TYPE
		SYNTAX		INTEGER { ready(0), trigger(1) }
		MAX-ACCESS	read-write
		STATUS		current
		DESCRIPTION	"
			style='Event button'
			path='/Audio Control/Audio Control AES/AES Output 3/Preset'
		"
		::= { alchemistHd3GCtrlEntries 18928 }

	audioDelayPreset201 OBJECT-TYPE
		SYNTAX		INTEGER { ready(0), trigger(1) }
		MAX-ACCESS	read-write
		STATUS		current
		DESCRIPTION	"
			style='Event button'
			path='/Audio Control/Audio Control AES/AES Output 4/Preset'
		"
		::= { alchemistHd3GCtrlEntries 18929 }

	audioDelayPreset211 OBJECT-TYPE
		SYNTAX		INTEGER { ready(0), trigger(1) }
		MAX-ACCESS	read-write
		STATUS		current
		DESCRIPTION	"
			style='Event button'
			path='/Audio Control/Audio Control AES/AES Output 5/Preset'
		"
		::= { alchemistHd3GCtrlEntries 18930 }

	audioDelayPreset221 OBJECT-TYPE
		SYNTAX		INTEGER { ready(0), trigger(1) }
		MAX-ACCESS	read-write
		STATUS		current
		DESCRIPTION	"
			style='Event button'
			path='/Audio Control/Audio Control AES/AES Output 6/Preset'
		"
		::= { alchemistHd3GCtrlEntries 18931 }

	audioDelayPreset231 OBJECT-TYPE
		SYNTAX		INTEGER { ready(0), trigger(1) }
		MAX-ACCESS	read-write
		STATUS		current
		DESCRIPTION	"
			style='Event button'
			path='/Audio Control/Audio Control AES/AES Output 7/Preset'
		"
		::= { alchemistHd3GCtrlEntries 18932 }

	audioDelayPreset241 OBJECT-TYPE
		SYNTAX		INTEGER { ready(0), trigger(1) }
		MAX-ACCESS	read-write
		STATUS		current
		DESCRIPTION	"
			style='Event button'
			path='/Audio Control/Audio Control AES/AES Output 8/Preset'
		"
		::= { alchemistHd3GCtrlEntries 18933 }

	audioDelayTrack10 OBJECT-TYPE
		SYNTAX		INTEGER { disable(0), enable(1) }
		MAX-ACCESS	read-write
		STATUS		current
		DESCRIPTION	"
			style='Checkbox'
			range='0..1'
			path='/Audio Control/Audio Control A/Output A EMB 1/Channel 1/Delay Track'
		"
		::= { alchemistHd3GCtrlEntries 18940 }

	audioDelayTrack20 OBJECT-TYPE
		SYNTAX		INTEGER { disable(0), enable(1) }
		MAX-ACCESS	read-write
		STATUS		current
		DESCRIPTION	"
			style='Checkbox'
			range='0..1'
			path='/Audio Control/Audio Control A/Output A EMB 2/Channel 1/Delay Track'
		"
		::= { alchemistHd3GCtrlEntries 18941 }

	audioDelayTrack30 OBJECT-TYPE
		SYNTAX		INTEGER { disable(0), enable(1) }
		MAX-ACCESS	read-write
		STATUS		current
		DESCRIPTION	"
			style='Checkbox'
			range='0..1'
			path='/Audio Control/Audio Control A/Output A EMB 3/Channel 1/Delay Track'
		"
		::= { alchemistHd3GCtrlEntries 18942 }

	audioDelayTrack40 OBJECT-TYPE
		SYNTAX		INTEGER { disable(0), enable(1) }
		MAX-ACCESS	read-write
		STATUS		current
		DESCRIPTION	"
			style='Checkbox'
			range='0..1'
			path='/Audio Control/Audio Control A/Output A EMB 4/Channel 1/Delay Track'
		"
		::= { alchemistHd3GCtrlEntries 18943 }

	audioDelayTrack50 OBJECT-TYPE
		SYNTAX		INTEGER { disable(0), enable(1) }
		MAX-ACCESS	read-write
		STATUS		current
		DESCRIPTION	"
			style='Checkbox'
			range='0..1'
			path='/Audio Control/Audio Control A/Output A EMB 5/Channel 1/Delay Track'
		"
		::= { alchemistHd3GCtrlEntries 18944 }

	audioDelayTrack60 OBJECT-TYPE
		SYNTAX		INTEGER { disable(0), enable(1) }
		MAX-ACCESS	read-write
		STATUS		current
		DESCRIPTION	"
			style='Checkbox'
			range='0..1'
			path='/Audio Control/Audio Control A/Output A EMB 6/Channel 1/Delay Track'
		"
		::= { alchemistHd3GCtrlEntries 18945 }

	audioDelayTrack70 OBJECT-TYPE
		SYNTAX		INTEGER { disable(0), enable(1) }
		MAX-ACCESS	read-write
		STATUS		current
		DESCRIPTION	"
			style='Checkbox'
			range='0..1'
			path='/Audio Control/Audio Control A/Output A EMB 7/Channel 1/Delay Track'
		"
		::= { alchemistHd3GCtrlEntries 18946 }

	audioDelayTrack80 OBJECT-TYPE
		SYNTAX		INTEGER { disable(0), enable(1) }
		MAX-ACCESS	read-write
		STATUS		current
		DESCRIPTION	"
			style='Checkbox'
			range='0..1'
			path='/Audio Control/Audio Control A/Output A EMB 8/Channel 1/Delay Track'
		"
		::= { alchemistHd3GCtrlEntries 18947 }

	audioDelayTrack90 OBJECT-TYPE
		SYNTAX		INTEGER { disable(0), enable(1) }
		MAX-ACCESS	read-write
		STATUS		current
		DESCRIPTION	"
			style='Checkbox'
			range='0..1'
			path='/Audio Control/Audio Control B/Output B EMB 1/Channel 1/Delay Track'
		"
		::= { alchemistHd3GCtrlEntries 18948 }

	audioDelayTrack100 OBJECT-TYPE
		SYNTAX		INTEGER { disable(0), enable(1) }
		MAX-ACCESS	read-write
		STATUS		current
		DESCRIPTION	"
			style='Checkbox'
			range='0..1'
			path='/Audio Control/Audio Control B/Output B EMB 2/Channel 1/Delay Track'
		"
		::= { alchemistHd3GCtrlEntries 18949 }

	audioDelayTrack110 OBJECT-TYPE
		SYNTAX		INTEGER { disable(0), enable(1) }
		MAX-ACCESS	read-write
		STATUS		current
		DESCRIPTION	"
			style='Checkbox'
			range='0..1'
			path='/Audio Control/Audio Control B/Output B EMB 3/Channel 1/Delay Track'
		"
		::= { alchemistHd3GCtrlEntries 18950 }

	audioDelayTrack120 OBJECT-TYPE
		SYNTAX		INTEGER { disable(0), enable(1) }
		MAX-ACCESS	read-write
		STATUS		current
		DESCRIPTION	"
			style='Checkbox'
			range='0..1'
			path='/Audio Control/Audio Control B/Output B EMB 4/Channel 1/Delay Track'
		"
		::= { alchemistHd3GCtrlEntries 18951 }

	audioDelayTrack130 OBJECT-TYPE
		SYNTAX		INTEGER { disable(0), enable(1) }
		MAX-ACCESS	read-write
		STATUS		current
		DESCRIPTION	"
			style='Checkbox'
			range='0..1'
			path='/Audio Control/Audio Control B/Output B EMB 5/Channel 1/Delay Track'
		"
		::= { alchemistHd3GCtrlEntries 18952 }

	audioDelayTrack140 OBJECT-TYPE
		SYNTAX		INTEGER { disable(0), enable(1) }
		MAX-ACCESS	read-write
		STATUS		current
		DESCRIPTION	"
			style='Checkbox'
			range='0..1'
			path='/Audio Control/Audio Control B/Output B EMB 6/Channel 1/Delay Track'
		"
		::= { alchemistHd3GCtrlEntries 18953 }

	audioDelayTrack150 OBJECT-TYPE
		SYNTAX		INTEGER { disable(0), enable(1) }
		MAX-ACCESS	read-write
		STATUS		current
		DESCRIPTION	"
			style='Checkbox'
			range='0..1'
			path='/Audio Control/Audio Control B/Output B EMB 7/Channel 1/Delay Track'
		"
		::= { alchemistHd3GCtrlEntries 18954 }

	audioDelayTrack160 OBJECT-TYPE
		SYNTAX		INTEGER { disable(0), enable(1) }
		MAX-ACCESS	read-write
		STATUS		current
		DESCRIPTION	"
			style='Checkbox'
			range='0..1'
			path='/Audio Control/Audio Control B/Output B EMB 8/Channel 1/Delay Track'
		"
		::= { alchemistHd3GCtrlEntries 18955 }

	audioDelayTrack170 OBJECT-TYPE
		SYNTAX		INTEGER { disable(0), enable(1) }
		MAX-ACCESS	read-write
		STATUS		current
		DESCRIPTION	"
			style='Checkbox'
			range='0..1'
			path='/Audio Control/Audio Control AES/AES Output 1/Channel 1/Delay Track'
		"
		::= { alchemistHd3GCtrlEntries 18956 }

	audioDelayTrack180 OBJECT-TYPE
		SYNTAX		INTEGER { disable(0), enable(1) }
		MAX-ACCESS	read-write
		STATUS		current
		DESCRIPTION	"
			style='Checkbox'
			range='0..1'
			path='/Audio Control/Audio Control AES/AES Output 2/Channel 1/Delay Track'
		"
		::= { alchemistHd3GCtrlEntries 18957 }

	audioDelayTrack190 OBJECT-TYPE
		SYNTAX		INTEGER { disable(0), enable(1) }
		MAX-ACCESS	read-write
		STATUS		current
		DESCRIPTION	"
			style='Checkbox'
			range='0..1'
			path='/Audio Control/Audio Control AES/AES Output 3/Channel 1/Delay Track'
		"
		::= { alchemistHd3GCtrlEntries 18958 }

	audioDelayTrack200 OBJECT-TYPE
		SYNTAX		INTEGER { disable(0), enable(1) }
		MAX-ACCESS	read-write
		STATUS		current
		DESCRIPTION	"
			style='Checkbox'
			range='0..1'
			path='/Audio Control/Audio Control AES/AES Output 4/Channel 1/Delay Track'
		"
		::= { alchemistHd3GCtrlEntries 18959 }

	audioDelayTrack210 OBJECT-TYPE
		SYNTAX		INTEGER { disable(0), enable(1) }
		MAX-ACCESS	read-write
		STATUS		current
		DESCRIPTION	"
			style='Checkbox'
			range='0..1'
			path='/Audio Control/Audio Control AES/AES Output 5/Channel 1/Delay Track'
		"
		::= { alchemistHd3GCtrlEntries 18960 }

	audioDelayTrack220 OBJECT-TYPE
		SYNTAX		INTEGER { disable(0), enable(1) }
		MAX-ACCESS	read-write
		STATUS		current
		DESCRIPTION	"
			style='Checkbox'
			range='0..1'
			path='/Audio Control/Audio Control AES/AES Output 6/Channel 1/Delay Track'
		"
		::= { alchemistHd3GCtrlEntries 18961 }

	audioDelayTrack230 OBJECT-TYPE
		SYNTAX		INTEGER { disable(0), enable(1) }
		MAX-ACCESS	read-write
		STATUS		current
		DESCRIPTION	"
			style='Checkbox'
			range='0..1'
			path='/Audio Control/Audio Control AES/AES Output 7/Channel 1/Delay Track'
		"
		::= { alchemistHd3GCtrlEntries 18962 }

	audioDelayTrack240 OBJECT-TYPE
		SYNTAX		INTEGER { disable(0), enable(1) }
		MAX-ACCESS	read-write
		STATUS		current
		DESCRIPTION	"
			style='Checkbox'
			range='0..1'
			path='/Audio Control/Audio Control AES/AES Output 8/Channel 1/Delay Track'
		"
		::= { alchemistHd3GCtrlEntries 18963 }

	audioDelayTrack11 OBJECT-TYPE
		SYNTAX		INTEGER { disable(0), enable(1) }
		MAX-ACCESS	read-write
		STATUS		current
		DESCRIPTION	"
			style='Checkbox'
			range='0..1'
			path='/Audio Control/Audio Control A/Output A EMB 1/Channel 2/Delay Track'
		"
		::= { alchemistHd3GCtrlEntries 18964 }

	audioDelayTrack21 OBJECT-TYPE
		SYNTAX		INTEGER { disable(0), enable(1) }
		MAX-ACCESS	read-write
		STATUS		current
		DESCRIPTION	"
			style='Checkbox'
			range='0..1'
			path='/Audio Control/Audio Control A/Output A EMB 2/Channel 1/Delay Track'
		"
		::= { alchemistHd3GCtrlEntries 18965 }

	audioDelayTrack31 OBJECT-TYPE
		SYNTAX		INTEGER { disable(0), enable(1) }
		MAX-ACCESS	read-write
		STATUS		current
		DESCRIPTION	"
			style='Checkbox'
			range='0..1'
			path='/Audio Control/Audio Control A/Output A EMB 3/Channel 2/Delay Track'
		"
		::= { alchemistHd3GCtrlEntries 18966 }

	audioDelayTrack41 OBJECT-TYPE
		SYNTAX		INTEGER { disable(0), enable(1) }
		MAX-ACCESS	read-write
		STATUS		current
		DESCRIPTION	"
			style='Checkbox'
			range='0..1'
			path='/Audio Control/Audio Control A/Output A EMB 4/Channel 2/Delay Track'
		"
		::= { alchemistHd3GCtrlEntries 18967 }

	audioDelayTrack51 OBJECT-TYPE
		SYNTAX		INTEGER { disable(0), enable(1) }
		MAX-ACCESS	read-write
		STATUS		current
		DESCRIPTION	"
			style='Checkbox'
			range='0..1'
			path='/Audio Control/Audio Control A/Output A EMB 5/Channel 2/Delay Track'
		"
		::= { alchemistHd3GCtrlEntries 18968 }

	audioDelayTrack61 OBJECT-TYPE
		SYNTAX		INTEGER { disable(0), enable(1) }
		MAX-ACCESS	read-write
		STATUS		current
		DESCRIPTION	"
			style='Checkbox'
			range='0..1'
			path='/Audio Control/Audio Control A/Output A EMB 6/Channel 2/Delay Track'
		"
		::= { alchemistHd3GCtrlEntries 18969 }

	audioDelayTrack71 OBJECT-TYPE
		SYNTAX		INTEGER { disable(0), enable(1) }
		MAX-ACCESS	read-write
		STATUS		current
		DESCRIPTION	"
			style='Checkbox'
			range='0..1'
			path='/Audio Control/Audio Control A/Output A EMB 7/Channel 2/Delay Track'
		"
		::= { alchemistHd3GCtrlEntries 18970 }

	audioDelayTrack81 OBJECT-TYPE
		SYNTAX		INTEGER { disable(0), enable(1) }
		MAX-ACCESS	read-write
		STATUS		current
		DESCRIPTION	"
			style='Checkbox'
			range='0..1'
			path='/Audio Control/Audio Control A/Output A EMB 8/Channel 2/Delay Track'
		"
		::= { alchemistHd3GCtrlEntries 18971 }

	audioDelayTrack91 OBJECT-TYPE
		SYNTAX		INTEGER { disable(0), enable(1) }
		MAX-ACCESS	read-write
		STATUS		current
		DESCRIPTION	"
			style='Checkbox'
			range='0..1'
			path='/Audio Control/Audio Control B/Output B EMB 1/Channel 2/Delay Track'
		"
		::= { alchemistHd3GCtrlEntries 18972 }

	audioDelayTrack101 OBJECT-TYPE
		SYNTAX		INTEGER { disable(0), enable(1) }
		MAX-ACCESS	read-write
		STATUS		current
		DESCRIPTION	"
			style='Checkbox'
			range='0..1'
			path='/Audio Control/Audio Control B/Output B EMB 2/Channel 1/Delay Track'
		"
		::= { alchemistHd3GCtrlEntries 18973 }

	audioDelayTrack111 OBJECT-TYPE
		SYNTAX		INTEGER { disable(0), enable(1) }
		MAX-ACCESS	read-write
		STATUS		current
		DESCRIPTION	"
			style='Checkbox'
			range='0..1'
			path='/Audio Control/Audio Control B/Output B EMB 3/Channel 2/Delay Track'
		"
		::= { alchemistHd3GCtrlEntries 18974 }

	audioDelayTrack121 OBJECT-TYPE
		SYNTAX		INTEGER { disable(0), enable(1) }
		MAX-ACCESS	read-write
		STATUS		current
		DESCRIPTION	"
			style='Checkbox'
			range='0..1'
			path='/Audio Control/Audio Control B/Output B EMB 4/Channel 2/Delay Track'
		"
		::= { alchemistHd3GCtrlEntries 18975 }

	audioDelayTrack131 OBJECT-TYPE
		SYNTAX		INTEGER { disable(0), enable(1) }
		MAX-ACCESS	read-write
		STATUS		current
		DESCRIPTION	"
			style='Checkbox'
			range='0..1'
			path='/Audio Control/Audio Control B/Output B EMB 5/Channel 2/Delay Track'
		"
		::= { alchemistHd3GCtrlEntries 18976 }

	audioDelayTrack141 OBJECT-TYPE
		SYNTAX		INTEGER { disable(0), enable(1) }
		MAX-ACCESS	read-write
		STATUS		current
		DESCRIPTION	"
			style='Checkbox'
			range='0..1'
			path='/Audio Control/Audio Control B/Output B EMB 6/Channel 2/Delay Track'
		"
		::= { alchemistHd3GCtrlEntries 18977 }

	audioDelayTrack151 OBJECT-TYPE
		SYNTAX		INTEGER { disable(0), enable(1) }
		MAX-ACCESS	read-write
		STATUS		current
		DESCRIPTION	"
			style='Checkbox'
			range='0..1'
			path='/Audio Control/Audio Control B/Output B EMB 7/Channel 2/Delay Track'
		"
		::= { alchemistHd3GCtrlEntries 18978 }

	audioDelayTrack161 OBJECT-TYPE
		SYNTAX		INTEGER { disable(0), enable(1) }
		MAX-ACCESS	read-write
		STATUS		current
		DESCRIPTION	"
			style='Checkbox'
			range='0..1'
			path='/Audio Control/Audio Control B/Output B EMB 8/Channel 2/Delay Track'
		"
		::= { alchemistHd3GCtrlEntries 18979 }

	audioDelayTrack171 OBJECT-TYPE
		SYNTAX		INTEGER { disable(0), enable(1) }
		MAX-ACCESS	read-write
		STATUS		current
		DESCRIPTION	"
			style='Checkbox'
			range='0..1'
			path='/Audio Control/Audio Control AES/AES Output 1/Channel 2/Delay Track'
		"
		::= { alchemistHd3GCtrlEntries 18980 }

	audioDelayTrack181 OBJECT-TYPE
		SYNTAX		INTEGER { disable(0), enable(1) }
		MAX-ACCESS	read-write
		STATUS		current
		DESCRIPTION	"
			style='Checkbox'
			range='0..1'
			path='/Audio Control/Audio Control AES/AES Output 2/Channel 1/Delay Track'
		"
		::= { alchemistHd3GCtrlEntries 18981 }

	audioDelayTrack191 OBJECT-TYPE
		SYNTAX		INTEGER { disable(0), enable(1) }
		MAX-ACCESS	read-write
		STATUS		current
		DESCRIPTION	"
			style='Checkbox'
			range='0..1'
			path='/Audio Control/Audio Control AES/AES Output 3/Channel 2/Delay Track'
		"
		::= { alchemistHd3GCtrlEntries 18982 }

	audioDelayTrack201 OBJECT-TYPE
		SYNTAX		INTEGER { disable(0), enable(1) }
		MAX-ACCESS	read-write
		STATUS		current
		DESCRIPTION	"
			style='Checkbox'
			range='0..1'
			path='/Audio Control/Audio Control AES/AES Output 4/Channel 2/Delay Track'
		"
		::= { alchemistHd3GCtrlEntries 18983 }

	audioDelayTrack211 OBJECT-TYPE
		SYNTAX		INTEGER { disable(0), enable(1) }
		MAX-ACCESS	read-write
		STATUS		current
		DESCRIPTION	"
			style='Checkbox'
			range='0..1'
			path='/Audio Control/Audio Control AES/AES Output 5/Channel 2/Delay Track'
		"
		::= { alchemistHd3GCtrlEntries 18984 }

	audioDelayTrack221 OBJECT-TYPE
		SYNTAX		INTEGER { disable(0), enable(1) }
		MAX-ACCESS	read-write
		STATUS		current
		DESCRIPTION	"
			style='Checkbox'
			range='0..1'
			path='/Audio Control/Audio Control AES/AES Output 6/Channel 2/Delay Track'
		"
		::= { alchemistHd3GCtrlEntries 18985 }

	audioDelayTrack231 OBJECT-TYPE
		SYNTAX		INTEGER { disable(0), enable(1) }
		MAX-ACCESS	read-write
		STATUS		current
		DESCRIPTION	"
			style='Checkbox'
			range='0..1'
			path='/Audio Control/Audio Control AES/AES Output 7/Channel 2/Delay Track'
		"
		::= { alchemistHd3GCtrlEntries 18986 }

	audioDelayTrack241 OBJECT-TYPE
		SYNTAX		INTEGER { disable(0), enable(1) }
		MAX-ACCESS	read-write
		STATUS		current
		DESCRIPTION	"
			style='Checkbox'
			range='0..1'
			path='/Audio Control/Audio Control AES/AES Output 8/Channel 2/Delay Track'
		"
		::= { alchemistHd3GCtrlEntries 18987 }

	dolbyDecAuxDownmixMode1 OBJECT-TYPE
		SYNTAX		INTEGER {
					ltRt(0),
					loRo(1),
					loPlusRoLoPlusRo(2),
					mute(3)
				}
		MAX-ACCESS	read-write
		STATUS		current
		DESCRIPTION	"
			style='Radiobutton list'
			preset='ltRt'
			path='/Dolby Decoder/Dolby Decoder/Downmix Mode'
		"
		::= { alchemistHd3GCtrlEntries 25960 }

	dolbyDecAuxDownmixMode2 OBJECT-TYPE
		SYNTAX		INTEGER {
					ltRt(0),
					loRo(1),
					loPlusRoLoPlusRo(2),
					mute(3)
				}
		MAX-ACCESS	read-write
		STATUS		current
		DESCRIPTION	"
			style='Radiobutton list'
			preset='ltRt'
			path='/Dolby 2 Decoder/Dolby 2 Decoder/Downmix Mode'
		"
		::= { alchemistHd3GCtrlEntries 25961 }

	dolbyDecActiveProgram1 OBJECT-TYPE
		SYNTAX		Integer32 (1..8)
		MAX-ACCESS	read-write
		STATUS		current
		DESCRIPTION	"
			style='Numeric control'
			range='1..8'
			preset='1'
			path='/Decoded Metadata 1/Decoded Metadata 1/Active Program'
		"
		::= { alchemistHd3GCtrlEntries 25962 }

	dolbyDecActiveProgram2 OBJECT-TYPE
		SYNTAX		Integer32 (1..8)
		MAX-ACCESS	read-write
		STATUS		current
		DESCRIPTION	"
			style='Numeric control'
			range='1..8'
			preset='1'
			path='/Decoded Metadata 2/Decoded Metadata 2/Active Program'
		"
		::= { alchemistHd3GCtrlEntries 25963 }

	dolbyEncActiveProgram1 OBJECT-TYPE
		SYNTAX		Integer32 (1..8)
		MAX-ACCESS	read-write
		STATUS		current
		DESCRIPTION	"
			style='Numeric control'
			range='1..8'
			preset='1'
			path='/Dolby 1 Encoder/Dolby Enc 1 Meta/Internal Metadata 1/Active Program'
		"
		::= { alchemistHd3GCtrlEntries 25964 }

	dolbyEncActiveProgram2 OBJECT-TYPE
		SYNTAX		Integer32 (1..8)
		MAX-ACCESS	read-write
		STATUS		current
		DESCRIPTION	"
			style='Numeric control'
			range='1..8'
			preset='1'
			path='/Dolby 2 Encoder/Dolby Enc 2 Meta/Internal Metadata 2/Active Program'
		"
		::= { alchemistHd3GCtrlEntries 25965 }

	dolbyDecAuxDownmixProgram1 OBJECT-TYPE
		SYNTAX		INTEGER {
					program1(1),
					program2(2),
					program3(3),
					program4(4),
					program5(5),
					program6(6),
					program7(7),
					program8(8)
				}
		MAX-ACCESS	read-write
		STATUS		current
		DESCRIPTION	"
			style='Radiobutton list'
			preset='program1'
			path='/Dolby Decoder/Dolby Decoder/Downmix Program'
		"
		::= { alchemistHd3GCtrlEntries 25966 }

	dolbyDecAuxDownmixProgram2 OBJECT-TYPE
		SYNTAX		Integer32 (1..8)
		MAX-ACCESS	read-write
		STATUS		current
		DESCRIPTION	"
			style='Numeric control'
			range='1..8'
			preset='1'
			path='/Dolby 2 Decoder/Dolby 2 Decoder/Downmix Program'
		"
		::= { alchemistHd3GCtrlEntries 25967 }

	dolbyEncSrc101 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb1Ch1'
			path='/Dolby 1 Encoder//Channel 1/2/Encoder 1 Src - Ch1'
		"
		::= { alchemistHd3GCtrlEntries 26880 }

	dolbyEncSrc111 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb1Ch2'
			path='/Dolby 1 Encoder//Channel 1/2/Encoder 1 Src - Ch2'
		"
		::= { alchemistHd3GCtrlEntries 26881 }

	dolbyEncSrc201 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb2Ch1'
			path='/Dolby 1 Encoder//Channel 3/4/Encoder 1 Src - Ch3'
		"
		::= { alchemistHd3GCtrlEntries 26882 }

	dolbyEncSrc211 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb2Ch2'
			path='/Dolby 1 Encoder//Channel 3/4/Encoder 1 Src - Ch4'
		"
		::= { alchemistHd3GCtrlEntries 26883 }

	dolbyEncSrc301 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb3Ch1'
			path='/Dolby 1 Encoder//Channel 5/6/Encoder 1 Src - Ch5'
		"
		::= { alchemistHd3GCtrlEntries 26884 }

	dolbyEncSrc311 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb3Ch2'
			path='/Dolby 1 Encoder//Channel 5/6/Encoder 1 Src - Ch6'
		"
		::= { alchemistHd3GCtrlEntries 26885 }

	dolbyEncSrc401 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb4Ch1'
			path='/Dolby 1 Encoder//Channel 7/8/Encoder 1 Src - Ch7'
		"
		::= { alchemistHd3GCtrlEntries 26886 }

	dolbyEncSrc411 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb4Ch2'
			path='/Dolby 1 Encoder//Channel 7/8/Encoder 1 Src - Ch8'
		"
		::= { alchemistHd3GCtrlEntries 26887 }

	dolbyEncSrc102 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb1Ch1'
			path='/Dolby 2 Encoder//Channel 1/2/Encoder 2 Src - Ch1'
		"
		::= { alchemistHd3GCtrlEntries 26888 }

	dolbyEncSrc112 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb1Ch2'
			path='/Dolby 2 Encoder//Channel 1/2/Encoder 2 Src - Ch2'
		"
		::= { alchemistHd3GCtrlEntries 26889 }

	dolbyEncSrc202 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb2Ch1'
			path='/Dolby 2 Encoder//Channel 3/4/Encoder 2 Src - Ch3'
		"
		::= { alchemistHd3GCtrlEntries 26890 }

	dolbyEncSrc212 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb2Ch2'
			path='/Dolby 2 Encoder//Channel 3/4/Encoder 2 Src - Ch4'
		"
		::= { alchemistHd3GCtrlEntries 26891 }

	dolbyEncSrc302 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb3Ch1'
			path='/Dolby 2 Encoder//Channel 5/6/Encoder 2 Src - Ch5'
		"
		::= { alchemistHd3GCtrlEntries 26892 }

	dolbyEncSrc312 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb3Ch2'
			path='/Dolby 2 Encoder//Channel 5/6/Encoder 2 Src - Ch6'
		"
		::= { alchemistHd3GCtrlEntries 26893 }

	dolbyEncSrc402 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb4Ch1'
			path='/Dolby 2 Encoder//Channel 7/8/Encoder 2 Src - Ch7'
		"
		::= { alchemistHd3GCtrlEntries 26894 }

	dolbyEncSrc412 OBJECT-TYPE
		SYNTAX		INTEGER {
					emb1Ch1(34),
					emb1Ch2(35),
					emb2Ch1(36),
					emb2Ch2(37),
					emb3Ch1(38),
					emb3Ch2(39),
					emb4Ch1(40),
					emb4Ch2(41),
					emb5Ch1(42),
					emb5Ch2(43),
					emb6Ch1(44),
					emb6Ch2(45),
					emb7Ch1(46),
					emb7Ch2(47),
					emb8Ch1(48),
					emb8Ch2(49),
					aes1Ch1(66),
					aes1Ch2(67),
					aes2Ch1(68),
					aes2Ch2(69),
					aes3Ch1(70),
					aes3Ch2(71),
					aes4Ch1(72),
					aes4Ch2(73),
					aes5Ch1(74),
					aes5Ch2(75),
					aes6Ch1(76),
					aes6Ch2(77),
					aes7Ch1(78),
					aes7Ch2(79),
					aes8Ch1(80),
					aes8Ch2(81),
					dec11Ch1(98),
					dec11Ch2(99),
					dec12Ch1(100),
					dec12Ch2(101),
					dec13Ch1(102),
					dec13Ch2(103),
					dec14Ch1(104),
					dec14Ch2(105),
					dec1AuxCh1(106),
					dec1AuxCh2(107),
					dec21Ch1(130),
					dec21Ch2(131),
					dec22Ch1(132),
					dec22Ch2(133),
					dec23Ch1(134),
					dec23Ch2(135),
					dec24Ch1(136),
					dec24Ch2(137),
					dec2AuxCh1(138),
					dec2AuxCh2(139),
					enc1(162),
					enc2(164)
				}
		MAX-ACCESS	read-write
		STATUS		current
		DESCRIPTION	"
			style='Radiobutton list'
			preset='emb4Ch2'
			path='/Dolby 2 Encoder//Channel 7/8/Encoder 2 Src - Ch8'
		"
		::= { alchemistHd3GCtrlEntries 26895 }

	audioDelayEnc101 OBJECT-TYPE
		SYNTAX		Integer32 (-250..250)
		MAX-ACCESS	read-write
		STATUS		current
		DESCRIPTION	"
			style='Numeric control'
			range='-250mS..250mS'
			path='/Dolby 1 Encoder/Delay/Channel 1/Delay'
		"
		::= { alchemistHd3GCtrlEntries 28600 }

	audioDelayEnc111 OBJECT-TYPE
		SYNTAX		Integer32 (-250..250)
		MAX-ACCESS	read-write
		STATUS		current
		DESCRIPTION	"
			style='Numeric control'
			range='-250mS..250mS'
			path='/Dolby 1 Encoder/Delay/Channel 2/Delay'
		"
		::= { alchemistHd3GCtrlEntries 28601 }

	audioDelayEnc201 OBJECT-TYPE
		SYNTAX		Integer32 (-250..250)
		MAX-ACCESS	read-write
		STATUS		current
		DESCRIPTION	"
			style='Numeric control'
			range='-250mS..250mS'
			path='/Dolby 1 Encoder/Delay/Channel 3/Delay'
		"
		::= { alchemistHd3GCtrlEntries 28602 }

	audioDelayEnc211 OBJECT-TYPE
		SYNTAX		Integer32 (-250..250)
		MAX-ACCESS	read-write
		STATUS		current
		DESCRIPTION	"
			style='Numeric control'
			range='-250mS..250mS'
			path='/Dolby 1 Encoder/Delay/Channel 4/Delay'
		"
		::= { alchemistHd3GCtrlEntries 28603 }

	audioDelayEnc301 OBJECT-TYPE
		SYNTAX		Integer32 (-250..250)
		MAX-ACCESS	read-write
		STATUS		current
		DESCRIPTION	"
			style='Numeric control'
			range='-250mS..250mS'
			path='/Dolby 1 Encoder/Delay/Channel 5/Delay'
		"
		::= { alchemistHd3GCtrlEntries 28604 }

	audioDelayEnc311 OBJECT-TYPE
		SYNTAX		Integer32 (-250..250)
		MAX-ACCESS	read-write
		STATUS		current
		DESCRIPTION	"
			style='Numeric control'
			range='-250mS..250mS'
			path='/Dolby 1 Encoder/Delay/Channel 6/Delay'
		"
		::= { alchemistHd3GCtrlEntries 28605 }

	audioDelayEnc401 OBJECT-TYPE
		SYNTAX		Integer32 (-250..250)
		MAX-ACCESS	read-write
		STATUS		current
		DESCRIPTION	"
			style='Numeric control'
			range='-250mS..250mS'
			path='/Dolby 1 Encoder/Delay/Channel 7/Delay'
		"
		::= { alchemistHd3GCtrlEntries 28606 }

	audioDelayEnc411 OBJECT-TYPE
		SYNTAX		Integer32 (-250..250)
		MAX-ACCESS	read-write
		STATUS		current
		DESCRIPTION	"
			style='Numeric control'
			range='-250mS..250mS'
			path='/Dolby 1 Encoder/Delay/Channel 8/Delay'
		"
		::= { alchemistHd3GCtrlEntries 28607 }

	audioDelayEnc102 OBJECT-TYPE
		SYNTAX		Integer32 (-250..250)
		MAX-ACCESS	read-write
		STATUS		current
		DESCRIPTION	"
			style='Numeric control'
			range='-250mS..250mS'
			path='/Dolby 2 Encoder/Delay/Channel 1/Delay'
		"
		::= { alchemistHd3GCtrlEntries 28608 }

	audioDelayEnc112 OBJECT-TYPE
		SYNTAX		Integer32 (-250..250)
		MAX-ACCESS	read-write
		STATUS		current
		DESCRIPTION	"
			style='Numeric control'
			range='-250mS..250mS'
			path='/Dolby 2 Encoder/Delay/Channel 2/Delay'
		"
		::= { alchemistHd3GCtrlEntries 28609 }

	audioDelayEnc202 OBJECT-TYPE
		SYNTAX		Integer32 (-250..250)
		MAX-ACCESS	read-write
		STATUS		current
		DESCRIPTION	"
			style='Numeric control'
			range='-250mS..250mS'
			path='/Dolby 2 Encoder/Delay/Channel 3/Delay'
		"
		::= { alchemistHd3GCtrlEntries 28610 }

	audioDelayEnc212 OBJECT-TYPE
		SYNTAX		Integer32 (-250..250)
		MAX-ACCESS	read-write
		STATUS		current
		DESCRIPTION	"
			style='Numeric control'
			range='-250mS..250mS'
			path='/Dolby 2 Encoder/Delay/Channel 4/Delay'
		"
		::= { alchemistHd3GCtrlEntries 28611 }

	audioDelayEnc302 OBJECT-TYPE
		SYNTAX		Integer32 (-250..250)
		MAX-ACCESS	read-write
		STATUS		current
		DESCRIPTION	"
			style='Numeric control'
			range='-250mS..250mS'
			path='/Dolby 2 Encoder/Delay/Channel 5/Delay'
		"
		::= { alchemistHd3GCtrlEntries 28612 }

	audioDelayEnc312 OBJECT-TYPE
		SYNTAX		Integer32 (-250..250)
		MAX-ACCESS	read-write
		STATUS		current
		DESCRIPTION	"
			style='Numeric control'
			range='-250mS..250mS'
			path='/Dolby 2 Encoder/Delay/Channel 6/Delay'
		"
		::= { alchemistHd3GCtrlEntries 28613 }

	audioDelayEnc402 OBJECT-TYPE
		SYNTAX		Integer32 (-250..250)
		MAX-ACCESS	read-write
		STATUS		current
		DESCRIPTION	"
			style='Numeric control'
			range='-250mS..250mS'
			path='/Dolby 2 Encoder/Delay/Channel 7/Delay'
		"
		::= { alchemistHd3GCtrlEntries 28614 }

	audioDelayEnc412 OBJECT-TYPE
		SYNTAX		Integer32 (-250..250)
		MAX-ACCESS	read-write
		STATUS		current
		DESCRIPTION	"
			style='Numeric control'
			range='-250mS..250mS'
			path='/Dolby 2 Encoder/Delay/Channel 8/Delay'
		"
		::= { alchemistHd3GCtrlEntries 28615 }

	audioDelayPresetEnc101 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 28620 }

	audioDelayPresetEnc111 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 28621 }

	audioDelayPresetEnc201 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 28622 }

	audioDelayPresetEnc211 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 28623 }

	audioDelayPresetEnc301 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 28624 }

	audioDelayPresetEnc311 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 28625 }

	audioDelayPresetEnc401 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 28626 }

	audioDelayPresetEnc411 OBJECT-TYPE
		SYNTAX		INTEGER { ready(0), trigger(1) }
		MAX-ACCESS	read-write
		STATUS		current
		DESCRIPTION	"
			style='Event button'
			path='/Dolby 1 Encoder/Presets/Preset'
		"
		::= { alchemistHd3GCtrlEntries 28627 }

	audioDelayPresetEnc102 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 28628 }

	audioDelayPresetEnc112 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 28629 }

	audioDelayPresetEnc202 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 28630 }

	audioDelayPresetEnc212 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 28631 }

	audioDelayPresetEnc302 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 28632 }

	audioDelayPresetEnc312 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 28633 }

	audioDelayPresetEnc402 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 28634 }

	audioDelayPresetEnc412 OBJECT-TYPE
		SYNTAX		INTEGER { ready(0), trigger(1) }
		MAX-ACCESS	read-write
		STATUS		current
		DESCRIPTION	"
			style='Event button'
			path='/Dolby 2 Encoder/Presets/Preset'
		"
		::= { alchemistHd3GCtrlEntries 28635 }

	audioDelayTrackEnc101 OBJECT-TYPE
		SYNTAX		INTEGER { disable(0), enable(1) }
		MAX-ACCESS	read-write
		STATUS		current
		DESCRIPTION	"
			style='Checkbox'
			range='0..1'
			path='/Dolby 1 Encoder/Delay/Channel 1/Track'
		"
		::= { alchemistHd3GCtrlEntries 28640 }

	audioDelayTrackEnc111 OBJECT-TYPE
		SYNTAX		INTEGER { disable(0), enable(1) }
		MAX-ACCESS	read-write
		STATUS		current
		DESCRIPTION	"
			style='Checkbox'
			range='0..1'
			path='/Dolby 1 Encoder/Delay/Channel 2/Track'
		"
		::= { alchemistHd3GCtrlEntries 28641 }

	audioDelayTrackEnc201 OBJECT-TYPE
		SYNTAX		INTEGER { disable(0), enable(1) }
		MAX-ACCESS	read-write
		STATUS		current
		DESCRIPTION	"
			style='Checkbox'
			range='0..1'
			path='/Dolby 1 Encoder/Delay/Channel 3/Track'
		"
		::= { alchemistHd3GCtrlEntries 28642 }

	audioDelayTrackEnc211 OBJECT-TYPE
		SYNTAX		INTEGER { disable(0), enable(1) }
		MAX-ACCESS	read-write
		STATUS		current
		DESCRIPTION	"
			style='Checkbox'
			range='0..1'
			path='/Dolby 1 Encoder/Delay/Channel 4/Track'
		"
		::= { alchemistHd3GCtrlEntries 28643 }

	audioDelayTrackEnc301 OBJECT-TYPE
		SYNTAX		INTEGER { disable(0), enable(1) }
		MAX-ACCESS	read-write
		STATUS		current
		DESCRIPTION	"
			style='Checkbox'
			range='0..1'
			path='/Dolby 1 Encoder/Delay/Channel 5/Track'
		"
		::= { alchemistHd3GCtrlEntries 28644 }

	audioDelayTrackEnc311 OBJECT-TYPE
		SYNTAX		INTEGER { disable(0), enable(1) }
		MAX-ACCESS	read-write
		STATUS		current
		DESCRIPTION	"
			style='Checkbox'
			range='0..1'
			path='/Dolby 1 Encoder/Delay/Channel 6/Track'
		"
		::= { alchemistHd3GCtrlEntries 28645 }

	audioDelayTrackEnc401 OBJECT-TYPE
		SYNTAX		INTEGER { disable(0), enable(1) }
		MAX-ACCESS	read-write
		STATUS		current
		DESCRIPTION	"
			style='Checkbox'
			range='0..1'
			path='/Dolby 1 Encoder/Delay/Channel 7/Track'
		"
		::= { alchemistHd3GCtrlEntries 28646 }

	audioDelayTrackEnc411 OBJECT-TYPE
		SYNTAX		INTEGER { disable(0), enable(1) }
		MAX-ACCESS	read-write
		STATUS		current
		DESCRIPTION	"
			style='Checkbox'
			range='0..1'
			path='/Dolby 1 Encoder/Delay/Channel 8/Track'
		"
		::= { alchemistHd3GCtrlEntries 28647 }

	audioDelayTrackEnc102 OBJECT-TYPE
		SYNTAX		INTEGER { disable(0), enable(1) }
		MAX-ACCESS	read-write
		STATUS		current
		DESCRIPTION	"
			style='Checkbox'
			range='0..1'
			path='/Dolby 2 Encoder/Delay/Channel 1/Track'
		"
		::= { alchemistHd3GCtrlEntries 28648 }

	audioDelayTrackEnc112 OBJECT-TYPE
		SYNTAX		INTEGER { disable(0), enable(1) }
		MAX-ACCESS	read-write
		STATUS		current
		DESCRIPTION	"
			style='Checkbox'
			range='0..1'
			path='/Dolby 2 Encoder/Delay/Channel 2/Track'
		"
		::= { alchemistHd3GCtrlEntries 28649 }

	audioDelayTrackEnc202 OBJECT-TYPE
		SYNTAX		INTEGER { disable(0), enable(1) }
		MAX-ACCESS	read-write
		STATUS		current
		DESCRIPTION	"
			style='Checkbox'
			range='0..1'
			path='/Dolby 2 Encoder/Delay/Channel 3/Track'
		"
		::= { alchemistHd3GCtrlEntries 28650 }

	audioDelayTrackEnc212 OBJECT-TYPE
		SYNTAX		INTEGER { disable(0), enable(1) }
		MAX-ACCESS	read-write
		STATUS		current
		DESCRIPTION	"
			style='Checkbox'
			range='0..1'
			path='/Dolby 2 Encoder/Delay/Channel 4/Track'
		"
		::= { alchemistHd3GCtrlEntries 28651 }

	audioDelayTrackEnc302 OBJECT-TYPE
		SYNTAX		INTEGER { disable(0), enable(1) }
		MAX-ACCESS	read-write
		STATUS		current
		DESCRIPTION	"
			style='Checkbox'
			range='0..1'
			path='/Dolby 2 Encoder/Delay/Channel 5/Track'
		"
		::= { alchemistHd3GCtrlEntries 28652 }

	audioDelayTrackEnc312 OBJECT-TYPE
		SYNTAX		INTEGER { disable(0), enable(1) }
		MAX-ACCESS	read-write
		STATUS		current
		DESCRIPTION	"
			style='Checkbox'
			range='0..1'
			path='/Dolby 2 Encoder/Delay/Channel 6/Track'
		"
		::= { alchemistHd3GCtrlEntries 28653 }

	audioDelayTrackEnc402 OBJECT-TYPE
		SYNTAX		INTEGER { disable(0), enable(1) }
		MAX-ACCESS	read-write
		STATUS		current
		DESCRIPTION	"
			style='Checkbox'
			range='0..1'
			path='/Dolby 2 Encoder/Delay/Channel 7/Track'
		"
		::= { alchemistHd3GCtrlEntries 28654 }

	audioDelayTrackEnc412 OBJECT-TYPE
		SYNTAX		INTEGER { disable(0), enable(1) }
		MAX-ACCESS	read-write
		STATUS		current
		DESCRIPTION	"
			style='Checkbox'
			range='0..1'
			path='/Dolby 2 Encoder/Delay/Channel 8/Track'
		"
		::= { alchemistHd3GCtrlEntries 28655 }

	decAc3Ac3Datarate1 OBJECT-TYPE
		SYNTAX		Integer32
		MAX-ACCESS	read-only
		STATUS		current
		DESCRIPTION	"
			style='ReadOnly numeric'
			path='/Decoded Metadata 1/Decoded Metadata 1/Datarate'
		"
		::= { alchemistHd3GCtrlEntries 40001 }

	decAc3Ac3Bsmod1 OBJECT-TYPE
		SYNTAX		Integer32
		MAX-ACCESS	read-only
		STATUS		current
		DESCRIPTION	"
			style='ReadOnly numeric'
			path='/Decoded Metadata 1/Decoded Metadata 1/Bitstream Mode'
		"
		::= { alchemistHd3GCtrlEntries 40002 }

	decAc3Ac3Acmod1 OBJECT-TYPE
		SYNTAX		Integer32
		MAX-ACCESS	read-only
		STATUS		current
		DESCRIPTION	"
			style='ReadOnly numeric'
			path='/Decoded Metadata 1/Decoded Metadata 1/Channel Mode'
		"
		::= { alchemistHd3GCtrlEntries 40003 }

	decAc3Ac3Cmixlev1 OBJECT-TYPE
		SYNTAX		Integer32
		MAX-ACCESS	read-only
		STATUS		current
		DESCRIPTION	"
			style='ReadOnly numeric'
			path='/Decoded Metadata 1/Decoded Metadata 1/Center Dmix Level'
		"
		::= { alchemistHd3GCtrlEntries 40004 }

	decAc3Ac3Surmixlev1 OBJECT-TYPE
		SYNTAX		Integer32
		MAX-ACCESS	read-only
		STATUS		current
		DESCRIPTION	"
			style='ReadOnly numeric'
			path='/Decoded Metadata 1/Decoded Metadata 1/Surround Dmix Level'
		"
		::= { alchemistHd3GCtrlEntries 40005 }

	decAc3Ac3Dsurmod1 OBJECT-TYPE
		SYNTAX		Integer32
		MAX-ACCESS	read-only
		STATUS		current
		DESCRIPTION	"
			style='ReadOnly numeric'
			path='/Decoded Metadata 1/Decoded Metadata 1/Dolby Surround Mode'
		"
		::= { alchemistHd3GCtrlEntries 40006 }

	decAc3Ac3Dsurexmod1 OBJECT-TYPE
		SYNTAX		Integer32
		MAX-ACCESS	read-only
		STATUS		current
		DESCRIPTION	"
			style='ReadOnly numeric'
			path='/Decoded Metadata 1/Decoded Metadata 1/Dolby Surround EX'
		"
		::= { alchemistHd3GCtrlEntries 40007 }

	decAc3Ac3Lfeon1 OBJECT-TYPE
		SYNTAX		Integer32
		MAX-ACCESS	read-only
		STATUS		current
		DESCRIPTION	"
			style='ReadOnly numeric'
			path='/Decoded Metadata 1/Decoded Metadata 1/LFE Channel'
		"
		::= { alchemistHd3GCtrlEntries 40008 }

	decAc3Ac3Dialnorm1 OBJECT-TYPE
		SYNTAX		Integer32
		MAX-ACCESS	read-only
		STATUS		current
		DESCRIPTION	"
			style='ReadOnly numeric'
			path='/Decoded Metadata 1/Decoded Metadata 1/Dialogue Level'
		"
		::= { alchemistHd3GCtrlEntries 40009 }

	decAc3Ac3Audprodie1 OBJECT-TYPE
		SYNTAX		Integer32
		MAX-ACCESS	read-only
		STATUS		current
		DESCRIPTION	"
			style='ReadOnly numeric'
			path='/Decoded Metadata 1/Decoded Metadata 1/Audio Production'
		"
		::= { alchemistHd3GCtrlEntries 40010 }

	decAc3Ac3Mixlev1 OBJECT-TYPE
		SYNTAX		Integer32
		MAX-ACCESS	read-only
		STATUS		current
		DESCRIPTION	"
			style='ReadOnly numeric'
			path='/Decoded Metadata 1/Decoded Metadata 1/Mixing Level'
		"
		::= { alchemistHd3GCtrlEntries 40011 }

	decAc3Ac3Roomtyp1 OBJECT-TYPE
		SYNTAX		Integer32
		MAX-ACCESS	read-only
		STATUS		current
		DESCRIPTION	"
			style='ReadOnly numeric'
			path='/Decoded Metadata 1/Decoded Metadata 1/Room Type'
		"
		::= { alchemistHd3GCtrlEntries 40012 }

	decAc3Ac3Copyrightb1 OBJECT-TYPE
		SYNTAX		Integer32
		MAX-ACCESS	read-only
		STATUS		current
		DESCRIPTION	"
			style='ReadOnly numeric'
			path='/Decoded Metadata 1/Decoded Metadata 1/Copyright Bit'
		"
		::= { alchemistHd3GCtrlEntries 40013 }

	decAc3Ac3Origbs1 OBJECT-TYPE
		SYNTAX		Integer32
		MAX-ACCESS	read-only
		STATUS		current
		DESCRIPTION	"
			style='ReadOnly numeric'
			path='/Decoded Metadata 1/Decoded Metadata 1/Original Bitstream'
		"
		::= { alchemistHd3GCtrlEntries 40014 }

	decAc3Ac3Dmixmod1 OBJECT-TYPE
		SYNTAX		Integer32
		MAX-ACCESS	read-only
		STATUS		current
		DESCRIPTION	"
			style='ReadOnly numeric'
			path='/Decoded Metadata 1/Decoded Metadata 1/Pref Stereo Dmix'
		"
		::= { alchemistHd3GCtrlEntries 40015 }

	decAc3Ac3Ltrtcmixlev1 OBJECT-TYPE
		SYNTAX		Integer32
		MAX-ACCESS	read-only
		STATUS		current
		DESCRIPTION	"
			style='ReadOnly numeric'
			path='/Decoded Metadata 1/Decoded Metadata 1/Lt/Rt Ctr Dmix Lev'
		"
		::= { alchemistHd3GCtrlEntries 40016 }

	decAc3Ac3Lorocmixlev1 OBJECT-TYPE
		SYNTAX		Integer32
		MAX-ACCESS	read-only
		STATUS		current
		DESCRIPTION	"
			style='ReadOnly numeric'
			path='/Decoded Metadata 1/Decoded Metadata 1/Lo/Ro Ctr Dmix Lev'
		"
		::= { alchemistHd3GCtrlEntries 40017 }

	decAc3Ac3Ltrtsurmixlev1 OBJECT-TYPE
		SYNTAX		Integer32
		MAX-ACCESS	read-only
		STATUS		current
		DESCRIPTION	"
			style='ReadOnly numeric'
			path='/Decoded Metadata 1/Decoded Metadata 1/Lt/Rt Sur Dmix Lev'
		"
		::= { alchemistHd3GCtrlEntries 40018 }

	decAc3Ac3Lorosurmixlev1 OBJECT-TYPE
		SYNTAX		Integer32
		MAX-ACCESS	read-only
		STATUS		current
		DESCRIPTION	"
			style='ReadOnly numeric'
			path='/Decoded Metadata 1/Decoded Metadata 1/Lo/Ro Sur Dmix Lev'
		"
		::= { alchemistHd3GCtrlEntries 40019 }

	decAc3Ac3Adconvtyp1 OBJECT-TYPE
		SYNTAX		Integer32
		MAX-ACCESS	read-only
		STATUS		current
		DESCRIPTION	"
			style='ReadOnly numeric'
			path='/Decoded Metadata 1/Decoded Metadata 1/A/D Convertor Type'
		"
		::= { alchemistHd3GCtrlEntries 40020 }

	decAc3Ac3Hpfon1 OBJECT-TYPE
		SYNTAX		Integer32
		MAX-ACCESS	read-only
		STATUS		current
		DESCRIPTION	"
			style='ReadOnly numeric'
			path='/Decoded Metadata 1/Decoded Metadata 1/DC Filter'
		"
		::= { alchemistHd3GCtrlEntries 40021 }

	decAc3Ac3Bwlpfon1 OBJECT-TYPE
		SYNTAX		Integer32
		MAX-ACCESS	read-only
		STATUS		current
		DESCRIPTION	"
			style='ReadOnly numeric'
			path='/Decoded Metadata 1/Decoded Metadata 1/Lowpass Filter'
		"
		::= { alchemistHd3GCtrlEntries 40022 }

	decAc3Ac3Lfelpfon1 OBJECT-TYPE
		SYNTAX		Integer32
		MAX-ACCESS	read-only
		STATUS		current
		DESCRIPTION	"
			style='ReadOnly numeric'
			path='/Decoded Metadata 1/Decoded Metadata 1/LFE Lowpass Filter'
		"
		::= { alchemistHd3GCtrlEntries 40023 }

	decAc3Ac3Sur90on1 OBJECT-TYPE
		SYNTAX		Integer32
		MAX-ACCESS	read-only
		STATUS		current
		DESCRIPTION	"
			style='ReadOnly numeric'
			path='/Decoded Metadata 1/Decoded Metadata 1/Sur Phase Shift'
		"
		::= { alchemistHd3GCtrlEntries 40024 }

	decAc3Ac3Suratton1 OBJECT-TYPE
		SYNTAX		Integer32
		MAX-ACCESS	read-only
		STATUS		current
		DESCRIPTION	"
			style='ReadOnly numeric'
			path='/Decoded Metadata 1/Decoded Metadata 1/Sur 3dB attenuation'
		"
		::= { alchemistHd3GCtrlEntries 40025 }

	decAc3Ac3Rfpremphon1 OBJECT-TYPE
		SYNTAX		Integer32
		MAX-ACCESS	read-only
		STATUS		current
		DESCRIPTION	"
			style='ReadOnly numeric'
			path='/Decoded Metadata 1/Decoded Metadata 1/RF Over Protect'
		"
		::= { alchemistHd3GCtrlEntries 40026 }

	decAc3Ac3Compr11 OBJECT-TYPE
		SYNTAX		Integer32
		MAX-ACCESS	read-only
		STATUS		current
		DESCRIPTION	"
			style='ReadOnly numeric'
			path='/Decoded Metadata 1/Decoded Metadata 1/RF Mode Pro'
		"
		::= { alchemistHd3GCtrlEntries 40027 }

	decAc3Ac3Dynrng11 OBJECT-TYPE
		SYNTAX		Integer32
		MAX-ACCESS	read-only
		STATUS		current
		DESCRIPTION	"
			style='ReadOnly numeric'
			path='/Decoded Metadata 1/Decoded Metadata 1/Line Mode Pro'
		"
		::= { alchemistHd3GCtrlEntries 40028 }

	decAc3Ac3Dheadphonmod1 OBJECT-TYPE
		SYNTAX		Integer32
		MAX-ACCESS	read-only
		STATUS		current
		DESCRIPTION	"
			style='ReadOnly numeric'
			path='/Decoded Metadata 1/Decoded Metadata 1/Headphone Mode'
		"
		::= { alchemistHd3GCtrlEntries 40029 }

	dolbyDecProgDesc1 OBJECT-TYPE
		SYNTAX		RollCallString
		MAX-ACCESS	read-only
		STATUS		current
		DESCRIPTION	"
			style='ReadOnly string'
			path='/Decoded Metadata 1/Decoded Metadata 1/Program Description'
		"
		::= { alchemistHd3GCtrlEntries 40040 }

	decMetaFrameRateCode1 OBJECT-TYPE
		SYNTAX		RollCallString
		MAX-ACCESS	read-only
		STATUS		current
		DESCRIPTION	"
			style='ReadOnly string'
			path='/Decoded Metadata 1/Decoded Metadata 1/Dolby Frame Rate'
		"
		::= { alchemistHd3GCtrlEntries 40041 }

	decMetaProgramConfig1 OBJECT-TYPE
		SYNTAX		RollCallString
		MAX-ACCESS	read-only
		STATUS		current
		DESCRIPTION	"
			style='ReadOnly string'
			path='/Decoded Metadata 1/Decoded Metadata 1/Program Config'
		"
		::= { alchemistHd3GCtrlEntries 40042 }

	decAc3Ac3Datarate2 OBJECT-TYPE
		SYNTAX		Integer32
		MAX-ACCESS	read-only
		STATUS		current
		DESCRIPTION	"
			style='ReadOnly numeric'
			path='/Decoded Metadata 2/Decoded Metadata 2/Datarate'
		"
		::= { alchemistHd3GCtrlEntries 40101 }

	decAc3Ac3Bsmod2 OBJECT-TYPE
		SYNTAX		Integer32
		MAX-ACCESS	read-only
		STATUS		current
		DESCRIPTION	"
			style='ReadOnly numeric'
			path='/Decoded Metadata 2/Decoded Metadata 2/Bitstream Mode'
		"
		::= { alchemistHd3GCtrlEntries 40102 }

	decAc3Ac3Acmod2 OBJECT-TYPE
		SYNTAX		Integer32
		MAX-ACCESS	read-only
		STATUS		current
		DESCRIPTION	"
			style='ReadOnly numeric'
			path='/Decoded Metadata 2/Decoded Metadata 2/Channel Mode'
		"
		::= { alchemistHd3GCtrlEntries 40103 }

	decAc3Ac3Cmixlev2 OBJECT-TYPE
		SYNTAX		Integer32
		MAX-ACCESS	read-only
		STATUS		current
		DESCRIPTION	"
			style='ReadOnly numeric'
			path='/Decoded Metadata 2/Decoded Metadata 2/Center Dmix Level'
		"
		::= { alchemistHd3GCtrlEntries 40104 }

	decAc3Ac3Surmixlev2 OBJECT-TYPE
		SYNTAX		Integer32
		MAX-ACCESS	read-only
		STATUS		current
		DESCRIPTION	"
			style='ReadOnly numeric'
			path='/Decoded Metadata 2/Decoded Metadata 2/Surround Dmix Level'
		"
		::= { alchemistHd3GCtrlEntries 40105 }

	decAc3Ac3Dsurmod2 OBJECT-TYPE
		SYNTAX		Integer32
		MAX-ACCESS	read-only
		STATUS		current
		DESCRIPTION	"
			style='ReadOnly numeric'
			path='/Decoded Metadata 2/Decoded Metadata 2/Dolby Surround Mode'
		"
		::= { alchemistHd3GCtrlEntries 40106 }

	decAc3Ac3Dsurexmod2 OBJECT-TYPE
		SYNTAX		Integer32
		MAX-ACCESS	read-only
		STATUS		current
		DESCRIPTION	"
			style='ReadOnly numeric'
			path='/Decoded Metadata 2/Decoded Metadata 2/Dolby Surround EX'
		"
		::= { alchemistHd3GCtrlEntries 40107 }

	decAc3Ac3Lfeon2 OBJECT-TYPE
		SYNTAX		Integer32
		MAX-ACCESS	read-only
		STATUS		current
		DESCRIPTION	"
			style='ReadOnly numeric'
			path='/Decoded Metadata 2/Decoded Metadata 2/LFE Channel'
		"
		::= { alchemistHd3GCtrlEntries 40108 }

	decAc3Ac3Dialnorm2 OBJECT-TYPE
		SYNTAX		Integer32
		MAX-ACCESS	read-only
		STATUS		current
		DESCRIPTION	"
			style='ReadOnly numeric'
			path='/Decoded Metadata 2/Decoded Metadata 2/Dialogue Level'
		"
		::= { alchemistHd3GCtrlEntries 40109 }

	decAc3Ac3Audprodie2 OBJECT-TYPE
		SYNTAX		Integer32
		MAX-ACCESS	read-only
		STATUS		current
		DESCRIPTION	"
			style='ReadOnly numeric'
			path='/Decoded Metadata 2/Decoded Metadata 2/Audio Production'
		"
		::= { alchemistHd3GCtrlEntries 40110 }

	decAc3Ac3Mixlev2 OBJECT-TYPE
		SYNTAX		Integer32
		MAX-ACCESS	read-only
		STATUS		current
		DESCRIPTION	"
			style='ReadOnly numeric'
			path='/Decoded Metadata 2/Decoded Metadata 2/Mixing Level'
		"
		::= { alchemistHd3GCtrlEntries 40111 }

	decAc3Ac3Roomtyp2 OBJECT-TYPE
		SYNTAX		Integer32
		MAX-ACCESS	read-only
		STATUS		current
		DESCRIPTION	"
			style='ReadOnly numeric'
			path='/Decoded Metadata 2/Decoded Metadata 2/Room Type'
		"
		::= { alchemistHd3GCtrlEntries 40112 }

	decAc3Ac3Copyrightb2 OBJECT-TYPE
		SYNTAX		Integer32
		MAX-ACCESS	read-only
		STATUS		current
		DESCRIPTION	"
			style='ReadOnly numeric'
			path='/Decoded Metadata 2/Decoded Metadata 2/Copyright Bit'
		"
		::= { alchemistHd3GCtrlEntries 40113 }

	decAc3Ac3Origbs2 OBJECT-TYPE
		SYNTAX		Integer32
		MAX-ACCESS	read-only
		STATUS		current
		DESCRIPTION	"
			style='ReadOnly numeric'
			path='/Decoded Metadata 2/Decoded Metadata 2/Original Bitstream'
		"
		::= { alchemistHd3GCtrlEntries 40114 }

	decAc3Ac3Dmixmod2 OBJECT-TYPE
		SYNTAX		Integer32
		MAX-ACCESS	read-only
		STATUS		current
		DESCRIPTION	"
			style='ReadOnly numeric'
			path='/Decoded Metadata 2/Decoded Metadata 2/Pref Stereo Dmix'
		"
		::= { alchemistHd3GCtrlEntries 40115 }

	decAc3Ac3Ltrtcmixlev2 OBJECT-TYPE
		SYNTAX		Integer32
		MAX-ACCESS	read-only
		STATUS		current
		DESCRIPTION	"
			style='ReadOnly numeric'
			path='/Decoded Metadata 2/Decoded Metadata 2/Lt/Rt Ctr Dmix Level'
		"
		::= { alchemistHd3GCtrlEntries 40116 }

	decAc3Ac3Lorocmixlev2 OBJECT-TYPE
		SYNTAX		Integer32
		MAX-ACCESS	read-only
		STATUS		current
		DESCRIPTION	"
			style='ReadOnly numeric'
			path='/Decoded Metadata 2/Decoded Metadata 2/Lo/Ro Ctr Dmix Level'
		"
		::= { alchemistHd3GCtrlEntries 40117 }

	decAc3Ac3Ltrtsurmixlev2 OBJECT-TYPE
		SYNTAX		Integer32
		MAX-ACCESS	read-only
		STATUS		current
		DESCRIPTION	"
			style='ReadOnly numeric'
			path='/Decoded Metadata 2/Decoded Metadata 2/Lt/Rt Sur Dmix Level'
		"
		::= { alchemistHd3GCtrlEntries 40118 }

	decAc3Ac3Lorosurmixlev2 OBJECT-TYPE
		SYNTAX		Integer32
		MAX-ACCESS	read-only
		STATUS		current
		DESCRIPTION	"
			style='ReadOnly numeric'
			path='/Decoded Metadata 2/Decoded Metadata 2/Lo/Ro Sur Dmix Level'
		"
		::= { alchemistHd3GCtrlEntries 40119 }

	decAc3Ac3Adconvtyp2 OBJECT-TYPE
		SYNTAX		Integer32
		MAX-ACCESS	read-only
		STATUS		current
		DESCRIPTION	"
			style='ReadOnly numeric'
			path='/Decoded Metadata 2/Decoded Metadata 2/A/D Convertor Type'
		"
		::= { alchemistHd3GCtrlEntries 40120 }

	decAc3Ac3Hpfon2 OBJECT-TYPE
		SYNTAX		Integer32
		MAX-ACCESS	read-only
		STATUS		current
		DESCRIPTION	"
			style='ReadOnly numeric'
			path='/Decoded Metadata 2/Decoded Metadata 2/DC Filter'
		"
		::= { alchemistHd3GCtrlEntries 40121 }

	decAc3Ac3Bwlpfon2 OBJECT-TYPE
		SYNTAX		Integer32
		MAX-ACCESS	read-only
		STATUS		current
		DESCRIPTION	"
			style='ReadOnly numeric'
			path='/Decoded Metadata 2/Decoded Metadata 2/Lowpass Filter'
		"
		::= { alchemistHd3GCtrlEntries 40122 }

	decAc3Ac3Lfelpfon2 OBJECT-TYPE
		SYNTAX		Integer32
		MAX-ACCESS	read-only
		STATUS		current
		DESCRIPTION	"
			style='ReadOnly numeric'
			path='/Decoded Metadata 2/Decoded Metadata 2/LFE Lowpass Filter'
		"
		::= { alchemistHd3GCtrlEntries 40123 }

	decAc3Ac3Sur90on2 OBJECT-TYPE
		SYNTAX		Integer32
		MAX-ACCESS	read-only
		STATUS		current
		DESCRIPTION	"
			style='ReadOnly numeric'
			path='/Decoded Metadata 2/Decoded Metadata 2/Sur Phase Shift'
		"
		::= { alchemistHd3GCtrlEntries 40124 }

	decAc3Ac3Suratton2 OBJECT-TYPE
		SYNTAX		Integer32
		MAX-ACCESS	read-only
		STATUS		current
		DESCRIPTION	"
			style='ReadOnly numeric'
			path='/Decoded Metadata 2/Decoded Metadata 2/Sur 3dB attenuation'
		"
		::= { alchemistHd3GCtrlEntries 40125 }

	decAc3Ac3Rfpremphon2 OBJECT-TYPE
		SYNTAX		Integer32
		MAX-ACCESS	read-only
		STATUS		current
		DESCRIPTION	"
			style='ReadOnly numeric'
			path='/Decoded Metadata 2/Decoded Metadata 2/RF Over Protect'
		"
		::= { alchemistHd3GCtrlEntries 40126 }

	decAc3Ac3Compr12 OBJECT-TYPE
		SYNTAX		Integer32
		MAX-ACCESS	read-only
		STATUS		current
		DESCRIPTION	"
			style='ReadOnly numeric'
			path='/Decoded Metadata 2/Decoded Metadata 2/RF Mode Pro'
		"
		::= { alchemistHd3GCtrlEntries 40127 }

	decAc3Ac3Dynrng12 OBJECT-TYPE
		SYNTAX		Integer32
		MAX-ACCESS	read-only
		STATUS		current
		DESCRIPTION	"
			style='ReadOnly numeric'
			path='/Decoded Metadata 2/Decoded Metadata 2/Line Mode Pro'
		"
		::= { alchemistHd3GCtrlEntries 40128 }

	decAc3Ac3Dheadphonmod2 OBJECT-TYPE
		SYNTAX		Integer32
		MAX-ACCESS	read-only
		STATUS		current
		DESCRIPTION	"
			style='ReadOnly numeric'
			path='/Decoded Metadata 2/Decoded Metadata 2/Headphone Mode'
		"
		::= { alchemistHd3GCtrlEntries 40129 }

	dolbyDecProgDesc2 OBJECT-TYPE
		SYNTAX		RollCallString
		MAX-ACCESS	read-only
		STATUS		current
		DESCRIPTION	"
			style='ReadOnly string'
			path='/Decoded Metadata 2/Decoded Metadata 2/Program Description'
		"
		::= { alchemistHd3GCtrlEntries 40140 }

	decMetaFrameRateCode2 OBJECT-TYPE
		SYNTAX		RollCallString
		MAX-ACCESS	read-only
		STATUS		current
		DESCRIPTION	"
			style='ReadOnly string'
			path='/Decoded Metadata 2/Decoded Metadata 2/Dolby Frame Rate'
		"
		::= { alchemistHd3GCtrlEntries 40141 }

	decMetaProgramConfig2 OBJECT-TYPE
		SYNTAX		RollCallString
		MAX-ACCESS	read-only
		STATUS		current
		DESCRIPTION	"
			style='ReadOnly string'
			path='/Decoded Metadata 2/Decoded Metadata 2/Program Config'
		"
		::= { alchemistHd3GCtrlEntries 40142 }

	encAc3Ac3Datarate1 OBJECT-TYPE
		SYNTAX		Integer32 (0..18)
		MAX-ACCESS	read-write
		STATUS		current
		DESCRIPTION	"
			style='Numeric control'
			range='0..18'
			preset='14'
			path='/Dolby 1 Encoder/Dolby Enc 1 Meta/Internal Metadata 1/Datarate'
		"
		::= { alchemistHd3GCtrlEntries 40501 }

	encAc3Ac3Bsmod1 OBJECT-TYPE
		SYNTAX		INTEGER {
					completeMain(0),
					musicAndEffects(1),
					visuallyImpaired(2),
					hearingImpaired(3),
					dialogue(4),
					commentary(5),
					emergency(6),
					voiceOverOrKaraoke(7)
				}
		MAX-ACCESS	read-write
		STATUS		current
		DESCRIPTION	"
			style='Radiobutton list'
			preset='completeMain'
			path='/Dolby 1 Encoder/Dolby Enc 1 Meta/Internal Metadata 1/Bitstream Mode'
		"
		::= { alchemistHd3GCtrlEntries 40502 }

	encAc3Ac3Acmod1 OBJECT-TYPE
		SYNTAX		INTEGER {
					v(0),
					v10(1),
					v20(2),
					v30(3),
					v21(4),
					v31(5),
					v22(6),
					v32(7)
				}
		MAX-ACCESS	read-write
		STATUS		current
		DESCRIPTION	"
			style='Radiobutton list'
			preset='v'
			path='/Dolby 1 Encoder/Dolby Enc 1 Meta/Internal Metadata 1/Channel Mode'
		"
		::= { alchemistHd3GCtrlEntries 40503 }

	encAc3Ac3Cmixlev1 OBJECT-TYPE
		SYNTAX		INTEGER {
					v070730Db(0),
					v059645Db(1),
					v050060Db(2)
				}
		MAX-ACCESS	read-write
		STATUS		current
		DESCRIPTION	"
			style='Radiobutton list'
			preset='v070730Db'
			path='/Dolby 1 Encoder/Dolby Enc 1 Meta/Internal Metadata 1/Center Downmix Level'
		"
		::= { alchemistHd3GCtrlEntries 40504 }

	encAc3Ac3Surmixlev1 OBJECT-TYPE
		SYNTAX		INTEGER {
					v070730Db(0),
					v050060Db(1),
					v0000InfDb(2)
				}
		MAX-ACCESS	read-write
		STATUS		current
		DESCRIPTION	"
			style='Radiobutton list'
			preset='v070730Db'
			path='/Dolby 1 Encoder/Dolby Enc 1 Meta/Internal Metadata 1/Surround Downmix Level'
		"
		::= { alchemistHd3GCtrlEntries 40505 }

	encAc3Ac3Dsurmod1 OBJECT-TYPE
		SYNTAX		INTEGER {
					notIndicated(0),
					notDolbySurr(1),
					dolbySurr(2)
				}
		MAX-ACCESS	read-write
		STATUS		current
		DESCRIPTION	"
			style='Radiobutton list'
			preset='notIndicated'
			path='/Dolby 1 Encoder/Dolby Enc 1 Meta/Internal Metadata 1/Dolby Surround Mode'
		"
		::= { alchemistHd3GCtrlEntries 40506 }

	encAc3Ac3Dsurexmod1 OBJECT-TYPE
		SYNTAX		INTEGER {
					notIndicated(0),
					notDolbyEx(1),
					dolbySurrEx(2)
				}
		MAX-ACCESS	read-write
		STATUS		current
		DESCRIPTION	"
			style='Radiobutton list'
			preset='notIndicated'
			path='/Dolby 1 Encoder/Dolby Enc 1 Meta/Internal Metadata 1/Dolby Surround EX'
		"
		::= { alchemistHd3GCtrlEntries 40507 }

	encAc3Ac3Lfeon1 OBJECT-TYPE
		SYNTAX		INTEGER {
					disabled(0),
					enabled(1)
				}
		MAX-ACCESS	read-write
		STATUS		current
		DESCRIPTION	"
			style='Radiobutton list'
			preset='disabled'
			path='/Dolby 1 Encoder/Dolby Enc 1 Meta/Internal Metadata 1/LFE Channel'
		"
		::= { alchemistHd3GCtrlEntries 40508 }

	encAc3Ac3Dialnorm1 OBJECT-TYPE
		SYNTAX		Integer32 (-31..-1)
		MAX-ACCESS	read-write
		STATUS		current
		DESCRIPTION	"
			style='Numeric control'
			range='-31..-1'
			preset='-27'
			path='/Dolby 1 Encoder/Dolby Enc 1 Meta/Internal Metadata 1/Dialogue Level'
		"
		::= { alchemistHd3GCtrlEntries 40509 }

	encAc3Ac3Audprodie1 OBJECT-TYPE
		SYNTAX		INTEGER {
					no(0),
					yes(1)
				}
		MAX-ACCESS	read-write
		STATUS		current
		DESCRIPTION	"
			style='Radiobutton list'
			preset='no'
			path='/Dolby 1 Encoder/Dolby Enc 1 Meta/Internal Metadata 1/Audio Production'
		"
		::= { alchemistHd3GCtrlEntries 40510 }

	encAc3Ac3Mixlev1 OBJECT-TYPE
		SYNTAX		Integer32 (80..111)
		MAX-ACCESS	read-write
		STATUS		current
		DESCRIPTION	"
			style='Numeric control'
			range='80..111'
			preset='80'
			path='/Dolby 1 Encoder/Dolby Enc 1 Meta/Internal Metadata 1/Mixing Level'
		"
		::= { alchemistHd3GCtrlEntries 40511 }

	encAc3Ac3Roomtyp1 OBJECT-TYPE
		SYNTAX		INTEGER {
					notIndicated(0),
					large(1),
					small(2)
				}
		MAX-ACCESS	read-write
		STATUS		current
		DESCRIPTION	"
			style='Radiobutton list'
			preset='notIndicated'
			path='/Dolby 1 Encoder/Dolby Enc 1 Meta/Internal Metadata 1/Room Type'
		"
		::= { alchemistHd3GCtrlEntries 40512 }

	encAc3Ac3Dmixmod1 OBJECT-TYPE
		SYNTAX		INTEGER {
					notIndicated(0),
					ltRtPreferred(1),
					loRoPreferred(2)
				}
		MAX-ACCESS	read-write
		STATUS		current
		DESCRIPTION	"
			style='Radiobutton list'
			preset='notIndicated'
			path='/Dolby 1 Encoder/Dolby Enc 1 Meta/Internal Metadata 1/Preferred Stereo Downmix'
		"
		::= { alchemistHd3GCtrlEntries 40515 }

	encAc3Ac3Ltrtcmixlev1 OBJECT-TYPE
		SYNTAX		INTEGER {
					v1414Plus3Db(0),
					v1189Plus15Db(1),
					v100000Db(2),
					v084115Db(3),
					v070730Db(4),
					v059545Db(5),
					v050060Db(6),
					v0000InfDb(7)
				}
		MAX-ACCESS	read-write
		STATUS		current
		DESCRIPTION	"
			style='Radiobutton list'
			preset='v1414Plus3Db'
			path='/Dolby 1 Encoder/Dolby Enc 1 Meta/Internal Metadata 1/Lt/Rt Center Downmix Level'
		"
		::= { alchemistHd3GCtrlEntries 40516 }

	encAc3Ac3Lorocmixlev1 OBJECT-TYPE
		SYNTAX		INTEGER {
					v1414Plus3Db(0),
					v1189Plus15Db(1),
					v100000Db(2),
					v084115Db(3),
					v070730Db(4),
					v059545Db(5),
					v050060Db(6),
					v0000InfDb(7)
				}
		MAX-ACCESS	read-write
		STATUS		current
		DESCRIPTION	"
			style='Radiobutton list'
			preset='v1414Plus3Db'
			path='/Dolby 1 Encoder/Dolby Enc 1 Meta/Internal Metadata 1/Lo/Ro Center Downmix Level'
		"
		::= { alchemistHd3GCtrlEntries 40517 }

	encAc3Ac3Ltrtsurmixlev1 OBJECT-TYPE
		SYNTAX		INTEGER {
					v084115Db(3),
					v070730Db(4),
					v059545Db(5),
					v050060Db(6),
					v0000InfDb(7)
				}
		MAX-ACCESS	read-write
		STATUS		current
		DESCRIPTION	"
			style='Radiobutton list'
			preset='v070730Db'
			path='/Dolby 1 Encoder/Dolby Enc 1 Meta/Internal Metadata 1/Lt/Rt Surround Downmix Level'
		"
		::= { alchemistHd3GCtrlEntries 40518 }

	encAc3Ac3Lorosurmixlev1 OBJECT-TYPE
		SYNTAX		INTEGER {
					v084115Db(3),
					v070730Db(4),
					v059545Db(5),
					v050060Db(6),
					v0000InfDb(7)
				}
		MAX-ACCESS	read-write
		STATUS		current
		DESCRIPTION	"
			style='Radiobutton list'
			preset='v070730Db'
			path='/Dolby 1 Encoder/Dolby Enc 1 Meta/Internal Metadata 1/Lo/Ro Surround Downmix Level'
		"
		::= { alchemistHd3GCtrlEntries 40519 }

	encAc3Ac3Hpfon1 OBJECT-TYPE
		SYNTAX		INTEGER {
					enabled(1),
					disabled(0)
				}
		MAX-ACCESS	read-write
		STATUS		current
		DESCRIPTION	"
			style='Radiobutton list'
			preset='disabled'
			path='/Dolby 1 Encoder/Dolby Enc 1 Meta/Internal Metadata 1/DC Filter'
		"
		::= { alchemistHd3GCtrlEntries 40521 }

	encAc3Ac3Bwlpfon1 OBJECT-TYPE
		SYNTAX		INTEGER {
					enabled(1),
					disabled(0)
				}
		MAX-ACCESS	read-write
		STATUS		current
		DESCRIPTION	"
			style='Radiobutton list'
			preset='disabled'
			path='/Dolby 1 Encoder/Dolby Enc 1 Meta/Internal Metadata 1/Lowpass Filter'
		"
		::= { alchemistHd3GCtrlEntries 40522 }

	encAc3Ac3Lfelpfon1 OBJECT-TYPE
		SYNTAX		INTEGER {
					enabled(1),
					disabled(0)
				}
		MAX-ACCESS	read-write
		STATUS		current
		DESCRIPTION	"
			style='Radiobutton list'
			preset='disabled'
			path='/Dolby 1 Encoder/Dolby Enc 1 Meta/Internal Metadata 1/LFE Lowpass Filter'
		"
		::= { alchemistHd3GCtrlEntries 40523 }

	encAc3Ac3Sur90on1 OBJECT-TYPE
		SYNTAX		INTEGER {
					enabled(1),
					disabled(0)
				}
		MAX-ACCESS	read-write
		STATUS		current
		DESCRIPTION	"
			style='Radiobutton list'
			preset='disabled'
			path='/Dolby 1 Encoder/Dolby Enc 1 Meta/Internal Metadata 1/Surround Phase Shift'
		"
		::= { alchemistHd3GCtrlEntries 40524 }

	encAc3Ac3Suratton1 OBJECT-TYPE
		SYNTAX		INTEGER {
					enabled(1),
					disabled(0)
				}
		MAX-ACCESS	read-write
		STATUS		current
		DESCRIPTION	"
			style='Radiobutton list'
			preset='disabled'
			path='/Dolby 1 Encoder/Dolby Enc 1 Meta/Internal Metadata 1/Surround 3dB attenuation'
		"
		::= { alchemistHd3GCtrlEntries 40525 }

	encAc3Ac3Compr11 OBJECT-TYPE
		SYNTAX		INTEGER {
					filmLight(2),
					filmStandard(1),
					musicLight(4),
					musicStandard(3),
					speech(5),
					none(0)
				}
		MAX-ACCESS	read-write
		STATUS		current
		DESCRIPTION	"
			style='Radiobutton list'
			preset='none'
			path='/Dolby 1 Encoder/Dolby Enc 1 Meta/Internal Metadata 1/RF Mode Pro'
		"
		::= { alchemistHd3GCtrlEntries 40527 }

	encAc3Ac3Dynrng11 OBJECT-TYPE
		SYNTAX		INTEGER {
					filmLight(2),
					filmStandard(1),
					musicLight(4),
					musicStandard(3),
					speech(5),
					none(0)
				}
		MAX-ACCESS	read-write
		STATUS		current
		DESCRIPTION	"
			style='Radiobutton list'
			preset='none'
			path='/Dolby 1 Encoder/Dolby Enc 1 Meta/Internal Metadata 1/Line Mode Pro'
		"
		::= { alchemistHd3GCtrlEntries 40528 }

	dolbyEncFrameRateCode1 OBJECT-TYPE
		SYNTAX		RollCallString
		MAX-ACCESS	read-only
		STATUS		current
		DESCRIPTION	"
			style='ReadOnly string'
			path='/Dolby 1 Encoder/Dolby Enc 1 Meta/Internal Metadata 1/Dolby Frame Rate'
		"
		::= { alchemistHd3GCtrlEntries 40529 }

	dolbyEncProgDesc1 OBJECT-TYPE
		SYNTAX		RollCallString
		MAX-ACCESS	read-write
		STATUS		current
		DESCRIPTION	"
			style='Editable string'
			path='/Dolby 1 Encoder/Dolby Enc 1 Meta/Internal Metadata 1/Program Description'
		"
		::= { alchemistHd3GCtrlEntries 40540 }

	dolbyEncPresetProgram1 OBJECT-TYPE
		SYNTAX		INTEGER { ready(0), trigger(1) }
		MAX-ACCESS	read-write
		STATUS		current
		DESCRIPTION	"
			style='Event button'
			path='/Dolby 1 Encoder/Dolby Enc 1 Meta/Internal Metadata 1/Preset Metadata'
		"
		::= { alchemistHd3GCtrlEntries 40541 }

	dolbyEncLoadSnapshot1 OBJECT-TYPE
		SYNTAX		INTEGER { ready(0), trigger(1) }
		MAX-ACCESS	read-write
		STATUS		current
		DESCRIPTION	"
			style='Event button'
			path='/Dolby 1 Encoder/Dolby Enc 1 Meta/Internal Metadata 1/Recall Snapshot'
		"
		::= { alchemistHd3GCtrlEntries 40542 }

	dolbyEncSaveSnapshot1 OBJECT-TYPE
		SYNTAX		INTEGER { ready(0), trigger(1) }
		MAX-ACCESS	read-write
		STATUS		current
		DESCRIPTION	"
			style='Event button'
			path='/Dolby 1 Encoder/Dolby Enc 1 Meta/Internal Metadata 1/Store Snapshot'
		"
		::= { alchemistHd3GCtrlEntries 40543 }

	encAc3Ac3Datarate2 OBJECT-TYPE
		SYNTAX		Integer32 (0..18)
		MAX-ACCESS	read-write
		STATUS		current
		DESCRIPTION	"
			style='Numeric control'
			range='0..18'
			preset='14'
			path='/Dolby 2 Encoder/Dolby Enc 2 Meta/Internal Metadata 2/Datarate'
		"
		::= { alchemistHd3GCtrlEntries 40601 }

	encAc3Ac3Bsmod2 OBJECT-TYPE
		SYNTAX		INTEGER {
					completeMain(0),
					musicAndEffects(1),
					visuallyImpaired(2),
					hearingImpaired(3),
					dialogue(4),
					commentary(5),
					emergency(6),
					voiceOverOrKaraoke(7)
				}
		MAX-ACCESS	read-write
		STATUS		current
		DESCRIPTION	"
			style='Radiobutton list'
			preset='completeMain'
			path='/Dolby 2 Encoder/Dolby Enc 2 Meta/Internal Metadata 2/Bitstream Mode'
		"
		::= { alchemistHd3GCtrlEntries 40602 }

	encAc3Ac3Acmod2 OBJECT-TYPE
		SYNTAX		INTEGER {
					v(0),
					v10(1),
					v20(2),
					v30(3),
					v21(4),
					v31(5),
					v22(6),
					v32(7)
				}
		MAX-ACCESS	read-write
		STATUS		current
		DESCRIPTION	"
			style='Radiobutton list'
			preset='v'
			path='/Dolby 2 Encoder/Dolby Enc 2 Meta/Internal Metadata 2/Channel Mode'
		"
		::= { alchemistHd3GCtrlEntries 40603 }

	encAc3Ac3Cmixlev2 OBJECT-TYPE
		SYNTAX		INTEGER {
					v070730Db(0),
					v059645Db(1),
					v050060Db(2)
				}
		MAX-ACCESS	read-write
		STATUS		current
		DESCRIPTION	"
			style='Radiobutton list'
			preset='v070730Db'
			path='/Dolby 2 Encoder/Dolby Enc 2 Meta/Internal Metadata 2/Center Downmix Level'
		"
		::= { alchemistHd3GCtrlEntries 40604 }

	encAc3Ac3Surmixlev2 OBJECT-TYPE
		SYNTAX		INTEGER {
					v070730Db(0),
					v050060Db(1),
					v0000InfDb(2)
				}
		MAX-ACCESS	read-write
		STATUS		current
		DESCRIPTION	"
			style='Radiobutton list'
			preset='v070730Db'
			path='/Dolby 2 Encoder/Dolby Enc 2 Meta/Internal Metadata 2/Surround Downmix Level'
		"
		::= { alchemistHd3GCtrlEntries 40605 }

	encAc3Ac3Dsurmod2 OBJECT-TYPE
		SYNTAX		INTEGER {
					notIndicated(0),
					notDolbySurr(1),
					dolbySurr(2)
				}
		MAX-ACCESS	read-write
		STATUS		current
		DESCRIPTION	"
			style='Radiobutton list'
			preset='notIndicated'
			path='/Dolby 2 Encoder/Dolby Enc 2 Meta/Internal Metadata 2/Dolby Surround Mode'
		"
		::= { alchemistHd3GCtrlEntries 40606 }

	encAc3Ac3Dsurexmod2 OBJECT-TYPE
		SYNTAX		INTEGER {
					notIndicated(0),
					notDolbyEx(1),
					dolbySurrEx(2)
				}
		MAX-ACCESS	read-write
		STATUS		current
		DESCRIPTION	"
			style='Radiobutton list'
			preset='notIndicated'
			path='/Dolby 2 Encoder/Dolby Enc 2 Meta/Internal Metadata 2/Dolby Surround EX'
		"
		::= { alchemistHd3GCtrlEntries 40607 }

	encAc3Ac3Lfeon2 OBJECT-TYPE
		SYNTAX		INTEGER {
					disabled(0),
					enabled(1)
				}
		MAX-ACCESS	read-write
		STATUS		current
		DESCRIPTION	"
			style='Radiobutton list'
			preset='disabled'
			path='/Dolby 2 Encoder/Dolby Enc 2 Meta/Internal Metadata 2/LFE Channel'
		"
		::= { alchemistHd3GCtrlEntries 40608 }

	encAc3Ac3Dialnorm2 OBJECT-TYPE
		SYNTAX		Integer32 (-31..-1)
		MAX-ACCESS	read-write
		STATUS		current
		DESCRIPTION	"
			style='Numeric control'
			range='-31..-1'
			preset='-27'
			path='/Dolby 2 Encoder/Dolby Enc 2 Meta/Internal Metadata 2/Dialogue Level'
		"
		::= { alchemistHd3GCtrlEntries 40609 }

	encAc3Ac3Audprodie2 OBJECT-TYPE
		SYNTAX		INTEGER {
					no(0),
					yes(1)
				}
		MAX-ACCESS	read-write
		STATUS		current
		DESCRIPTION	"
			style='Radiobutton list'
			preset='no'
			path='/Dolby 2 Encoder/Dolby Enc 2 Meta/Internal Metadata 2/Audio Production'
		"
		::= { alchemistHd3GCtrlEntries 40610 }

	encAc3Ac3Mixlev2 OBJECT-TYPE
		SYNTAX		Integer32 (80..111)
		MAX-ACCESS	read-write
		STATUS		current
		DESCRIPTION	"
			style='Numeric control'
			range='80..111'
			preset='80'
			path='/Dolby 2 Encoder/Dolby Enc 2 Meta/Internal Metadata 2/Mixing Level'
		"
		::= { alchemistHd3GCtrlEntries 40611 }

	encAc3Ac3Roomtyp2 OBJECT-TYPE
		SYNTAX		INTEGER {
					notIndicated(0),
					large(1),
					small(2)
				}
		MAX-ACCESS	read-write
		STATUS		current
		DESCRIPTION	"
			style='Radiobutton list'
			preset='notIndicated'
			path='/Dolby 2 Encoder/Dolby Enc 2 Meta/Internal Metadata 2/Room Type'
		"
		::= { alchemistHd3GCtrlEntries 40612 }

	encAc3Ac3Dmixmod2 OBJECT-TYPE
		SYNTAX		INTEGER {
					notIndicated(0),
					ltRtPreferred(1),
					loRoPreferred(2)
				}
		MAX-ACCESS	read-write
		STATUS		current
		DESCRIPTION	"
			style='Radiobutton list'
			preset='notIndicated'
			path='/Dolby 2 Encoder/Dolby Enc 2 Meta/Internal Metadata 2/Preferred Stereo Downmix'
		"
		::= { alchemistHd3GCtrlEntries 40615 }

	encAc3Ac3Ltrtcmixlev2 OBJECT-TYPE
		SYNTAX		INTEGER {
					v1414Plus3Db(0),
					v1189Plus15Db(1),
					v100000Db(2),
					v084115Db(3),
					v070730Db(4),
					v059545Db(5),
					v050060Db(6),
					v0000InfDb(7)
				}
		MAX-ACCESS	read-write
		STATUS		current
		DESCRIPTION	"
			style='Radiobutton list'
			preset='v1414Plus3Db'
			path='/Dolby 2 Encoder/Dolby Enc 2 Meta/Internal Metadata 2/Lt/Rt Center Downmix Level'
		"
		::= { alchemistHd3GCtrlEntries 40616 }

	encAc3Ac3Lorocmixlev2 OBJECT-TYPE
		SYNTAX		INTEGER {
					v1414Plus3Db(0),
					v1189Plus15Db(1),
					v100000Db(2),
					v084115Db(3),
					v070730Db(4),
					v059545Db(5),
					v050060Db(6),
					v0000InfDb(7)
				}
		MAX-ACCESS	read-write
		STATUS		current
		DESCRIPTION	"
			style='Radiobutton list'
			preset='v1414Plus3Db'
			path='/Dolby 2 Encoder/Dolby Enc 2 Meta/Internal Metadata 2/Lo/Ro Center Downmix Level'
		"
		::= { alchemistHd3GCtrlEntries 40617 }

	encAc3Ac3Ltrtsurmixlev2 OBJECT-TYPE
		SYNTAX		INTEGER {
					v084115Db(3),
					v070730Db(4),
					v059545Db(5),
					v050060Db(6),
					v0000InfDb(7)
				}
		MAX-ACCESS	read-write
		STATUS		current
		DESCRIPTION	"
			style='Radiobutton list'
			preset='v070730Db'
			path='/Dolby 2 Encoder/Dolby Enc 2 Meta/Internal Metadata 2/Lt/Rt Surround Downmix Level'
		"
		::= { alchemistHd3GCtrlEntries 40618 }

	encAc3Ac3Lorosurmixlev2 OBJECT-TYPE
		SYNTAX		INTEGER {
					v084115Db(3),
					v070730Db(4),
					v059545Db(5),
					v050060Db(6),
					v0000InfDb(7)
				}
		MAX-ACCESS	read-write
		STATUS		current
		DESCRIPTION	"
			style='Radiobutton list'
			preset='v070730Db'
			path='/Dolby 2 Encoder/Dolby Enc 2 Meta/Internal Metadata 2/Lo/Ro Surround Downmix Level'
		"
		::= { alchemistHd3GCtrlEntries 40619 }

	encAc3Ac3Hpfon2 OBJECT-TYPE
		SYNTAX		INTEGER {
					enabled(1),
					disabled(0)
				}
		MAX-ACCESS	read-write
		STATUS		current
		DESCRIPTION	"
			style='Radiobutton list'
			preset='disabled'
			path='/Dolby 2 Encoder/Dolby Enc 2 Meta/Internal Metadata 2/DC Filter'
		"
		::= { alchemistHd3GCtrlEntries 40621 }

	encAc3Ac3Bwlpfon2 OBJECT-TYPE
		SYNTAX		INTEGER {
					enabled(1),
					disabled(0)
				}
		MAX-ACCESS	read-write
		STATUS		current
		DESCRIPTION	"
			style='Radiobutton list'
			preset='disabled'
			path='/Dolby 2 Encoder/Dolby Enc 2 Meta/Internal Metadata 2/Lowpass Filter'
		"
		::= { alchemistHd3GCtrlEntries 40622 }

	encAc3Ac3Lfelpfon2 OBJECT-TYPE
		SYNTAX		INTEGER {
					enabled(1),
					disabled(0)
				}
		MAX-ACCESS	read-write
		STATUS		current
		DESCRIPTION	"
			style='Radiobutton list'
			preset='disabled'
			path='/Dolby 2 Encoder/Dolby Enc 2 Meta/Internal Metadata 2/LFE Lowpass Filter'
		"
		::= { alchemistHd3GCtrlEntries 40623 }

	encAc3Ac3Sur90on2 OBJECT-TYPE
		SYNTAX		INTEGER {
					enabled(1),
					disabled(0)
				}
		MAX-ACCESS	read-write
		STATUS		current
		DESCRIPTION	"
			style='Radiobutton list'
			preset='disabled'
			path='/Dolby 2 Encoder/Dolby Enc 2 Meta/Internal Metadata 2/Surround Phase Shift'
		"
		::= { alchemistHd3GCtrlEntries 40624 }

	encAc3Ac3Suratton2 OBJECT-TYPE
		SYNTAX		INTEGER {
					enabled(1),
					disabled(0)
				}
		MAX-ACCESS	read-write
		STATUS		current
		DESCRIPTION	"
			style='Radiobutton list'
			preset='disabled'
			path='/Dolby 2 Encoder/Dolby Enc 2 Meta/Internal Metadata 2/Surround 3dB attenuation'
		"
		::= { alchemistHd3GCtrlEntries 40625 }

	encAc3Ac3Compr12 OBJECT-TYPE
		SYNTAX		INTEGER {
					filmLight(2),
					filmStandard(1),
					musicLight(4),
					musicStandard(3),
					speech(5),
					none(0)
				}
		MAX-ACCESS	read-write
		STATUS		current
		DESCRIPTION	"
			style='Radiobutton list'
			preset='none'
			path='/Dolby 2 Encoder/Dolby Enc 2 Meta/Internal Metadata 2/RF Mode Pro'
		"
		::= { alchemistHd3GCtrlEntries 40627 }

	encAc3Ac3Dynrng12 OBJECT-TYPE
		SYNTAX		INTEGER {
					filmLight(2),
					filmStandard(1),
					musicLight(4),
					musicStandard(3),
					speech(5),
					none(0)
				}
		MAX-ACCESS	read-write
		STATUS		current
		DESCRIPTION	"
			style='Radiobutton list'
			preset='none'
			path='/Dolby 2 Encoder/Dolby Enc 2 Meta/Internal Metadata 2/Line Mode Pro'
		"
		::= { alchemistHd3GCtrlEntries 40628 }

	dolbyEncFrameRateCode2 OBJECT-TYPE
		SYNTAX		RollCallString
		MAX-ACCESS	read-only
		STATUS		current
		DESCRIPTION	"
			style='ReadOnly string'
			path='/Dolby 2 Encoder/Dolby Enc 2 Meta/Internal Metadata 2/Dolby Frame Rate'
		"
		::= { alchemistHd3GCtrlEntries 40629 }

	dolbyEncProgDesc2 OBJECT-TYPE
		SYNTAX		RollCallString
		MAX-ACCESS	read-write
		STATUS		current
		DESCRIPTION	"
			style='Editable string'
			path='/Dolby 2 Encoder/Dolby Enc 2 Meta/Internal Metadata 2/Program Description'
		"
		::= { alchemistHd3GCtrlEntries 40640 }

	dolbyEncPresetProgram2 OBJECT-TYPE
		SYNTAX		INTEGER { ready(0), trigger(1) }
		MAX-ACCESS	read-write
		STATUS		current
		DESCRIPTION	"
			style='Event button'
			path='/Dolby 2 Encoder/Dolby Enc 2 Meta/Internal Metadata 2/Preset Metadata'
		"
		::= { alchemistHd3GCtrlEntries 40641 }

	dolbyEncLoadSnapshot2 OBJECT-TYPE
		SYNTAX		INTEGER { ready(0), trigger(1) }
		MAX-ACCESS	read-write
		STATUS		current
		DESCRIPTION	"
			style='Event button'
			path='/Dolby 2 Encoder/Dolby Enc 2 Meta/Internal Metadata 2/Recall Snapshot'
		"
		::= { alchemistHd3GCtrlEntries 40642 }

	dolbyEncSaveSnapshot2 OBJECT-TYPE
		SYNTAX		INTEGER { ready(0), trigger(1) }
		MAX-ACCESS	read-write
		STATUS		current
		DESCRIPTION	"
			style='Event button'
			path='/Dolby 2 Encoder/Dolby Enc 2 Meta/Internal Metadata 2/Stove Snapshot'
		"
		::= { alchemistHd3GCtrlEntries 40643 }

	dolbyDecSnapshotSelect1 OBJECT-TYPE
		SYNTAX		INTEGER {
					snapshot1(1),
					snapshot2(2),
					snapshot3(3),
					snapshot4(4),
					snapshot5(5),
					snapshot6(6),
					snapshot7(7),
					snapshot8(8)
				}
		MAX-ACCESS	read-write
		STATUS		current
		DESCRIPTION	"
			style='Radiobutton list'
			preset='snapshot1'
			path='/Decoded Metadata 1/Decoded Metadata 1/Snapshot Select'
		"
		::= { alchemistHd3GCtrlEntries 45968 }

	dolbyDecSnapshotSelect2 OBJECT-TYPE
		SYNTAX		INTEGER {
					snapshot1(1),
					snapshot2(2),
					snapshot3(3),
					snapshot4(4),
					snapshot5(5),
					snapshot6(6),
					snapshot7(7),
					snapshot8(8)
				}
		MAX-ACCESS	read-write
		STATUS		current
		DESCRIPTION	"
			style='Radiobutton list'
			preset='snapshot1'
			path='/Decoded Metadata 2/Decoded Metadata 2/Snapshot Select'
		"
		::= { alchemistHd3GCtrlEntries 45969 }

	dolbyDecSnapshot1 OBJECT-TYPE
		SYNTAX		INTEGER { ready(0), trigger(1) }
		MAX-ACCESS	read-write
		STATUS		current
		DESCRIPTION	"
			style='Event button'
			path='/Decoded Metadata 1/Decoded Metadata 1/Snapshot metadata'
		"
		::= { alchemistHd3GCtrlEntries 45970 }

	dolbyDecSnapshot2 OBJECT-TYPE
		SYNTAX		INTEGER { ready(0), trigger(1) }
		MAX-ACCESS	read-write
		STATUS		current
		DESCRIPTION	"
			style='Event button'
			path='/Decoded Metadata 2/Decoded Metadata 2/Snapshot metadata'
		"
		::= { alchemistHd3GCtrlEntries 45971 }

	dolbyEncSnapshotSelect1 OBJECT-TYPE
		SYNTAX		INTEGER {
					snapshot1(1),
					snapshot2(2),
					snapshot3(3),
					snapshot4(4),
					snapshot5(5),
					snapshot6(6),
					snapshot7(7),
					snapshot8(8)
				}
		MAX-ACCESS	read-write
		STATUS		current
		DESCRIPTION	"
			style='Radiobutton list'
			preset='snapshot1'
			path='/Dolby 1 Encoder/Dolby Enc 1 Meta/Internal Metadata 1/Snapshot Select'
		"
		::= { alchemistHd3GCtrlEntries 45972 }

	dolbyEncSnapshotSelect2 OBJECT-TYPE
		SYNTAX		INTEGER {
					snapshot1(1),
					snapshot2(2),
					snapshot3(3),
					snapshot4(4),
					snapshot5(5),
					snapshot6(6),
					snapshot7(7),
					snapshot8(8)
				}
		MAX-ACCESS	read-write
		STATUS		current
		DESCRIPTION	"
			style='Radiobutton list'
			preset='snapshot1'
			path='/Dolby 2 Encoder/Dolby Enc 2 Meta/Internal Metadata 2/Snapshot Select'
		"
		::= { alchemistHd3GCtrlEntries 45973 }

	snapshotRenameSelect OBJECT-TYPE
		SYNTAX		INTEGER {
					snapshot1(1),
					snapshot2(2),
					snapshot3(3),
					snapshot4(4),
					snapshot5(5),
					snapshot6(6),
					snapshot7(7),
					snapshot8(8)
				}
		MAX-ACCESS	read-write
		STATUS		current
		DESCRIPTION	"
			style='Radiobutton list'
			path='/Memory/Metadata Snapshot Memory/Select'
		"
		::= { alchemistHd3GCtrlEntries 45974 }

	snapshotRename OBJECT-TYPE
		SYNTAX		RollCallString
		MAX-ACCESS	read-write
		STATUS		current
		DESCRIPTION	"
			style='Editable string'
			path='/Memory/Metadata Snapshot Memory/Snapshot Rename'
		"
		::= { alchemistHd3GCtrlEntries 45975 }

	vancSdid1 OBJECT-TYPE
		SYNTAX		Integer32 (0..255)
		MAX-ACCESS	read-write
		STATUS		current
		DESCRIPTION	"
			style='Numeric control'
			range='0..255'
			path='/VANC/VANC 1/VANC 1/S-DID'
		"
		::= { alchemistHd3GCtrlEntries 50000 }

	vancDid1 OBJECT-TYPE
		SYNTAX		Integer32 (0..255)
		MAX-ACCESS	read-write
		STATUS		current
		DESCRIPTION	"
			style='Numeric control'
			range='0..255'
			path='/VANC/VANC 1/VANC 1/DID'
		"
		::= { alchemistHd3GCtrlEntries 50001 }

	vancOutALine5251 OBJECT-TYPE
		SYNTAX		Integer32 (12..19)
		MAX-ACCESS	read-write
		STATUS		current
		DESCRIPTION	"
			style='Numeric control'
			range='12..19'
			preset='12'
			path='/VANC/VANC 1/VANC 1/525 Output/Output A Line'
		"
		::= { alchemistHd3GCtrlEntries 50002 }

	vancOutBLine5251 OBJECT-TYPE
		SYNTAX		Integer32 (12..19)
		MAX-ACCESS	read-write
		STATUS		current
		DESCRIPTION	"
			style='Numeric control'
			range='12..19'
			preset='12'
			path='/VANC/VANC 1/VANC 1/525 Output/Output B Line'
		"
		::= { alchemistHd3GCtrlEntries 50003 }

	vancOutALine6251 OBJECT-TYPE
		SYNTAX		Integer32 (8..22)
		MAX-ACCESS	read-write
		STATUS		current
		DESCRIPTION	"
			style='Numeric control'
			range='8..22'
			preset='8'
			path='/VANC/VANC 1/VANC 1/625 Output/Output A Line'
		"
		::= { alchemistHd3GCtrlEntries 50004 }

	vancOutBLine6251 OBJECT-TYPE
		SYNTAX		Integer32 (8..22)
		MAX-ACCESS	read-write
		STATUS		current
		DESCRIPTION	"
			style='Numeric control'
			range='8..22'
			preset='8'
			path='/VANC/VANC 1/VANC 1/625 Output/Output B Line'
		"
		::= { alchemistHd3GCtrlEntries 50005 }

	vancOutALine7201 OBJECT-TYPE
		SYNTAX		Integer32 (9..25)
		MAX-ACCESS	read-write
		STATUS		current
		DESCRIPTION	"
			style='Numeric control'
			range='9..25'
			preset='9'
			path='/VANC/VANC 1/VANC 1/720 Output/Output A Line'
		"
		::= { alchemistHd3GCtrlEntries 50006 }

	vancOutBLine7201 OBJECT-TYPE
		SYNTAX		Integer32 (9..25)
		MAX-ACCESS	read-write
		STATUS		current
		DESCRIPTION	"
			style='Numeric control'
			range='9..25'
			preset='9'
			path='/VANC/VANC 1/VANC 1/720 Output/Output B Line'
		"
		::= { alchemistHd3GCtrlEntries 50007 }

	vancOutALine1080I1 OBJECT-TYPE
		SYNTAX		Integer32 (9..20)
		MAX-ACCESS	read-write
		STATUS		current
		DESCRIPTION	"
			style='Numeric control'
			range='9..20'
			preset='9'
			path='/VANC/VANC 1/VANC 1/1080i Output/Output A Line'
		"
		::= { alchemistHd3GCtrlEntries 50008 }

	vancOutBLine1080I1 OBJECT-TYPE
		SYNTAX		Integer32 (9..20)
		MAX-ACCESS	read-write
		STATUS		current
		DESCRIPTION	"
			style='Numeric control'
			range='9..20'
			preset='9'
			path='/VANC/VANC 1/VANC 1/1080i Output/Output B Line'
		"
		::= { alchemistHd3GCtrlEntries 50009 }

	vancOutALine1080P1 OBJECT-TYPE
		SYNTAX		Integer32 (9..41)
		MAX-ACCESS	read-write
		STATUS		current
		DESCRIPTION	"
			style='Numeric control'
			range='9..41'
			preset='9'
			path='/VANC/VANC 1/VANC 1/1080p Output/Output A Line'
		"
		::= { alchemistHd3GCtrlEntries 50010 }

	vancOutBLine1080P1 OBJECT-TYPE
		SYNTAX		Integer32 (9..41)
		MAX-ACCESS	read-write
		STATUS		current
		DESCRIPTION	"
			style='Numeric control'
			range='9..41'
			preset='9'
			path='/VANC/VANC 1/VANC 1/1080p Output/Output B Line'
		"
		::= { alchemistHd3GCtrlEntries 50011 }

	vancFollowInput1 OBJECT-TYPE
		SYNTAX		INTEGER { disable(0), enable(1) }
		MAX-ACCESS	read-write
		STATUS		current
		DESCRIPTION	"
			style='Checkbox'
			range='0..1'
			path='/VANC/VANC 1/VANC 1/ Follow Input'
		"
		::= { alchemistHd3GCtrlEntries 50012 }

	vancOutALine525Enable1 OBJECT-TYPE
		SYNTAX		INTEGER { disable(0), enable(1) }
		MAX-ACCESS	read-write
		STATUS		current
		DESCRIPTION	"
			style='Checkbox'
			range='0..1'
			path='/VANC/VANC 1/VANC 1/525 Output/Enable'
		"
		::= { alchemistHd3GCtrlEntries 50013 }

	vancOutALine625Enable1 OBJECT-TYPE
		SYNTAX		INTEGER { disable(0), enable(1) }
		MAX-ACCESS	read-write
		STATUS		current
		DESCRIPTION	"
			style='Checkbox'
			range='0..1'
			path='/VANC/VANC 1/VANC 1/625 Output/Enable'
		"
		::= { alchemistHd3GCtrlEntries 50014 }

	vancOutALine720Enable1 OBJECT-TYPE
		SYNTAX		INTEGER { disable(0), enable(1) }
		MAX-ACCESS	read-write
		STATUS		current
		DESCRIPTION	"
			style='Checkbox'
			range='0..1'
			path='/VANC/VANC 1/VANC 1/720 Output/Enable'
		"
		::= { alchemistHd3GCtrlEntries 50015 }

	vancOutALine1080IEnable1 OBJECT-TYPE
		SYNTAX		INTEGER { disable(0), enable(1) }
		MAX-ACCESS	read-write
		STATUS		current
		DESCRIPTION	"
			style='Checkbox'
			range='0..1'
			path='/VANC/VANC 1/VANC 1/1080i Output/Enable'
		"
		::= { alchemistHd3GCtrlEntries 50016 }

	vancOutALine1080PEnable1 OBJECT-TYPE
		SYNTAX		INTEGER { disable(0), enable(1) }
		MAX-ACCESS	read-write
		STATUS		current
		DESCRIPTION	"
			style='Checkbox'
			range='0..1'
			path='/VANC/VANC 1/VANC 1/1080p Output/Enable'
		"
		::= { alchemistHd3GCtrlEntries 50017 }

	vancOutBLine525Enable1 OBJECT-TYPE
		SYNTAX		INTEGER { disable(0), enable(1) }
		MAX-ACCESS	read-write
		STATUS		current
		DESCRIPTION	"
			style='Checkbox'
			range='0..1'
			path='/VANC/VANC 1/VANC 1/525 Output/Enable'
		"
		::= { alchemistHd3GCtrlEntries 50018 }

	vancOutBLine625Enable1 OBJECT-TYPE
		SYNTAX		INTEGER { disable(0), enable(1) }
		MAX-ACCESS	read-write
		STATUS		current
		DESCRIPTION	"
			style='Checkbox'
			range='0..1'
			path='/VANC/VANC 1/VANC 1/625 Output/Enable'
		"
		::= { alchemistHd3GCtrlEntries 50019 }

	vancOutBLine720Enable1 OBJECT-TYPE
		SYNTAX		INTEGER { disable(0), enable(1) }
		MAX-ACCESS	read-write
		STATUS		current
		DESCRIPTION	"
			style='Checkbox'
			range='0..1'
			path='/VANC/VANC 1/VANC 1/720 Output/Enable'
		"
		::= { alchemistHd3GCtrlEntries 50020 }

	vancOutBLine1080IEnable1 OBJECT-TYPE
		SYNTAX		INTEGER { disable(0), enable(1) }
		MAX-ACCESS	read-write
		STATUS		current
		DESCRIPTION	"
			style='Checkbox'
			range='0..1'
			path='/VANC/VANC 1/VANC 1/1080i Output/Enable'
		"
		::= { alchemistHd3GCtrlEntries 50021 }

	vancOutBLine1080PEnable1 OBJECT-TYPE
		SYNTAX		INTEGER { disable(0), enable(1) }
		MAX-ACCESS	read-write
		STATUS		current
		DESCRIPTION	"
			style='Checkbox'
			range='0..1'
			path='/VANC/VANC 1/VANC 1/1080p Output/Enable'
		"
		::= { alchemistHd3GCtrlEntries 50022 }

	vancOutAActualLine1 OBJECT-TYPE
		SYNTAX		Integer32 (0..41)
		MAX-ACCESS	read-only
		STATUS		current
		DESCRIPTION	"
			style='ReadOnly numeric'
			range='0..41'
			path='/VANC/VANC 1/VANC 1/Actual Out A Line'
		"
		::= { alchemistHd3GCtrlEntries 50023 }

	vancOutBActualLine1 OBJECT-TYPE
		SYNTAX		Integer32 (0..41)
		MAX-ACCESS	read-only
		STATUS		current
		DESCRIPTION	"
			style='ReadOnly numeric'
			range='0..41'
			path='/VANC/VANC 1/VANC 1/Actual Out B Line'
		"
		::= { alchemistHd3GCtrlEntries 50024 }

	vancSdid2 OBJECT-TYPE
		SYNTAX		Integer32 (0..255)
		MAX-ACCESS	read-write
		STATUS		current
		DESCRIPTION	"
			style='Numeric control'
			range='0..255'
			path='/VANC/VANC 2/VANC 2/S-DID'
		"
		::= { alchemistHd3GCtrlEntries 50100 }

	vancDid2 OBJECT-TYPE
		SYNTAX		Integer32 (0..255)
		MAX-ACCESS	read-write
		STATUS		current
		DESCRIPTION	"
			style='Numeric control'
			range='0..255'
			path='/VANC/VANC 2/VANC 2/DID'
		"
		::= { alchemistHd3GCtrlEntries 50101 }

	vancOutALine5252 OBJECT-TYPE
		SYNTAX		Integer32 (12..19)
		MAX-ACCESS	read-write
		STATUS		current
		DESCRIPTION	"
			style='Numeric control'
			range='12..19'
			preset='12'
			path='/VANC/VANC 2/VANC 2/525 Output/Output A Line'
		"
		::= { alchemistHd3GCtrlEntries 50102 }

	vancOutBLine5252 OBJECT-TYPE
		SYNTAX		Integer32 (12..19)
		MAX-ACCESS	read-write
		STATUS		current
		DESCRIPTION	"
			style='Numeric control'
			range='12..19'
			preset='12'
			path='/VANC/VANC 2/VANC 2/525 Output/Output B Line'
		"
		::= { alchemistHd3GCtrlEntries 50103 }

	vancOutALine6252 OBJECT-TYPE
		SYNTAX		Integer32 (8..22)
		MAX-ACCESS	read-write
		STATUS		current
		DESCRIPTION	"
			style='Numeric control'
			range='8..22'
			preset='8'
			path='/VANC/VANC 2/VANC 2/625 Output/Output A Line'
		"
		::= { alchemistHd3GCtrlEntries 50104 }

	vancOutBLine6252 OBJECT-TYPE
		SYNTAX		Integer32 (8..22)
		MAX-ACCESS	read-write
		STATUS		current
		DESCRIPTION	"
			style='Numeric control'
			range='8..22'
			preset='8'
			path='/VANC/VANC 2/VANC 2/625 Output/Output B Line'
		"
		::= { alchemistHd3GCtrlEntries 50105 }

	vancOutALine7202 OBJECT-TYPE
		SYNTAX		Integer32 (9..25)
		MAX-ACCESS	read-write
		STATUS		current
		DESCRIPTION	"
			style='Numeric control'
			range='9..25'
			preset='9'
			path='/VANC/VANC 2/VANC 2/720 Output/Output A Line'
		"
		::= { alchemistHd3GCtrlEntries 50106 }

	vancOutBLine7202 OBJECT-TYPE
		SYNTAX		Integer32 (9..25)
		MAX-ACCESS	read-write
		STATUS		current
		DESCRIPTION	"
			style='Numeric control'
			range='9..25'
			preset='9'
			path='/VANC/VANC 2/VANC 2/720 Output/Output B Line'
		"
		::= { alchemistHd3GCtrlEntries 50107 }

	vancOutALine1080I2 OBJECT-TYPE
		SYNTAX		Integer32 (9..20)
		MAX-ACCESS	read-write
		STATUS		current
		DESCRIPTION	"
			style='Numeric control'
			range='9..20'
			preset='9'
			path='/VANC/VANC 2/VANC 2/1080i Output/Output A Line'
		"
		::= { alchemistHd3GCtrlEntries 50108 }

	vancOutBLine1080I2 OBJECT-TYPE
		SYNTAX		Integer32 (9..20)
		MAX-ACCESS	read-write
		STATUS		current
		DESCRIPTION	"
			style='Numeric control'
			range='9..20'
			preset='9'
			path='/VANC/VANC 2/VANC 2/1080i Output/Output B Line'
		"
		::= { alchemistHd3GCtrlEntries 50109 }

	vancOutALine1080P2 OBJECT-TYPE
		SYNTAX		Integer32 (9..41)
		MAX-ACCESS	read-write
		STATUS		current
		DESCRIPTION	"
			style='Numeric control'
			range='9..41'
			preset='9'
			path='/VANC/VANC 2/VANC 2/1080p Output/Output A Line'
		"
		::= { alchemistHd3GCtrlEntries 50110 }

	vancOutBLine1080P2 OBJECT-TYPE
		SYNTAX		Integer32 (9..41)
		MAX-ACCESS	read-write
		STATUS		current
		DESCRIPTION	"
			style='Numeric control'
			range='9..41'
			preset='9'
			path='/VANC/VANC 2/VANC 2/1080p Output/Output B Line'
		"
		::= { alchemistHd3GCtrlEntries 50111 }

	vancFollowInput2 OBJECT-TYPE
		SYNTAX		INTEGER { disable(0), enable(1) }
		MAX-ACCESS	read-write
		STATUS		current
		DESCRIPTION	"
			style='Checkbox'
			range='0..1'
			path='/VANC/VANC 2/VANC 2/ Follow Input'
		"
		::= { alchemistHd3GCtrlEntries 50112 }

	vancOutALine525Enable2 OBJECT-TYPE
		SYNTAX		INTEGER { disable(0), enable(1) }
		MAX-ACCESS	read-write
		STATUS		current
		DESCRIPTION	"
			style='Checkbox'
			range='0..1'
			path='/VANC/VANC 2/VANC 2/525 Output/Enable'
		"
		::= { alchemistHd3GCtrlEntries 50113 }

	vancOutALine625Enable2 OBJECT-TYPE
		SYNTAX		INTEGER { disable(0), enable(1) }
		MAX-ACCESS	read-write
		STATUS		current
		DESCRIPTION	"
			style='Checkbox'
			range='0..1'
			path='/VANC/VANC 2/VANC 2/625 Output/Enable'
		"
		::= { alchemistHd3GCtrlEntries 50114 }

	vancOutALine720Enable2 OBJECT-TYPE
		SYNTAX		INTEGER { disable(0), enable(1) }
		MAX-ACCESS	read-write
		STATUS		current
		DESCRIPTION	"
			style='Checkbox'
			range='0..1'
			path='/VANC/VANC 2/VANC 2/720 Output/Enable'
		"
		::= { alchemistHd3GCtrlEntries 50115 }

	vancOutALine1080IEnable2 OBJECT-TYPE
		SYNTAX		INTEGER { disable(0), enable(1) }
		MAX-ACCESS	read-write
		STATUS		current
		DESCRIPTION	"
			style='Checkbox'
			range='0..1'
			path='/VANC/VANC 2/VANC 2/1080i Output/Enable'
		"
		::= { alchemistHd3GCtrlEntries 50116 }

	vancOutALine1080PEnable2 OBJECT-TYPE
		SYNTAX		INTEGER { disable(0), enable(1) }
		MAX-ACCESS	read-write
		STATUS		current
		DESCRIPTION	"
			style='Checkbox'
			range='0..1'
			path='/VANC/VANC 2/VANC 2/1080p Output/Enable'
		"
		::= { alchemistHd3GCtrlEntries 50117 }

	vancOutBLine525Enable2 OBJECT-TYPE
		SYNTAX		INTEGER { disable(0), enable(1) }
		MAX-ACCESS	read-write
		STATUS		current
		DESCRIPTION	"
			style='Checkbox'
			range='0..1'
			path='/VANC/VANC 2/VANC 2/525 Output/Enable'
		"
		::= { alchemistHd3GCtrlEntries 50118 }

	vancOutBLine625Enable2 OBJECT-TYPE
		SYNTAX		INTEGER { disable(0), enable(1) }
		MAX-ACCESS	read-write
		STATUS		current
		DESCRIPTION	"
			style='Checkbox'
			range='0..1'
			path='/VANC/VANC 2/VANC 2/625 Output/Enable'
		"
		::= { alchemistHd3GCtrlEntries 50119 }

	vancOutBLine720Enable2 OBJECT-TYPE
		SYNTAX		INTEGER { disable(0), enable(1) }
		MAX-ACCESS	read-write
		STATUS		current
		DESCRIPTION	"
			style='Checkbox'
			range='0..1'
			path='/VANC/VANC 2/VANC 2/720 Output/Enable'
		"
		::= { alchemistHd3GCtrlEntries 50120 }

	vancOutBLine1080IEnable2 OBJECT-TYPE
		SYNTAX		INTEGER { disable(0), enable(1) }
		MAX-ACCESS	read-write
		STATUS		current
		DESCRIPTION	"
			style='Checkbox'
			range='0..1'
			path='/VANC/VANC 2/VANC 2/1080i Output/Enable'
		"
		::= { alchemistHd3GCtrlEntries 50121 }

	vancOutBLine1080PEnable2 OBJECT-TYPE
		SYNTAX		INTEGER { disable(0), enable(1) }
		MAX-ACCESS	read-write
		STATUS		current
		DESCRIPTION	"
			style='Checkbox'
			range='0..1'
			path='/VANC/VANC 2/VANC 2/1080p Output/Enable'
		"
		::= { alchemistHd3GCtrlEntries 50122 }

	vancOutAActualLine2 OBJECT-TYPE
		SYNTAX		Integer32 (0..41)
		MAX-ACCESS	read-only
		STATUS		current
		DESCRIPTION	"
			style='ReadOnly numeric'
			range='0..41'
			path='/VANC/VANC 2/VANC 2/Actual Out A Line'
		"
		::= { alchemistHd3GCtrlEntries 50123 }

	vancOutBActualLine2 OBJECT-TYPE
		SYNTAX		Integer32 (0..41)
		MAX-ACCESS	read-only
		STATUS		current
		DESCRIPTION	"
			style='ReadOnly numeric'
			range='0..41'
			path='/VANC/VANC 2/VANC 2/Actual Out B Line'
		"
		::= { alchemistHd3GCtrlEntries 50124 }

	vancSdid3 OBJECT-TYPE
		SYNTAX		Integer32 (0..255)
		MAX-ACCESS	read-write
		STATUS		current
		DESCRIPTION	"
			style='Numeric control'
			range='0..255'
			path='/VANC/VANC 3/VANC 3/S-DID'
		"
		::= { alchemistHd3GCtrlEntries 50200 }

	vancDid3 OBJECT-TYPE
		SYNTAX		Integer32 (0..255)
		MAX-ACCESS	read-write
		STATUS		current
		DESCRIPTION	"
			style='Numeric control'
			range='0..255'
			path='/VANC/VANC 3/VANC 3/DID'
		"
		::= { alchemistHd3GCtrlEntries 50201 }

	vancOutALine5253 OBJECT-TYPE
		SYNTAX		Integer32 (12..19)
		MAX-ACCESS	read-write
		STATUS		current
		DESCRIPTION	"
			style='Numeric control'
			range='12..19'
			preset='12'
			path='/VANC/VANC 3/VANC 3/525 Output/Output A Line'
		"
		::= { alchemistHd3GCtrlEntries 50202 }

	vancOutBLine5253 OBJECT-TYPE
		SYNTAX		Integer32 (12..19)
		MAX-ACCESS	read-write
		STATUS		current
		DESCRIPTION	"
			style='Numeric control'
			range='12..19'
			preset='12'
			path='/VANC/VANC 3/VANC 3/525 Output/Output B Line'
		"
		::= { alchemistHd3GCtrlEntries 50203 }

	vancOutALine6253 OBJECT-TYPE
		SYNTAX		Integer32 (8..22)
		MAX-ACCESS	read-write
		STATUS		current
		DESCRIPTION	"
			style='Numeric control'
			range='8..22'
			preset='8'
			path='/VANC/VANC 3/VANC 3/625 Output/Output A Line'
		"
		::= { alchemistHd3GCtrlEntries 50204 }

	vancOutBLine6253 OBJECT-TYPE
		SYNTAX		Integer32 (8..22)
		MAX-ACCESS	read-write
		STATUS		current
		DESCRIPTION	"
			style='Numeric control'
			range='8..22'
			preset='8'
			path='/VANC/VANC 3/VANC 3/625 Output/Output B Line'
		"
		::= { alchemistHd3GCtrlEntries 50205 }

	vancOutALine7203 OBJECT-TYPE
		SYNTAX		Integer32 (9..25)
		MAX-ACCESS	read-write
		STATUS		current
		DESCRIPTION	"
			style='Numeric control'
			range='9..25'
			preset='9'
			path='/VANC/VANC 3/VANC 3/720 Output/Output A Line'
		"
		::= { alchemistHd3GCtrlEntries 50206 }

	vancOutBLine7203 OBJECT-TYPE
		SYNTAX		Integer32 (9..25)
		MAX-ACCESS	read-write
		STATUS		current
		DESCRIPTION	"
			style='Numeric control'
			range='9..25'
			preset='9'
			path='/VANC/VANC 3/VANC 3/720 Output/Output B Line'
		"
		::= { alchemistHd3GCtrlEntries 50207 }

	vancOutALine1080I3 OBJECT-TYPE
		SYNTAX		Integer32 (9..20)
		MAX-ACCESS	read-write
		STATUS		current
		DESCRIPTION	"
			style='Numeric control'
			range='9..20'
			preset='9'
			path='/VANC/VANC 3/VANC 3/1080i Output/Output A Line'
		"
		::= { alchemistHd3GCtrlEntries 50208 }

	vancOutBLine1080I3 OBJECT-TYPE
		SYNTAX		Integer32 (9..20)
		MAX-ACCESS	read-write
		STATUS		current
		DESCRIPTION	"
			style='Numeric control'
			range='9..20'
			preset='9'
			path='/VANC/VANC 3/VANC 3/1080i Output/Output B Line'
		"
		::= { alchemistHd3GCtrlEntries 50209 }

	vancOutALine1080P3 OBJECT-TYPE
		SYNTAX		Integer32 (9..41)
		MAX-ACCESS	read-write
		STATUS		current
		DESCRIPTION	"
			style='Numeric control'
			range='9..41'
			preset='9'
			path='/VANC/VANC 3/VANC 3/1080p Output/Output A Line'
		"
		::= { alchemistHd3GCtrlEntries 50210 }

	vancOutBLine1080P3 OBJECT-TYPE
		SYNTAX		Integer32 (9..41)
		MAX-ACCESS	read-write
		STATUS		current
		DESCRIPTION	"
			style='Numeric control'
			range='9..41'
			preset='9'
			path='/VANC/VANC 3/VANC 3/1080p Output/Output B Line'
		"
		::= { alchemistHd3GCtrlEntries 50211 }

	vancFollowInput3 OBJECT-TYPE
		SYNTAX		INTEGER { disable(0), enable(1) }
		MAX-ACCESS	read-write
		STATUS		current
		DESCRIPTION	"
			style='Checkbox'
			range='0..1'
			path='/VANC/VANC 3/VANC 3/ Follow Input'
		"
		::= { alchemistHd3GCtrlEntries 50212 }

	vancOutALine525Enable3 OBJECT-TYPE
		SYNTAX		INTEGER { disable(0), enable(1) }
		MAX-ACCESS	read-write
		STATUS		current
		DESCRIPTION	"
			style='Checkbox'
			range='0..1'
			path='/VANC/VANC 3/VANC 3/525 Output/Enable'
		"
		::= { alchemistHd3GCtrlEntries 50213 }

	vancOutALine625Enable3 OBJECT-TYPE
		SYNTAX		INTEGER { disable(0), enable(1) }
		MAX-ACCESS	read-write
		STATUS		current
		DESCRIPTION	"
			style='Checkbox'
			range='0..1'
			path='/VANC/VANC 3/VANC 3/625 Output/Enable'
		"
		::= { alchemistHd3GCtrlEntries 50214 }

	vancOutALine720Enable3 OBJECT-TYPE
		SYNTAX		INTEGER { disable(0), enable(1) }
		MAX-ACCESS	read-write
		STATUS		current
		DESCRIPTION	"
			style='Checkbox'
			range='0..1'
			path='/VANC/VANC 3/VANC 3/720 Output/Enable'
		"
		::= { alchemistHd3GCtrlEntries 50215 }

	vancOutALine1080IEnable3 OBJECT-TYPE
		SYNTAX		INTEGER { disable(0), enable(1) }
		MAX-ACCESS	read-write
		STATUS		current
		DESCRIPTION	"
			style='Checkbox'
			range='0..1'
			path='/VANC/VANC 3/VANC 3/1080i Output/Enable'
		"
		::= { alchemistHd3GCtrlEntries 50216 }

	vancOutALine1080PEnable3 OBJECT-TYPE
		SYNTAX		INTEGER { disable(0), enable(1) }
		MAX-ACCESS	read-write
		STATUS		current
		DESCRIPTION	"
			style='Checkbox'
			range='0..1'
			path='/VANC/VANC 3/VANC 3/1080p Output/Enable'
		"
		::= { alchemistHd3GCtrlEntries 50217 }

	vancOutBLine525Enable3 OBJECT-TYPE
		SYNTAX		INTEGER { disable(0), enable(1) }
		MAX-ACCESS	read-write
		STATUS		current
		DESCRIPTION	"
			style='Checkbox'
			range='0..1'
			path='/VANC/VANC 3/VANC 3/525 Output/Enable'
		"
		::= { alchemistHd3GCtrlEntries 50218 }

	vancOutBLine625Enable3 OBJECT-TYPE
		SYNTAX		INTEGER { disable(0), enable(1) }
		MAX-ACCESS	read-write
		STATUS		current
		DESCRIPTION	"
			style='Checkbox'
			range='0..1'
			path='/VANC/VANC 3/VANC 3/625 Output/Enable'
		"
		::= { alchemistHd3GCtrlEntries 50219 }

	vancOutBLine720Enable3 OBJECT-TYPE
		SYNTAX		INTEGER { disable(0), enable(1) }
		MAX-ACCESS	read-write
		STATUS		current
		DESCRIPTION	"
			style='Checkbox'
			range='0..1'
			path='/VANC/VANC 3/VANC 3/720 Output/Enable'
		"
		::= { alchemistHd3GCtrlEntries 50220 }

	vancOutBLine1080IEnable3 OBJECT-TYPE
		SYNTAX		INTEGER { disable(0), enable(1) }
		MAX-ACCESS	read-write
		STATUS		current
		DESCRIPTION	"
			style='Checkbox'
			range='0..1'
			path='/VANC/VANC 3/VANC 3/1080i Output/Enable'
		"
		::= { alchemistHd3GCtrlEntries 50221 }

	vancOutBLine1080PEnable3 OBJECT-TYPE
		SYNTAX		INTEGER { disable(0), enable(1) }
		MAX-ACCESS	read-write
		STATUS		current
		DESCRIPTION	"
			style='Checkbox'
			range='0..1'
			path='/VANC/VANC 3/VANC 3/1080p Output/Enable'
		"
		::= { alchemistHd3GCtrlEntries 50222 }

	vancOutAActualLine3 OBJECT-TYPE
		SYNTAX		Integer32 (0..41)
		MAX-ACCESS	read-only
		STATUS		current
		DESCRIPTION	"
			style='ReadOnly numeric'
			range='0..41'
			path='/VANC/VANC 3/VANC 3/Actual Out A Line'
		"
		::= { alchemistHd3GCtrlEntries 50223 }

	vancOutBActualLine3 OBJECT-TYPE
		SYNTAX		Integer32 (0..41)
		MAX-ACCESS	read-only
		STATUS		current
		DESCRIPTION	"
			style='ReadOnly numeric'
			range='0..41'
			path='/VANC/VANC 3/VANC 3/Actual Out B Line'
		"
		::= { alchemistHd3GCtrlEntries 50224 }

	vancSdid4 OBJECT-TYPE
		SYNTAX		Integer32 (0..255)
		MAX-ACCESS	read-write
		STATUS		current
		DESCRIPTION	"
			style='Numeric control'
			range='0..255'
			path='/VANC/VANC 4/VANC 4/S-DID'
		"
		::= { alchemistHd3GCtrlEntries 50300 }

	vancDid4 OBJECT-TYPE
		SYNTAX		Integer32 (0..255)
		MAX-ACCESS	read-write
		STATUS		current
		DESCRIPTION	"
			style='Numeric control'
			range='0..255'
			path='/VANC/VANC 4/VANC 4/DID'
		"
		::= { alchemistHd3GCtrlEntries 50301 }

	vancOutALine5254 OBJECT-TYPE
		SYNTAX		Integer32 (12..19)
		MAX-ACCESS	read-write
		STATUS		current
		DESCRIPTION	"
			style='Numeric control'
			range='12..19'
			preset='12'
			path='/VANC/VANC 4/VANC 4/525 Output/Output A Line'
		"
		::= { alchemistHd3GCtrlEntries 50302 }

	vancOutBLine5254 OBJECT-TYPE
		SYNTAX		Integer32 (12..19)
		MAX-ACCESS	read-write
		STATUS		current
		DESCRIPTION	"
			style='Numeric control'
			range='12..19'
			preset='12'
			path='/VANC/VANC 4/VANC 4/525 Output/Output B Line'
		"
		::= { alchemistHd3GCtrlEntries 50303 }

	vancOutALine6254 OBJECT-TYPE
		SYNTAX		Integer32 (8..22)
		MAX-ACCESS	read-write
		STATUS		current
		DESCRIPTION	"
			style='Numeric control'
			range='8..22'
			preset='8'
			path='/VANC/VANC 4/VANC 4/625 Output/Output A Line'
		"
		::= { alchemistHd3GCtrlEntries 50304 }

	vancOutBLine6254 OBJECT-TYPE
		SYNTAX		Integer32 (8..22)
		MAX-ACCESS	read-write
		STATUS		current
		DESCRIPTION	"
			style='Numeric control'
			range='8..22'
			preset='8'
			path='/VANC/VANC 4/VANC 4/625 Output/Output B Line'
		"
		::= { alchemistHd3GCtrlEntries 50305 }

	vancOutALine7204 OBJECT-TYPE
		SYNTAX		Integer32 (9..25)
		MAX-ACCESS	read-write
		STATUS		current
		DESCRIPTION	"
			style='Numeric control'
			range='9..25'
			preset='9'
			path='/VANC/VANC 4/VANC 4/720 Output/Output A Line'
		"
		::= { alchemistHd3GCtrlEntries 50306 }

	vancOutBLine7204 OBJECT-TYPE
		SYNTAX		Integer32 (9..25)
		MAX-ACCESS	read-write
		STATUS		current
		DESCRIPTION	"
			style='Numeric control'
			range='9..25'
			preset='9'
			path='/VANC/VANC 4/VANC 4/720 Output/Output B Line'
		"
		::= { alchemistHd3GCtrlEntries 50307 }

	vancOutALine1080I4 OBJECT-TYPE
		SYNTAX		Integer32 (9..20)
		MAX-ACCESS	read-write
		STATUS		current
		DESCRIPTION	"
			style='Numeric control'
			range='9..20'
			preset='9'
			path='/VANC/VANC 4/VANC 4/1080i Output/Output A Line'
		"
		::= { alchemistHd3GCtrlEntries 50308 }

	vancOutBLine1080I4 OBJECT-TYPE
		SYNTAX		Integer32 (9..20)
		MAX-ACCESS	read-write
		STATUS		current
		DESCRIPTION	"
			style='Numeric control'
			range='9..20'
			preset='9'
			path='/VANC/VANC 4/VANC 4/1080i Output/Output B Line'
		"
		::= { alchemistHd3GCtrlEntries 50309 }

	vancOutALine1080P4 OBJECT-TYPE
		SYNTAX		Integer32 (9..41)
		MAX-ACCESS	read-write
		STATUS		current
		DESCRIPTION	"
			style='Numeric control'
			range='9..41'
			preset='9'
			path='/VANC/VANC 4/VANC 4/1080p Output/Output A Line'
		"
		::= { alchemistHd3GCtrlEntries 50310 }

	vancOutBLine1080P4 OBJECT-TYPE
		SYNTAX		Integer32 (9..41)
		MAX-ACCESS	read-write
		STATUS		current
		DESCRIPTION	"
			style='Numeric control'
			range='9..41'
			preset='9'
			path='/VANC/VANC 4/VANC 4/1080p Output/Output B Line'
		"
		::= { alchemistHd3GCtrlEntries 50311 }

	vancFollowInput4 OBJECT-TYPE
		SYNTAX		INTEGER { disable(0), enable(1) }
		MAX-ACCESS	read-write
		STATUS		current
		DESCRIPTION	"
			style='Checkbox'
			range='0..1'
			path='/VANC/VANC 4/VANC 4/ Follow Input'
		"
		::= { alchemistHd3GCtrlEntries 50312 }

	vancOutALine525Enable4 OBJECT-TYPE
		SYNTAX		INTEGER { disable(0), enable(1) }
		MAX-ACCESS	read-write
		STATUS		current
		DESCRIPTION	"
			style='Checkbox'
			range='0..1'
			path='/VANC/VANC 4/VANC 4/525 Output/Enable'
		"
		::= { alchemistHd3GCtrlEntries 50313 }

	vancOutALine625Enable4 OBJECT-TYPE
		SYNTAX		INTEGER { disable(0), enable(1) }
		MAX-ACCESS	read-write
		STATUS		current
		DESCRIPTION	"
			style='Checkbox'
			range='0..1'
			path='/VANC/VANC 4/VANC 4/625 Output/Enable'
		"
		::= { alchemistHd3GCtrlEntries 50314 }

	vancOutALine720Enable4 OBJECT-TYPE
		SYNTAX		INTEGER { disable(0), enable(1) }
		MAX-ACCESS	read-write
		STATUS		current
		DESCRIPTION	"
			style='Checkbox'
			range='0..1'
			path='/VANC/VANC 4/VANC 4/720 Output/Enable'
		"
		::= { alchemistHd3GCtrlEntries 50315 }

	vancOutALine1080IEnable4 OBJECT-TYPE
		SYNTAX		INTEGER { disable(0), enable(1) }
		MAX-ACCESS	read-write
		STATUS		current
		DESCRIPTION	"
			style='Checkbox'
			range='0..1'
			path='/VANC/VANC 4/VANC 4/1080i Output/Enable'
		"
		::= { alchemistHd3GCtrlEntries 50316 }

	vancOutALine1080PEnable4 OBJECT-TYPE
		SYNTAX		INTEGER { disable(0), enable(1) }
		MAX-ACCESS	read-write
		STATUS		current
		DESCRIPTION	"
			style='Checkbox'
			range='0..1'
			path='/VANC/VANC 4/VANC 4/1080p Output/Enable'
		"
		::= { alchemistHd3GCtrlEntries 50317 }

	vancOutBLine525Enable4 OBJECT-TYPE
		SYNTAX		INTEGER { disable(0), enable(1) }
		MAX-ACCESS	read-write
		STATUS		current
		DESCRIPTION	"
			style='Checkbox'
			range='0..1'
			path='/VANC/VANC 4/VANC 4/525 Output/Enable'
		"
		::= { alchemistHd3GCtrlEntries 50318 }

	vancOutBLine625Enable4 OBJECT-TYPE
		SYNTAX		INTEGER { disable(0), enable(1) }
		MAX-ACCESS	read-write
		STATUS		current
		DESCRIPTION	"
			style='Checkbox'
			range='0..1'
			path='/VANC/VANC 4/VANC 4/625 Output/Enable'
		"
		::= { alchemistHd3GCtrlEntries 50319 }

	vancOutBLine720Enable4 OBJECT-TYPE
		SYNTAX		INTEGER { disable(0), enable(1) }
		MAX-ACCESS	read-write
		STATUS		current
		DESCRIPTION	"
			style='Checkbox'
			range='0..1'
			path='/VANC/VANC 4/VANC 4/720 Output/Enable'
		"
		::= { alchemistHd3GCtrlEntries 50320 }

	vancOutBLine1080IEnable4 OBJECT-TYPE
		SYNTAX		INTEGER { disable(0), enable(1) }
		MAX-ACCESS	read-write
		STATUS		current
		DESCRIPTION	"
			style='Checkbox'
			range='0..1'
			path='/VANC/VANC 4/VANC 4/1080i Output/Enable'
		"
		::= { alchemistHd3GCtrlEntries 50321 }

	vancOutBLine1080PEnable4 OBJECT-TYPE
		SYNTAX		INTEGER { disable(0), enable(1) }
		MAX-ACCESS	read-write
		STATUS		current
		DESCRIPTION	"
			style='Checkbox'
			range='0..1'
			path='/VANC/VANC 4/VANC 4/1080p Output/Enable'
		"
		::= { alchemistHd3GCtrlEntries 50322 }

	vancOutAActualLine4 OBJECT-TYPE
		SYNTAX		Integer32 (0..41)
		MAX-ACCESS	read-only
		STATUS		current
		DESCRIPTION	"
			style='ReadOnly numeric'
			range='0..41'
			path='/VANC/VANC 4/VANC 4/Actual Out A Line'
		"
		::= { alchemistHd3GCtrlEntries 50323 }

	vancOutBActualLine4 OBJECT-TYPE
		SYNTAX		Integer32 (0..41)
		MAX-ACCESS	read-only
		STATUS		current
		DESCRIPTION	"
			style='ReadOnly numeric'
			range='0..41'
			path='/VANC/VANC 4/VANC 4/Actual Out B Line'
		"
		::= { alchemistHd3GCtrlEntries 50324 }

	vancSdid5 OBJECT-TYPE
		SYNTAX		Integer32 (0..255)
		MAX-ACCESS	read-write
		STATUS		current
		DESCRIPTION	"
			style='Numeric control'
			range='0..255'
			path='/VANC/VANC 5/VANC 5/S-DID'
		"
		::= { alchemistHd3GCtrlEntries 50400 }

	vancDid5 OBJECT-TYPE
		SYNTAX		Integer32 (0..255)
		MAX-ACCESS	read-write
		STATUS		current
		DESCRIPTION	"
			style='Numeric control'
			range='0..255'
			path='/VANC/VANC 5/VANC 5/DID'
		"
		::= { alchemistHd3GCtrlEntries 50401 }

	vancOutALine5255 OBJECT-TYPE
		SYNTAX		Integer32 (12..19)
		MAX-ACCESS	read-write
		STATUS		current
		DESCRIPTION	"
			style='Numeric control'
			range='12..19'
			preset='12'
			path='/VANC/VANC 5/VANC 5/525 Output/Output A Line'
		"
		::= { alchemistHd3GCtrlEntries 50402 }

	vancOutBLine5255 OBJECT-TYPE
		SYNTAX		Integer32 (12..19)
		MAX-ACCESS	read-write
		STATUS		current
		DESCRIPTION	"
			style='Numeric control'
			range='12..19'
			preset='12'
			path='/VANC/VANC 5/VANC 5/525 Output/Output B Line'
		"
		::= { alchemistHd3GCtrlEntries 50403 }

	vancOutALine6255 OBJECT-TYPE
		SYNTAX		Integer32 (8..22)
		MAX-ACCESS	read-write
		STATUS		current
		DESCRIPTION	"
			style='Numeric control'
			range='8..22'
			preset='8'
			path='/VANC/VANC 5/VANC 5/625 Output/Output A Line'
		"
		::= { alchemistHd3GCtrlEntries 50404 }

	vancOutBLine6255 OBJECT-TYPE
		SYNTAX		Integer32 (8..22)
		MAX-ACCESS	read-write
		STATUS		current
		DESCRIPTION	"
			style='Numeric control'
			range='8..22'
			preset='8'
			path='/VANC/VANC 5/VANC 5/625 Output/Output B Line'
		"
		::= { alchemistHd3GCtrlEntries 50405 }

	vancOutALine7205 OBJECT-TYPE
		SYNTAX		Integer32 (9..25)
		MAX-ACCESS	read-write
		STATUS		current
		DESCRIPTION	"
			style='Numeric control'
			range='9..25'
			preset='9'
			path='/VANC/VANC 5/VANC 5/720 Output/Output A Line'
		"
		::= { alchemistHd3GCtrlEntries 50406 }

	vancOutBLine7205 OBJECT-TYPE
		SYNTAX		Integer32 (9..25)
		MAX-ACCESS	read-write
		STATUS		current
		DESCRIPTION	"
			style='Numeric control'
			range='9..25'
			preset='9'
			path='/VANC/VANC 5/VANC 5/720 Output/Output B Line'
		"
		::= { alchemistHd3GCtrlEntries 50407 }

	vancOutALine1080I5 OBJECT-TYPE
		SYNTAX		Integer32 (9..20)
		MAX-ACCESS	read-write
		STATUS		current
		DESCRIPTION	"
			style='Numeric control'
			range='9..20'
			preset='9'
			path='/VANC/VANC 5/VANC 5/1080i Output/Output A Line'
		"
		::= { alchemistHd3GCtrlEntries 50408 }

	vancOutBLine1080I5 OBJECT-TYPE
		SYNTAX		Integer32 (9..20)
		MAX-ACCESS	read-write
		STATUS		current
		DESCRIPTION	"
			style='Numeric control'
			range='9..20'
			preset='9'
			path='/VANC/VANC 5/VANC 5/1080i Output/Output B Line'
		"
		::= { alchemistHd3GCtrlEntries 50409 }

	vancOutALine1080P5 OBJECT-TYPE
		SYNTAX		Integer32 (9..41)
		MAX-ACCESS	read-write
		STATUS		current
		DESCRIPTION	"
			style='Numeric control'
			range='9..41'
			preset='9'
			path='/VANC/VANC 5/VANC 5/1080p Output/Output A Line'
		"
		::= { alchemistHd3GCtrlEntries 50410 }

	vancOutBLine1080P5 OBJECT-TYPE
		SYNTAX		Integer32 (9..41)
		MAX-ACCESS	read-write
		STATUS		current
		DESCRIPTION	"
			style='Numeric control'
			range='9..41'
			preset='9'
			path='/VANC/VANC 5/VANC 5/1080p Output/Output B Line'
		"
		::= { alchemistHd3GCtrlEntries 50411 }

	vancFollowInput5 OBJECT-TYPE
		SYNTAX		INTEGER { disable(0), enable(1) }
		MAX-ACCESS	read-write
		STATUS		current
		DESCRIPTION	"
			style='Checkbox'
			range='0..1'
			path='/VANC/VANC 5/VANC 5/ Follow Input'
		"
		::= { alchemistHd3GCtrlEntries 50412 }

	vancOutALine525Enable5 OBJECT-TYPE
		SYNTAX		INTEGER { disable(0), enable(1) }
		MAX-ACCESS	read-write
		STATUS		current
		DESCRIPTION	"
			style='Checkbox'
			range='0..1'
			path='/VANC/VANC 5/VANC 5/525 Output/Enable'
		"
		::= { alchemistHd3GCtrlEntries 50413 }

	vancOutALine625Enable5 OBJECT-TYPE
		SYNTAX		INTEGER { disable(0), enable(1) }
		MAX-ACCESS	read-write
		STATUS		current
		DESCRIPTION	"
			style='Checkbox'
			range='0..1'
			path='/VANC/VANC 5/VANC 5/625 Output/Enable'
		"
		::= { alchemistHd3GCtrlEntries 50414 }

	vancOutALine720Enable5 OBJECT-TYPE
		SYNTAX		INTEGER { disable(0), enable(1) }
		MAX-ACCESS	read-write
		STATUS		current
		DESCRIPTION	"
			style='Checkbox'
			range='0..1'
			path='/VANC/VANC 5/VANC 5/720 Output/Enable'
		"
		::= { alchemistHd3GCtrlEntries 50415 }

	vancOutALine1080IEnable5 OBJECT-TYPE
		SYNTAX		INTEGER { disable(0), enable(1) }
		MAX-ACCESS	read-write
		STATUS		current
		DESCRIPTION	"
			style='Checkbox'
			range='0..1'
			path='/VANC/VANC 5/VANC 5/1080i Output/Enable'
		"
		::= { alchemistHd3GCtrlEntries 50416 }

	vancOutALine1080PEnable5 OBJECT-TYPE
		SYNTAX		INTEGER { disable(0), enable(1) }
		MAX-ACCESS	read-write
		STATUS		current
		DESCRIPTION	"
			style='Checkbox'
			range='0..1'
			path='/VANC/VANC 5/VANC 5/1080p Output/Enable'
		"
		::= { alchemistHd3GCtrlEntries 50417 }

	vancOutBLine525Enable5 OBJECT-TYPE
		SYNTAX		INTEGER { disable(0), enable(1) }
		MAX-ACCESS	read-write
		STATUS		current
		DESCRIPTION	"
			style='Checkbox'
			range='0..1'
			path='/VANC/VANC 5/VANC 5/525 Output/Enable'
		"
		::= { alchemistHd3GCtrlEntries 50418 }

	vancOutBLine625Enable5 OBJECT-TYPE
		SYNTAX		INTEGER { disable(0), enable(1) }
		MAX-ACCESS	read-write
		STATUS		current
		DESCRIPTION	"
			style='Checkbox'
			range='0..1'
			path='/VANC/VANC 5/VANC 5/625 Output/Enable'
		"
		::= { alchemistHd3GCtrlEntries 50419 }

	vancOutBLine720Enable5 OBJECT-TYPE
		SYNTAX		INTEGER { disable(0), enable(1) }
		MAX-ACCESS	read-write
		STATUS		current
		DESCRIPTION	"
			style='Checkbox'
			range='0..1'
			path='/VANC/VANC 5/VANC 5/720 Output/Enable'
		"
		::= { alchemistHd3GCtrlEntries 50420 }

	vancOutBLine1080IEnable5 OBJECT-TYPE
		SYNTAX		INTEGER { disable(0), enable(1) }
		MAX-ACCESS	read-write
		STATUS		current
		DESCRIPTION	"
			style='Checkbox'
			range='0..1'
			path='/VANC/VANC 5/VANC 5/1080i Output/Enable'
		"
		::= { alchemistHd3GCtrlEntries 50421 }

	vancOutBLine1080PEnable5 OBJECT-TYPE
		SYNTAX		INTEGER { disable(0), enable(1) }
		MAX-ACCESS	read-write
		STATUS		current
		DESCRIPTION	"
			style='Checkbox'
			range='0..1'
			path='/VANC/VANC 5/VANC 5/1080p Output/Enable'
		"
		::= { alchemistHd3GCtrlEntries 50422 }

	vancOutAActualLine5 OBJECT-TYPE
		SYNTAX		Integer32 (0..41)
		MAX-ACCESS	read-only
		STATUS		current
		DESCRIPTION	"
			style='ReadOnly numeric'
			range='0..41'
			path='/VANC/VANC 5/VANC 5/Actual Out A Line'
		"
		::= { alchemistHd3GCtrlEntries 50423 }

	vancOutBActualLine5 OBJECT-TYPE
		SYNTAX		Integer32 (0..41)
		MAX-ACCESS	read-only
		STATUS		current
		DESCRIPTION	"
			style='ReadOnly numeric'
			range='0..41'
			path='/VANC/VANC 5/VANC 5/Actual Out B Line'
		"
		::= { alchemistHd3GCtrlEntries 50424 }

	vancSdid6 OBJECT-TYPE
		SYNTAX		Integer32 (0..255)
		MAX-ACCESS	read-write
		STATUS		current
		DESCRIPTION	"
			style='Numeric control'
			range='0..255'
			path='/VANC/VANC 6/VANC 6/S-DID'
		"
		::= { alchemistHd3GCtrlEntries 50500 }

	vancDid6 OBJECT-TYPE
		SYNTAX		Integer32 (0..255)
		MAX-ACCESS	read-write
		STATUS		current
		DESCRIPTION	"
			style='Numeric control'
			range='0..255'
			path='/VANC/VANC 6/VANC 6/DID'
		"
		::= { alchemistHd3GCtrlEntries 50501 }

	vancOutALine5256 OBJECT-TYPE
		SYNTAX		Integer32 (12..19)
		MAX-ACCESS	read-write
		STATUS		current
		DESCRIPTION	"
			style='Numeric control'
			range='12..19'
			preset='12'
			path='/VANC/VANC 6/VANC 6/525 Output/Output A Line'
		"
		::= { alchemistHd3GCtrlEntries 50502 }

	vancOutBLine5256 OBJECT-TYPE
		SYNTAX		Integer32 (12..19)
		MAX-ACCESS	read-write
		STATUS		current
		DESCRIPTION	"
			style='Numeric control'
			range='12..19'
			preset='12'
			path='/VANC/VANC 6/VANC 6/525 Output/Output B Line'
		"
		::= { alchemistHd3GCtrlEntries 50503 }

	vancOutALine6256 OBJECT-TYPE
		SYNTAX		Integer32 (8..22)
		MAX-ACCESS	read-write
		STATUS		current
		DESCRIPTION	"
			style='Numeric control'
			range='8..22'
			preset='8'
			path='/VANC/VANC 6/VANC 6/625 Output/Output A Line'
		"
		::= { alchemistHd3GCtrlEntries 50504 }

	vancOutBLine6256 OBJECT-TYPE
		SYNTAX		Integer32 (8..22)
		MAX-ACCESS	read-write
		STATUS		current
		DESCRIPTION	"
			style='Numeric control'
			range='8..22'
			preset='8'
			path='/VANC/VANC 6/VANC 6/625 Output/Output B Line'
		"
		::= { alchemistHd3GCtrlEntries 50505 }

	vancOutALine7206 OBJECT-TYPE
		SYNTAX		Integer32 (9..25)
		MAX-ACCESS	read-write
		STATUS		current
		DESCRIPTION	"
			style='Numeric control'
			range='9..25'
			preset='9'
			path='/VANC/VANC 6/VANC 6/720 Output/Output A Line'
		"
		::= { alchemistHd3GCtrlEntries 50506 }

	vancOutBLine7206 OBJECT-TYPE
		SYNTAX		Integer32 (9..25)
		MAX-ACCESS	read-write
		STATUS		current
		DESCRIPTION	"
			style='Numeric control'
			range='9..25'
			preset='9'
			path='/VANC/VANC 6/VANC 6/720 Output/Output B Line'
		"
		::= { alchemistHd3GCtrlEntries 50507 }

	vancOutALine1080I6 OBJECT-TYPE
		SYNTAX		Integer32 (9..20)
		MAX-ACCESS	read-write
		STATUS		current
		DESCRIPTION	"
			style='Numeric control'
			range='9..20'
			preset='9'
			path='/VANC/VANC 6/VANC 6/1080i Output/Output A Line'
		"
		::= { alchemistHd3GCtrlEntries 50508 }

	vancOutBLine1080I6 OBJECT-TYPE
		SYNTAX		Integer32 (9..20)
		MAX-ACCESS	read-write
		STATUS		current
		DESCRIPTION	"
			style='Numeric control'
			range='9..20'
			preset='9'
			path='/VANC/VANC 6/VANC 6/1080i Output/Output B Line'
		"
		::= { alchemistHd3GCtrlEntries 50509 }

	vancOutALine1080P6 OBJECT-TYPE
		SYNTAX		Integer32 (9..41)
		MAX-ACCESS	read-write
		STATUS		current
		DESCRIPTION	"
			style='Numeric control'
			range='9..41'
			preset='9'
			path='/VANC/VANC 6/VANC 6/1080p Output/Output A Line'
		"
		::= { alchemistHd3GCtrlEntries 50510 }

	vancOutBLine1080P6 OBJECT-TYPE
		SYNTAX		Integer32 (9..41)
		MAX-ACCESS	read-write
		STATUS		current
		DESCRIPTION	"
			style='Numeric control'
			range='9..41'
			preset='9'
			path='/VANC/VANC 6/VANC 6/1080p Output/Output B Line'
		"
		::= { alchemistHd3GCtrlEntries 50511 }

	vancFollowInput6 OBJECT-TYPE
		SYNTAX		INTEGER { disable(0), enable(1) }
		MAX-ACCESS	read-write
		STATUS		current
		DESCRIPTION	"
			style='Checkbox'
			range='0..1'
			path='/VANC/VANC 6/VANC 6/ Follow Input'
		"
		::= { alchemistHd3GCtrlEntries 50512 }

	vancOutALine525Enable6 OBJECT-TYPE
		SYNTAX		INTEGER { disable(0), enable(1) }
		MAX-ACCESS	read-write
		STATUS		current
		DESCRIPTION	"
			style='Checkbox'
			range='0..1'
			path='/VANC/VANC 6/VANC 6/525 Output/Enable'
		"
		::= { alchemistHd3GCtrlEntries 50513 }

	vancOutALine625Enable6 OBJECT-TYPE
		SYNTAX		INTEGER { disable(0), enable(1) }
		MAX-ACCESS	read-write
		STATUS		current
		DESCRIPTION	"
			style='Checkbox'
			range='0..1'
			path='/VANC/VANC 6/VANC 6/625 Output/Enable'
		"
		::= { alchemistHd3GCtrlEntries 50514 }

	vancOutALine720Enable6 OBJECT-TYPE
		SYNTAX		INTEGER { disable(0), enable(1) }
		MAX-ACCESS	read-write
		STATUS		current
		DESCRIPTION	"
			style='Checkbox'
			range='0..1'
			path='/VANC/VANC 6/VANC 6/720 Output/Enable'
		"
		::= { alchemistHd3GCtrlEntries 50515 }

	vancOutALine1080IEnable6 OBJECT-TYPE
		SYNTAX		INTEGER { disable(0), enable(1) }
		MAX-ACCESS	read-write
		STATUS		current
		DESCRIPTION	"
			style='Checkbox'
			range='0..1'
			path='/VANC/VANC 6/VANC 6/1080i Output/Enable'
		"
		::= { alchemistHd3GCtrlEntries 50516 }

	vancOutALine1080PEnable6 OBJECT-TYPE
		SYNTAX		INTEGER { disable(0), enable(1) }
		MAX-ACCESS	read-write
		STATUS		current
		DESCRIPTION	"
			style='Checkbox'
			range='0..1'
			path='/VANC/VANC 6/VANC 6/1080p Output/Enable'
		"
		::= { alchemistHd3GCtrlEntries 50517 }

	vancOutBLine525Enable6 OBJECT-TYPE
		SYNTAX		INTEGER { disable(0), enable(1) }
		MAX-ACCESS	read-write
		STATUS		current
		DESCRIPTION	"
			style='Checkbox'
			range='0..1'
			path='/VANC/VANC 6/VANC 6/525 Output/Enable'
		"
		::= { alchemistHd3GCtrlEntries 50518 }

	vancOutBLine625Enable6 OBJECT-TYPE
		SYNTAX		INTEGER { disable(0), enable(1) }
		MAX-ACCESS	read-write
		STATUS		current
		DESCRIPTION	"
			style='Checkbox'
			range='0..1'
			path='/VANC/VANC 6/VANC 6/625 Output/Enable'
		"
		::= { alchemistHd3GCtrlEntries 50519 }

	vancOutBLine720Enable6 OBJECT-TYPE
		SYNTAX		INTEGER { disable(0), enable(1) }
		MAX-ACCESS	read-write
		STATUS		current
		DESCRIPTION	"
			style='Checkbox'
			range='0..1'
			path='/VANC/VANC 6/VANC 6/720 Output/Enable'
		"
		::= { alchemistHd3GCtrlEntries 50520 }

	vancOutBLine1080IEnable6 OBJECT-TYPE
		SYNTAX		INTEGER { disable(0), enable(1) }
		MAX-ACCESS	read-write
		STATUS		current
		DESCRIPTION	"
			style='Checkbox'
			range='0..1'
			path='/VANC/VANC 6/VANC 6/1080i Output/Enable'
		"
		::= { alchemistHd3GCtrlEntries 50521 }

	vancOutBLine1080PEnable6 OBJECT-TYPE
		SYNTAX		INTEGER { disable(0), enable(1) }
		MAX-ACCESS	read-write
		STATUS		current
		DESCRIPTION	"
			style='Checkbox'
			range='0..1'
			path='/VANC/VANC 6/VANC 6/1080p Output/Enable'
		"
		::= { alchemistHd3GCtrlEntries 50522 }

	vancOutAActualLine6 OBJECT-TYPE
		SYNTAX		Integer32 (0..41)
		MAX-ACCESS	read-only
		STATUS		current
		DESCRIPTION	"
			style='ReadOnly numeric'
			range='0..41'
			path='/VANC/VANC 6/VANC 6/Actual Out A Line'
		"
		::= { alchemistHd3GCtrlEntries 50523 }

	vancOutBActualLine6 OBJECT-TYPE
		SYNTAX		Integer32 (0..41)
		MAX-ACCESS	read-only
		STATUS		current
		DESCRIPTION	"
			style='ReadOnly numeric'
			range='0..41'
			path='/VANC/VANC 6/VANC 6/Actual Out B Line'
		"
		::= { alchemistHd3GCtrlEntries 50524 }

	vancSdid7 OBJECT-TYPE
		SYNTAX		Integer32 (0..255)
		MAX-ACCESS	read-write
		STATUS		current
		DESCRIPTION	"
			style='Numeric control'
			range='0..255'
			path='/VANC/VANC 7/VANC 7/S-DID'
		"
		::= { alchemistHd3GCtrlEntries 50600 }

	vancDid7 OBJECT-TYPE
		SYNTAX		Integer32 (0..255)
		MAX-ACCESS	read-write
		STATUS		current
		DESCRIPTION	"
			style='Numeric control'
			range='0..255'
			path='/VANC/VANC 7/VANC 7/DID'
		"
		::= { alchemistHd3GCtrlEntries 50601 }

	vancOutALine5257 OBJECT-TYPE
		SYNTAX		Integer32 (12..19)
		MAX-ACCESS	read-write
		STATUS		current
		DESCRIPTION	"
			style='Numeric control'
			range='12..19'
			preset='12'
			path='/VANC/VANC 7/VANC 7/525 Output/Output A Line'
		"
		::= { alchemistHd3GCtrlEntries 50602 }

	vancOutBLine5257 OBJECT-TYPE
		SYNTAX		Integer32 (12..19)
		MAX-ACCESS	read-write
		STATUS		current
		DESCRIPTION	"
			style='Numeric control'
			range='12..19'
			preset='12'
			path='/VANC/VANC 7/VANC 7/525 Output/Output B Line'
		"
		::= { alchemistHd3GCtrlEntries 50603 }

	vancOutALine6257 OBJECT-TYPE
		SYNTAX		Integer32 (8..22)
		MAX-ACCESS	read-write
		STATUS		current
		DESCRIPTION	"
			style='Numeric control'
			range='8..22'
			preset='8'
			path='/VANC/VANC 7/VANC 7/625 Output/Output A Line'
		"
		::= { alchemistHd3GCtrlEntries 50604 }

	vancOutBLine6257 OBJECT-TYPE
		SYNTAX		Integer32 (8..22)
		MAX-ACCESS	read-write
		STATUS		current
		DESCRIPTION	"
			style='Numeric control'
			range='8..22'
			preset='8'
			path='/VANC/VANC 7/VANC 7/625 Output/Output B Line'
		"
		::= { alchemistHd3GCtrlEntries 50605 }

	vancOutALine7207 OBJECT-TYPE
		SYNTAX		Integer32 (9..25)
		MAX-ACCESS	read-write
		STATUS		current
		DESCRIPTION	"
			style='Numeric control'
			range='9..25'
			preset='9'
			path='/VANC/VANC 7/VANC 7/720 Output/Output A Line'
		"
		::= { alchemistHd3GCtrlEntries 50606 }

	vancOutBLine7207 OBJECT-TYPE
		SYNTAX		Integer32 (9..25)
		MAX-ACCESS	read-write
		STATUS		current
		DESCRIPTION	"
			style='Numeric control'
			range='9..25'
			preset='9'
			path='/VANC/VANC 7/VANC 7/720 Output/Output B Line'
		"
		::= { alchemistHd3GCtrlEntries 50607 }

	vancOutALine1080I7 OBJECT-TYPE
		SYNTAX		Integer32 (9..20)
		MAX-ACCESS	read-write
		STATUS		current
		DESCRIPTION	"
			style='Numeric control'
			range='9..20'
			preset='9'
			path='/VANC/VANC 7/VANC 7/1080i Output/Output A Line'
		"
		::= { alchemistHd3GCtrlEntries 50608 }

	vancOutBLine1080I7 OBJECT-TYPE
		SYNTAX		Integer32 (9..20)
		MAX-ACCESS	read-write
		STATUS		current
		DESCRIPTION	"
			style='Numeric control'
			range='9..20'
			preset='9'
			path='/VANC/VANC 7/VANC 7/1080i Output/Output B Line'
		"
		::= { alchemistHd3GCtrlEntries 50609 }

	vancOutALine1080P7 OBJECT-TYPE
		SYNTAX		Integer32 (9..41)
		MAX-ACCESS	read-write
		STATUS		current
		DESCRIPTION	"
			style='Numeric control'
			range='9..41'
			preset='9'
			path='/VANC/VANC 7/VANC 7/1080p Output/Output A Line'
		"
		::= { alchemistHd3GCtrlEntries 50610 }

	vancOutBLine1080P7 OBJECT-TYPE
		SYNTAX		Integer32 (9..41)
		MAX-ACCESS	read-write
		STATUS		current
		DESCRIPTION	"
			style='Numeric control'
			range='9..41'
			preset='9'
			path='/VANC/VANC 7/VANC 7/1080p Output/Output B Line'
		"
		::= { alchemistHd3GCtrlEntries 50611 }

	vancFollowInput7 OBJECT-TYPE
		SYNTAX		INTEGER { disable(0), enable(1) }
		MAX-ACCESS	read-write
		STATUS		current
		DESCRIPTION	"
			style='Checkbox'
			range='0..1'
			path='/VANC/VANC 7/VANC 7/ Follow Input'
		"
		::= { alchemistHd3GCtrlEntries 50612 }

	vancOutALine525Enable7 OBJECT-TYPE
		SYNTAX		INTEGER { disable(0), enable(1) }
		MAX-ACCESS	read-write
		STATUS		current
		DESCRIPTION	"
			style='Checkbox'
			range='0..1'
			path='/VANC/VANC 7/VANC 7/525 Output/Enable'
		"
		::= { alchemistHd3GCtrlEntries 50613 }

	vancOutALine625Enable7 OBJECT-TYPE
		SYNTAX		INTEGER { disable(0), enable(1) }
		MAX-ACCESS	read-write
		STATUS		current
		DESCRIPTION	"
			style='Checkbox'
			range='0..1'
			path='/VANC/VANC 7/VANC 7/625 Output/Enable'
		"
		::= { alchemistHd3GCtrlEntries 50614 }

	vancOutALine720Enable7 OBJECT-TYPE
		SYNTAX		INTEGER { disable(0), enable(1) }
		MAX-ACCESS	read-write
		STATUS		current
		DESCRIPTION	"
			style='Checkbox'
			range='0..1'
			path='/VANC/VANC 7/VANC 7/720 Output/Enable'
		"
		::= { alchemistHd3GCtrlEntries 50615 }

	vancOutALine1080IEnable7 OBJECT-TYPE
		SYNTAX		INTEGER { disable(0), enable(1) }
		MAX-ACCESS	read-write
		STATUS		current
		DESCRIPTION	"
			style='Checkbox'
			range='0..1'
			path='/VANC/VANC 7/VANC 7/1080i Output/Enable'
		"
		::= { alchemistHd3GCtrlEntries 50616 }

	vancOutALine1080PEnable7 OBJECT-TYPE
		SYNTAX		INTEGER { disable(0), enable(1) }
		MAX-ACCESS	read-write
		STATUS		current
		DESCRIPTION	"
			style='Checkbox'
			range='0..1'
			path='/VANC/VANC 7/VANC 7/1080p Output/Enable'
		"
		::= { alchemistHd3GCtrlEntries 50617 }

	vancOutBLine525Enable7 OBJECT-TYPE
		SYNTAX		INTEGER { disable(0), enable(1) }
		MAX-ACCESS	read-write
		STATUS		current
		DESCRIPTION	"
			style='Checkbox'
			range='0..1'
			path='/VANC/VANC 7/VANC 7/525 Output/Enable'
		"
		::= { alchemistHd3GCtrlEntries 50618 }

	vancOutBLine625Enable7 OBJECT-TYPE
		SYNTAX		INTEGER { disable(0), enable(1) }
		MAX-ACCESS	read-write
		STATUS		current
		DESCRIPTION	"
			style='Checkbox'
			range='0..1'
			path='/VANC/VANC 7/VANC 7/625 Output/Enable'
		"
		::= { alchemistHd3GCtrlEntries 50619 }

	vancOutBLine720Enable7 OBJECT-TYPE
		SYNTAX		INTEGER { disable(0), enable(1) }
		MAX-ACCESS	read-write
		STATUS		current
		DESCRIPTION	"
			style='Checkbox'
			range='0..1'
			path='/VANC/VANC 7/VANC 7/720 Output/Enable'
		"
		::= { alchemistHd3GCtrlEntries 50620 }

	vancOutBLine1080IEnable7 OBJECT-TYPE
		SYNTAX		INTEGER { disable(0), enable(1) }
		MAX-ACCESS	read-write
		STATUS		current
		DESCRIPTION	"
			style='Checkbox'
			range='0..1'
			path='/VANC/VANC 7/VANC 7/1080i Output/Enable'
		"
		::= { alchemistHd3GCtrlEntries 50621 }

	vancOutBLine1080PEnable7 OBJECT-TYPE
		SYNTAX		INTEGER { disable(0), enable(1) }
		MAX-ACCESS	read-write
		STATUS		current
		DESCRIPTION	"
			style='Checkbox'
			range='0..1'
			path='/VANC/VANC 7/VANC 7/1080p Output/Enable'
		"
		::= { alchemistHd3GCtrlEntries 50622 }

	vancOutAActualLine7 OBJECT-TYPE
		SYNTAX		Integer32 (0..41)
		MAX-ACCESS	read-only
		STATUS		current
		DESCRIPTION	"
			style='ReadOnly numeric'
			range='0..41'
			path='/VANC/VANC 7/VANC 7/Actual Out A Line'
		"
		::= { alchemistHd3GCtrlEntries 50623 }

	vancOutBActualLine7 OBJECT-TYPE
		SYNTAX		Integer32 (0..41)
		MAX-ACCESS	read-only
		STATUS		current
		DESCRIPTION	"
			style='ReadOnly numeric'
			range='0..41'
			path='/VANC/VANC 7/VANC 7/Actual Out B Line'
		"
		::= { alchemistHd3GCtrlEntries 50624 }

	vancSdid8 OBJECT-TYPE
		SYNTAX		Integer32 (0..255)
		MAX-ACCESS	read-write
		STATUS		current
		DESCRIPTION	"
			style='Numeric control'
			range='0..255'
			path='/VANC/VANC 8/VANC 8/S-DID'
		"
		::= { alchemistHd3GCtrlEntries 50700 }

	vancDid8 OBJECT-TYPE
		SYNTAX		Integer32 (0..255)
		MAX-ACCESS	read-write
		STATUS		current
		DESCRIPTION	"
			style='Numeric control'
			range='0..255'
			path='/VANC/VANC 8/VANC 8/DID'
		"
		::= { alchemistHd3GCtrlEntries 50701 }

	vancOutALine5258 OBJECT-TYPE
		SYNTAX		Integer32 (12..19)
		MAX-ACCESS	read-write
		STATUS		current
		DESCRIPTION	"
			style='Numeric control'
			range='12..19'
			preset='12'
			path='/VANC/VANC 8/VANC 8/525 Output/Output A Line'
		"
		::= { alchemistHd3GCtrlEntries 50702 }

	vancOutBLine5258 OBJECT-TYPE
		SYNTAX		Integer32 (12..19)
		MAX-ACCESS	read-write
		STATUS		current
		DESCRIPTION	"
			style='Numeric control'
			range='12..19'
			preset='12'
			path='/VANC/VANC 8/VANC 8/525 Output/Output B Line'
		"
		::= { alchemistHd3GCtrlEntries 50703 }

	vancOutALine6258 OBJECT-TYPE
		SYNTAX		Integer32 (8..22)
		MAX-ACCESS	read-write
		STATUS		current
		DESCRIPTION	"
			style='Numeric control'
			range='8..22'
			preset='8'
			path='/VANC/VANC 8/VANC 8/625 Output/Output A Line'
		"
		::= { alchemistHd3GCtrlEntries 50704 }

	vancOutBLine6258 OBJECT-TYPE
		SYNTAX		Integer32 (8..22)
		MAX-ACCESS	read-write
		STATUS		current
		DESCRIPTION	"
			style='Numeric control'
			range='8..22'
			preset='8'
			path='/VANC/VANC 8/VANC 8/625 Output/Output B Line'
		"
		::= { alchemistHd3GCtrlEntries 50705 }

	vancOutALine7208 OBJECT-TYPE
		SYNTAX		Integer32 (9..25)
		MAX-ACCESS	read-write
		STATUS		current
		DESCRIPTION	"
			style='Numeric control'
			range='9..25'
			preset='9'
			path='/VANC/VANC 8/VANC 8/720 Output/Output A Line'
		"
		::= { alchemistHd3GCtrlEntries 50706 }

	vancOutBLine7208 OBJECT-TYPE
		SYNTAX		Integer32 (9..25)
		MAX-ACCESS	read-write
		STATUS		current
		DESCRIPTION	"
			style='Numeric control'
			range='9..25'
			preset='9'
			path='/VANC/VANC 8/VANC 8/720 Output/Output B Line'
		"
		::= { alchemistHd3GCtrlEntries 50707 }

	vancOutALine1080I8 OBJECT-TYPE
		SYNTAX		Integer32 (9..20)
		MAX-ACCESS	read-write
		STATUS		current
		DESCRIPTION	"
			style='Numeric control'
			range='9..20'
			preset='9'
			path='/VANC/VANC 8/VANC 8/1080i Output/Output A Line'
		"
		::= { alchemistHd3GCtrlEntries 50708 }

	vancOutBLine1080I8 OBJECT-TYPE
		SYNTAX		Integer32 (9..20)
		MAX-ACCESS	read-write
		STATUS		current
		DESCRIPTION	"
			style='Numeric control'
			range='9..20'
			preset='9'
			path='/VANC/VANC 8/VANC 8/1080i Output/Output B Line'
		"
		::= { alchemistHd3GCtrlEntries 50709 }

	vancOutALine1080P8 OBJECT-TYPE
		SYNTAX		Integer32 (9..41)
		MAX-ACCESS	read-write
		STATUS		current
		DESCRIPTION	"
			style='Numeric control'
			range='9..41'
			preset='9'
			path='/VANC/VANC 8/VANC 8/1080p Output/Output A Line'
		"
		::= { alchemistHd3GCtrlEntries 50710 }

	vancOutBLine1080P8 OBJECT-TYPE
		SYNTAX		Integer32 (9..41)
		MAX-ACCESS	read-write
		STATUS		current
		DESCRIPTION	"
			style='Numeric control'
			range='9..41'
			preset='9'
			path='/VANC/VANC 8/VANC 8/1080p Output/Output B Line'
		"
		::= { alchemistHd3GCtrlEntries 50711 }

	vancFollowInput8 OBJECT-TYPE
		SYNTAX		INTEGER { disable(0), enable(1) }
		MAX-ACCESS	read-write
		STATUS		current
		DESCRIPTION	"
			style='Checkbox'
			range='0..1'
			path='/VANC/VANC 8/VANC 8/ Follow Input'
		"
		::= { alchemistHd3GCtrlEntries 50712 }

	vancOutALine525Enable8 OBJECT-TYPE
		SYNTAX		INTEGER { disable(0), enable(1) }
		MAX-ACCESS	read-write
		STATUS		current
		DESCRIPTION	"
			style='Checkbox'
			range='0..1'
			path='/VANC/VANC 8/VANC 8/525 Output/Enable'
		"
		::= { alchemistHd3GCtrlEntries 50713 }

	vancOutALine625Enable8 OBJECT-TYPE
		SYNTAX		INTEGER { disable(0), enable(1) }
		MAX-ACCESS	read-write
		STATUS		current
		DESCRIPTION	"
			style='Checkbox'
			range='0..1'
			path='/VANC/VANC 8/VANC 8/625 Output/Enable'
		"
		::= { alchemistHd3GCtrlEntries 50714 }

	vancOutALine720Enable8 OBJECT-TYPE
		SYNTAX		INTEGER { disable(0), enable(1) }
		MAX-ACCESS	read-write
		STATUS		current
		DESCRIPTION	"
			style='Checkbox'
			range='0..1'
			path='/VANC/VANC 8/VANC 8/720 Output/Enable'
		"
		::= { alchemistHd3GCtrlEntries 50715 }

	vancOutALine1080IEnable8 OBJECT-TYPE
		SYNTAX		INTEGER { disable(0), enable(1) }
		MAX-ACCESS	read-write
		STATUS		current
		DESCRIPTION	"
			style='Checkbox'
			range='0..1'
			path='/VANC/VANC 8/VANC 8/1080i Output/Enable'
		"
		::= { alchemistHd3GCtrlEntries 50716 }

	vancOutALine1080PEnable8 OBJECT-TYPE
		SYNTAX		INTEGER { disable(0), enable(1) }
		MAX-ACCESS	read-write
		STATUS		current
		DESCRIPTION	"
			style='Checkbox'
			range='0..1'
			path='/VANC/VANC 8/VANC 8/1080p Output/Enable'
		"
		::= { alchemistHd3GCtrlEntries 50717 }

	vancOutBLine525Enable8 OBJECT-TYPE
		SYNTAX		INTEGER { disable(0), enable(1) }
		MAX-ACCESS	read-write
		STATUS		current
		DESCRIPTION	"
			style='Checkbox'
			range='0..1'
			path='/VANC/VANC 8/VANC 8/525 Output/Enable'
		"
		::= { alchemistHd3GCtrlEntries 50718 }

	vancOutBLine625Enable8 OBJECT-TYPE
		SYNTAX		INTEGER { disable(0), enable(1) }
		MAX-ACCESS	read-write
		STATUS		current
		DESCRIPTION	"
			style='Checkbox'
			range='0..1'
			path='/VANC/VANC 8/VANC 8/625 Output/Enable'
		"
		::= { alchemistHd3GCtrlEntries 50719 }

	vancOutBLine720Enable8 OBJECT-TYPE
		SYNTAX		INTEGER { disable(0), enable(1) }
		MAX-ACCESS	read-write
		STATUS		current
		DESCRIPTION	"
			style='Checkbox'
			range='0..1'
			path='/VANC/VANC 8/VANC 8/720 Output/Enable'
		"
		::= { alchemistHd3GCtrlEntries 50720 }

	vancOutBLine1080IEnable8 OBJECT-TYPE
		SYNTAX		INTEGER { disable(0), enable(1) }
		MAX-ACCESS	read-write
		STATUS		current
		DESCRIPTION	"
			style='Checkbox'
			range='0..1'
			path='/VANC/VANC 8/VANC 8/1080i Output/Enable'
		"
		::= { alchemistHd3GCtrlEntries 50721 }

	vancOutBLine1080PEnable8 OBJECT-TYPE
		SYNTAX		INTEGER { disable(0), enable(1) }
		MAX-ACCESS	read-write
		STATUS		current
		DESCRIPTION	"
			style='Checkbox'
			range='0..1'
			path='/VANC/VANC 8/VANC 8/1080p Output/Enable'
		"
		::= { alchemistHd3GCtrlEntries 50722 }

	vancOutAActualLine8 OBJECT-TYPE
		SYNTAX		Integer32 (0..41)
		MAX-ACCESS	read-only
		STATUS		current
		DESCRIPTION	"
			style='ReadOnly numeric'
			range='0..41'
			path='/VANC/VANC 8/VANC 8/Actual Out A Line'
		"
		::= { alchemistHd3GCtrlEntries 50723 }

	vancOutBActualLine8 OBJECT-TYPE
		SYNTAX		Integer32 (0..41)
		MAX-ACCESS	read-only
		STATUS		current
		DESCRIPTION	"
			style='ReadOnly numeric'
			range='0..41'
			path='/VANC/VANC 8/VANC 8/Actual Out B Line'
		"
		::= { alchemistHd3GCtrlEntries 50724 }

	vancSdid9 OBJECT-TYPE
		SYNTAX		Integer32 (0..255)
		MAX-ACCESS	read-write
		STATUS		current
		DESCRIPTION	"
			style='Numeric control'
			range='0..255'
			path='/VANC/VANC 9/VANC 9/S-DID'
		"
		::= { alchemistHd3GCtrlEntries 50800 }

	vancDid9 OBJECT-TYPE
		SYNTAX		Integer32 (0..255)
		MAX-ACCESS	read-write
		STATUS		current
		DESCRIPTION	"
			style='Numeric control'
			range='0..255'
			path='/VANC/VANC 9/VANC 9/DID'
		"
		::= { alchemistHd3GCtrlEntries 50801 }

	vancOutALine5259 OBJECT-TYPE
		SYNTAX		Integer32 (12..19)
		MAX-ACCESS	read-write
		STATUS		current
		DESCRIPTION	"
			style='Numeric control'
			range='12..19'
			preset='12'
			path='/VANC/VANC 9/VANC 9/525 Output/Output A Line'
		"
		::= { alchemistHd3GCtrlEntries 50802 }

	vancOutBLine5259 OBJECT-TYPE
		SYNTAX		Integer32 (12..19)
		MAX-ACCESS	read-write
		STATUS		current
		DESCRIPTION	"
			style='Numeric control'
			range='12..19'
			preset='12'
			path='/VANC/VANC 9/VANC 9/525 Output/Output B Line'
		"
		::= { alchemistHd3GCtrlEntries 50803 }

	vancOutALine6259 OBJECT-TYPE
		SYNTAX		Integer32 (8..22)
		MAX-ACCESS	read-write
		STATUS		current
		DESCRIPTION	"
			style='Numeric control'
			range='8..22'
			preset='8'
			path='/VANC/VANC 9/VANC 9/625 Output/Output A Line'
		"
		::= { alchemistHd3GCtrlEntries 50804 }

	vancOutBLine6259 OBJECT-TYPE
		SYNTAX		Integer32 (8..22)
		MAX-ACCESS	read-write
		STATUS		current
		DESCRIPTION	"
			style='Numeric control'
			range='8..22'
			preset='8'
			path='/VANC/VANC 9/VANC 9/625 Output/Output B Line'
		"
		::= { alchemistHd3GCtrlEntries 50805 }

	vancOutALine7209 OBJECT-TYPE
		SYNTAX		Integer32 (9..25)
		MAX-ACCESS	read-write
		STATUS		current
		DESCRIPTION	"
			style='Numeric control'
			range='9..25'
			preset='9'
			path='/VANC/VANC 9/VANC 9/720 Output/Output A Line'
		"
		::= { alchemistHd3GCtrlEntries 50806 }

	vancOutBLine7209 OBJECT-TYPE
		SYNTAX		Integer32 (9..25)
		MAX-ACCESS	read-write
		STATUS		current
		DESCRIPTION	"
			style='Numeric control'
			range='9..25'
			preset='9'
			path='/VANC/VANC 9/VANC 9/720 Output/Output B Line'
		"
		::= { alchemistHd3GCtrlEntries 50807 }

	vancOutALine1080I9 OBJECT-TYPE
		SYNTAX		Integer32 (9..20)
		MAX-ACCESS	read-write
		STATUS		current
		DESCRIPTION	"
			style='Numeric control'
			range='9..20'
			preset='9'
			path='/VANC/VANC 9/VANC 9/1080i Output/Output A Line'
		"
		::= { alchemistHd3GCtrlEntries 50808 }

	vancOutBLine1080I9 OBJECT-TYPE
		SYNTAX		Integer32 (9..20)
		MAX-ACCESS	read-write
		STATUS		current
		DESCRIPTION	"
			style='Numeric control'
			range='9..20'
			preset='9'
			path='/VANC/VANC 9/VANC 9/1080i Output/Output B Line'
		"
		::= { alchemistHd3GCtrlEntries 50809 }

	vancOutALine1080P9 OBJECT-TYPE
		SYNTAX		Integer32 (9..41)
		MAX-ACCESS	read-write
		STATUS		current
		DESCRIPTION	"
			style='Numeric control'
			range='9..41'
			preset='9'
			path='/VANC/VANC 9/VANC 9/1080p Output/Output A Line'
		"
		::= { alchemistHd3GCtrlEntries 50810 }

	vancOutBLine1080P9 OBJECT-TYPE
		SYNTAX		Integer32 (9..41)
		MAX-ACCESS	read-write
		STATUS		current
		DESCRIPTION	"
			style='Numeric control'
			range='9..41'
			preset='9'
			path='/VANC/VANC 9/VANC 9/1080p Output/Output B Line'
		"
		::= { alchemistHd3GCtrlEntries 50811 }

	vancFollowInput9 OBJECT-TYPE
		SYNTAX		INTEGER { disable(0), enable(1) }
		MAX-ACCESS	read-write
		STATUS		current
		DESCRIPTION	"
			style='Checkbox'
			range='0..1'
			path='/VANC/VANC 9/VANC 9/ Follow Input'
		"
		::= { alchemistHd3GCtrlEntries 50812 }

	vancOutALine525Enable9 OBJECT-TYPE
		SYNTAX		INTEGER { disable(0), enable(1) }
		MAX-ACCESS	read-write
		STATUS		current
		DESCRIPTION	"
			style='Checkbox'
			range='0..1'
			path='/VANC/VANC 9/VANC 9/525 Output/Enable'
		"
		::= { alchemistHd3GCtrlEntries 50813 }

	vancOutALine625Enable9 OBJECT-TYPE
		SYNTAX		INTEGER { disable(0), enable(1) }
		MAX-ACCESS	read-write
		STATUS		current
		DESCRIPTION	"
			style='Checkbox'
			range='0..1'
			path='/VANC/VANC 9/VANC 9/625 Output/Enable'
		"
		::= { alchemistHd3GCtrlEntries 50814 }

	vancOutALine720Enable9 OBJECT-TYPE
		SYNTAX		INTEGER { disable(0), enable(1) }
		MAX-ACCESS	read-write
		STATUS		current
		DESCRIPTION	"
			style='Checkbox'
			range='0..1'
			path='/VANC/VANC 9/VANC 9/720 Output/Enable'
		"
		::= { alchemistHd3GCtrlEntries 50815 }

	vancOutALine1080IEnable9 OBJECT-TYPE
		SYNTAX		INTEGER { disable(0), enable(1) }
		MAX-ACCESS	read-write
		STATUS		current
		DESCRIPTION	"
			style='Checkbox'
			range='0..1'
			path='/VANC/VANC 9/VANC 9/1080i Output/Enable'
		"
		::= { alchemistHd3GCtrlEntries 50816 }

	vancOutALine1080PEnable9 OBJECT-TYPE
		SYNTAX		INTEGER { disable(0), enable(1) }
		MAX-ACCESS	read-write
		STATUS		current
		DESCRIPTION	"
			style='Checkbox'
			range='0..1'
			path='/VANC/VANC 9/VANC 9/1080p Output/Enable'
		"
		::= { alchemistHd3GCtrlEntries 50817 }

	vancOutBLine525Enable9 OBJECT-TYPE
		SYNTAX		INTEGER { disable(0), enable(1) }
		MAX-ACCESS	read-write
		STATUS		current
		DESCRIPTION	"
			style='Checkbox'
			range='0..1'
			path='/VANC/VANC 9/VANC 9/525 Output/Enable'
		"
		::= { alchemistHd3GCtrlEntries 50818 }

	vancOutBLine625Enable9 OBJECT-TYPE
		SYNTAX		INTEGER { disable(0), enable(1) }
		MAX-ACCESS	read-write
		STATUS		current
		DESCRIPTION	"
			style='Checkbox'
			range='0..1'
			path='/VANC/VANC 9/VANC 9/625 Output/Enable'
		"
		::= { alchemistHd3GCtrlEntries 50819 }

	vancOutBLine720Enable9 OBJECT-TYPE
		SYNTAX		INTEGER { disable(0), enable(1) }
		MAX-ACCESS	read-write
		STATUS		current
		DESCRIPTION	"
			style='Checkbox'
			range='0..1'
			path='/VANC/VANC 9/VANC 9/720 Output/Enable'
		"
		::= { alchemistHd3GCtrlEntries 50820 }

	vancOutBLine1080IEnable9 OBJECT-TYPE
		SYNTAX		INTEGER { disable(0), enable(1) }
		MAX-ACCESS	read-write
		STATUS		current
		DESCRIPTION	"
			style='Checkbox'
			range='0..1'
			path='/VANC/VANC 9/VANC 9/1080i Output/Enable'
		"
		::= { alchemistHd3GCtrlEntries 50821 }

	vancOutBLine1080PEnable9 OBJECT-TYPE
		SYNTAX		INTEGER { disable(0), enable(1) }
		MAX-ACCESS	read-write
		STATUS		current
		DESCRIPTION	"
			style='Checkbox'
			range='0..1'
			path='/VANC/VANC 9/VANC 9/1080p Output/Enable'
		"
		::= { alchemistHd3GCtrlEntries 50822 }

	vancOutAActualLine9 OBJECT-TYPE
		SYNTAX		Integer32 (0..41)
		MAX-ACCESS	read-only
		STATUS		current
		DESCRIPTION	"
			style='ReadOnly numeric'
			range='0..41'
			path='/VANC/VANC 9/VANC 9/Actual Out A Line'
		"
		::= { alchemistHd3GCtrlEntries 50823 }

	vancOutBActualLine9 OBJECT-TYPE
		SYNTAX		Integer32 (0..41)
		MAX-ACCESS	read-only
		STATUS		current
		DESCRIPTION	"
			style='ReadOnly numeric'
			range='0..41'
			path='/VANC/VANC 9/VANC 9/Actual Out B Line'
		"
		::= { alchemistHd3GCtrlEntries 50824 }

	vancSdid10 OBJECT-TYPE
		SYNTAX		Integer32 (0..255)
		MAX-ACCESS	read-write
		STATUS		current
		DESCRIPTION	"
			style='Numeric control'
			range='0..255'
			path='/VANC/VANC 10/VANC 10/S-DID'
		"
		::= { alchemistHd3GCtrlEntries 50900 }

	vancDid10 OBJECT-TYPE
		SYNTAX		Integer32 (0..255)
		MAX-ACCESS	read-write
		STATUS		current
		DESCRIPTION	"
			style='Numeric control'
			range='0..255'
			path='/VANC/VANC 10/VANC 10/DID'
		"
		::= { alchemistHd3GCtrlEntries 50901 }

	vancOutALine52510 OBJECT-TYPE
		SYNTAX		Integer32 (12..19)
		MAX-ACCESS	read-write
		STATUS		current
		DESCRIPTION	"
			style='Numeric control'
			range='12..19'
			preset='12'
			path='/VANC/VANC 10/VANC 10/525 Output/Output A Line'
		"
		::= { alchemistHd3GCtrlEntries 50902 }

	vancOutBLine52510 OBJECT-TYPE
		SYNTAX		Integer32 (12..19)
		MAX-ACCESS	read-write
		STATUS		current
		DESCRIPTION	"
			style='Numeric control'
			range='12..19'
			preset='12'
			path='/VANC/VANC 10/VANC 10/525 Output/Output B Line'
		"
		::= { alchemistHd3GCtrlEntries 50903 }

	vancOutALine62510 OBJECT-TYPE
		SYNTAX		Integer32 (8..22)
		MAX-ACCESS	read-write
		STATUS		current
		DESCRIPTION	"
			style='Numeric control'
			range='8..22'
			preset='8'
			path='/VANC/VANC 10/VANC 10/625 Output/Output A Line'
		"
		::= { alchemistHd3GCtrlEntries 50904 }

	vancOutBLine62510 OBJECT-TYPE
		SYNTAX		Integer32 (8..22)
		MAX-ACCESS	read-write
		STATUS		current
		DESCRIPTION	"
			style='Numeric control'
			range='8..22'
			preset='8'
			path='/VANC/VANC 10/VANC 10/625 Output/Output B Line'
		"
		::= { alchemistHd3GCtrlEntries 50905 }

	vancOutALine72010 OBJECT-TYPE
		SYNTAX		Integer32 (9..25)
		MAX-ACCESS	read-write
		STATUS		current
		DESCRIPTION	"
			style='Numeric control'
			range='9..25'
			preset='9'
			path='/VANC/VANC 10/VANC 10/720 Output/Output A Line'
		"
		::= { alchemistHd3GCtrlEntries 50906 }

	vancOutBLine72010 OBJECT-TYPE
		SYNTAX		Integer32 (9..25)
		MAX-ACCESS	read-write
		STATUS		current
		DESCRIPTION	"
			style='Numeric control'
			range='9..25'
			preset='9'
			path='/VANC/VANC 10/VANC 10/720 Output/Output B Line'
		"
		::= { alchemistHd3GCtrlEntries 50907 }

	vancOutALine1080I10 OBJECT-TYPE
		SYNTAX		Integer32 (9..20)
		MAX-ACCESS	read-write
		STATUS		current
		DESCRIPTION	"
			style='Numeric control'
			range='9..20'
			preset='9'
			path='/VANC/VANC 10/VANC 10/1080i Output/Output A Line'
		"
		::= { alchemistHd3GCtrlEntries 50908 }

	vancOutBLine1080I10 OBJECT-TYPE
		SYNTAX		Integer32 (9..20)
		MAX-ACCESS	read-write
		STATUS		current
		DESCRIPTION	"
			style='Numeric control'
			range='9..20'
			preset='9'
			path='/VANC/VANC 10/VANC 10/1080i Output/Output B Line'
		"
		::= { alchemistHd3GCtrlEntries 50909 }

	vancOutALine1080P10 OBJECT-TYPE
		SYNTAX		Integer32 (9..41)
		MAX-ACCESS	read-write
		STATUS		current
		DESCRIPTION	"
			style='Numeric control'
			range='9..41'
			preset='9'
			path='/VANC/VANC 10/VANC 10/1080p Output/Output A Line'
		"
		::= { alchemistHd3GCtrlEntries 50910 }

	vancOutBLine1080P10 OBJECT-TYPE
		SYNTAX		Integer32 (9..41)
		MAX-ACCESS	read-write
		STATUS		current
		DESCRIPTION	"
			style='Numeric control'
			range='9..41'
			preset='9'
			path='/VANC/VANC 10/VANC 10/1080p Output/Output B Line'
		"
		::= { alchemistHd3GCtrlEntries 50911 }

	vancFollowInput10 OBJECT-TYPE
		SYNTAX		INTEGER { disable(0), enable(1) }
		MAX-ACCESS	read-write
		STATUS		current
		DESCRIPTION	"
			style='Checkbox'
			range='0..1'
			path='/VANC/VANC 10/VANC 10/ Follow Input'
		"
		::= { alchemistHd3GCtrlEntries 50912 }

	vancOutALine525Enable10 OBJECT-TYPE
		SYNTAX		INTEGER { disable(0), enable(1) }
		MAX-ACCESS	read-write
		STATUS		current
		DESCRIPTION	"
			style='Checkbox'
			range='0..1'
			path='/VANC/VANC 10/VANC 10/525 Output/Enable'
		"
		::= { alchemistHd3GCtrlEntries 50913 }

	vancOutALine625Enable10 OBJECT-TYPE
		SYNTAX		INTEGER { disable(0), enable(1) }
		MAX-ACCESS	read-write
		STATUS		current
		DESCRIPTION	"
			style='Checkbox'
			range='0..1'
			path='/VANC/VANC 10/VANC 10/625 Output/Enable'
		"
		::= { alchemistHd3GCtrlEntries 50914 }

	vancOutALine720Enable10 OBJECT-TYPE
		SYNTAX		INTEGER { disable(0), enable(1) }
		MAX-ACCESS	read-write
		STATUS		current
		DESCRIPTION	"
			style='Checkbox'
			range='0..1'
			path='/VANC/VANC 10/VANC 10/720 Output/Enable'
		"
		::= { alchemistHd3GCtrlEntries 50915 }

	vancOutALine1080IEnable10 OBJECT-TYPE
		SYNTAX		INTEGER { disable(0), enable(1) }
		MAX-ACCESS	read-write
		STATUS		current
		DESCRIPTION	"
			style='Checkbox'
			range='0..1'
			path='/VANC/VANC 10/VANC 10/1080i Output/Enable'
		"
		::= { alchemistHd3GCtrlEntries 50916 }

	vancOutALine1080PEnable10 OBJECT-TYPE
		SYNTAX		INTEGER { disable(0), enable(1) }
		MAX-ACCESS	read-write
		STATUS		current
		DESCRIPTION	"
			style='Checkbox'
			range='0..1'
			path='/VANC/VANC 10/VANC 10/1080p Output/Enable'
		"
		::= { alchemistHd3GCtrlEntries 50917 }

	vancOutBLine525Enable10 OBJECT-TYPE
		SYNTAX		INTEGER { disable(0), enable(1) }
		MAX-ACCESS	read-write
		STATUS		current
		DESCRIPTION	"
			style='Checkbox'
			range='0..1'
			path='/VANC/VANC 10/VANC 10/525 Output/Enable'
		"
		::= { alchemistHd3GCtrlEntries 50918 }

	vancOutBLine625Enable10 OBJECT-TYPE
		SYNTAX		INTEGER { disable(0), enable(1) }
		MAX-ACCESS	read-write
		STATUS		current
		DESCRIPTION	"
			style='Checkbox'
			range='0..1'
			path='/VANC/VANC 10/VANC 10/625 Output/Enable'
		"
		::= { alchemistHd3GCtrlEntries 50919 }

	vancOutBLine720Enable10 OBJECT-TYPE
		SYNTAX		INTEGER { disable(0), enable(1) }
		MAX-ACCESS	read-write
		STATUS		current
		DESCRIPTION	"
			style='Checkbox'
			range='0..1'
			path='/VANC/VANC 10/VANC 10/720 Output/Enable'
		"
		::= { alchemistHd3GCtrlEntries 50920 }

	vancOutBLine1080IEnable10 OBJECT-TYPE
		SYNTAX		INTEGER { disable(0), enable(1) }
		MAX-ACCESS	read-write
		STATUS		current
		DESCRIPTION	"
			style='Checkbox'
			range='0..1'
			path='/VANC/VANC 10/VANC 10/1080i Output/Enable'
		"
		::= { alchemistHd3GCtrlEntries 50921 }

	vancOutBLine1080PEnable10 OBJECT-TYPE
		SYNTAX		INTEGER { disable(0), enable(1) }
		MAX-ACCESS	read-write
		STATUS		current
		DESCRIPTION	"
			style='Checkbox'
			range='0..1'
			path='/VANC/VANC 10/VANC 10/1080p Output/Enable'
		"
		::= { alchemistHd3GCtrlEntries 50922 }

	vancOutAActualLine10 OBJECT-TYPE
		SYNTAX		Integer32 (0..41)
		MAX-ACCESS	read-only
		STATUS		current
		DESCRIPTION	"
			style='ReadOnly numeric'
			range='0..41'
			path='/VANC/VANC 10/VANC 10/Actual Out A Line'
		"
		::= { alchemistHd3GCtrlEntries 50923 }

	vancOutBActualLine10 OBJECT-TYPE
		SYNTAX		Integer32 (0..41)
		MAX-ACCESS	read-only
		STATUS		current
		DESCRIPTION	"
			style='ReadOnly numeric'
			range='0..41'
			path='/VANC/VANC 10/VANC 10/Actual Out B Line'
		"
		::= { alchemistHd3GCtrlEntries 50924 }

	vancSdid11 OBJECT-TYPE
		SYNTAX		Integer32 (0..255)
		MAX-ACCESS	read-write
		STATUS		current
		DESCRIPTION	"
			style='Numeric control'
			range='0..255'
			path='/VANC/VANC 11/VANC 11/S-DID'
		"
		::= { alchemistHd3GCtrlEntries 51000 }

	vancDid11 OBJECT-TYPE
		SYNTAX		Integer32 (0..255)
		MAX-ACCESS	read-write
		STATUS		current
		DESCRIPTION	"
			style='Numeric control'
			range='0..255'
			path='/VANC/VANC 11/VANC 11/DID'
		"
		::= { alchemistHd3GCtrlEntries 51001 }

	vancOutALine52511 OBJECT-TYPE
		SYNTAX		Integer32 (12..19)
		MAX-ACCESS	read-write
		STATUS		current
		DESCRIPTION	"
			style='Numeric control'
			range='12..19'
			preset='12'
			path='/VANC/VANC 11/VANC 11/525 Output/Output A Line'
		"
		::= { alchemistHd3GCtrlEntries 51002 }

	vancOutBLine52511 OBJECT-TYPE
		SYNTAX		Integer32 (12..19)
		MAX-ACCESS	read-write
		STATUS		current
		DESCRIPTION	"
			style='Numeric control'
			range='12..19'
			preset='12'
			path='/VANC/VANC 11/VANC 11/525 Output/Output B Line'
		"
		::= { alchemistHd3GCtrlEntries 51003 }

	vancOutALine62511 OBJECT-TYPE
		SYNTAX		Integer32 (8..22)
		MAX-ACCESS	read-write
		STATUS		current
		DESCRIPTION	"
			style='Numeric control'
			range='8..22'
			preset='8'
			path='/VANC/VANC 11/VANC 11/625 Output/Output A Line'
		"
		::= { alchemistHd3GCtrlEntries 51004 }

	vancOutBLine62511 OBJECT-TYPE
		SYNTAX		Integer32 (8..22)
		MAX-ACCESS	read-write
		STATUS		current
		DESCRIPTION	"
			style='Numeric control'
			range='8..22'
			preset='8'
			path='/VANC/VANC 11/VANC 11/625 Output/Output B Line'
		"
		::= { alchemistHd3GCtrlEntries 51005 }

	vancOutALine72011 OBJECT-TYPE
		SYNTAX		Integer32 (9..25)
		MAX-ACCESS	read-write
		STATUS		current
		DESCRIPTION	"
			style='Numeric control'
			range='9..25'
			preset='9'
			path='/VANC/VANC 11/VANC 11/720 Output/Output A Line'
		"
		::= { alchemistHd3GCtrlEntries 51006 }

	vancOutBLine72011 OBJECT-TYPE
		SYNTAX		Integer32 (9..25)
		MAX-ACCESS	read-write
		STATUS		current
		DESCRIPTION	"
			style='Numeric control'
			range='9..25'
			preset='9'
			path='/VANC/VANC 11/VANC 11/720 Output/Output B Line'
		"
		::= { alchemistHd3GCtrlEntries 51007 }

	vancOutALine1080I11 OBJECT-TYPE
		SYNTAX		Integer32 (9..20)
		MAX-ACCESS	read-write
		STATUS		current
		DESCRIPTION	"
			style='Numeric control'
			range='9..20'
			preset='9'
			path='/VANC/VANC 11/VANC 11/1080i Output/Output A Line'
		"
		::= { alchemistHd3GCtrlEntries 51008 }

	vancOutBLine1080I11 OBJECT-TYPE
		SYNTAX		Integer32 (9..20)
		MAX-ACCESS	read-write
		STATUS		current
		DESCRIPTION	"
			style='Numeric control'
			range='9..20'
			preset='9'
			path='/VANC/VANC 11/VANC 11/1080i Output/Output B Line'
		"
		::= { alchemistHd3GCtrlEntries 51009 }

	vancOutALine1080P11 OBJECT-TYPE
		SYNTAX		Integer32 (9..41)
		MAX-ACCESS	read-write
		STATUS		current
		DESCRIPTION	"
			style='Numeric control'
			range='9..41'
			preset='9'
			path='/VANC/VANC 11/VANC 11/1080p Output/Output A Line'
		"
		::= { alchemistHd3GCtrlEntries 51010 }

	vancOutBLine1080P11 OBJECT-TYPE
		SYNTAX		Integer32 (9..41)
		MAX-ACCESS	read-write
		STATUS		current
		DESCRIPTION	"
			style='Numeric control'
			range='9..41'
			preset='9'
			path='/VANC/VANC 11/VANC 11/1080p Output/Output B Line'
		"
		::= { alchemistHd3GCtrlEntries 51011 }

	vancFollowInput11 OBJECT-TYPE
		SYNTAX		INTEGER { disable(0), enable(1) }
		MAX-ACCESS	read-write
		STATUS		current
		DESCRIPTION	"
			style='Checkbox'
			range='0..1'
			path='/VANC/VANC 11/VANC 11/ Follow Input'
		"
		::= { alchemistHd3GCtrlEntries 51012 }

	vancOutALine525Enable11 OBJECT-TYPE
		SYNTAX		INTEGER { disable(0), enable(1) }
		MAX-ACCESS	read-write
		STATUS		current
		DESCRIPTION	"
			style='Checkbox'
			range='0..1'
			path='/VANC/VANC 11/VANC 11/525 Output/Enable'
		"
		::= { alchemistHd3GCtrlEntries 51013 }

	vancOutALine625Enable11 OBJECT-TYPE
		SYNTAX		INTEGER { disable(0), enable(1) }
		MAX-ACCESS	read-write
		STATUS		current
		DESCRIPTION	"
			style='Checkbox'
			range='0..1'
			path='/VANC/VANC 11/VANC 11/625 Output/Enable'
		"
		::= { alchemistHd3GCtrlEntries 51014 }

	vancOutALine720Enable11 OBJECT-TYPE
		SYNTAX		INTEGER { disable(0), enable(1) }
		MAX-ACCESS	read-write
		STATUS		current
		DESCRIPTION	"
			style='Checkbox'
			range='0..1'
			path='/VANC/VANC 11/VANC 11/720 Output/Enable'
		"
		::= { alchemistHd3GCtrlEntries 51015 }

	vancOutALine1080IEnable11 OBJECT-TYPE
		SYNTAX		INTEGER { disable(0), enable(1) }
		MAX-ACCESS	read-write
		STATUS		current
		DESCRIPTION	"
			style='Checkbox'
			range='0..1'
			path='/VANC/VANC 11/VANC 11/1080i Output/Enable'
		"
		::= { alchemistHd3GCtrlEntries 51016 }

	vancOutALine1080PEnable11 OBJECT-TYPE
		SYNTAX		INTEGER { disable(0), enable(1) }
		MAX-ACCESS	read-write
		STATUS		current
		DESCRIPTION	"
			style='Checkbox'
			range='0..1'
			path='/VANC/VANC 11/VANC 11/1080p Output/Enable'
		"
		::= { alchemistHd3GCtrlEntries 51017 }

	vancOutBLine525Enable11 OBJECT-TYPE
		SYNTAX		INTEGER { disable(0), enable(1) }
		MAX-ACCESS	read-write
		STATUS		current
		DESCRIPTION	"
			style='Checkbox'
			range='0..1'
			path='/VANC/VANC 11/VANC 11/525 Output/Enable'
		"
		::= { alchemistHd3GCtrlEntries 51018 }

	vancOutBLine625Enable11 OBJECT-TYPE
		SYNTAX		INTEGER { disable(0), enable(1) }
		MAX-ACCESS	read-write
		STATUS		current
		DESCRIPTION	"
			style='Checkbox'
			range='0..1'
			path='/VANC/VANC 11/VANC 11/625 Output/Enable'
		"
		::= { alchemistHd3GCtrlEntries 51019 }

	vancOutBLine720Enable11 OBJECT-TYPE
		SYNTAX		INTEGER { disable(0), enable(1) }
		MAX-ACCESS	read-write
		STATUS		current
		DESCRIPTION	"
			style='Checkbox'
			range='0..1'
			path='/VANC/VANC 11/VANC 11/720 Output/Enable'
		"
		::= { alchemistHd3GCtrlEntries 51020 }

	vancOutBLine1080IEnable11 OBJECT-TYPE
		SYNTAX		INTEGER { disable(0), enable(1) }
		MAX-ACCESS	read-write
		STATUS		current
		DESCRIPTION	"
			style='Checkbox'
			range='0..1'
			path='/VANC/VANC 11/VANC 11/1080i Output/Enable'
		"
		::= { alchemistHd3GCtrlEntries 51021 }

	vancOutBLine1080PEnable11 OBJECT-TYPE
		SYNTAX		INTEGER { disable(0), enable(1) }
		MAX-ACCESS	read-write
		STATUS		current
		DESCRIPTION	"
			style='Checkbox'
			range='0..1'
			path='/VANC/VANC 11/VANC 11/1080p Output/Enable'
		"
		::= { alchemistHd3GCtrlEntries 51022 }

	vancOutAActualLine11 OBJECT-TYPE
		SYNTAX		Integer32 (0..41)
		MAX-ACCESS	read-only
		STATUS		current
		DESCRIPTION	"
			style='ReadOnly numeric'
			range='0..41'
			path='/VANC/VANC 11/VANC 11/Actual Out A Line'
		"
		::= { alchemistHd3GCtrlEntries 51023 }

	vancOutBActualLine11 OBJECT-TYPE
		SYNTAX		Integer32 (0..41)
		MAX-ACCESS	read-only
		STATUS		current
		DESCRIPTION	"
			style='ReadOnly numeric'
			range='0..41'
			path='/VANC/VANC 11/VANC 11/Actual Out B Line'
		"
		::= { alchemistHd3GCtrlEntries 51024 }

	vancSdid12 OBJECT-TYPE
		SYNTAX		Integer32 (0..255)
		MAX-ACCESS	read-write
		STATUS		current
		DESCRIPTION	"
			style='Numeric control'
			range='0..255'
			path='/VANC/VANC 12/VANC 12/S-DID'
		"
		::= { alchemistHd3GCtrlEntries 51100 }

	vancDid12 OBJECT-TYPE
		SYNTAX		Integer32 (0..255)
		MAX-ACCESS	read-write
		STATUS		current
		DESCRIPTION	"
			style='Numeric control'
			range='0..255'
			path='/VANC/VANC 12/VANC 12/DID'
		"
		::= { alchemistHd3GCtrlEntries 51101 }

	vancOutALine52512 OBJECT-TYPE
		SYNTAX		Integer32 (12..19)
		MAX-ACCESS	read-write
		STATUS		current
		DESCRIPTION	"
			style='Numeric control'
			range='12..19'
			preset='12'
			path='/VANC/VANC 12/VANC 12/525 Output/Output A Line'
		"
		::= { alchemistHd3GCtrlEntries 51102 }

	vancOutBLine52512 OBJECT-TYPE
		SYNTAX		Integer32 (12..19)
		MAX-ACCESS	read-write
		STATUS		current
		DESCRIPTION	"
			style='Numeric control'
			range='12..19'
			preset='12'
			path='/VANC/VANC 12/VANC 12/525 Output/Output B Line'
		"
		::= { alchemistHd3GCtrlEntries 51103 }

	vancOutALine62512 OBJECT-TYPE
		SYNTAX		Integer32 (8..22)
		MAX-ACCESS	read-write
		STATUS		current
		DESCRIPTION	"
			style='Numeric control'
			range='8..22'
			preset='8'
			path='/VANC/VANC 12/VANC 12/625 Output/Output A Line'
		"
		::= { alchemistHd3GCtrlEntries 51104 }

	vancOutBLine62512 OBJECT-TYPE
		SYNTAX		Integer32 (8..22)
		MAX-ACCESS	read-write
		STATUS		current
		DESCRIPTION	"
			style='Numeric control'
			range='8..22'
			preset='8'
			path='/VANC/VANC 12/VANC 12/625 Output/Output B Line'
		"
		::= { alchemistHd3GCtrlEntries 51105 }

	vancOutALine72012 OBJECT-TYPE
		SYNTAX		Integer32 (9..25)
		MAX-ACCESS	read-write
		STATUS		current
		DESCRIPTION	"
			style='Numeric control'
			range='9..25'
			preset='9'
			path='/VANC/VANC 12/VANC 12/720 Output/Output A Line'
		"
		::= { alchemistHd3GCtrlEntries 51106 }

	vancOutBLine72012 OBJECT-TYPE
		SYNTAX		Integer32 (9..25)
		MAX-ACCESS	read-write
		STATUS		current
		DESCRIPTION	"
			style='Numeric control'
			range='9..25'
			preset='9'
			path='/VANC/VANC 12/VANC 12/720 Output/Output B Line'
		"
		::= { alchemistHd3GCtrlEntries 51107 }

	vancOutALine1080I12 OBJECT-TYPE
		SYNTAX		Integer32 (9..20)
		MAX-ACCESS	read-write
		STATUS		current
		DESCRIPTION	"
			style='Numeric control'
			range='9..20'
			preset='9'
			path='/VANC/VANC 12/VANC 12/1080i Output/Output A Line'
		"
		::= { alchemistHd3GCtrlEntries 51108 }

	vancOutBLine1080I12 OBJECT-TYPE
		SYNTAX		Integer32 (9..20)
		MAX-ACCESS	read-write
		STATUS		current
		DESCRIPTION	"
			style='Numeric control'
			range='9..20'
			preset='9'
			path='/VANC/VANC 12/VANC 12/1080i Output/Output B Line'
		"
		::= { alchemistHd3GCtrlEntries 51109 }

	vancOutALine1080P12 OBJECT-TYPE
		SYNTAX		Integer32 (9..41)
		MAX-ACCESS	read-write
		STATUS		current
		DESCRIPTION	"
			style='Numeric control'
			range='9..41'
			preset='9'
			path='/VANC/VANC 12/VANC 12/1080p Output/Output A Line'
		"
		::= { alchemistHd3GCtrlEntries 51110 }

	vancOutBLine1080P12 OBJECT-TYPE
		SYNTAX		Integer32 (9..41)
		MAX-ACCESS	read-write
		STATUS		current
		DESCRIPTION	"
			style='Numeric control'
			range='9..41'
			preset='9'
			path='/VANC/VANC 12/VANC 12/1080p Output/Output B Line'
		"
		::= { alchemistHd3GCtrlEntries 51111 }

	vancFollowInput12 OBJECT-TYPE
		SYNTAX		INTEGER { disable(0), enable(1) }
		MAX-ACCESS	read-write
		STATUS		current
		DESCRIPTION	"
			style='Checkbox'
			range='0..1'
			path='/VANC/VANC 12/VANC 12/ Follow Input'
		"
		::= { alchemistHd3GCtrlEntries 51112 }

	vancOutALine525Enable12 OBJECT-TYPE
		SYNTAX		INTEGER { disable(0), enable(1) }
		MAX-ACCESS	read-write
		STATUS		current
		DESCRIPTION	"
			style='Checkbox'
			range='0..1'
			path='/VANC/VANC 12/VANC 12/525 Output/Enable'
		"
		::= { alchemistHd3GCtrlEntries 51113 }

	vancOutALine625Enable12 OBJECT-TYPE
		SYNTAX		INTEGER { disable(0), enable(1) }
		MAX-ACCESS	read-write
		STATUS		current
		DESCRIPTION	"
			style='Checkbox'
			range='0..1'
			path='/VANC/VANC 12/VANC 12/625 Output/Enable'
		"
		::= { alchemistHd3GCtrlEntries 51114 }

	vancOutALine720Enable12 OBJECT-TYPE
		SYNTAX		INTEGER { disable(0), enable(1) }
		MAX-ACCESS	read-write
		STATUS		current
		DESCRIPTION	"
			style='Checkbox'
			range='0..1'
			path='/VANC/VANC 12/VANC 12/720 Output/Enable'
		"
		::= { alchemistHd3GCtrlEntries 51115 }

	vancOutALine1080IEnable12 OBJECT-TYPE
		SYNTAX		INTEGER { disable(0), enable(1) }
		MAX-ACCESS	read-write
		STATUS		current
		DESCRIPTION	"
			style='Checkbox'
			range='0..1'
			path='/VANC/VANC 12/VANC 12/1080i Output/Enable'
		"
		::= { alchemistHd3GCtrlEntries 51116 }

	vancOutALine1080PEnable12 OBJECT-TYPE
		SYNTAX		INTEGER { disable(0), enable(1) }
		MAX-ACCESS	read-write
		STATUS		current
		DESCRIPTION	"
			style='Checkbox'
			range='0..1'
			path='/VANC/VANC 12/VANC 12/1080p Output/Enable'
		"
		::= { alchemistHd3GCtrlEntries 51117 }

	vancOutBLine525Enable12 OBJECT-TYPE
		SYNTAX		INTEGER { disable(0), enable(1) }
		MAX-ACCESS	read-write
		STATUS		current
		DESCRIPTION	"
			style='Checkbox'
			range='0..1'
			path='/VANC/VANC 12/VANC 12/525 Output/Enable'
		"
		::= { alchemistHd3GCtrlEntries 51118 }

	vancOutBLine625Enable12 OBJECT-TYPE
		SYNTAX		INTEGER { disable(0), enable(1) }
		MAX-ACCESS	read-write
		STATUS		current
		DESCRIPTION	"
			style='Checkbox'
			range='0..1'
			path='/VANC/VANC 12/VANC 12/625 Output/Enable'
		"
		::= { alchemistHd3GCtrlEntries 51119 }

	vancOutBLine720Enable12 OBJECT-TYPE
		SYNTAX		INTEGER { disable(0), enable(1) }
		MAX-ACCESS	read-write
		STATUS		current
		DESCRIPTION	"
			style='Checkbox'
			range='0..1'
			path='/VANC/VANC 12/VANC 12/720 Output/Enable'
		"
		::= { alchemistHd3GCtrlEntries 51120 }

	vancOutBLine1080IEnable12 OBJECT-TYPE
		SYNTAX		INTEGER { disable(0), enable(1) }
		MAX-ACCESS	read-write
		STATUS		current
		DESCRIPTION	"
			style='Checkbox'
			range='0..1'
			path='/VANC/VANC 12/VANC 12/1080i Output/Enable'
		"
		::= { alchemistHd3GCtrlEntries 51121 }

	vancOutBLine1080PEnable12 OBJECT-TYPE
		SYNTAX		INTEGER { disable(0), enable(1) }
		MAX-ACCESS	read-write
		STATUS		current
		DESCRIPTION	"
			style='Checkbox'
			range='0..1'
			path='/VANC/VANC 12/VANC 12/1080p Output/Enable'
		"
		::= { alchemistHd3GCtrlEntries 51122 }

	vancOutAActualLine12 OBJECT-TYPE
		SYNTAX		Integer32 (0..41)
		MAX-ACCESS	read-only
		STATUS		current
		DESCRIPTION	"
			style='ReadOnly numeric'
			range='0..41'
			path='/VANC/VANC 12/VANC 12/Actual Out A Line'
		"
		::= { alchemistHd3GCtrlEntries 51123 }

	vancOutBActualLine12 OBJECT-TYPE
		SYNTAX		Integer32 (0..41)
		MAX-ACCESS	read-only
		STATUS		current
		DESCRIPTION	"
			style='ReadOnly numeric'
			range='0..41'
			path='/VANC/VANC 12/VANC 12/Actual Out B Line'
		"
		::= { alchemistHd3GCtrlEntries 51124 }

	vancSdid13 OBJECT-TYPE
		SYNTAX		Integer32 (0..255)
		MAX-ACCESS	read-write
		STATUS		current
		DESCRIPTION	"
			style='Numeric control'
			range='0..255'
			path='/VANC/VANC 13/VANC 13/S-DID'
		"
		::= { alchemistHd3GCtrlEntries 51200 }

	vancDid13 OBJECT-TYPE
		SYNTAX		Integer32 (0..255)
		MAX-ACCESS	read-write
		STATUS		current
		DESCRIPTION	"
			style='Numeric control'
			range='0..255'
			path='/VANC/VANC 13/VANC 13/DID'
		"
		::= { alchemistHd3GCtrlEntries 51201 }

	vancOutALine52513 OBJECT-TYPE
		SYNTAX		Integer32 (12..19)
		MAX-ACCESS	read-write
		STATUS		current
		DESCRIPTION	"
			style='Numeric control'
			range='12..19'
			preset='12'
			path='/VANC/VANC 13/VANC 13/525 Output/Output A Line'
		"
		::= { alchemistHd3GCtrlEntries 51202 }

	vancOutBLine52513 OBJECT-TYPE
		SYNTAX		Integer32 (12..19)
		MAX-ACCESS	read-write
		STATUS		current
		DESCRIPTION	"
			style='Numeric control'
			range='12..19'
			preset='12'
			path='/VANC/VANC 13/VANC 13/525 Output/Output B Line'
		"
		::= { alchemistHd3GCtrlEntries 51203 }

	vancOutALine62513 OBJECT-TYPE
		SYNTAX		Integer32 (8..22)
		MAX-ACCESS	read-write
		STATUS		current
		DESCRIPTION	"
			style='Numeric control'
			range='8..22'
			preset='8'
			path='/VANC/VANC 13/VANC 13/625 Output/Output A Line'
		"
		::= { alchemistHd3GCtrlEntries 51204 }

	vancOutBLine62513 OBJECT-TYPE
		SYNTAX		Integer32 (8..22)
		MAX-ACCESS	read-write
		STATUS		current
		DESCRIPTION	"
			style='Numeric control'
			range='8..22'
			preset='8'
			path='/VANC/VANC 13/VANC 13/625 Output/Output B Line'
		"
		::= { alchemistHd3GCtrlEntries 51205 }

	vancOutALine72013 OBJECT-TYPE
		SYNTAX		Integer32 (9..25)
		MAX-ACCESS	read-write
		STATUS		current
		DESCRIPTION	"
			style='Numeric control'
			range='9..25'
			preset='9'
			path='/VANC/VANC 13/VANC 13/720 Output/Output A Line'
		"
		::= { alchemistHd3GCtrlEntries 51206 }

	vancOutBLine72013 OBJECT-TYPE
		SYNTAX		Integer32 (9..25)
		MAX-ACCESS	read-write
		STATUS		current
		DESCRIPTION	"
			style='Numeric control'
			range='9..25'
			preset='9'
			path='/VANC/VANC 13/VANC 13/720 Output/Output B Line'
		"
		::= { alchemistHd3GCtrlEntries 51207 }

	vancOutALine1080I13 OBJECT-TYPE
		SYNTAX		Integer32 (9..20)
		MAX-ACCESS	read-write
		STATUS		current
		DESCRIPTION	"
			style='Numeric control'
			range='9..20'
			preset='9'
			path='/VANC/VANC 13/VANC 13/1080i Output/Output A Line'
		"
		::= { alchemistHd3GCtrlEntries 51208 }

	vancOutBLine1080I13 OBJECT-TYPE
		SYNTAX		Integer32 (9..20)
		MAX-ACCESS	read-write
		STATUS		current
		DESCRIPTION	"
			style='Numeric control'
			range='9..20'
			preset='9'
			path='/VANC/VANC 13/VANC 13/1080i Output/Output B Line'
		"
		::= { alchemistHd3GCtrlEntries 51209 }

	vancOutALine1080P13 OBJECT-TYPE
		SYNTAX		Integer32 (9..41)
		MAX-ACCESS	read-write
		STATUS		current
		DESCRIPTION	"
			style='Numeric control'
			range='9..41'
			preset='9'
			path='/VANC/VANC 13/VANC 13/1080p Output/Output A Line'
		"
		::= { alchemistHd3GCtrlEntries 51210 }

	vancOutBLine1080P13 OBJECT-TYPE
		SYNTAX		Integer32 (9..41)
		MAX-ACCESS	read-write
		STATUS		current
		DESCRIPTION	"
			style='Numeric control'
			range='9..41'
			preset='9'
			path='/VANC/VANC 13/VANC 13/1080p Output/Output B Line'
		"
		::= { alchemistHd3GCtrlEntries 51211 }

	vancFollowInput13 OBJECT-TYPE
		SYNTAX		INTEGER { disable(0), enable(1) }
		MAX-ACCESS	read-write
		STATUS		current
		DESCRIPTION	"
			style='Checkbox'
			range='0..1'
			path='/VANC/VANC 13/VANC 13/ Follow Input'
		"
		::= { alchemistHd3GCtrlEntries 51212 }

	vancOutALine525Enable13 OBJECT-TYPE
		SYNTAX		INTEGER { disable(0), enable(1) }
		MAX-ACCESS	read-write
		STATUS		current
		DESCRIPTION	"
			style='Checkbox'
			range='0..1'
			path='/VANC/VANC 13/VANC 13/525 Output/Enable'
		"
		::= { alchemistHd3GCtrlEntries 51213 }

	vancOutALine625Enable13 OBJECT-TYPE
		SYNTAX		INTEGER { disable(0), enable(1) }
		MAX-ACCESS	read-write
		STATUS		current
		DESCRIPTION	"
			style='Checkbox'
			range='0..1'
			path='/VANC/VANC 13/VANC 13/625 Output/Enable'
		"
		::= { alchemistHd3GCtrlEntries 51214 }

	vancOutALine720Enable13 OBJECT-TYPE
		SYNTAX		INTEGER { disable(0), enable(1) }
		MAX-ACCESS	read-write
		STATUS		current
		DESCRIPTION	"
			style='Checkbox'
			range='0..1'
			path='/VANC/VANC 13/VANC 13/720 Output/Enable'
		"
		::= { alchemistHd3GCtrlEntries 51215 }

	vancOutALine1080IEnable13 OBJECT-TYPE
		SYNTAX		INTEGER { disable(0), enable(1) }
		MAX-ACCESS	read-write
		STATUS		current
		DESCRIPTION	"
			style='Checkbox'
			range='0..1'
			path='/VANC/VANC 13/VANC 13/1080i Output/Enable'
		"
		::= { alchemistHd3GCtrlEntries 51216 }

	vancOutALine1080PEnable13 OBJECT-TYPE
		SYNTAX		INTEGER { disable(0), enable(1) }
		MAX-ACCESS	read-write
		STATUS		current
		DESCRIPTION	"
			style='Checkbox'
			range='0..1'
			path='/VANC/VANC 13/VANC 13/1080p Output/Enable'
		"
		::= { alchemistHd3GCtrlEntries 51217 }

	vancOutBLine525Enable13 OBJECT-TYPE
		SYNTAX		INTEGER { disable(0), enable(1) }
		MAX-ACCESS	read-write
		STATUS		current
		DESCRIPTION	"
			style='Checkbox'
			range='0..1'
			path='/VANC/VANC 13/VANC 13/525 Output/Enable'
		"
		::= { alchemistHd3GCtrlEntries 51218 }

	vancOutBLine625Enable13 OBJECT-TYPE
		SYNTAX		INTEGER { disable(0), enable(1) }
		MAX-ACCESS	read-write
		STATUS		current
		DESCRIPTION	"
			style='Checkbox'
			range='0..1'
			path='/VANC/VANC 13/VANC 13/625 Output/Enable'
		"
		::= { alchemistHd3GCtrlEntries 51219 }

	vancOutBLine720Enable13 OBJECT-TYPE
		SYNTAX		INTEGER { disable(0), enable(1) }
		MAX-ACCESS	read-write
		STATUS		current
		DESCRIPTION	"
			style='Checkbox'
			range='0..1'
			path='/VANC/VANC 13/VANC 13/720 Output/Enable'
		"
		::= { alchemistHd3GCtrlEntries 51220 }

	vancOutBLine1080IEnable13 OBJECT-TYPE
		SYNTAX		INTEGER { disable(0), enable(1) }
		MAX-ACCESS	read-write
		STATUS		current
		DESCRIPTION	"
			style='Checkbox'
			range='0..1'
			path='/VANC/VANC 13/VANC 13/1080i Output/Enable'
		"
		::= { alchemistHd3GCtrlEntries 51221 }

	vancOutBLine1080PEnable13 OBJECT-TYPE
		SYNTAX		INTEGER { disable(0), enable(1) }
		MAX-ACCESS	read-write
		STATUS		current
		DESCRIPTION	"
			style='Checkbox'
			range='0..1'
			path='/VANC/VANC 13/VANC 13/1080p Output/Enable'
		"
		::= { alchemistHd3GCtrlEntries 51222 }

	vancOutAActualLine13 OBJECT-TYPE
		SYNTAX		Integer32 (0..41)
		MAX-ACCESS	read-only
		STATUS		current
		DESCRIPTION	"
			style='ReadOnly numeric'
			range='0..41'
			path='/VANC/VANC 13/VANC 13/Actual Out A Line'
		"
		::= { alchemistHd3GCtrlEntries 51223 }

	vancOutBActualLine13 OBJECT-TYPE
		SYNTAX		Integer32 (0..41)
		MAX-ACCESS	read-only
		STATUS		current
		DESCRIPTION	"
			style='ReadOnly numeric'
			range='0..41'
			path='/VANC/VANC 13/VANC 13/Actual Out B Line'
		"
		::= { alchemistHd3GCtrlEntries 51224 }

	vancSdid14 OBJECT-TYPE
		SYNTAX		Integer32 (0..255)
		MAX-ACCESS	read-write
		STATUS		current
		DESCRIPTION	"
			style='Numeric control'
			range='0..255'
			path='/VANC/VANC 14/VANC 14/S-DID'
		"
		::= { alchemistHd3GCtrlEntries 51300 }

	vancDid14 OBJECT-TYPE
		SYNTAX		Integer32 (0..255)
		MAX-ACCESS	read-write
		STATUS		current
		DESCRIPTION	"
			style='Numeric control'
			range='0..255'
			path='/VANC/VANC 14/VANC 14/DID'
		"
		::= { alchemistHd3GCtrlEntries 51301 }

	vancOutALine52514 OBJECT-TYPE
		SYNTAX		Integer32 (12..19)
		MAX-ACCESS	read-write
		STATUS		current
		DESCRIPTION	"
			style='Numeric control'
			range='12..19'
			preset='12'
			path='/VANC/VANC 14/VANC 14/525 Output/Output A Line'
		"
		::= { alchemistHd3GCtrlEntries 51302 }

	vancOutBLine52514 OBJECT-TYPE
		SYNTAX		Integer32 (12..19)
		MAX-ACCESS	read-write
		STATUS		current
		DESCRIPTION	"
			style='Numeric control'
			range='12..19'
			preset='12'
			path='/VANC/VANC 14/VANC 14/525 Output/Output B Line'
		"
		::= { alchemistHd3GCtrlEntries 51303 }

	vancOutALine62514 OBJECT-TYPE
		SYNTAX		Integer32 (8..22)
		MAX-ACCESS	read-write
		STATUS		current
		DESCRIPTION	"
			style='Numeric control'
			range='8..22'
			preset='8'
			path='/VANC/VANC 14/VANC 14/625 Output/Output A Line'
		"
		::= { alchemistHd3GCtrlEntries 51304 }

	vancOutBLine62514 OBJECT-TYPE
		SYNTAX		Integer32 (8..22)
		MAX-ACCESS	read-write
		STATUS		current
		DESCRIPTION	"
			style='Numeric control'
			range='8..22'
			preset='8'
			path='/VANC/VANC 14/VANC 14/625 Output/Output B Line'
		"
		::= { alchemistHd3GCtrlEntries 51305 }

	vancOutALine72014 OBJECT-TYPE
		SYNTAX		Integer32 (9..25)
		MAX-ACCESS	read-write
		STATUS		current
		DESCRIPTION	"
			style='Numeric control'
			range='9..25'
			preset='9'
			path='/VANC/VANC 14/VANC 14/720 Output/Output A Line'
		"
		::= { alchemistHd3GCtrlEntries 51306 }

	vancOutBLine72014 OBJECT-TYPE
		SYNTAX		Integer32 (9..25)
		MAX-ACCESS	read-write
		STATUS		current
		DESCRIPTION	"
			style='Numeric control'
			range='9..25'
			preset='9'
			path='/VANC/VANC 14/VANC 14/720 Output/Output B Line'
		"
		::= { alchemistHd3GCtrlEntries 51307 }

	vancOutALine1080I14 OBJECT-TYPE
		SYNTAX		Integer32 (9..20)
		MAX-ACCESS	read-write
		STATUS		current
		DESCRIPTION	"
			style='Numeric control'
			range='9..20'
			preset='9'
			path='/VANC/VANC 14/VANC 14/1080i Output/Output A Line'
		"
		::= { alchemistHd3GCtrlEntries 51308 }

	vancOutBLine1080I14 OBJECT-TYPE
		SYNTAX		Integer32 (9..20)
		MAX-ACCESS	read-write
		STATUS		current
		DESCRIPTION	"
			style='Numeric control'
			range='9..20'
			preset='9'
			path='/VANC/VANC 14/VANC 14/1080i Output/Output B Line'
		"
		::= { alchemistHd3GCtrlEntries 51309 }

	vancOutALine1080P14 OBJECT-TYPE
		SYNTAX		Integer32 (9..41)
		MAX-ACCESS	read-write
		STATUS		current
		DESCRIPTION	"
			style='Numeric control'
			range='9..41'
			preset='9'
			path='/VANC/VANC 14/VANC 14/1080p Output/Output A Line'
		"
		::= { alchemistHd3GCtrlEntries 51310 }

	vancOutBLine1080P14 OBJECT-TYPE
		SYNTAX		Integer32 (9..41)
		MAX-ACCESS	read-write
		STATUS		current
		DESCRIPTION	"
			style='Numeric control'
			range='9..41'
			preset='9'
			path='/VANC/VANC 14/VANC 14/1080p Output/Output B Line'
		"
		::= { alchemistHd3GCtrlEntries 51311 }

	vancFollowInput14 OBJECT-TYPE
		SYNTAX		INTEGER { disable(0), enable(1) }
		MAX-ACCESS	read-write
		STATUS		current
		DESCRIPTION	"
			style='Checkbox'
			range='0..1'
			path='/VANC/VANC 14/VANC 14/ Follow Input'
		"
		::= { alchemistHd3GCtrlEntries 51312 }

	vancOutALine525Enable14 OBJECT-TYPE
		SYNTAX		INTEGER { disable(0), enable(1) }
		MAX-ACCESS	read-write
		STATUS		current
		DESCRIPTION	"
			style='Checkbox'
			range='0..1'
			path='/VANC/VANC 14/VANC 14/525 Output/Enable'
		"
		::= { alchemistHd3GCtrlEntries 51313 }

	vancOutALine625Enable14 OBJECT-TYPE
		SYNTAX		INTEGER { disable(0), enable(1) }
		MAX-ACCESS	read-write
		STATUS		current
		DESCRIPTION	"
			style='Checkbox'
			range='0..1'
			path='/VANC/VANC 14/VANC 14/625 Output/Enable'
		"
		::= { alchemistHd3GCtrlEntries 51314 }

	vancOutALine720Enable14 OBJECT-TYPE
		SYNTAX		INTEGER { disable(0), enable(1) }
		MAX-ACCESS	read-write
		STATUS		current
		DESCRIPTION	"
			style='Checkbox'
			range='0..1'
			path='/VANC/VANC 14/VANC 14/720 Output/Enable'
		"
		::= { alchemistHd3GCtrlEntries 51315 }

	vancOutALine1080IEnable14 OBJECT-TYPE
		SYNTAX		INTEGER { disable(0), enable(1) }
		MAX-ACCESS	read-write
		STATUS		current
		DESCRIPTION	"
			style='Checkbox'
			range='0..1'
			path='/VANC/VANC 14/VANC 14/1080i Output/Enable'
		"
		::= { alchemistHd3GCtrlEntries 51316 }

	vancOutALine1080PEnable14 OBJECT-TYPE
		SYNTAX		INTEGER { disable(0), enable(1) }
		MAX-ACCESS	read-write
		STATUS		current
		DESCRIPTION	"
			style='Checkbox'
			range='0..1'
			path='/VANC/VANC 14/VANC 14/1080p Output/Enable'
		"
		::= { alchemistHd3GCtrlEntries 51317 }

	vancOutBLine525Enable14 OBJECT-TYPE
		SYNTAX		INTEGER { disable(0), enable(1) }
		MAX-ACCESS	read-write
		STATUS		current
		DESCRIPTION	"
			style='Checkbox'
			range='0..1'
			path='/VANC/VANC 14/VANC 14/525 Output/Enable'
		"
		::= { alchemistHd3GCtrlEntries 51318 }

	vancOutBLine625Enable14 OBJECT-TYPE
		SYNTAX		INTEGER { disable(0), enable(1) }
		MAX-ACCESS	read-write
		STATUS		current
		DESCRIPTION	"
			style='Checkbox'
			range='0..1'
			path='/VANC/VANC 14/VANC 14/625 Output/Enable'
		"
		::= { alchemistHd3GCtrlEntries 51319 }

	vancOutBLine720Enable14 OBJECT-TYPE
		SYNTAX		INTEGER { disable(0), enable(1) }
		MAX-ACCESS	read-write
		STATUS		current
		DESCRIPTION	"
			style='Checkbox'
			range='0..1'
			path='/VANC/VANC 14/VANC 14/720 Output/Enable'
		"
		::= { alchemistHd3GCtrlEntries 51320 }

	vancOutBLine1080IEnable14 OBJECT-TYPE
		SYNTAX		INTEGER { disable(0), enable(1) }
		MAX-ACCESS	read-write
		STATUS		current
		DESCRIPTION	"
			style='Checkbox'
			range='0..1'
			path='/VANC/VANC 14/VANC 14/1080i Output/Enable'
		"
		::= { alchemistHd3GCtrlEntries 51321 }

	vancOutBLine1080PEnable14 OBJECT-TYPE
		SYNTAX		INTEGER { disable(0), enable(1) }
		MAX-ACCESS	read-write
		STATUS		current
		DESCRIPTION	"
			style='Checkbox'
			range='0..1'
			path='/VANC/VANC 14/VANC 14/1080p Output/Enable'
		"
		::= { alchemistHd3GCtrlEntries 51322 }

	vancOutAActualLine14 OBJECT-TYPE
		SYNTAX		Integer32 (0..41)
		MAX-ACCESS	read-only
		STATUS		current
		DESCRIPTION	"
			style='ReadOnly numeric'
			range='0..41'
			path='/VANC/VANC 14/VANC 14/Actual Out A Line'
		"
		::= { alchemistHd3GCtrlEntries 51323 }

	vancOutBActualLine14 OBJECT-TYPE
		SYNTAX		Integer32 (0..41)
		MAX-ACCESS	read-only
		STATUS		current
		DESCRIPTION	"
			style='ReadOnly numeric'
			range='0..41'
			path='/VANC/VANC 14/VANC 14/Actual Out B Line'
		"
		::= { alchemistHd3GCtrlEntries 51324 }

	vancSdid15 OBJECT-TYPE
		SYNTAX		Integer32 (0..255)
		MAX-ACCESS	read-write
		STATUS		current
		DESCRIPTION	"
			style='Numeric control'
			range='0..255'
			path='/VANC/VANC 15/VANC 15/S-DID'
		"
		::= { alchemistHd3GCtrlEntries 51400 }

	vancDid15 OBJECT-TYPE
		SYNTAX		Integer32 (0..255)
		MAX-ACCESS	read-write
		STATUS		current
		DESCRIPTION	"
			style='Numeric control'
			range='0..255'
			path='/VANC/VANC 15/VANC 15/DID'
		"
		::= { alchemistHd3GCtrlEntries 51401 }

	vancOutALine52515 OBJECT-TYPE
		SYNTAX		Integer32 (12..19)
		MAX-ACCESS	read-write
		STATUS		current
		DESCRIPTION	"
			style='Numeric control'
			range='12..19'
			preset='12'
			path='/VANC/VANC 15/VANC 15/525 Output/Output A Line'
		"
		::= { alchemistHd3GCtrlEntries 51402 }

	vancOutBLine52515 OBJECT-TYPE
		SYNTAX		Integer32 (12..19)
		MAX-ACCESS	read-write
		STATUS		current
		DESCRIPTION	"
			style='Numeric control'
			range='12..19'
			preset='12'
			path='/VANC/VANC 15/VANC 15/525 Output/Output B Line'
		"
		::= { alchemistHd3GCtrlEntries 51403 }

	vancOutALine62515 OBJECT-TYPE
		SYNTAX		Integer32 (8..22)
		MAX-ACCESS	read-write
		STATUS		current
		DESCRIPTION	"
			style='Numeric control'
			range='8..22'
			preset='8'
			path='/VANC/VANC 15/VANC 15/625 Output/Output A Line'
		"
		::= { alchemistHd3GCtrlEntries 51404 }

	vancOutBLine62515 OBJECT-TYPE
		SYNTAX		Integer32 (8..22)
		MAX-ACCESS	read-write
		STATUS		current
		DESCRIPTION	"
			style='Numeric control'
			range='8..22'
			preset='8'
			path='/VANC/VANC 15/VANC 15/625 Output/Output B Line'
		"
		::= { alchemistHd3GCtrlEntries 51405 }

	vancOutALine72015 OBJECT-TYPE
		SYNTAX		Integer32 (9..25)
		MAX-ACCESS	read-write
		STATUS		current
		DESCRIPTION	"
			style='Numeric control'
			range='9..25'
			preset='9'
			path='/VANC/VANC 15/VANC 15/720 Output/Output A Line'
		"
		::= { alchemistHd3GCtrlEntries 51406 }

	vancOutBLine72015 OBJECT-TYPE
		SYNTAX		Integer32 (9..25)
		MAX-ACCESS	read-write
		STATUS		current
		DESCRIPTION	"
			style='Numeric control'
			range='9..25'
			preset='9'
			path='/VANC/VANC 15/VANC 15/720 Output/Output B Line'
		"
		::= { alchemistHd3GCtrlEntries 51407 }

	vancOutALine1080I15 OBJECT-TYPE
		SYNTAX		Integer32 (9..20)
		MAX-ACCESS	read-write
		STATUS		current
		DESCRIPTION	"
			style='Numeric control'
			range='9..20'
			preset='9'
			path='/VANC/VANC 15/VANC 15/1080i Output/Output A Line'
		"
		::= { alchemistHd3GCtrlEntries 51408 }

	vancOutBLine1080I15 OBJECT-TYPE
		SYNTAX		Integer32 (9..20)
		MAX-ACCESS	read-write
		STATUS		current
		DESCRIPTION	"
			style='Numeric control'
			range='9..20'
			preset='9'
			path='/VANC/VANC 15/VANC 15/1080i Output/Output B Line'
		"
		::= { alchemistHd3GCtrlEntries 51409 }

	vancOutALine1080P15 OBJECT-TYPE
		SYNTAX		Integer32 (9..41)
		MAX-ACCESS	read-write
		STATUS		current
		DESCRIPTION	"
			style='Numeric control'
			range='9..41'
			preset='9'
			path='/VANC/VANC 15/VANC 15/1080p Output/Output A Line'
		"
		::= { alchemistHd3GCtrlEntries 51410 }

	vancOutBLine1080P15 OBJECT-TYPE
		SYNTAX		Integer32 (9..41)
		MAX-ACCESS	read-write
		STATUS		current
		DESCRIPTION	"
			style='Numeric control'
			range='9..41'
			preset='9'
			path='/VANC/VANC 15/VANC 15/1080p Output/Output B Line'
		"
		::= { alchemistHd3GCtrlEntries 51411 }

	vancFollowInput15 OBJECT-TYPE
		SYNTAX		INTEGER { disable(0), enable(1) }
		MAX-ACCESS	read-write
		STATUS		current
		DESCRIPTION	"
			style='Checkbox'
			range='0..1'
			path='/VANC/VANC 15/VANC 15/ Follow Input'
		"
		::= { alchemistHd3GCtrlEntries 51412 }

	vancOutALine525Enable15 OBJECT-TYPE
		SYNTAX		INTEGER { disable(0), enable(1) }
		MAX-ACCESS	read-write
		STATUS		current
		DESCRIPTION	"
			style='Checkbox'
			range='0..1'
			path='/VANC/VANC 15/VANC 15/525 Output/Enable'
		"
		::= { alchemistHd3GCtrlEntries 51413 }

	vancOutALine625Enable15 OBJECT-TYPE
		SYNTAX		INTEGER { disable(0), enable(1) }
		MAX-ACCESS	read-write
		STATUS		current
		DESCRIPTION	"
			style='Checkbox'
			range='0..1'
			path='/VANC/VANC 15/VANC 15/625 Output/Enable'
		"
		::= { alchemistHd3GCtrlEntries 51414 }

	vancOutALine720Enable15 OBJECT-TYPE
		SYNTAX		INTEGER { disable(0), enable(1) }
		MAX-ACCESS	read-write
		STATUS		current
		DESCRIPTION	"
			style='Checkbox'
			range='0..1'
			path='/VANC/VANC 15/VANC 15/720 Output/Enable'
		"
		::= { alchemistHd3GCtrlEntries 51415 }

	vancOutALine1080IEnable15 OBJECT-TYPE
		SYNTAX		INTEGER { disable(0), enable(1) }
		MAX-ACCESS	read-write
		STATUS		current
		DESCRIPTION	"
			style='Checkbox'
			range='0..1'
			path='/VANC/VANC 15/VANC 15/1080i Output/Enable'
		"
		::= { alchemistHd3GCtrlEntries 51416 }

	vancOutALine1080PEnable15 OBJECT-TYPE
		SYNTAX		INTEGER { disable(0), enable(1) }
		MAX-ACCESS	read-write
		STATUS		current
		DESCRIPTION	"
			style='Checkbox'
			range='0..1'
			path='/VANC/VANC 15/VANC 15/1080p Output/Enable'
		"
		::= { alchemistHd3GCtrlEntries 51417 }

	vancOutBLine525Enable15 OBJECT-TYPE
		SYNTAX		INTEGER { disable(0), enable(1) }
		MAX-ACCESS	read-write
		STATUS		current
		DESCRIPTION	"
			style='Checkbox'
			range='0..1'
			path='/VANC/VANC 15/VANC 15/525 Output/Enable'
		"
		::= { alchemistHd3GCtrlEntries 51418 }

	vancOutBLine625Enable15 OBJECT-TYPE
		SYNTAX		INTEGER { disable(0), enable(1) }
		MAX-ACCESS	read-write
		STATUS		current
		DESCRIPTION	"
			style='Checkbox'
			range='0..1'
			path='/VANC/VANC 15/VANC 15/625 Output/Enable'
		"
		::= { alchemistHd3GCtrlEntries 51419 }

	vancOutBLine720Enable15 OBJECT-TYPE
		SYNTAX		INTEGER { disable(0), enable(1) }
		MAX-ACCESS	read-write
		STATUS		current
		DESCRIPTION	"
			style='Checkbox'
			range='0..1'
			path='/VANC/VANC 15/VANC 15/720 Output/Enable'
		"
		::= { alchemistHd3GCtrlEntries 51420 }

	vancOutBLine1080IEnable15 OBJECT-TYPE
		SYNTAX		INTEGER { disable(0), enable(1) }
		MAX-ACCESS	read-write
		STATUS		current
		DESCRIPTION	"
			style='Checkbox'
			range='0..1'
			path='/VANC/VANC 15/VANC 15/1080i Output/Enable'
		"
		::= { alchemistHd3GCtrlEntries 51421 }

	vancOutBLine1080PEnable15 OBJECT-TYPE
		SYNTAX		INTEGER { disable(0), enable(1) }
		MAX-ACCESS	read-write
		STATUS		current
		DESCRIPTION	"
			style='Checkbox'
			range='0..1'
			path='/VANC/VANC 15/VANC 15/1080p Output/Enable'
		"
		::= { alchemistHd3GCtrlEntries 51422 }

	vancOutAActualLine15 OBJECT-TYPE
		SYNTAX		Integer32 (0..41)
		MAX-ACCESS	read-only
		STATUS		current
		DESCRIPTION	"
			style='ReadOnly numeric'
			range='0..41'
			path='/VANC/VANC 15/VANC 15/Actual Out A Line'
		"
		::= { alchemistHd3GCtrlEntries 51423 }

	vancOutBActualLine15 OBJECT-TYPE
		SYNTAX		Integer32 (0..41)
		MAX-ACCESS	read-only
		STATUS		current
		DESCRIPTION	"
			style='ReadOnly numeric'
			range='0..41'
			path='/VANC/VANC 15/VANC 15/Actual Out B Line'
		"
		::= { alchemistHd3GCtrlEntries 51424 }

	vancSdid16 OBJECT-TYPE
		SYNTAX		Integer32 (0..255)
		MAX-ACCESS	read-write
		STATUS		current
		DESCRIPTION	"
			style='Numeric control'
			range='0..255'
			path='/VANC/VANC 16/VANC 16/S-DID'
		"
		::= { alchemistHd3GCtrlEntries 51500 }

	vancDid16 OBJECT-TYPE
		SYNTAX		Integer32 (0..255)
		MAX-ACCESS	read-write
		STATUS		current
		DESCRIPTION	"
			style='Numeric control'
			range='0..255'
			path='/VANC/VANC 16/VANC 16/DID'
		"
		::= { alchemistHd3GCtrlEntries 51501 }

	vancOutALine52516 OBJECT-TYPE
		SYNTAX		Integer32 (12..19)
		MAX-ACCESS	read-write
		STATUS		current
		DESCRIPTION	"
			style='Numeric control'
			range='12..19'
			preset='12'
			path='/VANC/VANC 16/VANC 16/525 Output/Output A Line'
		"
		::= { alchemistHd3GCtrlEntries 51502 }

	vancOutBLine52516 OBJECT-TYPE
		SYNTAX		Integer32 (12..19)
		MAX-ACCESS	read-write
		STATUS		current
		DESCRIPTION	"
			style='Numeric control'
			range='12..19'
			preset='12'
			path='/VANC/VANC 16/VANC 16/525 Output/Output B Line'
		"
		::= { alchemistHd3GCtrlEntries 51503 }

	vancOutALine62516 OBJECT-TYPE
		SYNTAX		Integer32 (8..22)
		MAX-ACCESS	read-write
		STATUS		current
		DESCRIPTION	"
			style='Numeric control'
			range='8..22'
			preset='8'
			path='/VANC/VANC 16/VANC 16/625 Output/Output A Line'
		"
		::= { alchemistHd3GCtrlEntries 51504 }

	vancOutBLine62516 OBJECT-TYPE
		SYNTAX		Integer32 (8..22)
		MAX-ACCESS	read-write
		STATUS		current
		DESCRIPTION	"
			style='Numeric control'
			range='8..22'
			preset='8'
			path='/VANC/VANC 16/VANC 16/625 Output/Output B Line'
		"
		::= { alchemistHd3GCtrlEntries 51505 }

	vancOutALine72016 OBJECT-TYPE
		SYNTAX		Integer32 (9..25)
		MAX-ACCESS	read-write
		STATUS		current
		DESCRIPTION	"
			style='Numeric control'
			range='9..25'
			preset='9'
			path='/VANC/VANC 16/VANC 16/720 Output/Output A Line'
		"
		::= { alchemistHd3GCtrlEntries 51506 }

	vancOutBLine72016 OBJECT-TYPE
		SYNTAX		Integer32 (9..25)
		MAX-ACCESS	read-write
		STATUS		current
		DESCRIPTION	"
			style='Numeric control'
			range='9..25'
			preset='9'
			path='/VANC/VANC 16/VANC 16/720 Output/Output B Line'
		"
		::= { alchemistHd3GCtrlEntries 51507 }

	vancOutALine1080I16 OBJECT-TYPE
		SYNTAX		Integer32 (9..20)
		MAX-ACCESS	read-write
		STATUS		current
		DESCRIPTION	"
			style='Numeric control'
			range='9..20'
			preset='9'
			path='/VANC/VANC 16/VANC 16/1080i Output/Output A Line'
		"
		::= { alchemistHd3GCtrlEntries 51508 }

	vancOutBLine1080I16 OBJECT-TYPE
		SYNTAX		Integer32 (9..20)
		MAX-ACCESS	read-write
		STATUS		current
		DESCRIPTION	"
			style='Numeric control'
			range='9..20'
			preset='9'
			path='/VANC/VANC 16/VANC 16/1080i Output/Output B Line'
		"
		::= { alchemistHd3GCtrlEntries 51509 }

	vancOutALine1080P16 OBJECT-TYPE
		SYNTAX		Integer32 (9..41)
		MAX-ACCESS	read-write
		STATUS		current
		DESCRIPTION	"
			style='Numeric control'
			range='9..41'
			preset='9'
			path='/VANC/VANC 16/VANC 16/1080p Output/Output A Line'
		"
		::= { alchemistHd3GCtrlEntries 51510 }

	vancOutBLine1080P16 OBJECT-TYPE
		SYNTAX		Integer32 (9..41)
		MAX-ACCESS	read-write
		STATUS		current
		DESCRIPTION	"
			style='Numeric control'
			range='9..41'
			preset='9'
			path='/VANC/VANC 16/VANC 16/1080p Output/Output B Line'
		"
		::= { alchemistHd3GCtrlEntries 51511 }

	vancFollowInput16 OBJECT-TYPE
		SYNTAX		INTEGER { disable(0), enable(1) }
		MAX-ACCESS	read-write
		STATUS		current
		DESCRIPTION	"
			style='Checkbox'
			range='0..1'
			path='/VANC/VANC 16/VANC 16/ Follow Input'
		"
		::= { alchemistHd3GCtrlEntries 51512 }

	vancOutALine525Enable16 OBJECT-TYPE
		SYNTAX		INTEGER { disable(0), enable(1) }
		MAX-ACCESS	read-write
		STATUS		current
		DESCRIPTION	"
			style='Checkbox'
			range='0..1'
			path='/VANC/VANC 16/VANC 16/525 Output/Enable'
		"
		::= { alchemistHd3GCtrlEntries 51513 }

	vancOutALine625Enable16 OBJECT-TYPE
		SYNTAX		INTEGER { disable(0), enable(1) }
		MAX-ACCESS	read-write
		STATUS		current
		DESCRIPTION	"
			style='Checkbox'
			range='0..1'
			path='/VANC/VANC 16/VANC 16/625 Output/Enable'
		"
		::= { alchemistHd3GCtrlEntries 51514 }

	vancOutALine720Enable16 OBJECT-TYPE
		SYNTAX		INTEGER { disable(0), enable(1) }
		MAX-ACCESS	read-write
		STATUS		current
		DESCRIPTION	"
			style='Checkbox'
			range='0..1'
			path='/VANC/VANC 16/VANC 16/720 Output/Enable'
		"
		::= { alchemistHd3GCtrlEntries 51515 }

	vancOutALine1080IEnable16 OBJECT-TYPE
		SYNTAX		INTEGER { disable(0), enable(1) }
		MAX-ACCESS	read-write
		STATUS		current
		DESCRIPTION	"
			style='Checkbox'
			range='0..1'
			path='/VANC/VANC 16/VANC 16/1080i Output/Enable'
		"
		::= { alchemistHd3GCtrlEntries 51516 }

	vancOutALine1080PEnable16 OBJECT-TYPE
		SYNTAX		INTEGER { disable(0), enable(1) }
		MAX-ACCESS	read-write
		STATUS		current
		DESCRIPTION	"
			style='Checkbox'
			range='0..1'
			path='/VANC/VANC 16/VANC 16/1080p Output/Enable'
		"
		::= { alchemistHd3GCtrlEntries 51517 }

	vancOutBLine525Enable16 OBJECT-TYPE
		SYNTAX		INTEGER { disable(0), enable(1) }
		MAX-ACCESS	read-write
		STATUS		current
		DESCRIPTION	"
			style='Checkbox'
			range='0..1'
			path='/VANC/VANC 16/VANC 16/525 Output/Enable'
		"
		::= { alchemistHd3GCtrlEntries 51518 }

	vancOutBLine625Enable16 OBJECT-TYPE
		SYNTAX		INTEGER { disable(0), enable(1) }
		MAX-ACCESS	read-write
		STATUS		current
		DESCRIPTION	"
			style='Checkbox'
			range='0..1'
			path='/VANC/VANC 16/VANC 16/625 Output/Enable'
		"
		::= { alchemistHd3GCtrlEntries 51519 }

	vancOutBLine720Enable16 OBJECT-TYPE
		SYNTAX		INTEGER { disable(0), enable(1) }
		MAX-ACCESS	read-write
		STATUS		current
		DESCRIPTION	"
			style='Checkbox'
			range='0..1'
			path='/VANC/VANC 16/VANC 16/720 Output/Enable'
		"
		::= { alchemistHd3GCtrlEntries 51520 }

	vancOutBLine1080IEnable16 OBJECT-TYPE
		SYNTAX		INTEGER { disable(0), enable(1) }
		MAX-ACCESS	read-write
		STATUS		current
		DESCRIPTION	"
			style='Checkbox'
			range='0..1'
			path='/VANC/VANC 16/VANC 16/1080i Output/Enable'
		"
		::= { alchemistHd3GCtrlEntries 51521 }

	vancOutBLine1080PEnable16 OBJECT-TYPE
		SYNTAX		INTEGER { disable(0), enable(1) }
		MAX-ACCESS	read-write
		STATUS		current
		DESCRIPTION	"
			style='Checkbox'
			range='0..1'
			path='/VANC/VANC 16/VANC 16/1080p Output/Enable'
		"
		::= { alchemistHd3GCtrlEntries 51522 }

	vancOutAActualLine16 OBJECT-TYPE
		SYNTAX		Integer32 (0..41)
		MAX-ACCESS	read-only
		STATUS		current
		DESCRIPTION	"
			style='ReadOnly numeric'
			range='0..41'
			path='/VANC/VANC 16/VANC 16/Actual Out A Line'
		"
		::= { alchemistHd3GCtrlEntries 51523 }

	vancOutBActualLine16 OBJECT-TYPE
		SYNTAX		Integer32 (0..41)
		MAX-ACCESS	read-only
		STATUS		current
		DESCRIPTION	"
			style='ReadOnly numeric'
			range='0..41'
			path='/VANC/VANC 16/VANC 16/Actual Out B Line'
		"
		::= { alchemistHd3GCtrlEntries 51524 }

	vancDisplayStatus1To8 OBJECT-TYPE
		SYNTAX		INTEGER { disable(0), enable(1) }
		MAX-ACCESS	read-write
		STATUS		current
		DESCRIPTION	"
			style='Checkbox'
			range='0..1'
			path='/VANC/ 1 to 8'
		"
		::= { alchemistHd3GCtrlEntries 51600 }

	vancDisplayStatus9To16 OBJECT-TYPE
		SYNTAX		INTEGER { disable(0), enable(1) }
		MAX-ACCESS	read-write
		STATUS		current
		DESCRIPTION	"
			style='Checkbox'
			range='0..1'
			path='/VANC/ 9 to 16'
		"
		::= { alchemistHd3GCtrlEntries 51601 }

	closedCaptionsLine21Blanking OBJECT-TYPE
		SYNTAX		INTEGER {
					auto(0),
					on(1),
					off(2)
				}
		MAX-ACCESS	read-write
		STATUS		current
		DESCRIPTION	"
			style='Radiobutton list'
			preset='auto'
			path='/Closed Captions/Closed Captions/525 Input Setup/Line 21 blanking'
		"
		::= { alchemistHd3GCtrlEntries 52000 }

	closedCaptionsIp525608Source OBJECT-TYPE
		SYNTAX		INTEGER {
					auto(0),
					line21(1),
					v708Cb(2)
				}
		MAX-ACCESS	read-write
		STATUS		current
		DESCRIPTION	"
			style='Radiobutton list'
			preset='auto'
			path='/Closed Captions/Closed Captions/525 Input Setup/608 Source'
		"
		::= { alchemistHd3GCtrlEntries 52001 }

	closedCaptionsLine21Enable OBJECT-TYPE
		SYNTAX		INTEGER { disable(0), enable(1) }
		MAX-ACCESS	read-write
		STATUS		current
		DESCRIPTION	"
			style='Checkbox'
			range='0..1'
			path='/Closed Captions/Closed Captions/525 Output/Enable Line 21'
		"
		::= { alchemistHd3GCtrlEntries 52010 }

	closedCaptionsLine284Enable OBJECT-TYPE
		SYNTAX		INTEGER { disable(0), enable(1) }
		MAX-ACCESS	read-write
		STATUS		current
		DESCRIPTION	"
			style='Checkbox'
			range='0..1'
			path='/Closed Captions/Closed Captions/525 Output/Enable Line 284'
		"
		::= { alchemistHd3GCtrlEntries 52011 }

	closedCaptions708LineEnable525I OBJECT-TYPE
		SYNTAX		INTEGER { disable(0), enable(1) }
		MAX-ACCESS	read-write
		STATUS		current
		DESCRIPTION	"
			style='Checkbox'
			range='0..1'
			path='/Closed Captions/Closed Captions/525 Output/Enable 708'
		"
		::= { alchemistHd3GCtrlEntries 52020 }

	closedCaptions708LineEnable625I OBJECT-TYPE
		SYNTAX		INTEGER { disable(0), enable(1) }
		MAX-ACCESS	read-write
		STATUS		current
		DESCRIPTION	"
			style='Checkbox'
			range='0..1'
			path='/Closed Captions/Closed Captions/625 Output/Enable 708'
		"
		::= { alchemistHd3GCtrlEntries 52021 }

	closedCaptions708LineEnable750P OBJECT-TYPE
		SYNTAX		INTEGER { disable(0), enable(1) }
		MAX-ACCESS	read-write
		STATUS		current
		DESCRIPTION	"
			style='Checkbox'
			range='0..1'
			path='/Closed Captions/Closed Captions/720 Output/Enable 708'
		"
		::= { alchemistHd3GCtrlEntries 52022 }

	closedCaptions708LineEnable1125I OBJECT-TYPE
		SYNTAX		INTEGER { disable(0), enable(1) }
		MAX-ACCESS	read-write
		STATUS		current
		DESCRIPTION	"
			style='Checkbox'
			range='0..1'
			path='/Closed Captions/Closed Captions/1080i Output/Enable 708'
		"
		::= { alchemistHd3GCtrlEntries 52023 }

	closedCaptions708LineEnable1125P OBJECT-TYPE
		SYNTAX		INTEGER { disable(0), enable(1) }
		MAX-ACCESS	read-write
		STATUS		current
		DESCRIPTION	"
			style='Checkbox'
			range='0..1'
			path='/Closed Captions/Closed Captions/1080p Output/Enable 708'
		"
		::= { alchemistHd3GCtrlEntries 52024 }

	closedCaptions708Line525I OBJECT-TYPE
		SYNTAX		Integer32 (12..19)
		MAX-ACCESS	read-write
		STATUS		current
		DESCRIPTION	"
			style='Numeric control'
			range='12..19'
			preset='12'
			path='/Closed Captions/Closed Captions/525 Output/708 Line'
		"
		::= { alchemistHd3GCtrlEntries 52031 }

	closedCaptions708Line625I OBJECT-TYPE
		SYNTAX		Integer32 (8..22)
		MAX-ACCESS	read-write
		STATUS		current
		DESCRIPTION	"
			style='Numeric control'
			range='8..22'
			preset='8'
			path='/Closed Captions/Closed Captions/625 Output/708 Line'
		"
		::= { alchemistHd3GCtrlEntries 52033 }

	closedCaptions708Line750P OBJECT-TYPE
		SYNTAX		Integer32 (9..25)
		MAX-ACCESS	read-write
		STATUS		current
		DESCRIPTION	"
			style='Numeric control'
			range='9..25'
			preset='11'
			path='/Closed Captions/Closed Captions/720 Output/708 Line'
		"
		::= { alchemistHd3GCtrlEntries 52035 }

	closedCaptions708Line1125I OBJECT-TYPE
		SYNTAX		Integer32 (9..20)
		MAX-ACCESS	read-write
		STATUS		current
		DESCRIPTION	"
			style='Numeric control'
			range='9..20'
			preset='14'
			path='/Closed Captions/Closed Captions/1080i Output/708 Line'
		"
		::= { alchemistHd3GCtrlEntries 52037 }

	closedCaptions708Line1125P OBJECT-TYPE
		SYNTAX		Integer32 (9..41)
		MAX-ACCESS	read-write
		STATUS		current
		DESCRIPTION	"
			style='Numeric control'
			range='9..41'
			preset='14'
			path='/Closed Captions/Closed Captions/1080p Output/708 Line'
		"
		::= { alchemistHd3GCtrlEntries 52039 }

	closedCaptionsActualIn0 OBJECT-TYPE
		SYNTAX		Integer32 (0..41)
		MAX-ACCESS	read-only
		STATUS		current
		DESCRIPTION	"
			style='ReadOnly numeric'
			range='0..41'
			path='/Closed Captions/Closed Captions/Input Status/608 (21)'
		"
		::= { alchemistHd3GCtrlEntries 52040 }

	closedCaptionsActualIn1 OBJECT-TYPE
		SYNTAX		Integer32 (0..41)
		MAX-ACCESS	read-only
		STATUS		current
		DESCRIPTION	"
			style='ReadOnly numeric'
			range='0..41'
			path='/Closed Captions/Closed Captions/Input Status/608 (284)'
		"
		::= { alchemistHd3GCtrlEntries 52041 }

	closedCaptionsActualIn2 OBJECT-TYPE
		SYNTAX		Integer32 (0..41)
		MAX-ACCESS	read-only
		STATUS		current
		DESCRIPTION	"
			style='ReadOnly numeric'
			range='0..41'
			path='/Closed Captions/Closed Captions/Input Status/708'
		"
		::= { alchemistHd3GCtrlEntries 52042 }

	closedCaptionsActualOut00 OBJECT-TYPE
		SYNTAX		Integer32 (0..41)
		MAX-ACCESS	read-only
		STATUS		current
		DESCRIPTION	"
			style='ReadOnly numeric'
			range='0..41'
			path='/Closed Captions/Closed Captions/Output Status/Out A 608 (21) Line Number'
		"
		::= { alchemistHd3GCtrlEntries 52043 }

	closedCaptionsActualOut10 OBJECT-TYPE
		SYNTAX		Integer32 (0..41)
		MAX-ACCESS	read-only
		STATUS		current
		DESCRIPTION	"
			style='ReadOnly numeric'
			range='0..41'
			path='/Closed Captions/Closed Captions/Output Status/Out B 608 (21) Line Number'
		"
		::= { alchemistHd3GCtrlEntries 52044 }

	closedCaptionsActualOut01 OBJECT-TYPE
		SYNTAX		Integer32 (0..41)
		MAX-ACCESS	read-only
		STATUS		current
		DESCRIPTION	"
			style='ReadOnly numeric'
			range='0..41'
			path='/Closed Captions/Closed Captions/Output Status/Out A 608 (284) Line Number'
		"
		::= { alchemistHd3GCtrlEntries 52045 }

	closedCaptionsActualOut11 OBJECT-TYPE
		SYNTAX		Integer32 (0..41)
		MAX-ACCESS	read-only
		STATUS		current
		DESCRIPTION	"
			style='ReadOnly numeric'
			range='0..41'
			path='/Closed Captions/Closed Captions/Output Status/Out B 608 (284) Line Number'
		"
		::= { alchemistHd3GCtrlEntries 52046 }

	closedCaptionsActualOut02 OBJECT-TYPE
		SYNTAX		Integer32 (0..41)
		MAX-ACCESS	read-only
		STATUS		current
		DESCRIPTION	"
			style='ReadOnly numeric'
			range='0..41'
			path='/Closed Captions/Closed Captions/Output Status/Out A 708 Line Number'
		"
		::= { alchemistHd3GCtrlEntries 52047 }

	closedCaptionsActualOut12 OBJECT-TYPE
		SYNTAX		Integer32 (0..41)
		MAX-ACCESS	read-only
		STATUS		current
		DESCRIPTION	"
			style='ReadOnly numeric'
			range='0..41'
			path='/Closed Captions/Closed Captions/Output Status/Out B 708 Line Number'
		"
		::= { alchemistHd3GCtrlEntries 52048 }

	closedCaptionsActualOutSrc0 OBJECT-TYPE
		SYNTAX		Integer32 (0..41)
		MAX-ACCESS	read-only
		STATUS		current
		DESCRIPTION	"
			style='ReadOnly numeric'
			range='0..41'
			path='/Closed Captions/Closed Captions/Output Status/Out 608 (21) Source'
		"
		::= { alchemistHd3GCtrlEntries 52049 }

	closedCaptionsActualOutSrc1 OBJECT-TYPE
		SYNTAX		Integer32 (0..41)
		MAX-ACCESS	read-only
		STATUS		current
		DESCRIPTION	"
			style='ReadOnly numeric'
			range='0..41'
			path='/Closed Captions/Closed Captions/Output Status/Out 608 (284) Source'
		"
		::= { alchemistHd3GCtrlEntries 52050 }

	closedCaptionsActualOutSrc2 OBJECT-TYPE
		SYNTAX		Integer32 (0..41)
		MAX-ACCESS	read-only
		STATUS		current
		DESCRIPTION	"
			style='ReadOnly numeric'
			range='0..41'
			path='/Closed Captions/Closed Captions/Output Status/Out 708 Source'
		"
		::= { alchemistHd3GCtrlEntries 52051 }


-- ********************************
-- Status

	alchemistHd3GStatEntries OBJECT IDENTIFIER ::= { conversionAlchemistHd3G 2 }

	logInpLossStat OBJECT-TYPE
		SYNTAX		RollCallString
		MAX-ACCESS	read-only
		STATUS		current
		DESCRIPTION	"
			style='ReadOnly string'
			path='/System/Inp Loss Status'
		"
		::= { alchemistHd3GStatEntries 5964 }

	logInpStdStat OBJECT-TYPE
		SYNTAX		RollCallString
		MAX-ACCESS	read-only
		STATUS		current
		DESCRIPTION	"
			style='ReadOnly string'
			path='/System/Inp Std Status'
		"
		::= { alchemistHd3GStatEntries 5965 }

	logOutAStdStat OBJECT-TYPE
		SYNTAX		RollCallString
		MAX-ACCESS	read-only
		STATUS		current
		DESCRIPTION	"
			style='ReadOnly string'
			path='/System/Out A Std Status'
		"
		::= { alchemistHd3GStatEntries 5968 }

	logOutBStdStat OBJECT-TYPE
		SYNTAX		RollCallString
		MAX-ACCESS	read-only
		STATUS		current
		DESCRIPTION	"
			style='ReadOnly string'
			path='/System/Out B Std Status'
		"
		::= { alchemistHd3GStatEntries 5969 }

	logRefStdStat OBJECT-TYPE
		SYNTAX		RollCallString
		MAX-ACCESS	read-only
		STATUS		current
		DESCRIPTION	"
			style='ReadOnly string'
			path='/System/Ref Std Status'
		"
		::= { alchemistHd3GStatEntries 5970 }

	logStatusStat OBJECT-TYPE
		SYNTAX		RollCallString
		MAX-ACCESS	read-only
		STATUS		current
		DESCRIPTION	"
			style='ReadOnly string'
			path='/System/Status Status'
		"
		::= { alchemistHd3GStatEntries 5972 }


-- ********************************
-- Config

	alchemistHd3GConfEntries OBJECT IDENTIFIER ::= { conversionAlchemistHd3G 3 }

	snmpEnab OBJECT-TYPE
		SYNTAX		INTEGER { disable(0), enable(1) }
		MAX-ACCESS	read-write
		STATUS		current
		DESCRIPTION	"
			style='Checkbox'
			path='/System/SNMP/Physical/Enable SNMP'
		"
		::= { alchemistHd3GConfEntries 59900 }

	snmpRdcommunity OBJECT-TYPE
		SYNTAX		RollCallString
		MAX-ACCESS	read-write
		STATUS		current
		DESCRIPTION	"
			style='Editable string'
			path='/System/SNMP/Interface/Read Community'
		"
		::= { alchemistHd3GConfEntries 59902 }

	snmpWrcommunity OBJECT-TYPE
		SYNTAX		RollCallString
		MAX-ACCESS	read-write
		STATUS		current
		DESCRIPTION	"
			style='Editable string'
			path='/System/SNMP/Interface/Write Community'
		"
		::= { alchemistHd3GConfEntries 59903 }

	snmpContact OBJECT-TYPE
		SYNTAX		RollCallString
		MAX-ACCESS	read-write
		STATUS		current
		DESCRIPTION	"
			style='Editable string'
			path='/System/SNMP/Interface/Contact'
		"
		::= { alchemistHd3GConfEntries 59904 }

	snmpLocation OBJECT-TYPE
		SYNTAX		RollCallString
		MAX-ACCESS	read-write
		STATUS		current
		DESCRIPTION	"
			style='Editable string'
			path='/System/SNMP/Interface/Physical Location'
		"
		::= { alchemistHd3GConfEntries 59905 }

	snmpPort OBJECT-TYPE
		SYNTAX		Integer32 (1..65535)
		MAX-ACCESS	read-write
		STATUS		current
		DESCRIPTION	"
			style='Numeric control'
			range='1..65535'
			preset='161'
			path='/System/SNMP/Physical/UDP Port'
		"
		::= { alchemistHd3GConfEntries 59906 }

	snmpSendall OBJECT-TYPE
		SYNTAX		INTEGER { ready(0), trigger(1) }
		MAX-ACCESS	read-write
		STATUS		current
		DESCRIPTION	"
			style='Event button'
			path='/System/SNMP/Physical/Resend all Traps'
		"
		::= { alchemistHd3GConfEntries 59907 }

	snmpName OBJECT-TYPE
		SYNTAX		RollCallString
		MAX-ACCESS	read-write
		STATUS		current
		DESCRIPTION	"
			style='Editable string'
			path='/System/SNMP/Physical/Name'
		"
		::= { alchemistHd3GConfEntries 59908 }

	snmpTrap1Enab OBJECT-TYPE
		SYNTAX		INTEGER { disable(0), enable(1) }
		MAX-ACCESS	read-write
		STATUS		current
		DESCRIPTION	"
			style='Checkbox'
			path='/System/SNMP/Traps/Trap 1/Trap 1 Enable'
		"
		::= { alchemistHd3GConfEntries 59910 }

	snmpTrap1Addr OBJECT-TYPE
		SYNTAX		IpAddress
		MAX-ACCESS	read-write
		STATUS		current
		DESCRIPTION	"
			style='IPv4 address'
			path='/System/SNMP/Traps/Trap 1/Trap 1 IP Address'
		"
		::= { alchemistHd3GConfEntries 59911 }

	snmpTrap1Port OBJECT-TYPE
		SYNTAX		Integer32 (1..65535)
		MAX-ACCESS	read-write
		STATUS		current
		DESCRIPTION	"
			style='Numeric control'
			range='1..65535'
			preset='162'
			path='/System/SNMP/Traps/Trap 1/Trap 1 UDP Port'
		"
		::= { alchemistHd3GConfEntries 59912 }

	snmpTrap1Community OBJECT-TYPE
		SYNTAX		RollCallString
		MAX-ACCESS	read-write
		STATUS		current
		DESCRIPTION	"
			style='Editable string'
			path='/System/SNMP/Traps/Trap 1/Trap 1 Community'
		"
		::= { alchemistHd3GConfEntries 59913 }

	snmpTrap2Enab OBJECT-TYPE
		SYNTAX		INTEGER { disable(0), enable(1) }
		MAX-ACCESS	read-write
		STATUS		current
		DESCRIPTION	"
			style='Checkbox'
			path='/System/SNMP/Traps/Trap 2/Trap 2 Enable'
		"
		::= { alchemistHd3GConfEntries 59920 }

	snmpTrap2Addr OBJECT-TYPE
		SYNTAX		IpAddress
		MAX-ACCESS	read-write
		STATUS		current
		DESCRIPTION	"
			style='IPv4 address'
			path='/System/SNMP/Traps/Trap 2/Trap 2 IP Address'
		"
		::= { alchemistHd3GConfEntries 59921 }

	snmpTrap2Port OBJECT-TYPE
		SYNTAX		Integer32 (1..65535)
		MAX-ACCESS	read-write
		STATUS		current
		DESCRIPTION	"
			style='Numeric control'
			range='1..65535'
			preset='162'
			path='/System/SNMP/Traps/Trap 2/Trap 2 UDP Port'
		"
		::= { alchemistHd3GConfEntries 59922 }

	snmpTrap2Community OBJECT-TYPE
		SYNTAX		RollCallString
		MAX-ACCESS	read-write
		STATUS		current
		DESCRIPTION	"
			style='Editable string'
			path='/System/SNMP/Traps/Trap 2/Trap 2 Community'
		"
		::= { alchemistHd3GConfEntries 59923 }

	snmpTrap3Enab OBJECT-TYPE
		SYNTAX		INTEGER { disable(0), enable(1) }
		MAX-ACCESS	read-write
		STATUS		current
		DESCRIPTION	"
			style='Checkbox'
			path='/System/SNMP/Traps/Trap 3/Trap 3 Enable'
		"
		::= { alchemistHd3GConfEntries 59930 }

	snmpTrap3Addr OBJECT-TYPE
		SYNTAX		IpAddress
		MAX-ACCESS	read-write
		STATUS		current
		DESCRIPTION	"
			style='IPv4 address'
			path='/System/SNMP/Traps/Trap 3/Trap 3 IP Address'
		"
		::= { alchemistHd3GConfEntries 59931 }

	snmpTrap3Port OBJECT-TYPE
		SYNTAX		Integer32 (1..65535)
		MAX-ACCESS	read-write
		STATUS		current
		DESCRIPTION	"
			style='Numeric control'
			range='1..65535'
			preset='162'
			path='/System/SNMP/Traps/Trap 3/Trap 3 UDP Port'
		"
		::= { alchemistHd3GConfEntries 59932 }

	snmpTrap3Community OBJECT-TYPE
		SYNTAX		RollCallString
		MAX-ACCESS	read-write
		STATUS		current
		DESCRIPTION	"
			style='Editable string'
			path='/System/SNMP/Traps/Trap 3/Trap 3 Community'
		"
		::= { alchemistHd3GConfEntries 59933 }

	snmpTrap4Enab OBJECT-TYPE
		SYNTAX		INTEGER { disable(0), enable(1) }
		MAX-ACCESS	read-write
		STATUS		current
		DESCRIPTION	"
			style='Checkbox'
			path='/System/SNMP/Traps/Trap 4/Trap 4 Enable'
		"
		::= { alchemistHd3GConfEntries 59940 }

	snmpTrap4Addr OBJECT-TYPE
		SYNTAX		IpAddress
		MAX-ACCESS	read-write
		STATUS		current
		DESCRIPTION	"
			style='IPv4 address'
			path='/System/SNMP/Traps/Trap 4/Trap 4 IP Address'
		"
		::= { alchemistHd3GConfEntries 59941 }

	snmpTrap4Port OBJECT-TYPE
		SYNTAX		Integer32 (1..65535)
		MAX-ACCESS	read-write
		STATUS		current
		DESCRIPTION	"
			style='Numeric control'
			range='1..65535'
			preset='162'
			path='/System/SNMP/Traps/Trap 4/Trap 4 UDP Port'
		"
		::= { alchemistHd3GConfEntries 59942 }

	snmpTrap4Community OBJECT-TYPE
		SYNTAX		RollCallString
		MAX-ACCESS	read-write
		STATUS		current
		DESCRIPTION	"
			style='Editable string'
			path='/System/SNMP/Traps/Trap 4/Trap 4 Community'
		"
		::= { alchemistHd3GConfEntries 59943 }

END
