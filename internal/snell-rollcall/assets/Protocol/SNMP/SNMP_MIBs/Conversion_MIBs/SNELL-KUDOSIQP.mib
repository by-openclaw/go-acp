-- ************************************************************************************
--       Product:KudosIQP
--       Product Id#:626
--       Command Set:9
--       Filename:SNELL-KUDOSIQP.mib
--       Source File:IQPFrameCombined.xml and IQPChannelCombined.xml
--       Source Ver:2.1K.9
--       Date:21/07/2014
--       Time:13:08
--
--       Copyright (c) 2014 Snell Ltd
--       All rights reserved.
--
-- ************************************************************************************

SNELL-KudosIQP-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    conversionKudosIQP,
    conversionKudosIQPMib
        FROM SNELL-WILCOX-PRODUCT-REG;

conversionKudosIQPMi MODULE-IDENTITY
    LAST-UPDATED "1407211308Z"
    ORGANIZATION "Snell Ltd"
    CONTACT-INFO
        "Primary Author:Generated by Kudos IQP PCMIB tool

         postal:    Hartman House
                    Danehill
                    Lower Earley,
                    Reading, Berks
                    RG6 4PB
         phone:     +44 (0)118 9866123
         email:     support.uk@snellgroup.com"
    DESCRIPTION
        "This file defines the Snell card, command set translations."
    
    REVISION "1407211308Z"
    DESCRIPTION "Sole revision, this file generated on each release"
    ::= { conversionKudosIQPMib 1 }




--********************************************************************************
--*
--*  Snell Card:
--*  command set:
--*  list commands/menus:
--*
--******************************************************************************
    kudosIQP OBJECT IDENTIFIER ::= { conversionKudosIQP 0 }
    kudosFrameNoteEntries OBJECT IDENTIFIER ::= { kudosIQP 0 }


    i0SerialNoStatus NOTIFICATION-TYPE
        OBJECTS            { i0LoggingSerialNoStatus } 
        STATUS            current
        DESCRIPTION
                "CMNT: - Serial Number
                 TYPE: - Display
                 PAGE: - Logging
                    Serial No. Status  cmdID= 5000  "
        ::= { kudosFrameNoteEntries 5000 }


    i0UptimeStatus NOTIFICATION-TYPE
        OBJECTS            { i0LoggingUptimeStatus } 
        STATUS            current
        DESCRIPTION
                "CMNT: - Uptime in ddd:hh:mm:ss
                 TYPE: - Display
                 PAGE: - Logging
                    Uptime Status  cmdID= 5001  "
        ::= { kudosFrameNoteEntries 5001 }


    i0PSU1StateStatus NOTIFICATION-TYPE
        OBJECTS            { i0LoggingPSU1StateStatus } 
        STATUS            current
        DESCRIPTION
                "CMNT: - FAIL:Missing or OK:XVdc
                 TYPE: - Display
                 PAGE: - Logging
                    PSU 1 State Status  cmdID= 5002  "
        ::= { kudosFrameNoteEntries 5002 }


    i0PSU2StateStatus NOTIFICATION-TYPE
        OBJECTS            { i0LoggingPSU2StateStatus } 
        STATUS            current
        DESCRIPTION
                "CMNT: - FAIL:Missing or OK:XVdc
                 TYPE: - Display
                 PAGE: - Logging
                    PSU 2 State Status  cmdID= 5003  "
        ::= { kudosFrameNoteEntries 5003 }


    i0ReferenceStandardStatus NOTIFICATION-TYPE
        OBJECTS            { i0LoggingReferenceStandardStatus } 
        STATUS            current
        DESCRIPTION
                "CMNT: - WARN: or format type
                 TYPE: - Display
                 PAGE: - Logging
                    Reference Standard Status  cmdID= 5004  "
        ::= { kudosFrameNoteEntries 5004 }


    i0GenlockCh1Status NOTIFICATION-TYPE
        OBJECTS            { i0LoggingGenlockCh1Status } 
        STATUS            current
        DESCRIPTION
                "CMNT: - WARN:Free Run , OK:Genlock , OK:Clocklock  , WARN:Lost
                 TYPE: - Display
                 PAGE: - Logging
                    Genlock Ch 1 Status  cmdID= 5005  "
        ::= { kudosFrameNoteEntries 5005 }


    i0GenlockCh2Status NOTIFICATION-TYPE
        OBJECTS            { i0LoggingGenlockCh2Status } 
        STATUS            current
        DESCRIPTION
                "CMNT: - WARN:Free Run , OK:Genlock , OK:Clocklock  , WARN:Lost
                 TYPE: - Display
                 PAGE: - Logging
                    Genlock Ch 2 Status  cmdID= 5006  "
        ::= { kudosFrameNoteEntries 5006 }


    i0GenlockCh3Status NOTIFICATION-TYPE
        OBJECTS            { i0LoggingGenlockCh3Status } 
        STATUS            current
        DESCRIPTION
                "CMNT: - WARN:Free Run , OK:Genlock , OK:Clocklock  , WARN:Lost
                 TYPE: - Display
                 PAGE: - Logging
                    Genlock Ch 3 Status  cmdID= 5007  "
        ::= { kudosFrameNoteEntries 5007 }


    i0GenlockCh4Status NOTIFICATION-TYPE
        OBJECTS            { i0LoggingGenlockCh4Status } 
        STATUS            current
        DESCRIPTION
                "CMNT: - WARN:Free Run , OK:Genlock , OK:Clocklock  , WARN:Lost
                 TYPE: - Display
                 PAGE: - Logging
                    Genlock Ch 4 Status  cmdID= 5008  "
        ::= { kudosFrameNoteEntries 5008 }
    kudosFrameCtrlEntries OBJECT IDENTIFIER ::= { kudosIQP 1 }


    i0GenlockSourceCh12 OBJECT-TYPE
        SYNTAX            INTEGER {
                            valRefLock(0),
                            valCh1Input(1),
                            valCh2Input(2),
                            valFreeRun(3)
                            }
        MAX-ACCESS        read-write
        STATUS            current
        DESCRIPTION
                "CMNT: - 
                 TYPE: - RadiobuttonList
                 PAGE: - Genlock
                    Source Ch 1 & 2  cmdID= 10048
                    Ref Lock  value= 0
                    Ch 1 Input  value= 1
                    Ch 2 Input  value= 2
                    Free Run  value= 3  "
        ::= { kudosFrameCtrlEntries 10048 }


    i0GenlockSourceCh34 OBJECT-TYPE
        SYNTAX            INTEGER {
                            valRefLock(0),
                            valCh3Input(1),
                            valCh4Input(2),
                            valFreeRun(3)
                            }
        MAX-ACCESS        read-write
        STATUS            current
        DESCRIPTION
                "CMNT: - 
                 TYPE: - RadiobuttonList
                 PAGE: - Genlock
                    Source Ch 3 & 4  cmdID= 10049
                    Ref Lock  value= 0
                    Ch 3 Input  value= 1
                    Ch 4 Input  value= 2
                    Free Run  value= 3  "
        ::= { kudosFrameCtrlEntries 10049 }


    i0GenlockCurrentReferenceStandard OBJECT-TYPE
        SYNTAX            RollCallString
        MAX-ACCESS        read-only
        STATUS            current
        DESCRIPTION
                "CMNT: - 
                 TYPE: - Display
                 PAGE: - Genlock
                    Current Reference Standard  cmdID= 10166  "
        ::= { kudosFrameCtrlEntries 10166 }


    i0GenlockTimingCh1VerticalTiming OBJECT-TYPE
        SYNTAX            INTEGER
        MAX-ACCESS        read-write
        STATUS            current
        DESCRIPTION
                "CMNT: - 
                 TYPE: - Number
                 PAGE: - Timing
                    Vertical Timing  cmdID= 10050
                    min= -1125  max= 1125  step= 1  format= %0.0f lines  div_scale= 1  preset= 0
                    Min = -1125 lines  Max = 1125 lines  Step = 1 lines  Preset = 0 lines  "
        ::= { kudosFrameCtrlEntries 10050 }


    i0GenlockTimingCh1HorizontalTiming OBJECT-TYPE
        SYNTAX            INTEGER
        MAX-ACCESS        read-write
        STATUS            current
        DESCRIPTION
                "CMNT: - 
                 TYPE: - Number
                 PAGE: - Timing
                    Horizontal Timing  cmdID= 10051
                    min= -2640  max= 2640  step= 1  format= %0.0f pixels  div_scale= 1  preset= 0
                    Min = -2640 pixels  Max = 2640 pixels  Step = 1 pixels  Preset = 0 pixels  "
        ::= { kudosFrameCtrlEntries 10051 }


    i0GenlockTimingCh1Status OBJECT-TYPE
        SYNTAX            RollCallString
        MAX-ACCESS        read-only
        STATUS            current
        DESCRIPTION
                "CMNT: - 
                 TYPE: - Display
                 PAGE: - Timing
                    Status  cmdID= 10162  "
        ::= { kudosFrameCtrlEntries 10162 }


    i0GenlockTimingCh2VerticalTiming OBJECT-TYPE
        SYNTAX            INTEGER
        MAX-ACCESS        read-write
        STATUS            current
        DESCRIPTION
                "CMNT: - 
                 TYPE: - Number
                 PAGE: - Timing
                    Vertical Timing  cmdID= 10052
                    min= -1125  max= 1125  step= 1  format= %0.0f lines  div_scale= 1  preset= 0
                    Min = -1125 lines  Max = 1125 lines  Step = 1 lines  Preset = 0 lines  "
        ::= { kudosFrameCtrlEntries 10052 }


    i0GenlockTimingCh2HorizontalTiming OBJECT-TYPE
        SYNTAX            INTEGER
        MAX-ACCESS        read-write
        STATUS            current
        DESCRIPTION
                "CMNT: - 
                 TYPE: - Number
                 PAGE: - Timing
                    Horizontal Timing  cmdID= 10053
                    min= -2640  max= 2640  step= 1  format= %0.0f pixels  div_scale= 1  preset= 0
                    Min = -2640 pixels  Max = 2640 pixels  Step = 1 pixels  Preset = 0 pixels  "
        ::= { kudosFrameCtrlEntries 10053 }


    i0GenlockTimingCh2Status OBJECT-TYPE
        SYNTAX            RollCallString
        MAX-ACCESS        read-only
        STATUS            current
        DESCRIPTION
                "CMNT: - 
                 TYPE: - Display
                 PAGE: - Timing
                    Status  cmdID= 10163  "
        ::= { kudosFrameCtrlEntries 10163 }


    i0GenlockTimingCh3VerticalTiming OBJECT-TYPE
        SYNTAX            INTEGER
        MAX-ACCESS        read-write
        STATUS            current
        DESCRIPTION
                "CMNT: - 
                 TYPE: - Number
                 PAGE: - Timing
                    Vertical Timing  cmdID= 10054
                    min= -1125  max= 1125  step= 1  format= %0.0f lines  div_scale= 1  preset= 0
                    Min = -1125 lines  Max = 1125 lines  Step = 1 lines  Preset = 0 lines  "
        ::= { kudosFrameCtrlEntries 10054 }


    i0GenlockTimingCh3HorizontalTiming OBJECT-TYPE
        SYNTAX            INTEGER
        MAX-ACCESS        read-write
        STATUS            current
        DESCRIPTION
                "CMNT: - 
                 TYPE: - Number
                 PAGE: - Timing
                    Horizontal Timing  cmdID= 10055
                    min= -2640  max= 2640  step= 1  format= %0.0f pixels  div_scale= 1  preset= 0
                    Min = -2640 pixels  Max = 2640 pixels  Step = 1 pixels  Preset = 0 pixels  "
        ::= { kudosFrameCtrlEntries 10055 }


    i0GenlockTimingCh3Status OBJECT-TYPE
        SYNTAX            RollCallString
        MAX-ACCESS        read-only
        STATUS            current
        DESCRIPTION
                "CMNT: - 
                 TYPE: - Display
                 PAGE: - Timing
                    Status  cmdID= 10164  "
        ::= { kudosFrameCtrlEntries 10164 }


    i0GenlockTimingCh4VerticalTiming OBJECT-TYPE
        SYNTAX            INTEGER
        MAX-ACCESS        read-write
        STATUS            current
        DESCRIPTION
                "CMNT: - 
                 TYPE: - Number
                 PAGE: - Timing
                    Vertical Timing  cmdID= 10056
                    min= -1125  max= 1125  step= 1  format= %0.0f lines  div_scale= 1  preset= 0
                    Min = -1125 lines  Max = 1125 lines  Step = 1 lines  Preset = 0 lines  "
        ::= { kudosFrameCtrlEntries 10056 }


    i0GenlockTimingCh4HorizontalTiming OBJECT-TYPE
        SYNTAX            INTEGER
        MAX-ACCESS        read-write
        STATUS            current
        DESCRIPTION
                "CMNT: - 
                 TYPE: - Number
                 PAGE: - Timing
                    Horizontal Timing  cmdID= 10057
                    min= -2640  max= 2640  step= 1  format= %0.0f pixels  div_scale= 1  preset= 0
                    Min = -2640 pixels  Max = 2640 pixels  Step = 1 pixels  Preset = 0 pixels  "
        ::= { kudosFrameCtrlEntries 10057 }


    i0GenlockTimingCh4Status OBJECT-TYPE
        SYNTAX            RollCallString
        MAX-ACCESS        read-only
        STATUS            current
        DESCRIPTION
                "CMNT: - 
                 TYPE: - Display
                 PAGE: - Timing
                    Status  cmdID= 10165  "
        ::= { kudosFrameCtrlEntries 10165 }


    i0AudioRoutingAES1 OBJECT-TYPE
        SYNTAX            INTEGER {
                            valCh1Pair1(0),
                            valCh1Pair2(1),
                            valCh1Pair3(2),
                            valCh1Pair4(3),
                            valCh2Pair1(4),
                            valCh2Pair2(5),
                            valCh2Pair3(6),
                            valCh2Pair4(7),
                            valCh3Pair1(8),
                            valCh3Pair2(9),
                            valCh3Pair3(10),
                            valCh3Pair4(11),
                            valCh4Pair1(12),
                            valCh4Pair2(13),
                            valCh4Pair3(14),
                            valCh4Pair4(15)
                            }
        MAX-ACCESS        read-write
        STATUS            current
        DESCRIPTION
                "CMNT: - 
                 TYPE: - RadiobuttonList
                 PAGE: - Audio Routing
                    AES 1  cmdID= 10073
                    Ch 1 Pair 1  value= 0
                    Ch 1 Pair 2  value= 1
                    Ch 1 Pair 3  value= 2
                    Ch 1 Pair 4  value= 3
                    Ch 2 Pair 1  value= 4
                    Ch 2 Pair 2  value= 5
                    Ch 2 Pair 3  value= 6
                    Ch 2 Pair 4  value= 7
                    Ch 3 Pair 1  value= 8
                    Ch 3 Pair 2  value= 9
                    Ch 3 Pair 3  value= 10
                    Ch 3 Pair 4  value= 11
                    Ch 4 Pair 1  value= 12
                    Ch 4 Pair 2  value= 13
                    Ch 4 Pair 3  value= 14
                    Ch 4 Pair 4  value= 15  "
        ::= { kudosFrameCtrlEntries 10073 }


    i0AudioRoutingAES2 OBJECT-TYPE
        SYNTAX            INTEGER {
                            valCh1Pair1(0),
                            valCh1Pair2(1),
                            valCh1Pair3(2),
                            valCh1Pair4(3),
                            valCh2Pair1(4),
                            valCh2Pair2(5),
                            valCh2Pair3(6),
                            valCh2Pair4(7),
                            valCh3Pair1(8),
                            valCh3Pair2(9),
                            valCh3Pair3(10),
                            valCh3Pair4(11),
                            valCh4Pair1(12),
                            valCh4Pair2(13),
                            valCh4Pair3(14),
                            valCh4Pair4(15)
                            }
        MAX-ACCESS        read-write
        STATUS            current
        DESCRIPTION
                "CMNT: - 
                 TYPE: - RadiobuttonList
                 PAGE: - Audio Routing
                    AES 2  cmdID= 10074
                    Ch 1 Pair 1  value= 0
                    Ch 1 Pair 2  value= 1
                    Ch 1 Pair 3  value= 2
                    Ch 1 Pair 4  value= 3
                    Ch 2 Pair 1  value= 4
                    Ch 2 Pair 2  value= 5
                    Ch 2 Pair 3  value= 6
                    Ch 2 Pair 4  value= 7
                    Ch 3 Pair 1  value= 8
                    Ch 3 Pair 2  value= 9
                    Ch 3 Pair 3  value= 10
                    Ch 3 Pair 4  value= 11
                    Ch 4 Pair 1  value= 12
                    Ch 4 Pair 2  value= 13
                    Ch 4 Pair 3  value= 14
                    Ch 4 Pair 4  value= 15  "
        ::= { kudosFrameCtrlEntries 10074 }


    i0AudioRoutingAES3 OBJECT-TYPE
        SYNTAX            INTEGER {
                            valCh1Pair1(0),
                            valCh1Pair2(1),
                            valCh1Pair3(2),
                            valCh1Pair4(3),
                            valCh2Pair1(4),
                            valCh2Pair2(5),
                            valCh2Pair3(6),
                            valCh2Pair4(7),
                            valCh3Pair1(8),
                            valCh3Pair2(9),
                            valCh3Pair3(10),
                            valCh3Pair4(11),
                            valCh4Pair1(12),
                            valCh4Pair2(13),
                            valCh4Pair3(14),
                            valCh4Pair4(15)
                            }
        MAX-ACCESS        read-write
        STATUS            current
        DESCRIPTION
                "CMNT: - 
                 TYPE: - RadiobuttonList
                 PAGE: - Audio Routing
                    AES 3  cmdID= 10075
                    Ch 1 Pair 1  value= 0
                    Ch 1 Pair 2  value= 1
                    Ch 1 Pair 3  value= 2
                    Ch 1 Pair 4  value= 3
                    Ch 2 Pair 1  value= 4
                    Ch 2 Pair 2  value= 5
                    Ch 2 Pair 3  value= 6
                    Ch 2 Pair 4  value= 7
                    Ch 3 Pair 1  value= 8
                    Ch 3 Pair 2  value= 9
                    Ch 3 Pair 3  value= 10
                    Ch 3 Pair 4  value= 11
                    Ch 4 Pair 1  value= 12
                    Ch 4 Pair 2  value= 13
                    Ch 4 Pair 3  value= 14
                    Ch 4 Pair 4  value= 15  "
        ::= { kudosFrameCtrlEntries 10075 }


    i0AudioRoutingAES4 OBJECT-TYPE
        SYNTAX            INTEGER {
                            valCh1Pair1(0),
                            valCh1Pair2(1),
                            valCh1Pair3(2),
                            valCh1Pair4(3),
                            valCh2Pair1(4),
                            valCh2Pair2(5),
                            valCh2Pair3(6),
                            valCh2Pair4(7),
                            valCh3Pair1(8),
                            valCh3Pair2(9),
                            valCh3Pair3(10),
                            valCh3Pair4(11),
                            valCh4Pair1(12),
                            valCh4Pair2(13),
                            valCh4Pair3(14),
                            valCh4Pair4(15)
                            }
        MAX-ACCESS        read-write
        STATUS            current
        DESCRIPTION
                "CMNT: - 
                 TYPE: - RadiobuttonList
                 PAGE: - Audio Routing
                    AES 4  cmdID= 10076
                    Ch 1 Pair 1  value= 0
                    Ch 1 Pair 2  value= 1
                    Ch 1 Pair 3  value= 2
                    Ch 1 Pair 4  value= 3
                    Ch 2 Pair 1  value= 4
                    Ch 2 Pair 2  value= 5
                    Ch 2 Pair 3  value= 6
                    Ch 2 Pair 4  value= 7
                    Ch 3 Pair 1  value= 8
                    Ch 3 Pair 2  value= 9
                    Ch 3 Pair 3  value= 10
                    Ch 3 Pair 4  value= 11
                    Ch 4 Pair 1  value= 12
                    Ch 4 Pair 2  value= 13
                    Ch 4 Pair 3  value= 14
                    Ch 4 Pair 4  value= 15  "
        ::= { kudosFrameCtrlEntries 10076 }


    i0AudioRoutingAnalogGroup1 OBJECT-TYPE
        SYNTAX            INTEGER {
                            valCh1Pairs12(0),
                            valCh1Pairs34(1),
                            valCh2Pairs12(2),
                            valCh2Pairs34(3),
                            valCh3Pairs12(4),
                            valCh3Pairs34(5),
                            valCh4Pairs12(6),
                            valCh4Pairs34(7),
                            valChs12Pair1(8),
                            valChs12Pair2(9),
                            valChs12Pair3(10),
                            valChs12Pair4(11),
                            valChs34Pair1(12),
                            valChs34Pair2(13),
                            valChs34Pair3(14),
                            valChs34Pair4(15)
                            }
        MAX-ACCESS        read-write
        STATUS            current
        DESCRIPTION
                "CMNT: - 
                 TYPE: - RadiobuttonList
                 PAGE: - Audio Routing
                    Analog Group 1  cmdID= 10077
                    Ch 1 Pairs 1 & 2  value= 0
                    Ch 1 Pairs 3 & 4  value= 1
                    Ch 2 Pairs 1 & 2  value= 2
                    Ch 2 Pairs 3 & 4  value= 3
                    Ch 3 Pairs 1 & 2  value= 4
                    Ch 3 Pairs 3 & 4  value= 5
                    Ch 4 Pairs 1 & 2  value= 6
                    Ch 4 Pairs 3 & 4  value= 7
                    Chs 1 & 2 Pair 1  value= 8
                    Chs 1 & 2 Pair 2  value= 9
                    Chs 1 & 2 Pair 3  value= 10
                    Chs 1 & 2 Pair 4  value= 11
                    Chs 3 & 4 Pair 1  value= 12
                    Chs 3 & 4 Pair 2  value= 13
                    Chs 3 & 4 Pair 3  value= 14
                    Chs 3 & 4 Pair 4  value= 15  "
        ::= { kudosFrameCtrlEntries 10077 }


    i0AudioRoutingAnalogGroup2 OBJECT-TYPE
        SYNTAX            INTEGER {
                            valCh1Pairs12(0),
                            valCh1Pairs34(1),
                            valCh2Pairs12(2),
                            valCh2Pairs34(3),
                            valCh3Pairs12(4),
                            valCh3Pairs34(5),
                            valCh4Pairs12(6),
                            valCh4Pairs34(7),
                            valChs12Pair1(8),
                            valChs12Pair2(9),
                            valChs12Pair3(10),
                            valChs12Pair4(11),
                            valChs34Pair1(12),
                            valChs34Pair2(13),
                            valChs34Pair3(14),
                            valChs34Pair4(15)
                            }
        MAX-ACCESS        read-write
        STATUS            current
        DESCRIPTION
                "CMNT: - 
                 TYPE: - RadiobuttonList
                 PAGE: - Audio Routing
                    Analog Group 2  cmdID= 10078
                    Ch 1 Pairs 1 & 2  value= 0
                    Ch 1 Pairs 3 & 4  value= 1
                    Ch 2 Pairs 1 & 2  value= 2
                    Ch 2 Pairs 3 & 4  value= 3
                    Ch 3 Pairs 1 & 2  value= 4
                    Ch 3 Pairs 3 & 4  value= 5
                    Ch 4 Pairs 1 & 2  value= 6
                    Ch 4 Pairs 3 & 4  value= 7
                    Chs 1 & 2 Pair 1  value= 8
                    Chs 1 & 2 Pair 2  value= 9
                    Chs 1 & 2 Pair 3  value= 10
                    Chs 1 & 2 Pair 4  value= 11
                    Chs 3 & 4 Pair 1  value= 12
                    Chs 3 & 4 Pair 2  value= 13
                    Chs 3 & 4 Pair 3  value= 14
                    Chs 3 & 4 Pair 4  value= 15  "
        ::= { kudosFrameCtrlEntries 10078 }


    i0AudioControlAESInputTypePair1 OBJECT-TYPE
        SYNTAX            INTEGER {
                            valBalanced(0),
                            valUnbalanced(1)
                            }
        MAX-ACCESS        read-write
        STATUS            current
        DESCRIPTION
                "CMNT: - 
                 TYPE: - RadiobuttonList
                 PAGE: - Audio Control
                    Pair 1  cmdID= 10064
                    Balanced  value= 0
                    Unbalanced  value= 1  "
        ::= { kudosFrameCtrlEntries 10064 }


    i0AudioControlAESInputTypePair2 OBJECT-TYPE
        SYNTAX            INTEGER {
                            valBalanced(0),
                            valUnbalanced(1)
                            }
        MAX-ACCESS        read-write
        STATUS            current
        DESCRIPTION
                "CMNT: - 
                 TYPE: - RadiobuttonList
                 PAGE: - Audio Control
                    Pair 2  cmdID= 10065
                    Balanced  value= 0
                    Unbalanced  value= 1  "
        ::= { kudosFrameCtrlEntries 10065 }


    i0AudioControlAESInputTypePair3 OBJECT-TYPE
        SYNTAX            INTEGER {
                            valBalanced(0),
                            valUnbalanced(1)
                            }
        MAX-ACCESS        read-write
        STATUS            current
        DESCRIPTION
                "CMNT: - 
                 TYPE: - RadiobuttonList
                 PAGE: - Audio Control
                    Pair 3  cmdID= 10066
                    Balanced  value= 0
                    Unbalanced  value= 1  "
        ::= { kudosFrameCtrlEntries 10066 }


    i0AudioControlAESInputTypePair4 OBJECT-TYPE
        SYNTAX            INTEGER {
                            valBalanced(0),
                            valUnbalanced(1)
                            }
        MAX-ACCESS        read-write
        STATUS            current
        DESCRIPTION
                "CMNT: - 
                 TYPE: - RadiobuttonList
                 PAGE: - Audio Control
                    Pair 4  cmdID= 10067
                    Balanced  value= 0
                    Unbalanced  value= 1  "
        ::= { kudosFrameCtrlEntries 10067 }


    i0AudioControlAnalogInADCHeadroomPair1 OBJECT-TYPE
        SYNTAX            INTEGER
        MAX-ACCESS        read-write
        STATUS            current
        DESCRIPTION
                "CMNT: - 
                 TYPE: - Number
                 PAGE: - Audio Control
                    Pair 1  cmdID= 10058
                    min= 24  max= 48  step= 1  format= %d  div_scale= 2  preset= 36
                    Min = 12  Max = 24  Step = 0  Preset = 18  "
        ::= { kudosFrameCtrlEntries 10058 }


    i0AudioControlAnalogInADCHeadroomPair2 OBJECT-TYPE
        SYNTAX            INTEGER
        MAX-ACCESS        read-write
        STATUS            current
        DESCRIPTION
                "CMNT: - 
                 TYPE: - Number
                 PAGE: - Audio Control
                    Pair 2  cmdID= 10059
                    min= 24  max= 48  step= 1  format= %d  div_scale= 2  preset= 36
                    Min = 12  Max = 24  Step = 0  Preset = 18  "
        ::= { kudosFrameCtrlEntries 10059 }


    i0AudioControlAnalogInADCHeadroomPair3 OBJECT-TYPE
        SYNTAX            INTEGER
        MAX-ACCESS        read-write
        STATUS            current
        DESCRIPTION
                "CMNT: - 
                 TYPE: - Number
                 PAGE: - Audio Control
                    Pair 3  cmdID= 10060
                    min= 24  max= 48  step= 1  format= %d  div_scale= 2  preset= 36
                    Min = 12  Max = 24  Step = 0  Preset = 18  "
        ::= { kudosFrameCtrlEntries 10060 }


    i0AudioControlAnalogInADCHeadroomPair4 OBJECT-TYPE
        SYNTAX            INTEGER
        MAX-ACCESS        read-write
        STATUS            current
        DESCRIPTION
                "CMNT: - 
                 TYPE: - Number
                 PAGE: - Audio Control
                    Pair 4  cmdID= 10061
                    min= 24  max= 48  step= 1  format= %d  div_scale= 2  preset= 36
                    Min = 12  Max = 24  Step = 0  Preset = 18  "
        ::= { kudosFrameCtrlEntries 10061 }


    i0AudioControlAnalogOutDACLevelPair1 OBJECT-TYPE
        SYNTAX            INTEGER
        MAX-ACCESS        read-write
        STATUS            current
        DESCRIPTION
                "CMNT: - 
                 TYPE: - Number
                 PAGE: - Audio Control
                    Pair 1  cmdID= 10069
                    min= 24  max= 48  step= 1  format= %d  div_scale= 2  preset= 36
                    Min = 12  Max = 24  Step = 0  Preset = 18  "
        ::= { kudosFrameCtrlEntries 10069 }


    i0AudioControlAnalogOutDACLevelPair2 OBJECT-TYPE
        SYNTAX            INTEGER
        MAX-ACCESS        read-write
        STATUS            current
        DESCRIPTION
                "CMNT: - 
                 TYPE: - Number
                 PAGE: - Audio Control
                    Pair 2  cmdID= 10070
                    min= 24  max= 48  step= 1  format= %d  div_scale= 2  preset= 36
                    Min = 12  Max = 24  Step = 0  Preset = 18  "
        ::= { kudosFrameCtrlEntries 10070 }


    i0AudioControlAnalogOutDACLevelPair3 OBJECT-TYPE
        SYNTAX            INTEGER
        MAX-ACCESS        read-write
        STATUS            current
        DESCRIPTION
                "CMNT: - 
                 TYPE: - Number
                 PAGE: - Audio Control
                    Pair 3  cmdID= 10071
                    min= 24  max= 48  step= 1  format= %d  div_scale= 2  preset= 36
                    Min = 12  Max = 24  Step = 0  Preset = 18  "
        ::= { kudosFrameCtrlEntries 10071 }


    i0AudioControlAnalogOutDACLevelPair4 OBJECT-TYPE
        SYNTAX            INTEGER
        MAX-ACCESS        read-write
        STATUS            current
        DESCRIPTION
                "CMNT: - 
                 TYPE: - Number
                 PAGE: - Audio Control
                    Pair 4  cmdID= 10072
                    min= 24  max= 48  step= 1  format= %d  div_scale= 2  preset= 36
                    Min = 12  Max = 24  Step = 0  Preset = 18  "
        ::= { kudosFrameCtrlEntries 10072 }


    i0CVBSDecoderASource OBJECT-TYPE
        SYNTAX            INTEGER {
                            valInput1(0),
                            valInput2(1),
                            valYC(2)
                            }
        MAX-ACCESS        read-write
        STATUS            current
        DESCRIPTION
                "CMNT: - 
                 TYPE: - RadiobuttonList
                 PAGE: - CVBS
                    Source  cmdID= 10024
                    Input 1  value= 0
                    Input 2  value= 1
                    Y/C  value= 2  "
        ::= { kudosFrameCtrlEntries 10024 }


    i0CVBSDecoderAACC OBJECT-TYPE
        SYNTAX            INTEGER { disable(0), enable(1)  }
        MAX-ACCESS        read-write
        STATUS            current
        DESCRIPTION
                "CMNT: - 
                 TYPE: - Checkbox
                 PAGE: - CVBS
                    ACC  cmdID= 10020  "
        ::= { kudosFrameCtrlEntries 10020 }


    i0CVBSDecoderACTI OBJECT-TYPE
        SYNTAX            INTEGER { disable(0), enable(1)  }
        MAX-ACCESS        read-write
        STATUS            current
        DESCRIPTION
                "CMNT: - 
                 TYPE: - Checkbox
                 PAGE: - CVBS
                    CTI  cmdID= 10021  "
        ::= { kudosFrameCtrlEntries 10021 }


    i0CVBSDecoderAPedestal OBJECT-TYPE
        SYNTAX            INTEGER {
                            valOff(0),
                            valOn(1)
                            }
        MAX-ACCESS        read-write
        STATUS            current
        DESCRIPTION
                "CMNT: - 
                 TYPE: - RadiobuttonList
                 PAGE: - CVBS
                    Pedestal  cmdID= 10022
                    Off  value= 0
                    On  value= 1  "
        ::= { kudosFrameCtrlEntries 10022 }


    i0CVBSDecoderANTSCHue OBJECT-TYPE
        SYNTAX            INTEGER
        MAX-ACCESS        read-write
        STATUS            current
        DESCRIPTION
                "CMNT: - 
                 TYPE: - Number
                 PAGE: - CVBS
                    NTSC Hue  cmdID= 10023
                    min= -180  max= 180  step= 1  format= %d deg  div_scale= 1  preset= 0
                    Min = -180 deg  Max = 180 deg  Step = 1 deg  Preset = 0 deg  "
        ::= { kudosFrameCtrlEntries 10023 }


    i0CVBSEncoderASource OBJECT-TYPE
        SYNTAX            INTEGER {
                            valCh1(0),
                            valCh2(1),
                            valCh3(2),
                            valCh4(3)
                            }
        MAX-ACCESS        read-write
        STATUS            current
        DESCRIPTION
                "CMNT: - 
                 TYPE: - RadiobuttonList
                 PAGE: - CVBS
                    Source  cmdID= 10040
                    Ch 1  value= 0
                    Ch 2  value= 1
                    Ch 3  value= 2
                    Ch 4  value= 3  "
        ::= { kudosFrameCtrlEntries 10040 }


    i0CVBSEncoderAFormat OBJECT-TYPE
        SYNTAX            INTEGER {
                            valPALNTSC(0),
                            valPALnNPALnM(1),
                            valPALNTSCnJ(2)
                            }
        MAX-ACCESS        read-write
        STATUS            current
        DESCRIPTION
                "CMNT: - 
                 TYPE: - RadiobuttonList
                 PAGE: - CVBS
                    Format  cmdID= 10041
                    PAL/NTSC  value= 0
                    PAL-N/PAL-M  value= 1
                    PAL/NTSC-J  value= 2  "
        ::= { kudosFrameCtrlEntries 10041 }


    i0CVBSDecoderBSource OBJECT-TYPE
        SYNTAX            INTEGER {
                            valInput1(0),
                            valInput2(1),
                            valYC(2)
                            }
        MAX-ACCESS        read-write
        STATUS            current
        DESCRIPTION
                "CMNT: - 
                 TYPE: - RadiobuttonList
                 PAGE: - CVBS
                    Source  cmdID= 10029
                    Input 1  value= 0
                    Input 2  value= 1
                    Y/C  value= 2  "
        ::= { kudosFrameCtrlEntries 10029 }


    i0CVBSDecoderBACC OBJECT-TYPE
        SYNTAX            INTEGER { disable(0), enable(1)  }
        MAX-ACCESS        read-write
        STATUS            current
        DESCRIPTION
                "CMNT: - 
                 TYPE: - Checkbox
                 PAGE: - CVBS
                    ACC  cmdID= 10025  "
        ::= { kudosFrameCtrlEntries 10025 }


    i0CVBSDecoderBCTI OBJECT-TYPE
        SYNTAX            INTEGER { disable(0), enable(1)  }
        MAX-ACCESS        read-write
        STATUS            current
        DESCRIPTION
                "CMNT: - 
                 TYPE: - Checkbox
                 PAGE: - CVBS
                    CTI  cmdID= 10026  "
        ::= { kudosFrameCtrlEntries 10026 }


    i0CVBSDecoderBPedestal OBJECT-TYPE
        SYNTAX            INTEGER {
                            valOff(0),
                            valOn(1)
                            }
        MAX-ACCESS        read-write
        STATUS            current
        DESCRIPTION
                "CMNT: - 
                 TYPE: - RadiobuttonList
                 PAGE: - CVBS
                    Pedestal  cmdID= 10027
                    Off  value= 0
                    On  value= 1  "
        ::= { kudosFrameCtrlEntries 10027 }


    i0CVBSDecoderBNTSCHue OBJECT-TYPE
        SYNTAX            INTEGER
        MAX-ACCESS        read-write
        STATUS            current
        DESCRIPTION
                "CMNT: - 
                 TYPE: - Number
                 PAGE: - CVBS
                    NTSC Hue  cmdID= 10028
                    min= -180  max= 180  step= 1  format= %d deg  div_scale= 1  preset= 0
                    Min = -180 deg  Max = 180 deg  Step = 1 deg  Preset = 0 deg  "
        ::= { kudosFrameCtrlEntries 10028 }


    i0CVBSEncoderBSource OBJECT-TYPE
        SYNTAX            INTEGER {
                            valCh1(0),
                            valCh2(1),
                            valCh3(2),
                            valCh4(3)
                            }
        MAX-ACCESS        read-write
        STATUS            current
        DESCRIPTION
                "CMNT: - 
                 TYPE: - RadiobuttonList
                 PAGE: - CVBS
                    Source  cmdID= 10042
                    Ch 1  value= 0
                    Ch 2  value= 1
                    Ch 3  value= 2
                    Ch 4  value= 3  "
        ::= { kudosFrameCtrlEntries 10042 }


    i0CVBSEncoderBFormat OBJECT-TYPE
        SYNTAX            INTEGER {
                            valPALNTSC(0),
                            valPALnNPALnM(1),
                            valPALNTSCnJ(2)
                            }
        MAX-ACCESS        read-write
        STATUS            current
        DESCRIPTION
                "CMNT: - 
                 TYPE: - RadiobuttonList
                 PAGE: - CVBS
                    Format  cmdID= 10043
                    PAL/NTSC  value= 0
                    PAL-N/PAL-M  value= 1
                    PAL/NTSC-J  value= 2  "
        ::= { kudosFrameCtrlEntries 10043 }


    i0CVBSDecoderCSource OBJECT-TYPE
        SYNTAX            INTEGER {
                            valInput1(0),
                            valInput2(1),
                            valYC(2)
                            }
        MAX-ACCESS        read-write
        STATUS            current
        DESCRIPTION
                "CMNT: - 
                 TYPE: - RadiobuttonList
                 PAGE: - CVBS
                    Source  cmdID= 10034
                    Input 1  value= 0
                    Input 2  value= 1
                    Y/C  value= 2  "
        ::= { kudosFrameCtrlEntries 10034 }


    i0CVBSDecoderCACC OBJECT-TYPE
        SYNTAX            INTEGER { disable(0), enable(1)  }
        MAX-ACCESS        read-write
        STATUS            current
        DESCRIPTION
                "CMNT: - 
                 TYPE: - Checkbox
                 PAGE: - CVBS
                    ACC  cmdID= 10030  "
        ::= { kudosFrameCtrlEntries 10030 }


    i0CVBSDecoderCCTI OBJECT-TYPE
        SYNTAX            INTEGER { disable(0), enable(1)  }
        MAX-ACCESS        read-write
        STATUS            current
        DESCRIPTION
                "CMNT: - 
                 TYPE: - Checkbox
                 PAGE: - CVBS
                    CTI  cmdID= 10031  "
        ::= { kudosFrameCtrlEntries 10031 }


    i0CVBSDecoderCPedestal OBJECT-TYPE
        SYNTAX            INTEGER {
                            valOff(0),
                            valOn(1)
                            }
        MAX-ACCESS        read-write
        STATUS            current
        DESCRIPTION
                "CMNT: - 
                 TYPE: - RadiobuttonList
                 PAGE: - CVBS
                    Pedestal  cmdID= 10032
                    Off  value= 0
                    On  value= 1  "
        ::= { kudosFrameCtrlEntries 10032 }


    i0CVBSDecoderCNTSCHue OBJECT-TYPE
        SYNTAX            INTEGER
        MAX-ACCESS        read-write
        STATUS            current
        DESCRIPTION
                "CMNT: - 
                 TYPE: - Number
                 PAGE: - CVBS
                    NTSC Hue  cmdID= 10033
                    min= -180  max= 180  step= 1  format= %d deg  div_scale= 1  preset= 0
                    Min = -180 deg  Max = 180 deg  Step = 1 deg  Preset = 0 deg  "
        ::= { kudosFrameCtrlEntries 10033 }


    i0CVBSEncoderCSource OBJECT-TYPE
        SYNTAX            INTEGER {
                            valCh1(0),
                            valCh2(1),
                            valCh3(2),
                            valCh4(3)
                            }
        MAX-ACCESS        read-write
        STATUS            current
        DESCRIPTION
                "CMNT: - 
                 TYPE: - RadiobuttonList
                 PAGE: - CVBS
                    Source  cmdID= 10044
                    Ch 1  value= 0
                    Ch 2  value= 1
                    Ch 3  value= 2
                    Ch 4  value= 3  "
        ::= { kudosFrameCtrlEntries 10044 }


    i0CVBSEncoderCFormat OBJECT-TYPE
        SYNTAX            INTEGER {
                            valPALNTSC(0),
                            valPALnNPALnM(1),
                            valPALNTSCnJ(2)
                            }
        MAX-ACCESS        read-write
        STATUS            current
        DESCRIPTION
                "CMNT: - 
                 TYPE: - RadiobuttonList
                 PAGE: - CVBS
                    Format  cmdID= 10045
                    PAL/NTSC  value= 0
                    PAL-N/PAL-M  value= 1
                    PAL/NTSC-J  value= 2  "
        ::= { kudosFrameCtrlEntries 10045 }


    i0CVBSDecoderDSource OBJECT-TYPE
        SYNTAX            INTEGER {
                            valInput1(0),
                            valInput2(1),
                            valYC(2)
                            }
        MAX-ACCESS        read-write
        STATUS            current
        DESCRIPTION
                "CMNT: - 
                 TYPE: - RadiobuttonList
                 PAGE: - CVBS
                    Source  cmdID= 10039
                    Input 1  value= 0
                    Input 2  value= 1
                    Y/C  value= 2  "
        ::= { kudosFrameCtrlEntries 10039 }


    i0CVBSDecoderDACC OBJECT-TYPE
        SYNTAX            INTEGER { disable(0), enable(1)  }
        MAX-ACCESS        read-write
        STATUS            current
        DESCRIPTION
                "CMNT: - 
                 TYPE: - Checkbox
                 PAGE: - CVBS
                    ACC  cmdID= 10035  "
        ::= { kudosFrameCtrlEntries 10035 }


    i0CVBSDecoderDCTI OBJECT-TYPE
        SYNTAX            INTEGER { disable(0), enable(1)  }
        MAX-ACCESS        read-write
        STATUS            current
        DESCRIPTION
                "CMNT: - 
                 TYPE: - Checkbox
                 PAGE: - CVBS
                    CTI  cmdID= 10036  "
        ::= { kudosFrameCtrlEntries 10036 }


    i0CVBSDecoderDPedestal OBJECT-TYPE
        SYNTAX            INTEGER {
                            valOff(0),
                            valOn(1)
                            }
        MAX-ACCESS        read-write
        STATUS            current
        DESCRIPTION
                "CMNT: - 
                 TYPE: - RadiobuttonList
                 PAGE: - CVBS
                    Pedestal  cmdID= 10037
                    Off  value= 0
                    On  value= 1  "
        ::= { kudosFrameCtrlEntries 10037 }


    i0CVBSDecoderDNTSCHue OBJECT-TYPE
        SYNTAX            INTEGER
        MAX-ACCESS        read-write
        STATUS            current
        DESCRIPTION
                "CMNT: - 
                 TYPE: - Number
                 PAGE: - CVBS
                    NTSC Hue  cmdID= 10038
                    min= -180  max= 180  step= 1  format= %d deg  div_scale= 1  preset= 0
                    Min = -180 deg  Max = 180 deg  Step = 1 deg  Preset = 0 deg  "
        ::= { kudosFrameCtrlEntries 10038 }


    i0CVBSEncoderDSource OBJECT-TYPE
        SYNTAX            INTEGER {
                            valCh1(0),
                            valCh2(1),
                            valCh3(2),
                            valCh4(3)
                            }
        MAX-ACCESS        read-write
        STATUS            current
        DESCRIPTION
                "CMNT: - 
                 TYPE: - RadiobuttonList
                 PAGE: - CVBS
                    Source  cmdID= 10046
                    Ch 1  value= 0
                    Ch 2  value= 1
                    Ch 3  value= 2
                    Ch 4  value= 3  "
        ::= { kudosFrameCtrlEntries 10046 }


    i0CVBSEncoderDFormat OBJECT-TYPE
        SYNTAX            INTEGER {
                            valPALNTSC(0),
                            valPALnNPALnM(1),
                            valPALNTSCnJ(2)
                            }
        MAX-ACCESS        read-write
        STATUS            current
        DESCRIPTION
                "CMNT: - 
                 TYPE: - RadiobuttonList
                 PAGE: - CVBS
                    Format  cmdID= 10047
                    PAL/NTSC  value= 0
                    PAL-N/PAL-M  value= 1
                    PAL/NTSC-J  value= 2  "
        ::= { kudosFrameCtrlEntries 10047 }


    i0DolbyCh1DecoderSource OBJECT-TYPE
        SYNTAX            INTEGER {
                            valEmbedded1(0),
                            valEmbedded2(1),
                            valEmbedded3(2),
                            valEmbedded4(3),
                            valEmbedded5(4),
                            valEmbedded6(5),
                            valEmbedded7(6),
                            valEmbedded8(7),
                            valAES1(8),
                            valAES2(9),
                            valAES3(10),
                            valAES4(11)
                            }
        MAX-ACCESS        read-write
        STATUS            current
        DESCRIPTION
                "CMNT: - 
                 TYPE: - RadiobuttonList
                 PAGE: - Dolby
                    Decoder Source  cmdID= 10079
                    Embedded 1  value= 0
                    Embedded 2  value= 1
                    Embedded 3  value= 2
                    Embedded 4  value= 3
                    Embedded 5  value= 4
                    Embedded 6  value= 5
                    Embedded 7  value= 6
                    Embedded 8  value= 7
                    AES 1  value= 8
                    AES 2  value= 9
                    AES 3  value= 10
                    AES 4  value= 11  "
        ::= { kudosFrameCtrlEntries 10079 }


    i0DolbyCh1DolbyEDelayCompensation OBJECT-TYPE
        SYNTAX            INTEGER {
                            valEarlyEarly(0),
                            valEarlyNormal(1),
                            valEarlyLate(2),
                            valNormalNormal(3),
                            valNormalLate(4),
                            valLateLate(5)
                            }
        MAX-ACCESS        read-write
        STATUS            current
        DESCRIPTION
                "CMNT: - 
                 TYPE: - RadiobuttonList
                 PAGE: - Dolby
                    DolbyE Delay Compensation  cmdID= 10085
                    Early > Early  value= 0
                    Early > Normal  value= 1
                    Early > Late  value= 2
                    Normal > Normal  value= 3
                    Normal > Late  value= 4
                    Late > Late  value= 5  "
        ::= { kudosFrameCtrlEntries 10085 }


    i0DolbyCh1MetadataSource OBJECT-TYPE
        SYNTAX            INTEGER {
                            valDolbyDecoder(0),
                            valSMPTE2020(1)
                            }
        MAX-ACCESS        read-write
        STATUS            current
        DESCRIPTION
                "CMNT: - 
                 TYPE: - RadiobuttonList
                 PAGE: - Dolby
                    Metadata Source  cmdID= 10084
                    Dolby Decoder  value= 0
                    SMPTE 2020  value= 1  "
        ::= { kudosFrameCtrlEntries 10084 }


    i0DolbyCh1PacketType OBJECT-TYPE
        SYNTAX            INTEGER {
                            valA(0),
                            valB(1)
                            }
        MAX-ACCESS        read-write
        STATUS            current
        DESCRIPTION
                "CMNT: - 
                 TYPE: - RadiobuttonList
                 PAGE: - Dolby
                    Packet Type  cmdID= 10087
                    A  value= 0
                    B  value= 1  "
        ::= { kudosFrameCtrlEntries 10087 }


    i0DolbyCh1SMPTE2020OutputOutputLine OBJECT-TYPE
        SYNTAX            INTEGER
        MAX-ACCESS        read-write
        STATUS            current
        DESCRIPTION
                "CMNT: - 
                 TYPE: - Number
                 PAGE: - Dolby Ch 1
                    Output Line  cmdID= 10175
                    min= 8  max= 20  step= 1  format= %0.0f  div_scale= 1  preset= 10
                    Min = 8  Max = 20  Step = 1  Preset = 10  "
        ::= { kudosFrameCtrlEntries 10175 }


    i0DolbyCh1SMPTE2020OutputOutputEnable OBJECT-TYPE
        SYNTAX            INTEGER { disable(0), enable(1)  }
        MAX-ACCESS        read-write
        STATUS            current
        DESCRIPTION
                "CMNT: - 
                 TYPE: - Checkbox
                 PAGE: - Dolby Ch 1
                    Output Enable  cmdID= 10174  "
        ::= { kudosFrameCtrlEntries 10174 }


    i0DolbyCh1InputStatus OBJECT-TYPE
        SYNTAX            RollCallString
        MAX-ACCESS        read-only
        STATUS            current
        DESCRIPTION
                "CMNT: - 
                 TYPE: - Display
                 PAGE: - Dolby
                    Input Status  cmdID= 10080  "
        ::= { kudosFrameCtrlEntries 10080 }


    i0DolbyCh1DecoderRate OBJECT-TYPE
        SYNTAX            RollCallString
        MAX-ACCESS        read-only
        STATUS            current
        DESCRIPTION
                "CMNT: - 
                 TYPE: - Display
                 PAGE: - Dolby
                    Decoder Rate  cmdID= 10082  "
        ::= { kudosFrameCtrlEntries 10082 }


    i0DolbyCh1DecoderFormat OBJECT-TYPE
        SYNTAX            RollCallString
        MAX-ACCESS        read-only
        STATUS            current
        DESCRIPTION
                "CMNT: - 
                 TYPE: - Display
                 PAGE: - Dolby
                    Decoder Format  cmdID= 10081  "
        ::= { kudosFrameCtrlEntries 10081 }


    i0DolbyCh1DecoderVersion OBJECT-TYPE
        SYNTAX            RollCallString
        MAX-ACCESS        read-only
        STATUS            current
        DESCRIPTION
                "CMNT: - 
                 TYPE: - Display
                 PAGE: - Dolby
                    Decoder Version  cmdID= 10083  "
        ::= { kudosFrameCtrlEntries 10083 }


    i0DolbyCh1EncoderVersion OBJECT-TYPE
        SYNTAX            RollCallString
        MAX-ACCESS        read-only
        STATUS            current
        DESCRIPTION
                "CMNT: - 
                 TYPE: - Display
                 PAGE: - Dolby
                    Encoder Version  cmdID= 10086  "
        ::= { kudosFrameCtrlEntries 10086 }


    i0DolbyCh1DolbyMetadataOutputLineStatus OBJECT-TYPE
        SYNTAX            RollCallString
        MAX-ACCESS        read-only
        STATUS            current
        DESCRIPTION
                "CMNT: - 
                 TYPE: - Display
                 PAGE: - Dolby
                    Dolby Metadata Output Line Status  cmdID= 10180  "
        ::= { kudosFrameCtrlEntries 10180 }


    i0DolbyCh2DecoderSource OBJECT-TYPE
        SYNTAX            INTEGER {
                            valEmbedded1(0),
                            valEmbedded2(1),
                            valEmbedded3(2),
                            valEmbedded4(3),
                            valEmbedded5(4),
                            valEmbedded6(5),
                            valEmbedded7(6),
                            valEmbedded8(7),
                            valAES1(8),
                            valAES2(9),
                            valAES3(10),
                            valAES4(11)
                            }
        MAX-ACCESS        read-write
        STATUS            current
        DESCRIPTION
                "CMNT: - 
                 TYPE: - RadiobuttonList
                 PAGE: - Dolby
                    Decoder Source  cmdID= 10089
                    Embedded 1  value= 0
                    Embedded 2  value= 1
                    Embedded 3  value= 2
                    Embedded 4  value= 3
                    Embedded 5  value= 4
                    Embedded 6  value= 5
                    Embedded 7  value= 6
                    Embedded 8  value= 7
                    AES 1  value= 8
                    AES 2  value= 9
                    AES 3  value= 10
                    AES 4  value= 11  "
        ::= { kudosFrameCtrlEntries 10089 }


    i0DolbyCh2DolbyEDelayCompensation OBJECT-TYPE
        SYNTAX            INTEGER {
                            valEarlyEarly(0),
                            valEarlyNormal(1),
                            valEarlyLate(2),
                            valNormalNormal(3),
                            valNormalLate(4),
                            valLateLate(5)
                            }
        MAX-ACCESS        read-write
        STATUS            current
        DESCRIPTION
                "CMNT: - 
                 TYPE: - RadiobuttonList
                 PAGE: - Dolby
                    DolbyE Delay Compensation  cmdID= 10095
                    Early > Early  value= 0
                    Early > Normal  value= 1
                    Early > Late  value= 2
                    Normal > Normal  value= 3
                    Normal > Late  value= 4
                    Late > Late  value= 5  "
        ::= { kudosFrameCtrlEntries 10095 }


    i0DolbyCh2MetadataSource OBJECT-TYPE
        SYNTAX            INTEGER {
                            valDolbyDecoder(0),
                            valSMPTE2020(1)
                            }
        MAX-ACCESS        read-write
        STATUS            current
        DESCRIPTION
                "CMNT: - 
                 TYPE: - RadiobuttonList
                 PAGE: - Dolby
                    Metadata Source  cmdID= 10094
                    Dolby Decoder  value= 0
                    SMPTE 2020  value= 1  "
        ::= { kudosFrameCtrlEntries 10094 }


    i0DolbyCh2PacketType OBJECT-TYPE
        SYNTAX            INTEGER {
                            valA(0),
                            valB(1)
                            }
        MAX-ACCESS        read-write
        STATUS            current
        DESCRIPTION
                "CMNT: - 
                 TYPE: - RadiobuttonList
                 PAGE: - Dolby
                    Packet Type  cmdID= 10088
                    A  value= 0
                    B  value= 1  "
        ::= { kudosFrameCtrlEntries 10088 }


    i0DolbyCh2SMPTE2020OutputOutputLine OBJECT-TYPE
        SYNTAX            INTEGER
        MAX-ACCESS        read-write
        STATUS            current
        DESCRIPTION
                "CMNT: - 
                 TYPE: - Number
                 PAGE: - Dolby Ch 2
                    Output Line  cmdID= 10173
                    min= 8  max= 20  step= 1  format= %0.0f  div_scale= 1  preset= 10
                    Min = 8  Max = 20  Step = 1  Preset = 10  "
        ::= { kudosFrameCtrlEntries 10173 }


    i0DolbyCh2SMPTE2020OutputOutputEnable OBJECT-TYPE
        SYNTAX            INTEGER { disable(0), enable(1)  }
        MAX-ACCESS        read-write
        STATUS            current
        DESCRIPTION
                "CMNT: - 
                 TYPE: - Checkbox
                 PAGE: - Dolby Ch 2
                    Output Enable  cmdID= 10172  "
        ::= { kudosFrameCtrlEntries 10172 }


    i0DolbyCh2InputStatus OBJECT-TYPE
        SYNTAX            RollCallString
        MAX-ACCESS        read-only
        STATUS            current
        DESCRIPTION
                "CMNT: - 
                 TYPE: - Display
                 PAGE: - Dolby
                    Input Status  cmdID= 10090  "
        ::= { kudosFrameCtrlEntries 10090 }


    i0DolbyCh2DecoderRate OBJECT-TYPE
        SYNTAX            RollCallString
        MAX-ACCESS        read-only
        STATUS            current
        DESCRIPTION
                "CMNT: - 
                 TYPE: - Display
                 PAGE: - Dolby
                    Decoder Rate  cmdID= 10092  "
        ::= { kudosFrameCtrlEntries 10092 }


    i0DolbyCh2DecoderFormat OBJECT-TYPE
        SYNTAX            RollCallString
        MAX-ACCESS        read-only
        STATUS            current
        DESCRIPTION
                "CMNT: - 
                 TYPE: - Display
                 PAGE: - Dolby
                    Decoder Format  cmdID= 10091  "
        ::= { kudosFrameCtrlEntries 10091 }


    i0DolbyCh2DecoderVersion OBJECT-TYPE
        SYNTAX            RollCallString
        MAX-ACCESS        read-only
        STATUS            current
        DESCRIPTION
                "CMNT: - 
                 TYPE: - Display
                 PAGE: - Dolby
                    Decoder Version  cmdID= 10093  "
        ::= { kudosFrameCtrlEntries 10093 }


    i0DolbyCh2EncoderVersion OBJECT-TYPE
        SYNTAX            RollCallString
        MAX-ACCESS        read-only
        STATUS            current
        DESCRIPTION
                "CMNT: - 
                 TYPE: - Display
                 PAGE: - Dolby
                    Encoder Version  cmdID= 10096  "
        ::= { kudosFrameCtrlEntries 10096 }


    i0DolbyCh2DolbyMetadataOutputLineStatus OBJECT-TYPE
        SYNTAX            RollCallString
        MAX-ACCESS        read-only
        STATUS            current
        DESCRIPTION
                "CMNT: - 
                 TYPE: - Display
                 PAGE: - Dolby
                    Dolby Metadata Output Line Status  cmdID= 10181  "
        ::= { kudosFrameCtrlEntries 10181 }


    i0NetworkEthernetCurrentIPAddress OBJECT-TYPE
        SYNTAX            RollCallString
        MAX-ACCESS        read-only
        STATUS            current
        DESCRIPTION
                "CMNT: - 
                 TYPE: - Display
                 PAGE: - Network
                    Current IP Address  cmdID= 10105  "
        ::= { kudosFrameCtrlEntries 10105 }


    i0NetworkEthernetCurrentIPNetmask OBJECT-TYPE
        SYNTAX            RollCallString
        MAX-ACCESS        read-only
        STATUS            current
        DESCRIPTION
                "CMNT: - 
                 TYPE: - Display
                 PAGE: - Network
                    Current IP Netmask  cmdID= 10107  "
        ::= { kudosFrameCtrlEntries 10107 }


    i0NetworkEthernetCurrentIPGateway OBJECT-TYPE
        SYNTAX            RollCallString
        MAX-ACCESS        read-only
        STATUS            current
        DESCRIPTION
                "CMNT: - 
                 TYPE: - Display
                 PAGE: - Network
                    Current IP Gateway  cmdID= 10106  "
        ::= { kudosFrameCtrlEntries 10106 }


    i0NetworkEthernetMACAddress OBJECT-TYPE
        SYNTAX            RollCallString
        MAX-ACCESS        read-only
        STATUS            current
        DESCRIPTION
                "CMNT: - 
                 TYPE: - Display
                 PAGE: - Network
                    MAC Address  cmdID= 10108  "
        ::= { kudosFrameCtrlEntries 10108 }


    i0NetworkEthernetIPConfiguration OBJECT-TYPE
        SYNTAX            INTEGER {
                            valFixedAddress(0),
                            valDHCP(1)
                            }
        MAX-ACCESS        read-write
        STATUS            current
        DESCRIPTION
                "CMNT: - 
                 TYPE: - RadiobuttonList
                 PAGE: - Network
                    IP Configuration  cmdID= 10100
                    Fixed Address  value= 0
                    DHCP  value= 1  "
        ::= { kudosFrameCtrlEntries 10100 }


    i0NetworkEthernetIPAddress OBJECT-TYPE
        SYNTAX            RollCallString
        MAX-ACCESS        read-write
        STATUS            current
        DESCRIPTION
                "CMNT: - 
                 TYPE: - Editstring
                 PAGE: - Network
                    IP Address  cmdID= 10101
                    preset= 192.168.151.1"
        ::= { kudosFrameCtrlEntries 10101 }


    i0NetworkEthernetIPGateway OBJECT-TYPE
        SYNTAX            RollCallString
        MAX-ACCESS        read-write
        STATUS            current
        DESCRIPTION
                "CMNT: - 
                 TYPE: - Editstring
                 PAGE: - Network
                    IP Gateway  cmdID= 10102
                    preset= 192.168.151.200"
        ::= { kudosFrameCtrlEntries 10102 }


    i0NetworkEthernetIPNetmask OBJECT-TYPE
        SYNTAX            RollCallString
        MAX-ACCESS        read-write
        STATUS            current
        DESCRIPTION
                "CMNT: - 
                 TYPE: - Editstring
                 PAGE: - Network
                    IP Netmask  cmdID= 10103
                    preset= 255.255.255.0"
        ::= { kudosFrameCtrlEntries 10103 }


    i0NetworkEthernetApplyIPChanges OBJECT-TYPE
        SYNTAX            INTEGER { noAction(0),valApplyIPChanges(1) }
        MAX-ACCESS        read-write
        STATUS            current
        DESCRIPTION
                "CMNT: - 
                 TYPE: - Button
                 PAGE: - Network
                    Apply IP Changes  cmdID= 10104
                    value= 1  "
        ::= { kudosFrameCtrlEntries 10104 }


    i0NetworkEthernetIPConfigurationStatus OBJECT-TYPE
        SYNTAX            RollCallString
        MAX-ACCESS        read-only
        STATUS            current
        DESCRIPTION
                "CMNT: - 
                 TYPE: - Display
                 PAGE: - Network
                    IP Configuration Status  cmdID= 10171  "
        ::= { kudosFrameCtrlEntries 10171 }


    i0NetworkEthernetInterfaceStatus OBJECT-TYPE
        SYNTAX            RollCallString
        MAX-ACCESS        read-only
        STATUS            current
        DESCRIPTION
                "CMNT: - 
                 TYPE: - Display
                 PAGE: - Network
                    Interface Status  cmdID= 10109  "
        ::= { kudosFrameCtrlEntries 10109 }


    i0NetworkRollCallUnitName OBJECT-TYPE
        SYNTAX            RollCallString
        MAX-ACCESS        read-write
        STATUS            current
        DESCRIPTION
                "CMNT: - 
                 TYPE: - Editstring
                 PAGE: - Network
                    Unit Name  cmdID= 10110
                    preset= IQP"
        ::= { kudosFrameCtrlEntries 10110 }


    i0NetworkRollCallLogServerName OBJECT-TYPE
        SYNTAX            RollCallString
        MAX-ACCESS        read-write
        STATUS            current
        DESCRIPTION
                "CMNT: - 
                 TYPE: - Editstring
                 PAGE: - Network
                    Log Server Name  cmdID= 10111
                    preset= "
        ::= { kudosFrameCtrlEntries 10111 }


    i0NetworkRollCallServerName OBJECT-TYPE
        SYNTAX            RollCallString
        MAX-ACCESS        read-only
        STATUS            current
        DESCRIPTION
                "CMNT: - 
                 TYPE: - Display
                 PAGE: - Network
                    Server Name  cmdID= 10112  "
        ::= { kudosFrameCtrlEntries 10112 }


    i0NetworkRollCallServerAddress OBJECT-TYPE
        SYNTAX            RollCallString
        MAX-ACCESS        read-only
        STATUS            current
        DESCRIPTION
                "CMNT: - 
                 TYPE: - Display
                 PAGE: - Network
                    Server Address  cmdID= 10113  "
        ::= { kudosFrameCtrlEntries 10113 }


    i0NetworkRollCallIPSharePort OBJECT-TYPE
        SYNTAX            INTEGER
        MAX-ACCESS        read-write
        STATUS            current
        DESCRIPTION
                "CMNT: - 
                 TYPE: - Number
                 PAGE: - Network
                    IP Share Port  cmdID= 10114
                    min= 1024  max= 65535  step= 1  format= %d  div_scale= 1  preset= 2050
                    Min = 1024  Max = 65535  Step = 1  Preset = 2050  "
        ::= { kudosFrameCtrlEntries 10114 }


    i0NetworkRollCallIPBridgingPort OBJECT-TYPE
        SYNTAX            INTEGER
        MAX-ACCESS        read-write
        STATUS            current
        DESCRIPTION
                "CMNT: - 
                 TYPE: - Number
                 PAGE: - Network
                    IP Bridging Port  cmdID= 10115
                    min= 1024  max= 65535  step= 1  format= %d  div_scale= 1  preset= 2600
                    Min = 1024  Max = 65535  Step = 1  Preset = 2600  "
        ::= { kudosFrameCtrlEntries 10115 }


    i0FrontPanelForceSingleScreen OBJECT-TYPE
        SYNTAX            INTEGER {
                            valOff(0),
                            valOn(1)
                            }
        MAX-ACCESS        read-write
        STATUS            current
        DESCRIPTION
                "CMNT: - 
                 TYPE: - RadiobuttonList
                 PAGE: - Front Panel
                    Force Single Screen  cmdID= 10116
                    Off  value= 0
                    On  value= 1  "
        ::= { kudosFrameCtrlEntries 10116 }


    i0FrontPanelLockFrontPanel OBJECT-TYPE
        SYNTAX            INTEGER {
                            valNormal(0),
                            valLocked(1)
                            }
        MAX-ACCESS        read-write
        STATUS            current
        DESCRIPTION
                "CMNT: - 
                 TYPE: - RadiobuttonList
                 PAGE: - Front Panel
                    Lock Front Panel  cmdID= 10002
                    Normal  value= 0
                    Locked  value= 1  "
        ::= { kudosFrameCtrlEntries 10002 }


    i0FrontPanelCurrentChannel OBJECT-TYPE
        SYNTAX            INTEGER {
                            valCh1(0),
                            valCh2(1),
                            valCh3(2),
                            valCh4(3)
                            }
        MAX-ACCESS        read-write
        STATUS            current
        DESCRIPTION
                "CMNT: - 
                 TYPE: - RadiobuttonList
                 PAGE: - Front Panel
                    Current Channel  cmdID= 10001
                    Ch 1  value= 0
                    Ch 2  value= 1
                    Ch 3  value= 2
                    Ch 4  value= 3  "
        ::= { kudosFrameCtrlEntries 10001 }


    i0FrontPanelBrightness OBJECT-TYPE
        SYNTAX            INTEGER
        MAX-ACCESS        read-write
        STATUS            current
        DESCRIPTION
                "CMNT: - 
                 TYPE: - Number
                 PAGE: - Front Panel
                    Brightness  cmdID= 10003
                    min= 1  max= 63  step= 1  format= %d  div_scale= 1  preset= 48
                    Min = 1  Max = 63  Step = 1  Preset = 48  "
        ::= { kudosFrameCtrlEntries 10003 }


    i0FrontPanelHeadphonesSource OBJECT-TYPE
        SYNTAX            INTEGER {
                            valCh1Pair1(0),
                            valCh1Pair2(1),
                            valCh1Pair3(2),
                            valCh1Pair4(3),
                            valCh1Pair5(4),
                            valCh1Pair6(5),
                            valCh1Pair7(6),
                            valCh1Pair8(7),
                            valCh2Pair1(8),
                            valCh2Pair2(9),
                            valCh2Pair3(10),
                            valCh2Pair4(11),
                            valCh2Pair5(12),
                            valCh2Pair6(13),
                            valCh2Pair7(14),
                            valCh2Pair8(15),
                            valCh3Pair1(16),
                            valCh3Pair2(17),
                            valCh3Pair3(18),
                            valCh3Pair4(19),
                            valCh3Pair5(20),
                            valCh3Pair6(21),
                            valCh3Pair7(22),
                            valCh3Pair8(23),
                            valCh4Pair1(24),
                            valCh4Pair2(25),
                            valCh4Pair3(26),
                            valCh4Pair4(27),
                            valCh4Pair5(28),
                            valCh4Pair6(29),
                            valCh4Pair7(30),
                            valCh4Pair8(31)
                            }
        MAX-ACCESS        read-write
        STATUS            current
        DESCRIPTION
                "CMNT: - 
                 TYPE: - RadiobuttonList
                 PAGE: - Front Panel
                    Source  cmdID= 10097
                    Ch 1 Pair 1  value= 0
                    Ch 1 Pair 2  value= 1
                    Ch 1 Pair 3  value= 2
                    Ch 1 Pair 4  value= 3
                    Ch 1 Pair 5  value= 4
                    Ch 1 Pair 6  value= 5
                    Ch 1 Pair 7  value= 6
                    Ch 1 Pair 8  value= 7
                    Ch 2 Pair 1  value= 8
                    Ch 2 Pair 2  value= 9
                    Ch 2 Pair 3  value= 10
                    Ch 2 Pair 4  value= 11
                    Ch 2 Pair 5  value= 12
                    Ch 2 Pair 6  value= 13
                    Ch 2 Pair 7  value= 14
                    Ch 2 Pair 8  value= 15
                    Ch 3 Pair 1  value= 16
                    Ch 3 Pair 2  value= 17
                    Ch 3 Pair 3  value= 18
                    Ch 3 Pair 4  value= 19
                    Ch 3 Pair 5  value= 20
                    Ch 3 Pair 6  value= 21
                    Ch 3 Pair 7  value= 22
                    Ch 3 Pair 8  value= 23
                    Ch 4 Pair 1  value= 24
                    Ch 4 Pair 2  value= 25
                    Ch 4 Pair 3  value= 26
                    Ch 4 Pair 4  value= 27
                    Ch 4 Pair 5  value= 28
                    Ch 4 Pair 6  value= 29
                    Ch 4 Pair 7  value= 30
                    Ch 4 Pair 8  value= 31  "
        ::= { kudosFrameCtrlEntries 10097 }


    i0FrontPanelHeadphonesLevel OBJECT-TYPE
        SYNTAX            INTEGER
        MAX-ACCESS        read-write
        STATUS            current
        DESCRIPTION
                "CMNT: - 
                 TYPE: - Number
                 PAGE: - Front Panel
                    Level  cmdID= 10098
                    min= -140  max= 12  step= 1  format= %d  div_scale= 1  preset= -36
                    Min = -140  Max = 12  Step = 1  Preset = -36  "
        ::= { kudosFrameCtrlEntries 10098 }


    i0FrontPanelHeadphonesStatus OBJECT-TYPE
        SYNTAX            RollCallString
        MAX-ACCESS        read-only
        STATUS            current
        DESCRIPTION
                "CMNT: - 
                 TYPE: - Display
                 PAGE: - Front Panel
                    Status  cmdID= 10004  "
        ::= { kudosFrameCtrlEntries 10004 }


    i0MemoriesMemorySelect OBJECT-TYPE
        SYNTAX            INTEGER {
                            valMemory1(1),
                            valMemory2(2),
                            valMemory3(3),
                            valMemory4(4),
                            valMemory5(5),
                            valMemory6(6),
                            valMemory7(7),
                            valMemory8(8)
                            }
        MAX-ACCESS        read-write
        STATUS            current
        DESCRIPTION
                "CMNT: - 
                 TYPE: - RadiobuttonList
                 PAGE: - Memories
                    Memory Select  cmdID= 10117
                    Memory 1  value= 1
                    Memory 2  value= 2
                    Memory 3  value= 3
                    Memory 4  value= 4
                    Memory 5  value= 5
                    Memory 6  value= 6
                    Memory 7  value= 7
                    Memory 8  value= 8  "
        ::= { kudosFrameCtrlEntries 10117 }


    i0MemoriesSaveMemory OBJECT-TYPE
        SYNTAX            INTEGER { noAction(0),valSaveMemory(1) }
        MAX-ACCESS        read-write
        STATUS            current
        DESCRIPTION
                "CMNT: - 
                 TYPE: - Button
                 PAGE: - Memories
                    Save Memory  cmdID= 10118
                    value= 1  "
        ::= { kudosFrameCtrlEntries 10118 }


    i0MemoriesRecallMemory OBJECT-TYPE
        SYNTAX            INTEGER { noAction(0),valRecallMemory(1) }
        MAX-ACCESS        read-write
        STATUS            current
        DESCRIPTION
                "CMNT: - 
                 TYPE: - Button
                 PAGE: - Memories
                    Recall Memory  cmdID= 10119
                    value= 1  "
        ::= { kudosFrameCtrlEntries 10119 }


    i0MemoriesResettoDefaults OBJECT-TYPE
        SYNTAX            INTEGER { noAction(0),valResettoDefaults(1) }
        MAX-ACCESS        read-write
        STATUS            current
        DESCRIPTION
                "CMNT: - 
                 TYPE: - Button
                 PAGE: - Memories
                    Reset to Defaults  cmdID= 10121
                    value= 1  "
        ::= { kudosFrameCtrlEntries 10121 }


    i0MemoriesFactoryReset OBJECT-TYPE
        SYNTAX            INTEGER { noAction(0),valFactoryReset(1) }
        MAX-ACCESS        read-write
        STATUS            current
        DESCRIPTION
                "CMNT: - 
                 TYPE: - Button
                 PAGE: - Memories
                    Factory Reset  cmdID= 10000
                    value= 1  "
        ::= { kudosFrameCtrlEntries 10000 }


    i0MemoriesMemoryNameChangeName OBJECT-TYPE
        SYNTAX            RollCallString
        MAX-ACCESS        read-write
        STATUS            current
        DESCRIPTION
                "CMNT: - 
                 TYPE: - Editstring
                 PAGE: - Memories
                    Change Name  cmdID= 10120
                    preset= "
        ::= { kudosFrameCtrlEntries 10120 }


    i0LoggingSerialNoEnable OBJECT-TYPE
        SYNTAX            INTEGER { disable(0), enable(1)  }
        MAX-ACCESS        read-write
        STATUS            current
        DESCRIPTION
                "CMNT: - 
                 TYPE: - Checkbox
                 PAGE: - Logging
                    Serial No. Enable  cmdID= 10122  "
        ::= { kudosFrameCtrlEntries 10122 }


    i0LoggingUptimeEnable OBJECT-TYPE
        SYNTAX            INTEGER { disable(0), enable(1)  }
        MAX-ACCESS        read-write
        STATUS            current
        DESCRIPTION
                "CMNT: - 
                 TYPE: - Checkbox
                 PAGE: - Logging
                    Uptime Enable  cmdID= 10124  "
        ::= { kudosFrameCtrlEntries 10124 }


    i0LoggingPSU1StateEnable OBJECT-TYPE
        SYNTAX            INTEGER { disable(0), enable(1)  }
        MAX-ACCESS        read-write
        STATUS            current
        DESCRIPTION
                "CMNT: - 
                 TYPE: - Checkbox
                 PAGE: - Logging
                    PSU 1 State Enable  cmdID= 10126  "
        ::= { kudosFrameCtrlEntries 10126 }


    i0LoggingPSU2StateEnable OBJECT-TYPE
        SYNTAX            INTEGER { disable(0), enable(1)  }
        MAX-ACCESS        read-write
        STATUS            current
        DESCRIPTION
                "CMNT: - 
                 TYPE: - Checkbox
                 PAGE: - Logging
                    PSU 2 State Enable  cmdID= 10128  "
        ::= { kudosFrameCtrlEntries 10128 }


    i0LoggingReferenceStandardEnable OBJECT-TYPE
        SYNTAX            INTEGER { disable(0), enable(1)  }
        MAX-ACCESS        read-write
        STATUS            current
        DESCRIPTION
                "CMNT: - 
                 TYPE: - Checkbox
                 PAGE: - Logging
                    Reference Standard Enable  cmdID= 10130  "
        ::= { kudosFrameCtrlEntries 10130 }


    i0LoggingGenlockCh1Enable OBJECT-TYPE
        SYNTAX            INTEGER { disable(0), enable(1)  }
        MAX-ACCESS        read-write
        STATUS            current
        DESCRIPTION
                "CMNT: - 
                 TYPE: - Checkbox
                 PAGE: - Logging
                    Genlock Ch 1 Enable  cmdID= 10210  "
        ::= { kudosFrameCtrlEntries 10210 }


    i0LoggingGenlockCh2Enable OBJECT-TYPE
        SYNTAX            INTEGER { disable(0), enable(1)  }
        MAX-ACCESS        read-write
        STATUS            current
        DESCRIPTION
                "CMNT: - 
                 TYPE: - Checkbox
                 PAGE: - Logging
                    Genlock Ch 2 Enable  cmdID= 10212  "
        ::= { kudosFrameCtrlEntries 10212 }


    i0LoggingGenlockCh3Enable OBJECT-TYPE
        SYNTAX            INTEGER { disable(0), enable(1)  }
        MAX-ACCESS        read-write
        STATUS            current
        DESCRIPTION
                "CMNT: - 
                 TYPE: - Checkbox
                 PAGE: - Logging
                    Genlock Ch 3 Enable  cmdID= 10214  "
        ::= { kudosFrameCtrlEntries 10214 }


    i0LoggingGenlockCh4Enable OBJECT-TYPE
        SYNTAX            INTEGER { disable(0), enable(1)  }
        MAX-ACCESS        read-write
        STATUS            current
        DESCRIPTION
                "CMNT: - 
                 TYPE: - Checkbox
                 PAGE: - Logging
                    Genlock Ch 4 Enable  cmdID= 10216  "
        ::= { kudosFrameCtrlEntries 10216 }


    i0StatusSoftwareVersion OBJECT-TYPE
        SYNTAX            RollCallString
        MAX-ACCESS        read-only
        STATUS            current
        DESCRIPTION
                "CMNT: - 
                 TYPE: - Display
                 PAGE: - Status
                    Software Version  cmdID= 10133  "
        ::= { kudosFrameCtrlEntries 10133 }


    i0StatusSerialNumber OBJECT-TYPE
        SYNTAX            RollCallString
        MAX-ACCESS        read-only
        STATUS            current
        DESCRIPTION
                "CMNT: - 
                 TYPE: - Display
                 PAGE: - Status
                    Serial Number  cmdID= 10132  "
        ::= { kudosFrameCtrlEntries 10132 }


    i0StatusPSUA OBJECT-TYPE
        SYNTAX            RollCallString
        MAX-ACCESS        read-only
        STATUS            current
        DESCRIPTION
                "CMNT: - 
                 TYPE: - Display
                 PAGE: - Status
                    PSU A  cmdID= 10134  "
        ::= { kudosFrameCtrlEntries 10134 }


    i0StatusPSUB OBJECT-TYPE
        SYNTAX            RollCallString
        MAX-ACCESS        read-only
        STATUS            current
        DESCRIPTION
                "CMNT: - 
                 TYPE: - Display
                 PAGE: - Status
                    PSU B  cmdID= 10135  "
        ::= { kudosFrameCtrlEntries 10135 }


    i0StatusModule1Temperature OBJECT-TYPE
        SYNTAX            RollCallString
        MAX-ACCESS        read-only
        STATUS            current
        DESCRIPTION
                "CMNT: - 
                 TYPE: - Display
                 PAGE: - Status
                    Module 1 Temperature  cmdID= 10136  "
        ::= { kudosFrameCtrlEntries 10136 }


    i0StatusModule2Temperature OBJECT-TYPE
        SYNTAX            RollCallString
        MAX-ACCESS        read-only
        STATUS            current
        DESCRIPTION
                "CMNT: - 
                 TYPE: - Display
                 PAGE: - Status
                    Module 2 Temperature  cmdID= 10137  "
        ::= { kudosFrameCtrlEntries 10137 }


    i0StatusDolbyCh1 OBJECT-TYPE
        SYNTAX            RollCallString
        MAX-ACCESS        read-only
        STATUS            current
        DESCRIPTION
                "CMNT: - 
                 TYPE: - Display
                 PAGE: - Status
                    Dolby Ch 1  cmdID= 10176  "
        ::= { kudosFrameCtrlEntries 10176 }


    i0StatusDolbyCh2 OBJECT-TYPE
        SYNTAX            RollCallString
        MAX-ACCESS        read-only
        STATUS            current
        DESCRIPTION
                "CMNT: - 
                 TYPE: - Display
                 PAGE: - Status
                    Dolby Ch 2  cmdID= 10177  "
        ::= { kudosFrameCtrlEntries 10177 }


    i0CVBSCalibrationCVBSDecoderALumaGain OBJECT-TYPE
        SYNTAX            INTEGER
        MAX-ACCESS        read-write
        STATUS            current
        DESCRIPTION
                "CMNT: - 
                 TYPE: - Number
                 PAGE: - CVBS Calibration
                    Luma Gain  cmdID= 10138
                    min= 0  max= 2047  step= 1  format= %d  div_scale= 1  preset= 1014
                    Min = 0  Max = 2047  Step = 1  Preset = 1014  "
        ::= { kudosFrameCtrlEntries 10138 }


    i0CVBSCalibrationCVBSDecoderAChromaGain OBJECT-TYPE
        SYNTAX            INTEGER
        MAX-ACCESS        read-write
        STATUS            current
        DESCRIPTION
                "CMNT: - 
                 TYPE: - Number
                 PAGE: - CVBS Calibration
                    Chroma Gain  cmdID= 10139
                    min= 0  max= 2047  step= 1  format= %d  div_scale= 1  preset= 1095
                    Min = 0  Max = 2047  Step = 1  Preset = 1095  "
        ::= { kudosFrameCtrlEntries 10139 }


    i0CVBSCalibrationCVBSDecoderAYCChromaGain OBJECT-TYPE
        SYNTAX            INTEGER
        MAX-ACCESS        read-write
        STATUS            current
        DESCRIPTION
                "CMNT: - 
                 TYPE: - Number
                 PAGE: - CVBS Calibration
                    Y/C Chroma Gain  cmdID= 10140
                    min= 0  max= 2047  step= 1  format= %d  div_scale= 1  preset= 1041
                    Min = 0  Max = 2047  Step = 1  Preset = 1041  "
        ::= { kudosFrameCtrlEntries 10140 }


    i0CVBSCalibrationCVBSDecoderASaveDecoder OBJECT-TYPE
        SYNTAX            INTEGER { noAction(0),valSaveDecoder(1) }
        MAX-ACCESS        read-write
        STATUS            current
        DESCRIPTION
                "CMNT: - 
                 TYPE: - Button
                 PAGE: - CVBS Calibration
                    Save Decoder  cmdID= 10141
                    value= 1  "
        ::= { kudosFrameCtrlEntries 10141 }


    i0CVBSCalibrationCVBSEncoderADACGain OBJECT-TYPE
        SYNTAX            INTEGER
        MAX-ACCESS        read-write
        STATUS            current
        DESCRIPTION
                "CMNT: - 
                 TYPE: - Number
                 PAGE: - CVBS Calibration
                    DAC Gain  cmdID= 10142
                    min= -64  max= 64  step= 1  format= %d  div_scale= 1  preset= 0
                    Min = -64  Max = 64  Step = 1  Preset = 0  "
        ::= { kudosFrameCtrlEntries 10142 }


    i0CVBSCalibrationCVBSEncoderASaveEncoder OBJECT-TYPE
        SYNTAX            INTEGER { noAction(0),valSaveEncoder(1) }
        MAX-ACCESS        read-write
        STATUS            current
        DESCRIPTION
                "CMNT: - 
                 TYPE: - Button
                 PAGE: - CVBS Calibration
                    Save Encoder  cmdID= 10143
                    value= 1  "
        ::= { kudosFrameCtrlEntries 10143 }


    i0CVBSCalibrationCVBSDecoderBLumaGain OBJECT-TYPE
        SYNTAX            INTEGER
        MAX-ACCESS        read-write
        STATUS            current
        DESCRIPTION
                "CMNT: - 
                 TYPE: - Number
                 PAGE: - CVBS Calibration
                    Luma Gain  cmdID= 10144
                    min= 0  max= 2047  step= 1  format= %d  div_scale= 1  preset= 1014
                    Min = 0  Max = 2047  Step = 1  Preset = 1014  "
        ::= { kudosFrameCtrlEntries 10144 }


    i0CVBSCalibrationCVBSDecoderBChromaGain OBJECT-TYPE
        SYNTAX            INTEGER
        MAX-ACCESS        read-write
        STATUS            current
        DESCRIPTION
                "CMNT: - 
                 TYPE: - Number
                 PAGE: - CVBS Calibration
                    Chroma Gain  cmdID= 10145
                    min= 0  max= 2047  step= 1  format= %d  div_scale= 1  preset= 1095
                    Min = 0  Max = 2047  Step = 1  Preset = 1095  "
        ::= { kudosFrameCtrlEntries 10145 }


    i0CVBSCalibrationCVBSDecoderBYCChromaGain OBJECT-TYPE
        SYNTAX            INTEGER
        MAX-ACCESS        read-write
        STATUS            current
        DESCRIPTION
                "CMNT: - 
                 TYPE: - Number
                 PAGE: - CVBS Calibration
                    Y/C Chroma Gain  cmdID= 10146
                    min= 0  max= 2047  step= 1  format= %d  div_scale= 1  preset= 1041
                    Min = 0  Max = 2047  Step = 1  Preset = 1041  "
        ::= { kudosFrameCtrlEntries 10146 }


    i0CVBSCalibrationCVBSDecoderBSaveDecoder OBJECT-TYPE
        SYNTAX            INTEGER { noAction(0),valSaveDecoder(1) }
        MAX-ACCESS        read-write
        STATUS            current
        DESCRIPTION
                "CMNT: - 
                 TYPE: - Button
                 PAGE: - CVBS Calibration
                    Save Decoder  cmdID= 10147
                    value= 1  "
        ::= { kudosFrameCtrlEntries 10147 }


    i0CVBSCalibrationCVBSEncoderBDACGain OBJECT-TYPE
        SYNTAX            INTEGER
        MAX-ACCESS        read-write
        STATUS            current
        DESCRIPTION
                "CMNT: - 
                 TYPE: - Number
                 PAGE: - CVBS Calibration
                    DAC Gain  cmdID= 10148
                    min= -64  max= 64  step= 1  format= %d  div_scale= 1  preset= 0
                    Min = -64  Max = 64  Step = 1  Preset = 0  "
        ::= { kudosFrameCtrlEntries 10148 }


    i0CVBSCalibrationCVBSEncoderBSaveEncoder OBJECT-TYPE
        SYNTAX            INTEGER { noAction(0),valSaveEncoder(1) }
        MAX-ACCESS        read-write
        STATUS            current
        DESCRIPTION
                "CMNT: - 
                 TYPE: - Button
                 PAGE: - CVBS Calibration
                    Save Encoder  cmdID= 10149
                    value= 1  "
        ::= { kudosFrameCtrlEntries 10149 }


    i0CVBSCalibrationCVBSDecoderCLumaGain OBJECT-TYPE
        SYNTAX            INTEGER
        MAX-ACCESS        read-write
        STATUS            current
        DESCRIPTION
                "CMNT: - 
                 TYPE: - Number
                 PAGE: - CVBS Calibration
                    Luma Gain  cmdID= 10150
                    min= 0  max= 2047  step= 1  format= %d  div_scale= 1  preset= 1014
                    Min = 0  Max = 2047  Step = 1  Preset = 1014  "
        ::= { kudosFrameCtrlEntries 10150 }


    i0CVBSCalibrationCVBSDecoderCChromaGain OBJECT-TYPE
        SYNTAX            INTEGER
        MAX-ACCESS        read-write
        STATUS            current
        DESCRIPTION
                "CMNT: - 
                 TYPE: - Number
                 PAGE: - CVBS Calibration
                    Chroma Gain  cmdID= 10151
                    min= 0  max= 2047  step= 1  format= %d  div_scale= 1  preset= 1095
                    Min = 0  Max = 2047  Step = 1  Preset = 1095  "
        ::= { kudosFrameCtrlEntries 10151 }


    i0CVBSCalibrationCVBSDecoderCYCChromaGain OBJECT-TYPE
        SYNTAX            INTEGER
        MAX-ACCESS        read-write
        STATUS            current
        DESCRIPTION
                "CMNT: - 
                 TYPE: - Number
                 PAGE: - CVBS Calibration
                    Y/C Chroma Gain  cmdID= 10152
                    min= 0  max= 2047  step= 1  format= %d  div_scale= 1  preset= 1041
                    Min = 0  Max = 2047  Step = 1  Preset = 1041  "
        ::= { kudosFrameCtrlEntries 10152 }


    i0CVBSCalibrationCVBSDecoderCSaveDecoder OBJECT-TYPE
        SYNTAX            INTEGER { noAction(0),valSaveDecoder(1) }
        MAX-ACCESS        read-write
        STATUS            current
        DESCRIPTION
                "CMNT: - 
                 TYPE: - Button
                 PAGE: - CVBS Calibration
                    Save Decoder  cmdID= 10153
                    value= 1  "
        ::= { kudosFrameCtrlEntries 10153 }


    i0CVBSCalibrationCVBSEncoderCDACGain OBJECT-TYPE
        SYNTAX            INTEGER
        MAX-ACCESS        read-write
        STATUS            current
        DESCRIPTION
                "CMNT: - 
                 TYPE: - Number
                 PAGE: - CVBS Calibration
                    DAC Gain  cmdID= 10154
                    min= -64  max= 64  step= 1  format= %d  div_scale= 1  preset= 0
                    Min = -64  Max = 64  Step = 1  Preset = 0  "
        ::= { kudosFrameCtrlEntries 10154 }


    i0CVBSCalibrationCVBSEncoderCSaveEncoder OBJECT-TYPE
        SYNTAX            INTEGER { noAction(0),valSaveEncoder(1) }
        MAX-ACCESS        read-write
        STATUS            current
        DESCRIPTION
                "CMNT: - 
                 TYPE: - Button
                 PAGE: - CVBS Calibration
                    Save Encoder  cmdID= 10155
                    value= 1  "
        ::= { kudosFrameCtrlEntries 10155 }


    i0CVBSCalibrationCVBSDecoderDLumaGain OBJECT-TYPE
        SYNTAX            INTEGER
        MAX-ACCESS        read-write
        STATUS            current
        DESCRIPTION
                "CMNT: - 
                 TYPE: - Number
                 PAGE: - CVBS Calibration
                    Luma Gain  cmdID= 10156
                    min= 0  max= 2047  step= 1  format= %d  div_scale= 1  preset= 1014
                    Min = 0  Max = 2047  Step = 1  Preset = 1014  "
        ::= { kudosFrameCtrlEntries 10156 }


    i0CVBSCalibrationCVBSDecoderDChromaGain OBJECT-TYPE
        SYNTAX            INTEGER
        MAX-ACCESS        read-write
        STATUS            current
        DESCRIPTION
                "CMNT: - 
                 TYPE: - Number
                 PAGE: - CVBS Calibration
                    Chroma Gain  cmdID= 10157
                    min= 0  max= 2047  step= 1  format= %d  div_scale= 1  preset= 1095
                    Min = 0  Max = 2047  Step = 1  Preset = 1095  "
        ::= { kudosFrameCtrlEntries 10157 }


    i0CVBSCalibrationCVBSDecoderDYCChromaGain OBJECT-TYPE
        SYNTAX            INTEGER
        MAX-ACCESS        read-write
        STATUS            current
        DESCRIPTION
                "CMNT: - 
                 TYPE: - Number
                 PAGE: - CVBS Calibration
                    Y/C Chroma Gain  cmdID= 10158
                    min= 0  max= 2047  step= 1  format= %d  div_scale= 1  preset= 1041
                    Min = 0  Max = 2047  Step = 1  Preset = 1041  "
        ::= { kudosFrameCtrlEntries 10158 }


    i0CVBSCalibrationCVBSDecoderDSaveDecoder OBJECT-TYPE
        SYNTAX            INTEGER { noAction(0),valSaveDecoder(1) }
        MAX-ACCESS        read-write
        STATUS            current
        DESCRIPTION
                "CMNT: - 
                 TYPE: - Button
                 PAGE: - CVBS Calibration
                    Save Decoder  cmdID= 10159
                    value= 1  "
        ::= { kudosFrameCtrlEntries 10159 }


    i0CVBSCalibrationCVBSEncoderDDACGain OBJECT-TYPE
        SYNTAX            INTEGER
        MAX-ACCESS        read-write
        STATUS            current
        DESCRIPTION
                "CMNT: - 
                 TYPE: - Number
                 PAGE: - CVBS Calibration
                    DAC Gain  cmdID= 10160
                    min= -64  max= 64  step= 1  format= %d  div_scale= 1  preset= 0
                    Min = -64  Max = 64  Step = 1  Preset = 0  "
        ::= { kudosFrameCtrlEntries 10160 }


    i0CVBSCalibrationCVBSEncoderDSaveEncoder OBJECT-TYPE
        SYNTAX            INTEGER { noAction(0),valSaveEncoder(1) }
        MAX-ACCESS        read-write
        STATUS            current
        DESCRIPTION
                "CMNT: - 
                 TYPE: - Button
                 PAGE: - CVBS Calibration
                    Save Encoder  cmdID= 10161
                    value= 1  "
        ::= { kudosFrameCtrlEntries 10161 }
    kudosFrameStatEntries OBJECT IDENTIFIER ::= { kudosIQP 2 }


    i0LoggingSerialNoStatus OBJECT-TYPE
        SYNTAX            RollCallString
        MAX-ACCESS        read-only
        STATUS            current
        DESCRIPTION
                "CMNT: - Serial Number
                 TYPE: - Display
                 PAGE: - Logging
                    Serial No. Status  cmdID= 10123  "
        ::= { kudosFrameStatEntries 10123 }


    i0LoggingUptimeStatus OBJECT-TYPE
        SYNTAX            RollCallString
        MAX-ACCESS        read-only
        STATUS            current
        DESCRIPTION
                "CMNT: - Uptime in ddd:hh:mm:ss
                 TYPE: - Display
                 PAGE: - Logging
                    Uptime Status  cmdID= 10125  "
        ::= { kudosFrameStatEntries 10125 }


    i0LoggingPSU1StateStatus OBJECT-TYPE
        SYNTAX            RollCallString
        MAX-ACCESS        read-only
        STATUS            current
        DESCRIPTION
                "CMNT: - FAIL:Missing or OK:XVdc
                 TYPE: - Display
                 PAGE: - Logging
                    PSU 1 State Status  cmdID= 10127  "
        ::= { kudosFrameStatEntries 10127 }


    i0LoggingPSU2StateStatus OBJECT-TYPE
        SYNTAX            RollCallString
        MAX-ACCESS        read-only
        STATUS            current
        DESCRIPTION
                "CMNT: - FAIL:Missing or OK:XVdc
                 TYPE: - Display
                 PAGE: - Logging
                    PSU 2 State Status  cmdID= 10129  "
        ::= { kudosFrameStatEntries 10129 }


    i0LoggingReferenceStandardStatus OBJECT-TYPE
        SYNTAX            RollCallString
        MAX-ACCESS        read-only
        STATUS            current
        DESCRIPTION
                "CMNT: - WARN: or format type
                 TYPE: - Display
                 PAGE: - Logging
                    Reference Standard Status  cmdID= 10131  "
        ::= { kudosFrameStatEntries 10131 }


    i0LoggingGenlockCh1Status OBJECT-TYPE
        SYNTAX            RollCallString
        MAX-ACCESS        read-only
        STATUS            current
        DESCRIPTION
                "CMNT: - WARN:Free Run , OK:Genlock , OK:Clocklock  , WARN:Lost
                 TYPE: - Display
                 PAGE: - Logging
                    Genlock Ch 1 Status  cmdID= 10211  "
        ::= { kudosFrameStatEntries 10211 }


    i0LoggingGenlockCh2Status OBJECT-TYPE
        SYNTAX            RollCallString
        MAX-ACCESS        read-only
        STATUS            current
        DESCRIPTION
                "CMNT: - WARN:Free Run , OK:Genlock , OK:Clocklock  , WARN:Lost
                 TYPE: - Display
                 PAGE: - Logging
                    Genlock Ch 2 Status  cmdID= 10213  "
        ::= { kudosFrameStatEntries 10213 }


    i0LoggingGenlockCh3Status OBJECT-TYPE
        SYNTAX            RollCallString
        MAX-ACCESS        read-only
        STATUS            current
        DESCRIPTION
                "CMNT: - WARN:Free Run , OK:Genlock , OK:Clocklock  , WARN:Lost
                 TYPE: - Display
                 PAGE: - Logging
                    Genlock Ch 3 Status  cmdID= 10215  "
        ::= { kudosFrameStatEntries 10215 }


    i0LoggingGenlockCh4Status OBJECT-TYPE
        SYNTAX            RollCallString
        MAX-ACCESS        read-only
        STATUS            current
        DESCRIPTION
                "CMNT: - WARN:Free Run , OK:Genlock , OK:Clocklock  , WARN:Lost
                 TYPE: - Display
                 PAGE: - Logging
                    Genlock Ch 4 Status  cmdID= 10217  "
        ::= { kudosFrameStatEntries 10217 }
    kudosFrameConfEntries OBJECT IDENTIFIER ::= { kudosIQP 3 }


    i0SNMPMIB2sysContact OBJECT-TYPE
        SYNTAX            RollCallString
        MAX-ACCESS        read-write
        STATUS            current
        DESCRIPTION
                "CMNT: - 
                 TYPE: - Editstring
                 PAGE: - SNMP
                    MIB2 sysContact  cmdID= 10185
                    preset= www.snellgroup.com"
        ::= { kudosFrameConfEntries 10185 }


    i0SNMPMIB2sysName OBJECT-TYPE
        SYNTAX            RollCallString
        MAX-ACCESS        read-write
        STATUS            current
        DESCRIPTION
                "CMNT: - 
                 TYPE: - Editstring
                 PAGE: - SNMP
                    MIB2 sysName  cmdID= 10186
                    preset= System Name"
        ::= { kudosFrameConfEntries 10186 }


    i0SNMPMIB2sysLocation OBJECT-TYPE
        SYNTAX            RollCallString
        MAX-ACCESS        read-write
        STATUS            current
        DESCRIPTION
                "CMNT: - 
                 TYPE: - Editstring
                 PAGE: - SNMP
                    MIB2 sysLocation  cmdID= 10187
                    preset= Location Name"
        ::= { kudosFrameConfEntries 10187 }


    i0SNMPReadWritePort OBJECT-TYPE
        SYNTAX            RollCallString
        MAX-ACCESS        read-write
        STATUS            current
        DESCRIPTION
                "CMNT: - 
                 TYPE: - Editstring
                 PAGE: - SNMP
                    Read Write Port  cmdID= 10188
                    preset= 161"
        ::= { kudosFrameConfEntries 10188 }


    i0SNMPResendTraps OBJECT-TYPE
        SYNTAX            INTEGER { noAction(0),valResendTraps(1) }
        MAX-ACCESS        read-write
        STATUS            current
        DESCRIPTION
                "CMNT: - 
                 TYPE: - Button
                 PAGE: - SNMP
                    Resend Traps  cmdID= 10207
                    value= 1  "
        ::= { kudosFrameConfEntries 10207 }


    i0SNMPApplySNMPChanges OBJECT-TYPE
        SYNTAX            INTEGER { noAction(0),valApplySNMPChanges(1) }
        MAX-ACCESS        read-write
        STATUS            current
        DESCRIPTION
                "CMNT: - 
                 TYPE: - Button
                 PAGE: - SNMP
                    Apply SNMP Changes  cmdID= 10206
                    value= 1  "
        ::= { kudosFrameConfEntries 10206 }


    i0SNMPControlEnable OBJECT-TYPE
        SYNTAX            INTEGER { disable(0), enable(1)  }
        MAX-ACCESS        read-write
        STATUS            current
        DESCRIPTION
                "CMNT: - 
                 TYPE: - Checkbox
                 PAGE: - SNMP
                    Control Enable  cmdID= 10208  "
        ::= { kudosFrameConfEntries 10208 }


    i0SNMPTrapsEnable OBJECT-TYPE
        SYNTAX            INTEGER { disable(0), enable(1)  }
        MAX-ACCESS        read-write
        STATUS            current
        DESCRIPTION
                "CMNT: - 
                 TYPE: - Checkbox
                 PAGE: - SNMP
                    Traps Enable  cmdID= 10209  "
        ::= { kudosFrameConfEntries 10209 }


    i0SNMPTrapDest1TrapdestIPaddr OBJECT-TYPE
        SYNTAX            RollCallString
        MAX-ACCESS        read-write
        STATUS            current
        DESCRIPTION
                "CMNT: - 
                 TYPE: - Editstring
                 PAGE: - SNMP
                    Trap dest IP addr  cmdID= 10189
                    preset= 0.0.0.0"
        ::= { kudosFrameConfEntries 10189 }


    i0SNMPTrapDest1Trapdestport OBJECT-TYPE
        SYNTAX            RollCallString
        MAX-ACCESS        read-write
        STATUS            current
        DESCRIPTION
                "CMNT: - 
                 TYPE: - Editstring
                 PAGE: - SNMP
                    Trap dest port  cmdID= 10190
                    preset= 162"
        ::= { kudosFrameConfEntries 10190 }


    i0SNMPTrapDest1Trapcommunity OBJECT-TYPE
        SYNTAX            RollCallString
        MAX-ACCESS        read-write
        STATUS            current
        DESCRIPTION
                "CMNT: - 
                 TYPE: - Editstring
                 PAGE: - SNMP
                    Trap community  cmdID= 10191
                    preset= public"
        ::= { kudosFrameConfEntries 10191 }


    i0SNMPTrapDest2TrapdestIPaddr OBJECT-TYPE
        SYNTAX            RollCallString
        MAX-ACCESS        read-write
        STATUS            current
        DESCRIPTION
                "CMNT: - 
                 TYPE: - Editstring
                 PAGE: - SNMP
                    Trap dest IP addr  cmdID= 10192
                    preset= 0.0.0.0"
        ::= { kudosFrameConfEntries 10192 }


    i0SNMPTrapDest2Trapdestport OBJECT-TYPE
        SYNTAX            RollCallString
        MAX-ACCESS        read-write
        STATUS            current
        DESCRIPTION
                "CMNT: - 
                 TYPE: - Editstring
                 PAGE: - SNMP
                    Trap dest port  cmdID= 10193
                    preset= 162"
        ::= { kudosFrameConfEntries 10193 }


    i0SNMPTrapDest2Trapcommunity OBJECT-TYPE
        SYNTAX            RollCallString
        MAX-ACCESS        read-write
        STATUS            current
        DESCRIPTION
                "CMNT: - 
                 TYPE: - Editstring
                 PAGE: - SNMP
                    Trap community  cmdID= 10194
                    preset= public"
        ::= { kudosFrameConfEntries 10194 }


    i0SNMPTrapDest2EnableTrap OBJECT-TYPE
        SYNTAX            INTEGER { disable(0), enable(1)  }
        MAX-ACCESS        read-write
        STATUS            current
        DESCRIPTION
                "CMNT: - 
                 TYPE: - Checkbox
                 PAGE: - SNMP
                    Enable Trap  cmdID= 10195  "
        ::= { kudosFrameConfEntries 10195 }


    i0SNMPTrapDest3TrapdestIPaddr OBJECT-TYPE
        SYNTAX            RollCallString
        MAX-ACCESS        read-write
        STATUS            current
        DESCRIPTION
                "CMNT: - 
                 TYPE: - Editstring
                 PAGE: - SNMP
                    Trap dest IP addr  cmdID= 10196
                    preset= 0.0.0.0"
        ::= { kudosFrameConfEntries 10196 }


    i0SNMPTrapDest3Trapdestport OBJECT-TYPE
        SYNTAX            RollCallString
        MAX-ACCESS        read-write
        STATUS            current
        DESCRIPTION
                "CMNT: - 
                 TYPE: - Editstring
                 PAGE: - SNMP
                    Trap dest port  cmdID= 10197
                    preset= 162"
        ::= { kudosFrameConfEntries 10197 }


    i0SNMPTrapDest3Trapcommunity OBJECT-TYPE
        SYNTAX            RollCallString
        MAX-ACCESS        read-write
        STATUS            current
        DESCRIPTION
                "CMNT: - 
                 TYPE: - Editstring
                 PAGE: - SNMP
                    Trap community  cmdID= 10198
                    preset= public"
        ::= { kudosFrameConfEntries 10198 }


    i0SNMPTrapDest3EnableTrap OBJECT-TYPE
        SYNTAX            INTEGER { disable(0), enable(1)  }
        MAX-ACCESS        read-write
        STATUS            current
        DESCRIPTION
                "CMNT: - 
                 TYPE: - Checkbox
                 PAGE: - SNMP
                    Enable Trap  cmdID= 10199  "
        ::= { kudosFrameConfEntries 10199 }


    i0SNMPTrapDest4TrapdestIPaddr OBJECT-TYPE
        SYNTAX            RollCallString
        MAX-ACCESS        read-write
        STATUS            current
        DESCRIPTION
                "CMNT: - 
                 TYPE: - Editstring
                 PAGE: - SNMP
                    Trap dest IP addr  cmdID= 10200
                    preset= 0.0.0.0"
        ::= { kudosFrameConfEntries 10200 }


    i0SNMPTrapDest4Trapdestport OBJECT-TYPE
        SYNTAX            RollCallString
        MAX-ACCESS        read-write
        STATUS            current
        DESCRIPTION
                "CMNT: - 
                 TYPE: - Editstring
                 PAGE: - SNMP
                    Trap dest port  cmdID= 10201
                    preset= 162"
        ::= { kudosFrameConfEntries 10201 }


    i0SNMPTrapDest4Trapcommunity OBJECT-TYPE
        SYNTAX            RollCallString
        MAX-ACCESS        read-write
        STATUS            current
        DESCRIPTION
                "CMNT: - 
                 TYPE: - Editstring
                 PAGE: - SNMP
                    Trap community  cmdID= 10202
                    preset= public"
        ::= { kudosFrameConfEntries 10202 }


    i0SNMPTrapDest4EnableTrap OBJECT-TYPE
        SYNTAX            INTEGER { disable(0), enable(1)  }
        MAX-ACCESS        read-write
        STATUS            current
        DESCRIPTION
                "CMNT: - 
                 TYPE: - Checkbox
                 PAGE: - SNMP
                    Enable Trap  cmdID= 10203  "
        ::= { kudosFrameConfEntries 10203 }
    kudosConv1NoteEntries OBJECT IDENTIFIER ::= { kudosIQP 4 }


    i1InputIdentStatus NOTIFICATION-TYPE
        OBJECTS            { i1LoggingInputIdentStatus } 
        STATUS            current
        DESCRIPTION
                "CMNT: - Channel Name
                 TYPE: - Display
                 PAGE: - Logging
                    Input Ident Status  cmdID= 5000  "
        ::= { kudosConv1NoteEntries 5000 }


    i1InputStandardStatus NOTIFICATION-TYPE
        OBJECTS            { i1LoggingInputStandardStatus } 
        STATUS            current
        DESCRIPTION
                "CMNT: - WARN: or format
                 TYPE: - Display
                 PAGE: - Logging
                    Input Standard Status  cmdID= 5001  "
        ::= { kudosConv1NoteEntries 5001 }


    i1InputStateStatus NOTIFICATION-TYPE
        OBJECTS            { i1LoggingInputStateStatus } 
        STATUS            current
        DESCRIPTION
                "CMNT: - WARN: or OK
                 TYPE: - Display
                 PAGE: - Logging
                    Input State Status  cmdID= 5002  "
        ::= { kudosConv1NoteEntries 5002 }


    i1OutputStandardStatus NOTIFICATION-TYPE
        OBJECTS            { i1LoggingOutputStandardStatus } 
        STATUS            current
        DESCRIPTION
                "CMNT: - WARN: or format
                 TYPE: - Display
                 PAGE: - Logging
                    Output Standard Status  cmdID= 5003  "
        ::= { kudosConv1NoteEntries 5003 }


    i1OutputIdentStatus NOTIFICATION-TYPE
        OBJECTS            { i1LoggingOutputIdentStatus } 
        STATUS            current
        DESCRIPTION
                "CMNT: - Channel Name
                 TYPE: - Display
                 PAGE: - Logging
                    Output Ident Status  cmdID= 5004  "
        ::= { kudosConv1NoteEntries 5004 }


    i1TimeCodeStatus NOTIFICATION-TYPE
        OBJECTS            { i1LoggingTimeCodeStatus } 
        STATUS            current
        DESCRIPTION
                "CMNT: - LOST or OK
                 TYPE: - Display
                 PAGE: - Logging
                    TimeCode Status  cmdID= 5005  "
        ::= { kudosConv1NoteEntries 5005 }


    i1ClosedCaptionInputStatus NOTIFICATION-TYPE
        OBJECTS            { i1LoggingClosedCaptionInputStatus } 
        STATUS            current
        DESCRIPTION
                "CMNT: - LOST or OK
                 TYPE: - Display
                 PAGE: - Logging
                    Closed Caption Input Status  cmdID= 5006  "
        ::= { kudosConv1NoteEntries 5006 }


    i1WSTOutputLineStatus NOTIFICATION-TYPE
        OBJECTS            { i1LoggingWSTOutputLineStatus } 
        STATUS            current
        DESCRIPTION
                "CMNT: - off or line number
                 TYPE: - Display
                 PAGE: - Logging
                    WST Output Line Status  cmdID= 5007  "
        ::= { kudosConv1NoteEntries 5007 }


    i1RDD08OutputLineStatus NOTIFICATION-TYPE
        OBJECTS            { i1LoggingRDD08OutputLineStatus } 
        STATUS            current
        DESCRIPTION
                "CMNT: - off or line number
                 TYPE: - Display
                 PAGE: - Logging
                    RDD08 Output Line Status  cmdID= 5008  "
        ::= { kudosConv1NoteEntries 5008 }


    i1CEA708OutputLineStatus NOTIFICATION-TYPE
        OBJECTS            { i1LoggingCEA708OutputLineStatus } 
        STATUS            current
        DESCRIPTION
                "CMNT: - off or line number
                 TYPE: - Display
                 PAGE: - Logging
                    CEA-708 Output Line Status  cmdID= 5009  "
        ::= { kudosConv1NoteEntries 5009 }


    i12016OutputLineStatus NOTIFICATION-TYPE
        OBJECTS            { i1Logging2016OutputLineStatus } 
        STATUS            current
        DESCRIPTION
                "CMNT: - off or line number
                 TYPE: - Display
                 PAGE: - Logging
                    2016 Output Line Status  cmdID= 5010  "
        ::= { kudosConv1NoteEntries 5010 }


    i1L23OutputLineStatus NOTIFICATION-TYPE
        OBJECTS            { i1LoggingL23OutputLineStatus } 
        STATUS            current
        DESCRIPTION
                "CMNT: - off or line number
                 TYPE: - Display
                 PAGE: - Logging
                    L23 Output Line Status  cmdID= 5011  "
        ::= { kudosConv1NoteEntries 5011 }


    i1SignallingStatus NOTIFICATION-TYPE
        OBJECTS            { i1LoggingSignallingStatus } 
        STATUS            current
        DESCRIPTION
                "CMNT: - NONE or OK
                 TYPE: - Display
                 PAGE: - Logging
                    Signalling Status  cmdID= 5012  "
        ::= { kudosConv1NoteEntries 5012 }


    i1MSGStatus NOTIFICATION-TYPE
        OBJECTS            { i1LoggingMSGStatus } 
        STATUS            current
        DESCRIPTION
                "CMNT: - 
                 TYPE: - Display
                 PAGE: - Logging
                    MSG Status  cmdID= 5013  "
        ::= { kudosConv1NoteEntries 5013 }
    kudosConv1CtrlEntries OBJECT IDENTIFIER ::= { kudosIQP 5 }


    i1InputSelect OBJECT-TYPE
        SYNTAX            INTEGER {
                            valSDI1(0),
                            valSDI2(1),
                            valSDI3(2),
                            valSDI4(3),
                            valCVBSA(4),
                            valCVBSB(5),
                            valCVBSC(6),
                            valCVBSD(7),
                            valSFPA1(8),
                            valSFPA2(9),
                            valSFPB1(10),
                            valSFPB2(11)
                            }
        MAX-ACCESS        read-write
        STATUS            current
        DESCRIPTION
                "CMNT: - 
                 TYPE: - RadiobuttonList
                 PAGE: - Input
                    Input Select  cmdID= 10020
                    SDI 1  value= 0
                    SDI 2  value= 1
                    SDI 3  value= 2
                    SDI 4  value= 3
                    CVBS A  value= 4
                    CVBS B  value= 5
                    CVBS C  value= 6
                    CVBS D  value= 7
                    SFP A1  value= 8
                    SFP A2  value= 9
                    SFP B1  value= 10
                    SFP B2  value= 11  "
        ::= { kudosConv1CtrlEntries 10020 }


    i1InputStatusSDI1 OBJECT-TYPE
        SYNTAX            RollCallString
        MAX-ACCESS        read-only
        STATUS            current
        DESCRIPTION
                "CMNT: - 
                 TYPE: - Display
                 PAGE: - Input
                    SDI 1  cmdID= 10270  "
        ::= { kudosConv1CtrlEntries 10270 }


    i1InputStatusSDI2 OBJECT-TYPE
        SYNTAX            RollCallString
        MAX-ACCESS        read-only
        STATUS            current
        DESCRIPTION
                "CMNT: - 
                 TYPE: - Display
                 PAGE: - Input
                    SDI 2  cmdID= 10271  "
        ::= { kudosConv1CtrlEntries 10271 }


    i1InputStatusSDI3 OBJECT-TYPE
        SYNTAX            RollCallString
        MAX-ACCESS        read-only
        STATUS            current
        DESCRIPTION
                "CMNT: - 
                 TYPE: - Display
                 PAGE: - Input
                    SDI 3  cmdID= 10272  "
        ::= { kudosConv1CtrlEntries 10272 }


    i1InputStatusSDI4 OBJECT-TYPE
        SYNTAX            RollCallString
        MAX-ACCESS        read-only
        STATUS            current
        DESCRIPTION
                "CMNT: - 
                 TYPE: - Display
                 PAGE: - Input
                    SDI 4  cmdID= 10273  "
        ::= { kudosConv1CtrlEntries 10273 }


    i1InputStatusCVBS1 OBJECT-TYPE
        SYNTAX            RollCallString
        MAX-ACCESS        read-only
        STATUS            current
        DESCRIPTION
                "CMNT: - 
                 TYPE: - Display
                 PAGE: - Input
                    CVBS 1  cmdID= 10274  "
        ::= { kudosConv1CtrlEntries 10274 }


    i1InputStatusCVBS2 OBJECT-TYPE
        SYNTAX            RollCallString
        MAX-ACCESS        read-only
        STATUS            current
        DESCRIPTION
                "CMNT: - 
                 TYPE: - Display
                 PAGE: - Input
                    CVBS 2  cmdID= 10275  "
        ::= { kudosConv1CtrlEntries 10275 }


    i1InputStatusCVBS3 OBJECT-TYPE
        SYNTAX            RollCallString
        MAX-ACCESS        read-only
        STATUS            current
        DESCRIPTION
                "CMNT: - 
                 TYPE: - Display
                 PAGE: - Input
                    CVBS 3  cmdID= 10276  "
        ::= { kudosConv1CtrlEntries 10276 }


    i1InputStatusCVBS4 OBJECT-TYPE
        SYNTAX            RollCallString
        MAX-ACCESS        read-only
        STATUS            current
        DESCRIPTION
                "CMNT: - 
                 TYPE: - Display
                 PAGE: - Input
                    CVBS 4  cmdID= 10277  "
        ::= { kudosConv1CtrlEntries 10277 }


    i1InputStatusSFP1 OBJECT-TYPE
        SYNTAX            RollCallString
        MAX-ACCESS        read-only
        STATUS            current
        DESCRIPTION
                "CMNT: - 
                 TYPE: - Display
                 PAGE: - Input
                    SFP 1  cmdID= 10278  "
        ::= { kudosConv1CtrlEntries 10278 }


    i1InputStatusSFP2 OBJECT-TYPE
        SYNTAX            RollCallString
        MAX-ACCESS        read-only
        STATUS            current
        DESCRIPTION
                "CMNT: - 
                 TYPE: - Display
                 PAGE: - Input
                    SFP 2  cmdID= 10279  "
        ::= { kudosConv1CtrlEntries 10279 }


    i1InputStatusSFP3 OBJECT-TYPE
        SYNTAX            RollCallString
        MAX-ACCESS        read-only
        STATUS            current
        DESCRIPTION
                "CMNT: - 
                 TYPE: - Display
                 PAGE: - Input
                    SFP 3  cmdID= 10280  "
        ::= { kudosConv1CtrlEntries 10280 }


    i1InputStatusSFP4 OBJECT-TYPE
        SYNTAX            RollCallString
        MAX-ACCESS        read-only
        STATUS            current
        DESCRIPTION
                "CMNT: - 
                 TYPE: - Display
                 PAGE: - Input
                    SFP 4  cmdID= 10281  "
        ::= { kudosConv1CtrlEntries 10281 }


    i1InputStatusCurrentInputStandard OBJECT-TYPE
        SYNTAX            RollCallString
        MAX-ACCESS        read-only
        STATUS            current
        DESCRIPTION
                "CMNT: - 
                 TYPE: - Display
                 PAGE: - Input
                    Current Input Standard  cmdID= 10313  "
        ::= { kudosConv1CtrlEntries 10313 }


    i1OutputFormat OBJECT-TYPE
        SYNTAX            INTEGER {
                            val525625(0),
                            val720p(1),
                            val1080i(2),
                            val1080pnA(3),
                            val1080pnB(4)
                            }
        MAX-ACCESS        read-write
        STATUS            current
        DESCRIPTION
                "CMNT: - 
                 TYPE: - RadiobuttonList
                 PAGE: - Output
                    Output Format  cmdID= 10025
                    525/625  value= 0
                    720p  value= 1
                    1080i  value= 2
                    1080p-A  value= 3
                    1080p-B  value= 4  "
        ::= { kudosConv1CtrlEntries 10025 }


    i1OutputDefaultFieldRate OBJECT-TYPE
        SYNTAX            INTEGER {
                            valLastValidInput(0),
                            val23Hz(1),
                            val24Hz(2),
                            val25Hz(3),
                            val29Hz(4),
                            val30Hz(5),
                            val50Hz(6),
                            val59Hz(7),
                            val60Hz(8)
                            }
        MAX-ACCESS        read-write
        STATUS            current
        DESCRIPTION
                "CMNT: - 
                 TYPE: - RadiobuttonList
                 PAGE: - Output
                    Default Field Rate  cmdID= 10026
                    Last Valid Input  value= 0
                    23 Hz  value= 1
                    24 Hz  value= 2
                    25 Hz  value= 3
                    29 Hz  value= 4
                    30 Hz  value= 5
                    50 Hz  value= 6
                    59 Hz  value= 7
                    60 Hz  value= 8  "
        ::= { kudosConv1CtrlEntries 10026 }


    i1OutputStandard OBJECT-TYPE
        SYNTAX            INTEGER {
                            val62550i(2),
                            val52559i(3),
                            val72023p(4),
                            val72024p(5),
                            val72025p(6),
                            val72029p(7),
                            val72030p(8),
                            val72050p(9),
                            val72059p(10),
                            val72060p(11),
                            val108023p(12),
                            val108024p(13),
                            val108025p(14),
                            val108029p(15),
                            val108030p(16),
                            val108050i(17),
                            val108059i(18),
                            val108060i(19),
                            val108023psf(20),
                            val108024psf(21),
                            val108025psf(50),
                            val108029psf(51),
                            val108050pnA(22),
                            val108059pnA(23),
                            val108060pnA(24),
                            val108050pnB(25),
                            val108059pnB(26),
                            val108060pnB(27)
                            }
        MAX-ACCESS        read-write
        STATUS            current
        DESCRIPTION
                "CMNT: - 
                 TYPE: - RadiobuttonList
                 PAGE: - Output
                    Output Standard  cmdID= 10024
                    625 50i  value= 2
                    525 59i  value= 3
                    720 23p  value= 4
                    720 24p  value= 5
                    720 25p  value= 6
                    720 29p  value= 7
                    720 30p  value= 8
                    720 50p  value= 9
                    720 59p  value= 10
                    720 60p  value= 11
                    1080 23p  value= 12
                    1080 24p  value= 13
                    1080 25p  value= 14
                    1080 29p  value= 15
                    1080 30p  value= 16
                    1080 50i  value= 17
                    1080 59i  value= 18
                    1080 60i  value= 19
                    1080 23psf  value= 20
                    1080 24psf  value= 21
                    1080 25psf  value= 50
                    1080 29psf  value= 51
                    1080 50p-A  value= 22
                    1080 59p-A  value= 23
                    1080 60p-A  value= 24
                    1080 50p-B  value= 25
                    1080 59p-B  value= 26
                    1080 60p-B  value= 27  "
        ::= { kudosConv1CtrlEntries 10024 }


    i1OutputCurrentOutputStandard OBJECT-TYPE
        SYNTAX            RollCallString
        MAX-ACCESS        read-only
        STATUS            current
        DESCRIPTION
                "CMNT: - 
                 TYPE: - Display
                 PAGE: - Output
                    Current Output Standard  cmdID= 10314  "
        ::= { kudosConv1CtrlEntries 10314 }


    i1OutputBlankingEmbeddedAudio OBJECT-TYPE
        SYNTAX            INTEGER {
                            valEnable(0),
                            valBlank(1)
                            }
        MAX-ACCESS        read-write
        STATUS            current
        DESCRIPTION
                "CMNT: - 
                 TYPE: - RadiobuttonList
                 PAGE: - Output
                    Embedded Audio  cmdID= 10021
                    Enable  value= 0
                    Blank  value= 1  "
        ::= { kudosConv1CtrlEntries 10021 }


    i1OutputBlankingVAncillaryData OBJECT-TYPE
        SYNTAX            INTEGER {
                            valPass(0),
                            valStrip(1)
                            }
        MAX-ACCESS        read-write
        STATUS            current
        DESCRIPTION
                "CMNT: - 
                 TYPE: - RadiobuttonList
                 PAGE: - Output
                    V Ancillary Data  cmdID= 10022
                    Pass  value= 0
                    Strip  value= 1  "
        ::= { kudosConv1CtrlEntries 10022 }


    i1OutputBlankingSDHalfLine OBJECT-TYPE
        SYNTAX            INTEGER {
                            valPass(0),
                            valBlank(1)
                            }
        MAX-ACCESS        read-write
        STATUS            current
        DESCRIPTION
                "CMNT: - 
                 TYPE: - RadiobuttonList
                 PAGE: - Output
                    SD Half Line  cmdID= 10023
                    Pass  value= 0
                    Blank  value= 1  "
        ::= { kudosConv1CtrlEntries 10023 }


    i1OutputTestPatterns OBJECT-TYPE
        SYNTAX            INTEGER {
                            valOff(0),
                            valBlack(1),
                            valRamp(2),
                            valBars(3)
                            }
        MAX-ACCESS        read-write
        STATUS            current
        DESCRIPTION
                "CMNT: - 
                 TYPE: - RadiobuttonList
                 PAGE: - Output
                    Test Patterns  cmdID= 10054
                    Off  value= 0
                    Black  value= 1
                    Ramp  value= 2
                    Bars  value= 3  "
        ::= { kudosConv1CtrlEntries 10054 }


    i1OutputScrollingCaptionGeneratorCaptionEntry OBJECT-TYPE
        SYNTAX            RollCallString
        MAX-ACCESS        read-write
        STATUS            current
        DESCRIPTION
                "CMNT: - 
                 TYPE: - Editstring
                 PAGE: - Output
                    Caption Entry  cmdID= 10050
                    preset= Channel Number"
        ::= { kudosConv1CtrlEntries 10050 }


    i1OutputScrollingCaptionGeneratorCaptionScroll OBJECT-TYPE
        SYNTAX            INTEGER { disable(0), enable(1)  }
        MAX-ACCESS        read-write
        STATUS            current
        DESCRIPTION
                "CMNT: - 
                 TYPE: - Checkbox
                 PAGE: - Output
                    Caption Scroll  cmdID= 10052  "
        ::= { kudosConv1CtrlEntries 10052 }


    i1OutputScrollingCaptionGeneratorCaptionEnable OBJECT-TYPE
        SYNTAX            INTEGER { disable(0), enable(1)  }
        MAX-ACCESS        read-write
        STATUS            current
        DESCRIPTION
                "CMNT: - 
                 TYPE: - Checkbox
                 PAGE: - Output
                    Caption Enable  cmdID= 10051  "
        ::= { kudosConv1CtrlEntries 10051 }


    i1OutputFreeze OBJECT-TYPE
        SYNTAX            INTEGER { disable(0), enable(1)  }
        MAX-ACCESS        read-write
        STATUS            current
        DESCRIPTION
                "CMNT: - 
                 TYPE: - Checkbox
                 PAGE: - Output
                    Freeze  cmdID= 10053  "
        ::= { kudosConv1CtrlEntries 10053 }


    i1OutputLegalization OBJECT-TYPE
        SYNTAX            INTEGER {
                            valOff(0),
                            val700mV(1),
                            val721mV(2),
                            val735mV(3),
                            val746mV(4)
                            }
        MAX-ACCESS        read-write
        STATUS            current
        DESCRIPTION
                "CMNT: - 
                 TYPE: - RadiobuttonList
                 PAGE: - Output
                    Legalization  cmdID= 10049
                    Off  value= 0
                    700mV  value= 1
                    721mV  value= 2
                    735mV  value= 3
                    746mV  value= 4  "
        ::= { kudosConv1CtrlEntries 10049 }


    i1OutputLogoControlPreShaped OBJECT-TYPE
        SYNTAX            INTEGER { disable(0), enable(1)  }
        MAX-ACCESS        read-write
        STATUS            current
        DESCRIPTION
                "CMNT: - 
                 TYPE: - Checkbox
                 PAGE: - Output
                    Pre-Shaped  cmdID= 10055  "
        ::= { kudosConv1CtrlEntries 10055 }


    i1OutputLogoControlTake OBJECT-TYPE
        SYNTAX            INTEGER { disable(0), enable(1)  }
        MAX-ACCESS        read-write
        STATUS            current
        DESCRIPTION
                "CMNT: - 
                 TYPE: - Checkbox
                 PAGE: - Output
                    Take  cmdID= 10056  "
        ::= { kudosConv1CtrlEntries 10056 }


    i1OutputLogoControlHPosition OBJECT-TYPE
        SYNTAX            INTEGER
        MAX-ACCESS        read-write
        STATUS            current
        DESCRIPTION
                "CMNT: - 
                 TYPE: - Number
                 PAGE: - Output
                    H Position  cmdID= 10057
                    min= 0  max= 100  step= 1  format= %0.0f  div_scale= 1  preset= 10
                    Min = 0  Max = 100  Step = 1  Preset = 10  "
        ::= { kudosConv1CtrlEntries 10057 }


    i1OutputLogoControlVPosition OBJECT-TYPE
        SYNTAX            INTEGER
        MAX-ACCESS        read-write
        STATUS            current
        DESCRIPTION
                "CMNT: - 
                 TYPE: - Number
                 PAGE: - Output
                    V Position  cmdID= 10058
                    min= 0  max= 100  step= 1  format= %0.0f  div_scale= 1  preset= 10
                    Min = 0  Max = 100  Step = 1  Preset = 10  "
        ::= { kudosConv1CtrlEntries 10058 }


    i1OutputLogoControlTransparency OBJECT-TYPE
        SYNTAX            INTEGER
        MAX-ACCESS        read-write
        STATUS            current
        DESCRIPTION
                "CMNT: - 
                 TYPE: - Number
                 PAGE: - Output
                    Transparency  cmdID= 10059
                    min= 0  max= 100  step= 1  format= %0.0f  div_scale= 1  preset= 10
                    Min = 0  Max = 100  Step = 1  Preset = 10  "
        ::= { kudosConv1CtrlEntries 10059 }


    i1OutputLogoControlDelete OBJECT-TYPE
        SYNTAX            INTEGER { noAction(0),valDelete(1) }
        MAX-ACCESS        read-write
        STATUS            current
        DESCRIPTION
                "CMNT: - 
                 TYPE: - Button
                 PAGE: - Output
                    Delete  cmdID= 10060
                    value= 1  "
        ::= { kudosConv1CtrlEntries 10060 }


    i1OutputLogoControlCurrentSelectedLogo OBJECT-TYPE
        SYNTAX            RollCallString
        MAX-ACCESS        read-only
        STATUS            current
        DESCRIPTION
                "CMNT: - 
                 TYPE: - Display
                 PAGE: - Output
                    Current Selected Logo  cmdID= 10062  "
        ::= { kudosConv1CtrlEntries 10062 }


    i1OutputLogoControlLogoStatus OBJECT-TYPE
        SYNTAX            RollCallString
        MAX-ACCESS        read-only
        STATUS            current
        DESCRIPTION
                "CMNT: - 
                 TYPE: - Display
                 PAGE: - Output
                    Logo Status  cmdID= 15001  "
        ::= { kudosConv1CtrlEntries 15001 }


    i1OutputLogoControlLogoState OBJECT-TYPE
        SYNTAX            RollCallString
        MAX-ACCESS        read-only
        STATUS            current
        DESCRIPTION
                "CMNT: - 
                 TYPE: - Display
                 PAGE: - Output
                    Logo State  cmdID= 10063  "
        ::= { kudosConv1CtrlEntries 10063 }


    i1OutputLogoControlNewLogo OBJECT-TYPE
        SYNTAX            RollCallString
        MAX-ACCESS        read-write
        STATUS            current
        DESCRIPTION
                "CMNT: - 
                 TYPE: - Editstring
                 PAGE: - Output
                    New Logo  cmdID= 15000
                    preset= startupqwerty"
        ::= { kudosConv1CtrlEntries 15000 }


    i1OutputLogoControlLogoSelect OBJECT-TYPE
        SYNTAX            INTEGER {
                            valNoneSelected(-1),
                            valLogo1(1),
                            valLogo2(2),
                            valLogo3(3),
                            valLogo4(4),
                            valLogo5(5),
                            valLogo6(6),
                            valLogo7(7),
                            valLogo8(8),
                            valLogo9(9),
                            valLogo10(10),
                            valLogo11(11),
                            valLogo12(12),
                            valLogo13(13),
                            valLogo14(14),
                            valLogo15(15),
                            valLogo16(16),
                            valLogo17(17),
                            valLogo18(18),
                            valLogo19(19),
                            valLogo20(20),
                            valLogo21(21),
                            valLogo22(22),
                            valLogo23(23),
                            valLogo24(24),
                            valLogo25(25),
                            valLogo26(26),
                            valLogo27(27),
                            valLogo28(28),
                            valLogo29(29),
                            valLogo30(30),
                            valLogo31(31),
                            valLogo32(32),
                            valLogo33(33),
                            valLogo34(34),
                            valLogo35(35),
                            valLogo36(36),
                            valLogo37(37),
                            valLogo38(38),
                            valLogo39(39),
                            valLogo40(40),
                            valLogo41(41),
                            valLogo42(42),
                            valLogo43(43),
                            valLogo44(44),
                            valLogo45(45),
                            valLogo46(46),
                            valLogo47(47),
                            valLogo48(48),
                            valLogo49(49),
                            valLogo50(50),
                            valLogo51(51),
                            valLogo52(52),
                            valLogo53(53),
                            valLogo54(54),
                            valLogo55(55),
                            valLogo56(56),
                            valLogo57(57),
                            valLogo58(58),
                            valLogo59(59),
                            valLogo60(60),
                            valLogo61(61),
                            valLogo62(62),
                            valLogo63(63),
                            valLogo64(64)
                            }
        MAX-ACCESS        read-write
        STATUS            current
        DESCRIPTION
                "CMNT: - 
                 TYPE: - RadiobuttonList
                 PAGE: - Output
                    Logo Select  cmdID= 10061
                    None Selected  value= -1
                    Logo 1  value= 1
                    Logo 2  value= 2
                    Logo 3  value= 3
                    Logo 4  value= 4
                    Logo 5  value= 5
                    Logo 6  value= 6
                    Logo 7  value= 7
                    Logo 8  value= 8
                    Logo 9  value= 9
                    Logo 10  value= 10
                    Logo 11  value= 11
                    Logo 12  value= 12
                    Logo 13  value= 13
                    Logo 14  value= 14
                    Logo 15  value= 15
                    Logo 16  value= 16
                    Logo 17  value= 17
                    Logo 18  value= 18
                    Logo 19  value= 19
                    Logo 20  value= 20
                    Logo 21  value= 21
                    Logo 22  value= 22
                    Logo 23  value= 23
                    Logo 24  value= 24
                    Logo 25  value= 25
                    Logo 26  value= 26
                    Logo 27  value= 27
                    Logo 28  value= 28
                    Logo 29  value= 29
                    Logo 30  value= 30
                    Logo 31  value= 31
                    Logo 32  value= 32
                    Logo 33  value= 33
                    Logo 34  value= 34
                    Logo 35  value= 35
                    Logo 36  value= 36
                    Logo 37  value= 37
                    Logo 38  value= 38
                    Logo 39  value= 39
                    Logo 40  value= 40
                    Logo 41  value= 41
                    Logo 42  value= 42
                    Logo 43  value= 43
                    Logo 44  value= 44
                    Logo 45  value= 45
                    Logo 46  value= 46
                    Logo 47  value= 47
                    Logo 48  value= 48
                    Logo 49  value= 49
                    Logo 50  value= 50
                    Logo 51  value= 51
                    Logo 52  value= 52
                    Logo 53  value= 53
                    Logo 54  value= 54
                    Logo 55  value= 55
                    Logo 56  value= 56
                    Logo 57  value= 57
                    Logo 58  value= 58
                    Logo 59  value= 59
                    Logo 60  value= 60
                    Logo 61  value= 61
                    Logo 62  value= 62
                    Logo 63  value= 63
                    Logo 64  value= 64  "
        ::= { kudosConv1CtrlEntries 10061 }


    i1VideoProcAmpEnable OBJECT-TYPE
        SYNTAX            INTEGER { disable(0), enable(1)  }
        MAX-ACCESS        read-write
        STATUS            current
        DESCRIPTION
                "CMNT: - 
                 TYPE: - Checkbox
                 PAGE: - Video
                    Enable  cmdID= 10047  "
        ::= { kudosConv1CtrlEntries 10047 }


    i1VideoProcAmpContrast OBJECT-TYPE
        SYNTAX            INTEGER
        MAX-ACCESS        read-write
        STATUS            current
        DESCRIPTION
                "CMNT: - 
                 TYPE: - Number
                 PAGE: - Video
                    Contrast  cmdID= 10043
                    min= -60  max= 60  step= 2  format= %0.1fdB  div_scale= 10  preset= 0
                    Min = -6.0dB  Max = 6.0dB  Step = 0.2dB  Preset = 0.0dB  "
        ::= { kudosConv1CtrlEntries 10043 }


    i1VideoProcAmpSaturation OBJECT-TYPE
        SYNTAX            INTEGER
        MAX-ACCESS        read-write
        STATUS            current
        DESCRIPTION
                "CMNT: - 
                 TYPE: - Number
                 PAGE: - Video
                    Saturation  cmdID= 10044
                    min= -60  max= 60  step= 2  format= %0.1fdB  div_scale= 10  preset= 0
                    Min = -6.0dB  Max = 6.0dB  Step = 0.2dB  Preset = 0.0dB  "
        ::= { kudosConv1CtrlEntries 10044 }


    i1VideoProcAmpBlackLevel OBJECT-TYPE
        SYNTAX            INTEGER
        MAX-ACCESS        read-write
        STATUS            current
        DESCRIPTION
                "CMNT: - 
                 TYPE: - Number
                 PAGE: - Video
                    Black Level  cmdID= 10045
                    min= -1000  max= 1000  step= 8  format= %0.1fmV  div_scale= 10  preset= 0
                    Min = -100.0mV  Max = 100.0mV  Step = 0.8mV  Preset = 0.0mV  "
        ::= { kudosConv1CtrlEntries 10045 }


    i1VideoProcAmpGamma OBJECT-TYPE
        SYNTAX            INTEGER
        MAX-ACCESS        read-write
        STATUS            current
        DESCRIPTION
                "CMNT: - 
                 TYPE: - Number
                 PAGE: - Video
                    Gamma  cmdID= 10046
                    min= 4  max= 17  step= 1  format= %0.1f  div_scale= 10  preset= 10
                    Min = 0.4  Max = 1.7  Step = 0.1  Preset = 1.0  "
        ::= { kudosConv1CtrlEntries 10046 }


    i1VideoProcAmpYCOffset OBJECT-TYPE
        SYNTAX            INTEGER
        MAX-ACCESS        read-write
        STATUS            current
        DESCRIPTION
                "CMNT: - 
                 TYPE: - Number
                 PAGE: - Video
                    YC Offset  cmdID= 10048
                    min= -20  max= 20  step= 2  format= %0.0f  div_scale= 1  preset= 0
                    Min = -20  Max = 20  Step = 2  Preset = 0  "
        ::= { kudosConv1CtrlEntries 10048 }


    i1VideoEnhanceNonlinearEnhancerEnable OBJECT-TYPE
        SYNTAX            INTEGER { disable(0), enable(1)  }
        MAX-ACCESS        read-write
        STATUS            current
        DESCRIPTION
                "CMNT: - 
                 TYPE: - Checkbox
                 PAGE: - Enhance
                    Enable  cmdID= 10036  "
        ::= { kudosConv1CtrlEntries 10036 }


    i1VideoEnhanceNonlinearEnhancerLevel OBJECT-TYPE
        SYNTAX            INTEGER
        MAX-ACCESS        read-write
        STATUS            current
        DESCRIPTION
                "CMNT: - 
                 TYPE: - Number
                 PAGE: - Enhance
                    Level  cmdID= 10039
                    min= 0  max= 192  step= 1  format= %0.0f  div_scale= 1  preset= 0
                    Min = 0  Max = 192  Step = 1  Preset = 0  "
        ::= { kudosConv1CtrlEntries 10039 }


    i1VideoEnhanceNonlinearEnhancerMode OBJECT-TYPE
        SYNTAX            INTEGER {
                            valLow(0),
                            valMedium(1),
                            valHigh(2),
                            valSuper(3),
                            valManual(4)
                            }
        MAX-ACCESS        read-write
        STATUS            current
        DESCRIPTION
                "CMNT: - 
                 TYPE: - RadiobuttonList
                 PAGE: - Enhance
                    Mode  cmdID= 10037
                    Low  value= 0
                    Medium  value= 1
                    High  value= 2
                    Super  value= 3
                    Manual  value= 4  "
        ::= { kudosConv1CtrlEntries 10037 }


    i1VideoEnhanceNonlinearEnhancerFrequencyBand OBJECT-TYPE
        SYNTAX            INTEGER {
                            valLow(0),
                            valMedium(1),
                            valHigh(2)
                            }
        MAX-ACCESS        read-write
        STATUS            current
        DESCRIPTION
                "CMNT: - 
                 TYPE: - RadiobuttonList
                 PAGE: - Enhance
                    Frequency Band  cmdID= 10038
                    Low  value= 0
                    Medium  value= 1
                    High  value= 2  "
        ::= { kudosConv1CtrlEntries 10038 }


    i1VideoEnhanceNonlinearEnhancerNoiseRejection OBJECT-TYPE
        SYNTAX            INTEGER
        MAX-ACCESS        read-write
        STATUS            current
        DESCRIPTION
                "CMNT: - 
                 TYPE: - Number
                 PAGE: - Enhance
                    Noise Rejection  cmdID= 10040
                    min= 0  max= 100  step= 1  format= %0.0f  div_scale= 1  preset= 0
                    Min = 0  Max = 100  Step = 1  Preset = 0  "
        ::= { kudosConv1CtrlEntries 10040 }


    i1VideoEnhanceConversionAperturePreset OBJECT-TYPE
        SYNTAX            INTEGER { noAction(0),valPreset(1) }
        MAX-ACCESS        read-write
        STATUS            current
        DESCRIPTION
                "CMNT: - 
                 TYPE: - Button
                 PAGE: - Enhance
                    Preset  cmdID= 10335
                    value= 1  "
        ::= { kudosConv1CtrlEntries 10335 }


    i1VideoConversionApertureHorizontalSharpness OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Conversion Aperture
                    Sharpness  cmdID= 10072
                    Soft 2  value= 0
                    Soft 1  value= 1
                    Normal  value= 2
                    Sharp 1  value= 3
                    Sharp 2  value= 4  "
        ::= { kudosConv1CtrlEntries 10072 }


    i1VideoConversionApertureHorizontalDetail OBJECT-TYPE
        SYNTAX            INTEGER {
                            valLow2(0),
                            valLow1(1),
                            valNormal(2),
                            valHigh1(3),
                            valHigh2(4)
                            }
        MAX-ACCESS        read-write
        STATUS            current
        DESCRIPTION
                "CMNT: - 
                 TYPE: - RadiobuttonList
                 PAGE: - Conversion Aperture
                    Detail  cmdID= 10073
                    Low 2  value= 0
                    Low 1  value= 1
                    Normal  value= 2
                    High 1  value= 3
                    High 2  value= 4  "
        ::= { kudosConv1CtrlEntries 10073 }


    i1VideoConversionApertureVerticalLevel OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Conversion Aperture
                    Level  cmdID= 10042
                    Soft 2  value= 0
                    Soft 1  value= 1
                    Normal  value= 2
                    Sharp 1  value= 3
                    Sharp 2  value= 4  "
        ::= { kudosConv1CtrlEntries 10042 }


    i1VideoConversionApertureVerticalFrequencyBand OBJECT-TYPE
        SYNTAX            INTEGER {
                            valLow(0),
                            valMedium(1),
                            valHigh(2)
                            }
        MAX-ACCESS        read-write
        STATUS            current
        DESCRIPTION
                "CMNT: - 
                 TYPE: - RadiobuttonList
                 PAGE: - Conversion Aperture
                    Frequency Band  cmdID= 10041
                    Low  value= 0
                    Medium  value= 1
                    High  value= 2  "
        ::= { kudosConv1CtrlEntries 10041 }


    i1VideoNoiseReductionEnable OBJECT-TYPE
        SYNTAX            INTEGER { disable(0), enable(1)  }
        MAX-ACCESS        read-write
        STATUS            current
        DESCRIPTION
                "CMNT: - 
                 TYPE: - Checkbox
                 PAGE: - Video
                    Enable  cmdID= 10031  "
        ::= { kudosConv1CtrlEntries 10031 }


    i1VideoNoiseReductionRecursiveLuma OBJECT-TYPE
        SYNTAX            INTEGER
        MAX-ACCESS        read-write
        STATUS            current
        DESCRIPTION
                "CMNT: - 
                 TYPE: - Number
                 PAGE: - Noise Reduction
                    Luma  cmdID= 10027
                    min= 0  max= 7  step= 1  format= %0.0f  div_scale= 1  preset= 0
                    Min = 0  Max = 7  Step = 1  Preset = 0  "
        ::= { kudosConv1CtrlEntries 10027 }


    i1VideoNoiseReductionRecursiveChroma OBJECT-TYPE
        SYNTAX            INTEGER
        MAX-ACCESS        read-write
        STATUS            current
        DESCRIPTION
                "CMNT: - 
                 TYPE: - Number
                 PAGE: - Noise Reduction
                    Chroma  cmdID= 10028
                    min= 0  max= 7  step= 1  format= %0.0f  div_scale= 1  preset= 0
                    Min = 0  Max = 7  Step = 1  Preset = 0  "
        ::= { kudosConv1CtrlEntries 10028 }


    i1VideoNoiseReductionRecursiveMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10029
                    Auto  value= 0
                    Manual  value= 1  "
        ::= { kudosConv1CtrlEntries 10029 }


    i1VideoNoiseReductionRecursiveThreshold OBJECT-TYPE
        SYNTAX            INTEGER
        MAX-ACCESS        read-write
        STATUS            current
        DESCRIPTION
                "CMNT: - 
                 TYPE: - Number
                 PAGE: - Noise Reduction
                    Threshold  cmdID= 10030
                    min= 0  max= 7  step= 1  format= %0.0f  div_scale= 1  preset= 0
                    Min = 0  Max = 7  Step = 1  Preset = 0  "
        ::= { kudosConv1CtrlEntries 10030 }


    i1VideoNoiseReductionSpatialLevel OBJECT-TYPE
        SYNTAX            INTEGER
        MAX-ACCESS        read-write
        STATUS            current
        DESCRIPTION
                "CMNT: - 
                 TYPE: - Number
                 PAGE: - Noise Reduction
                    Level  cmdID= 10033
                    min= 0  max= 7  step= 1  format= %0.0f  div_scale= 1  preset= 0
                    Min = 0  Max = 7  Step = 1  Preset = 0  "
        ::= { kudosConv1CtrlEntries 10033 }


    i1VideoNoiseReductionSpatialMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10032
                    Auto  value= 0
                    Manual  value= 1  "
        ::= { kudosConv1CtrlEntries 10032 }


    i1VideoNoiseReductionSpatialThreshold OBJECT-TYPE
        SYNTAX            INTEGER
        MAX-ACCESS        read-write
        STATUS            current
        DESCRIPTION
                "CMNT: - 
                 TYPE: - Number
                 PAGE: - Noise Reduction
                    Threshold  cmdID= 10034
                    min= 1  max= 4  step= 1  format= %0.0f  div_scale= 1  preset= 1
                    Min = 1  Max = 4  Step = 1  Preset = 1  "
        ::= { kudosConv1CtrlEntries 10034 }


    i1VideoNoiseReductionSplitScreen OBJECT-TYPE
        SYNTAX            INTEGER { disable(0), enable(1)  }
        MAX-ACCESS        read-write
        STATUS            current
        DESCRIPTION
                "CMNT: - 
                 TYPE: - Checkbox
                 PAGE: - Video
                    Split Screen  cmdID= 10035  "
        ::= { kudosConv1CtrlEntries 10035 }


    i1ConvertUpConversionCleanEdgeUpconversion OBJECT-TYPE
        SYNTAX            INTEGER { disable(0), enable(1)  }
        MAX-ACCESS        read-write
        STATUS            current
        DESCRIPTION
                "CMNT: - 
                 TYPE: - Checkbox
                 PAGE: - Convert
                    Clean Edge Upconversion  cmdID= 10069  "
        ::= { kudosConv1CtrlEntries 10069 }


    i1ConvertMotionProcessingMotionProcess OBJECT-TYPE
        SYNTAX            INTEGER { disable(0), enable(1)  }
        MAX-ACCESS        read-write
        STATUS            current
        DESCRIPTION
                "CMNT: - 
                 TYPE: - Checkbox
                 PAGE: - Convert
                    Motion Process  cmdID= 10064  "
        ::= { kudosConv1CtrlEntries 10064 }


    i1ConvertMotionProcessingEnhancedMotion OBJECT-TYPE
        SYNTAX            INTEGER { disable(0), enable(1)  }
        MAX-ACCESS        read-write
        STATUS            current
        DESCRIPTION
                "CMNT: - 
                 TYPE: - Checkbox
                 PAGE: - Convert
                    Enhanced Motion  cmdID= 10065  "
        ::= { kudosConv1CtrlEntries 10065 }


    i1ConvertMotionProcessingStillProcess OBJECT-TYPE
        SYNTAX            INTEGER { disable(0), enable(1)  }
        MAX-ACCESS        read-write
        STATUS            current
        DESCRIPTION
                "CMNT: - 
                 TYPE: - Checkbox
                 PAGE: - Convert
                    Still Process  cmdID= 10066  "
        ::= { kudosConv1CtrlEntries 10066 }


    i1ConvertMotionProcessingEnhancedStill OBJECT-TYPE
        SYNTAX            INTEGER { disable(0), enable(1)  }
        MAX-ACCESS        read-write
        STATUS            current
        DESCRIPTION
                "CMNT: - 
                 TYPE: - Checkbox
                 PAGE: - Convert
                    Enhanced Still  cmdID= 10067  "
        ::= { kudosConv1CtrlEntries 10067 }


    i1ConvertMotionProcessingEnhancedFilm OBJECT-TYPE
        SYNTAX            INTEGER { disable(0), enable(1)  }
        MAX-ACCESS        read-write
        STATUS            current
        DESCRIPTION
                "CMNT: - 
                 TYPE: - Checkbox
                 PAGE: - Convert
                    Enhanced Film  cmdID= 10068  "
        ::= { kudosConv1CtrlEntries 10068 }


    i1ConvertMotionProcessingEnhancedDeinterlace OBJECT-TYPE
        SYNTAX            INTEGER { disable(0), enable(1)  }
        MAX-ACCESS        read-write
        STATUS            current
        DESCRIPTION
                "CMNT: - 
                 TYPE: - Checkbox
                 PAGE: - Convert
                    Enhanced De-interlace  cmdID= 10071  "
        ::= { kudosConv1CtrlEntries 10071 }


    i1ConvertMotionProcessingCleanCut OBJECT-TYPE
        SYNTAX            INTEGER { disable(0), enable(1)  }
        MAX-ACCESS        read-write
        STATUS            current
        DESCRIPTION
                "CMNT: - 
                 TYPE: - Checkbox
                 PAGE: - Convert
                    Clean Cut  cmdID= 10070  "
        ::= { kudosConv1CtrlEntries 10070 }


    i1ConvertInputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10323  "
        ::= { kudosConv1CtrlEntries 10323 }


    i1ConvertInputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10324
                    2:3  value= 0
                    2:2 (psf)  value= 1  "
        ::= { kudosConv1CtrlEntries 10324 }


    i1ConvertInputCadence23Source OBJECT-TYPE
        SYNTAX            INTEGER {
                            valAutomatic(0),
                            valInputTimecode(1)
                            }
        MAX-ACCESS        read-write
        STATUS            current
        DESCRIPTION
                "CMNT: - 
                 TYPE: - RadiobuttonList
                 PAGE: - Convert
                    2:3 Source  cmdID= 10325
                    Automatic  value= 0
                    Input Timecode  value= 1  "
        ::= { kudosConv1CtrlEntries 10325 }


    i1ConvertInputCadence23StartHour OBJECT-TYPE
        SYNTAX            INTEGER
        MAX-ACCESS        read-write
        STATUS            current
        DESCRIPTION
                "CMNT: - 
                 TYPE: - Number
                 PAGE: - Convert
                    2:3 Start Hour  cmdID= 10326
                    min= 0  max= 23  step= 1  format= %0.0f  div_scale= 1  preset= 1
                    Min = 0  Max = 23  Step = 1  Preset = 1  "
        ::= { kudosConv1CtrlEntries 10326 }


    i1ConvertOutputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10327  "
        ::= { kudosConv1CtrlEntries 10327 }


    i1ConvertOutputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10328
                    2:3  value= 0
                    2:2 (psf)  value= 1  "
        ::= { kudosConv1CtrlEntries 10328 }


    i1ConvertOutputCadence23Source OBJECT-TYPE
        SYNTAX            INTEGER {
                            valFreeRun(0),
                            valOutputTimecode(1)
                            }
        MAX-ACCESS        read-write
        STATUS            current
        DESCRIPTION
                "CMNT: - 
                 TYPE: - RadiobuttonList
                 PAGE: - Convert
                    2:3 Source  cmdID= 10329
                    Free Run  value= 0
                    Output Timecode  value= 1  "
        ::= { kudosConv1CtrlEntries 10329 }


    i1ConvertOutputCadence23StartHour OBJECT-TYPE
        SYNTAX            INTEGER
        MAX-ACCESS        read-write
        STATUS            current
        DESCRIPTION
                "CMNT: - 
                 TYPE: - Number
                 PAGE: - Convert
                    2:3 Start Hour  cmdID= 10330
                    min= 0  max= 23  step= 1  format= %0.0f  div_scale= 1  preset= 1
                    Min = 0  Max = 23  Step = 1  Preset = 1  "
        ::= { kudosConv1CtrlEntries 10330 }


    i1ARCSyncMode OBJECT-TYPE
        SYNTAX            INTEGER { disable(0), enable(1)  }
        MAX-ACCESS        read-write
        STATUS            current
        DESCRIPTION
                "CMNT: - 
                 TYPE: - Checkbox
                 PAGE: - ARC
                    Sync Mode  cmdID= 10079  "
        ::= { kudosConv1CtrlEntries 10079 }


    i1ARCSignalingDetected OBJECT-TYPE
        SYNTAX            RollCallString
        MAX-ACCESS        read-only
        STATUS            current
        DESCRIPTION
                "CMNT: - 
                 TYPE: - Display
                 PAGE: - ARC
                    Signaling Detected  cmdID= 10315  "
        ::= { kudosConv1CtrlEntries 10315 }


    i1ARCSidebarKeyingOutputCropMode OBJECT-TYPE
        SYNTAX            INTEGER {
                            valOff(0),
                            valOutputCrop(1),
                            valSidebarKey(2)
                            }
        MAX-ACCESS        read-write
        STATUS            current
        DESCRIPTION
                "CMNT: - 
                 TYPE: - RadiobuttonList
                 PAGE: - ARC
                    Mode  cmdID= 10091
                    Off  value= 0
                    Output Crop  value= 1
                    Sidebar Key  value= 2  "
        ::= { kudosConv1CtrlEntries 10091 }


    i1ARCSidebarKeyingOutputCropSidebarKeySource OBJECT-TYPE
        SYNTAX            INTEGER {
                            valSDI1(0),
                            valSDI2(1),
                            valSDI3(2),
                            valSDI4(3),
                            valCVBSA(4),
                            valCVBSB(5),
                            valCVBSC(6),
                            valCVBSD(7),
                            valSFPA1(8),
                            valSFPA2(9),
                            valSFPA3(10),
                            valSFPA4(11),
                            valOutput(20)
                            }
        MAX-ACCESS        read-write
        STATUS            current
        DESCRIPTION
                "CMNT: - 
                 TYPE: - RadiobuttonList
                 PAGE: - ARC
                    Sidebar Key Source  cmdID= 10092
                    SDI 1  value= 0
                    SDI 2  value= 1
                    SDI 3  value= 2
                    SDI 4  value= 3
                    CVBS A  value= 4
                    CVBS B  value= 5
                    CVBS C  value= 6
                    CVBS D  value= 7
                    SFP A1  value= 8
                    SFP A2  value= 9
                    SFP A3  value= 10
                    SFP A4  value= 11
                    Output  value= 20  "
        ::= { kudosConv1CtrlEntries 10092 }


    i1ARCSidebarKeyingOutputCropOutputCropPositionTop OBJECT-TYPE
        SYNTAX            INTEGER
        MAX-ACCESS        read-write
        STATUS            current
        DESCRIPTION
                "CMNT: - 
                 TYPE: - Number
                 PAGE: - Sidebar Keying & Output Crop
                    Top  cmdID= 10093
                    min= 0  max= 99  step= 1  format= %0.0f%%  div_scale= 1  preset= 0
                    Min = 0%  Max = 99%  Step = 1%  Preset = 0%  "
        ::= { kudosConv1CtrlEntries 10093 }


    i1ARCSidebarKeyingOutputCropOutputCropPositionBottom OBJECT-TYPE
        SYNTAX            INTEGER
        MAX-ACCESS        read-write
        STATUS            current
        DESCRIPTION
                "CMNT: - 
                 TYPE: - Number
                 PAGE: - Sidebar Keying & Output Crop
                    Bottom  cmdID= 10094
                    min= 0  max= 99  step= 1  format= %0.0f%%  div_scale= 1  preset= 0
                    Min = 0%  Max = 99%  Step = 1%  Preset = 0%  "
        ::= { kudosConv1CtrlEntries 10094 }


    i1ARCSidebarKeyingOutputCropOutputCropPositionLeft OBJECT-TYPE
        SYNTAX            INTEGER
        MAX-ACCESS        read-write
        STATUS            current
        DESCRIPTION
                "CMNT: - 
                 TYPE: - Number
                 PAGE: - Sidebar Keying & Output Crop
                    Left  cmdID= 10095
                    min= 0  max= 99  step= 1  format= %0.0f%%  div_scale= 1  preset= 0
                    Min = 0%  Max = 99%  Step = 1%  Preset = 0%  "
        ::= { kudosConv1CtrlEntries 10095 }


    i1ARCSidebarKeyingOutputCropOutputCropPositionRight OBJECT-TYPE
        SYNTAX            INTEGER
        MAX-ACCESS        read-write
        STATUS            current
        DESCRIPTION
                "CMNT: - 
                 TYPE: - Number
                 PAGE: - Sidebar Keying & Output Crop
                    Right  cmdID= 10096
                    min= 0  max= 99  step= 1  format= %0.0f%%  div_scale= 1  preset= 0
                    Min = 0%  Max = 99%  Step = 1%  Preset = 0%  "
        ::= { kudosConv1CtrlEntries 10096 }


    i1ARCPostScalingControlPostScalingEnable OBJECT-TYPE
        SYNTAX            INTEGER { disable(0), enable(1)  }
        MAX-ACCESS        read-write
        STATUS            current
        DESCRIPTION
                "CMNT: - 
                 TYPE: - Checkbox
                 PAGE: - ARC
                    Post Scaling Enable  cmdID= 10078  "
        ::= { kudosConv1CtrlEntries 10078 }


    i1ARCPostScalingControlSize OBJECT-TYPE
        SYNTAX            INTEGER
        MAX-ACCESS        read-write
        STATUS            current
        DESCRIPTION
                "CMNT: - 
                 TYPE: - Number
                 PAGE: - ARC
                    Size  cmdID= 10074
                    min= 80  max= 120  step= 1  format= %0.0f%%  div_scale= 1  preset= 100
                    Min = 80%  Max = 120%  Step = 1%  Preset = 100%  "
        ::= { kudosConv1CtrlEntries 10074 }


    i1ARCPostScalingControlAspect OBJECT-TYPE
        SYNTAX            INTEGER
        MAX-ACCESS        read-write
        STATUS            current
        DESCRIPTION
                "CMNT: - 
                 TYPE: - Number
                 PAGE: - ARC
                    Aspect  cmdID= 10075
                    min= 70  max= 150  step= 1  format= %0.0f%%  div_scale= 1  preset= 100
                    Min = 70%  Max = 150%  Step = 1%  Preset = 100%  "
        ::= { kudosConv1CtrlEntries 10075 }


    i1ARCPostScalingControlPan OBJECT-TYPE
        SYNTAX            INTEGER
        MAX-ACCESS        read-write
        STATUS            current
        DESCRIPTION
                "CMNT: - 
                 TYPE: - Number
                 PAGE: - ARC
                    Pan  cmdID= 10076
                    min= -50  max= 50  step= 1  format= %0.0f%  div_scale= 1  preset= 0
                    Min = -50  Max = 50  Step = 1  Preset = 0  "
        ::= { kudosConv1CtrlEntries 10076 }


    i1ARCPostScalingControlTilt OBJECT-TYPE
        SYNTAX            INTEGER
        MAX-ACCESS        read-write
        STATUS            current
        DESCRIPTION
                "CMNT: - 
                 TYPE: - Number
                 PAGE: - ARC
                    Tilt  cmdID= 10077
                    min= -50  max= 50  step= 1  format= %0.0f%  div_scale= 1  preset= 0
                    Min = -50  Max = 50  Step = 1  Preset = 0  "
        ::= { kudosConv1CtrlEntries 10077 }


    i1ARCScalerConfigUsePresets OBJECT-TYPE
        SYNTAX            INTEGER { disable(0), enable(1)  }
        MAX-ACCESS        read-write
        STATUS            current
        DESCRIPTION
                "CMNT: - 
                 TYPE: - Checkbox
                 PAGE: - ARC
                    Use Presets  cmdID= 10110  "
        ::= { kudosConv1CtrlEntries 10110 }


    i1ARCScalerConfigPresetsSDInputis702 OBJECT-TYPE
        SYNTAX            INTEGER { disable(0), enable(1)  }
        MAX-ACCESS        read-write
        STATUS            current
        DESCRIPTION
                "CMNT: - 
                 TYPE: - Checkbox
                 PAGE: - Scaler Config
                    SD Input is 702  cmdID= 10080  "
        ::= { kudosConv1CtrlEntries 10080 }


    i1ARCScalerConfigPresetsSDOutputis702 OBJECT-TYPE
        SYNTAX            INTEGER { disable(0), enable(1)  }
        MAX-ACCESS        read-write
        STATUS            current
        DESCRIPTION
                "CMNT: - 
                 TYPE: - Checkbox
                 PAGE: - Scaler Config
                    SD Output is 702  cmdID= 10081  "
        ::= { kudosConv1CtrlEntries 10081 }


    i1ARCPresetsSDCrossConversionSelectStdPreset OBJECT-TYPE
        SYNTAX            INTEGER {
                            valNone(0),
                            val169LB43HC(1),
                            val169LB169Ana(2),
                            val169LB149LB(3),
                            val169Ana43HC(4),
                            val169Ana169LB(5),
                            val169Ana149LB(6)
                            }
        MAX-ACCESS        read-write
        STATUS            current
        DESCRIPTION
                "CMNT: - 
                 TYPE: - RadiobuttonList
                 PAGE: - Presets
                    Select Std Preset  cmdID= 10082
                    None  value= 0
                    16:9 LB > 4:3 HC  value= 1
                    16:9 LB > 16:9 Ana  value= 2
                    16:9 LB > 14:9 LB  value= 3
                    16:9 Ana > 4:3 HC  value= 4
                    16:9 Ana > 16:9 LB  value= 5
                    16:9 Ana > 14:9 LB  value= 6  "
        ::= { kudosConv1CtrlEntries 10082 }


    i1ARCPresetsHDCrossConversionSelectStdPreset OBJECT-TYPE
        SYNTAX            INTEGER {
                            valNone(0),
                            val149PB169VC(1),
                            val43PB169VC(2),
                            val43PB149PBVC(3)
                            }
        MAX-ACCESS        read-write
        STATUS            current
        DESCRIPTION
                "CMNT: - 
                 TYPE: - RadiobuttonList
                 PAGE: - Presets
                    Select Std Preset  cmdID= 10083
                    None  value= 0
                    14:9 PB > 16:9 VC  value= 1
                    4:3 PB > 16:9 VC  value= 2
                    4:3 PB > 14:9 PB VC  value= 3  "
        ::= { kudosConv1CtrlEntries 10083 }


    i1ARCPresetsUpConversionSelectStdPreset OBJECT-TYPE
        SYNTAX            INTEGER {
                            val43169VC(0),
                            val4343PB(1),
                            val169LB169(2),
                            val169Ana169(3),
                            val149LB149PB(4)
                            }
        MAX-ACCESS        read-write
        STATUS            current
        DESCRIPTION
                "CMNT: - 
                 TYPE: - RadiobuttonList
                 PAGE: - Presets
                    Select Std Preset  cmdID= 10084
                    4:3 > 16:9 VC  value= 0
                    4:3 > 4:3 PB  value= 1
                    16:9 LB > 16:9  value= 2
                    16:9 Ana > 16:9  value= 3
                    14:9 LB > 14:9 PB  value= 4  "
        ::= { kudosConv1CtrlEntries 10084 }


    i1ARCPresetsDownConversionSelectStdPreset OBJECT-TYPE
        SYNTAX            INTEGER {
                            val16943HC(0),
                            val169169LB(1),
                            val169169Ana(2),
                            val43PB43(3),
                            val149PB149LB(4)
                            }
        MAX-ACCESS        read-write
        STATUS            current
        DESCRIPTION
                "CMNT: - 
                 TYPE: - RadiobuttonList
                 PAGE: - Presets
                    Select Std Preset  cmdID= 10085
                    16:9 > 4:3 HC  value= 0
                    16:9 > 16:9 LB  value= 1
                    16:9 > 16:9 Ana  value= 2
                    4:3 PB > 4:3  value= 3
                    14:9 PB > 14:9 LB  value= 4  "
        ::= { kudosConv1CtrlEntries 10085 }


    i1ARCScalerConfigInputConfigInputSignallingSource OBJECT-TYPE
        SYNTAX            INTEGER {
                            valSMPTE2016(0),
                            valL23ETSI(1),
                            valL23AFD(2),
                            valVISMPTE(3),
                            valVIAFD(4)
                            }
        MAX-ACCESS        read-write
        STATUS            current
        DESCRIPTION
                "CMNT: - 
                 TYPE: - RadiobuttonList
                 PAGE: - Scaler Config
                    Input Signalling Source  cmdID= 10090
                    SMPTE 2016  value= 0
                    L23 ETSI  value= 1
                    L23 AFD  value= 2
                    VI SMPTE  value= 3
                    VI AFD  value= 4  "
        ::= { kudosConv1CtrlEntries 10090 }


    i1ARCInputConfigIfInputSignallingNotPresentForceInputFormat OBJECT-TYPE
        SYNTAX            INTEGER { disable(0), enable(1)  }
        MAX-ACCESS        read-write
        STATUS            current
        DESCRIPTION
                "CMNT: - 
                 TYPE: - Checkbox
                 PAGE: - Input Config
                    Force Input Format  cmdID= 10109  "
        ::= { kudosConv1CtrlEntries 10109 }


    i1ARCInputConfigIfInputSignallingNotPresentSDInputFormat OBJECT-TYPE
        SYNTAX            INTEGER {
                            valNormal(0),
                            valAnamorphic(1),
                            val169Letterbox(2),
                            val149Letterbox(3)
                            }
        MAX-ACCESS        read-write
        STATUS            current
        DESCRIPTION
                "CMNT: - 
                 TYPE: - RadiobuttonList
                 PAGE: - Input Config
                    SD Input Format  cmdID= 10086
                    Normal  value= 0
                    Anamorphic  value= 1
                    16:9 Letterbox  value= 2
                    14:9 Letterbox  value= 3  "
        ::= { kudosConv1CtrlEntries 10086 }


    i1ARCInputConfigIfInputSignallingNotPresentHDInputFormat OBJECT-TYPE
        SYNTAX            INTEGER {
                            valNormal(0),
                            val149Pillarbox(1),
                            val43Pillarbox(2)
                            }
        MAX-ACCESS        read-write
        STATUS            current
        DESCRIPTION
                "CMNT: - 
                 TYPE: - RadiobuttonList
                 PAGE: - Input Config
                    HD Input Format  cmdID= 10087
                    Normal  value= 0
                    14:9 Pillarbox  value= 1
                    4:3 Pillarbox  value= 2  "
        ::= { kudosConv1CtrlEntries 10087 }


    i1ARCScalerConfigOutputConfigConversionScaling OBJECT-TYPE
        SYNTAX            INTEGER {
                            valFittoHeight(0),
                            valFittoWidth(1),
                            val149(2)
                            }
        MAX-ACCESS        read-write
        STATUS            current
        DESCRIPTION
                "CMNT: - 
                 TYPE: - RadiobuttonList
                 PAGE: - Scaler Config
                    Conversion Scaling  cmdID= 10089
                    Fit to Height  value= 0
                    Fit to Width  value= 1
                    14:9  value= 2  "
        ::= { kudosConv1CtrlEntries 10089 }


    i1ARCScalerConfigOutputConfigSDOutputFormat OBJECT-TYPE
        SYNTAX            INTEGER {
                            valNormal(0),
                            valAnamorphic(1)
                            }
        MAX-ACCESS        read-write
        STATUS            current
        DESCRIPTION
                "CMNT: - 
                 TYPE: - RadiobuttonList
                 PAGE: - Scaler Config
                    SD Output Format  cmdID= 10088
                    Normal  value= 0
                    Anamorphic  value= 1  "
        ::= { kudosConv1CtrlEntries 10088 }


    i1ARCOutputSignallingConfigSMPTE2016Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10104
                    Auto  value= 0
                    Pass  value= 1
                    Force  value= 2
                    Delete  value= 3  "
        ::= { kudosConv1CtrlEntries 10104 }


    i1ARCOutputSignallingConfigSMPTE2016OutputLinePAL OBJECT-TYPE
        SYNTAX            INTEGER
        MAX-ACCESS        read-write
        STATUS            current
        DESCRIPTION
                "CMNT: - 
                 TYPE: - Number
                 PAGE: - Output Signalling Config
                    Output Line PAL  cmdID= 10332
                    min= 7  max= 22  step= 1  format= %0.0f  div_scale= 1  preset= 12
                    Min = 7  Max = 22  Step = 1  Preset = 12  "
        ::= { kudosConv1CtrlEntries 10332 }


    i1ARCOutputSignallingConfigSMPTE2016OutputLineNTSC OBJECT-TYPE
        SYNTAX            INTEGER
        MAX-ACCESS        read-write
        STATUS            current
        DESCRIPTION
                "CMNT: - 
                 TYPE: - Number
                 PAGE: - Output Signalling Config
                    Output Line NTSC  cmdID= 10333
                    min= 11  max= 19  step= 1  format= %0.0f  div_scale= 1  preset= 11
                    Min = 11  Max = 19  Step = 1  Preset = 11  "
        ::= { kudosConv1CtrlEntries 10333 }


    i1ARCOutputSignallingConfigSMPTE2016OutputLineHD OBJECT-TYPE
        SYNTAX            INTEGER
        MAX-ACCESS        read-write
        STATUS            current
        DESCRIPTION
                "CMNT: - 
                 TYPE: - Number
                 PAGE: - Output Signalling Config
                    Output Line HD  cmdID= 10331
                    min= 9  max= 20  step= 1  format= %0.0f  div_scale= 1  preset= 11
                    Min = 9  Max = 20  Step = 1  Preset = 11  "
        ::= { kudosConv1CtrlEntries 10331 }


    i1ARCOutputSignallingConfigSMPTE2016OutputLineStatus OBJECT-TYPE
        SYNTAX            RollCallString
        MAX-ACCESS        read-only
        STATUS            current
        DESCRIPTION
                "CMNT: - 
                 TYPE: - Display
                 PAGE: - Output Signalling Config
                    Output Line Status  cmdID= 10334  "
        ::= { kudosConv1CtrlEntries 10334 }


    i1ARCOutputSignallingConfigVIMode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10101
                    Auto  value= 0
                    Pass  value= 1
                    Force  value= 2
                    Delete  value= 3  "
        ::= { kudosConv1CtrlEntries 10101 }


    i1ARCOutputSignallingConfigVIOutputFormat OBJECT-TYPE
        SYNTAX            INTEGER {
                            valSMPTE(0),
                            valAFD(1)
                            }
        MAX-ACCESS        read-write
        STATUS            current
        DESCRIPTION
                "CMNT: - 
                 TYPE: - RadiobuttonList
                 PAGE: - Output Signalling Config
                    Output Format  cmdID= 10102
                    SMPTE  value= 0
                    AFD  value= 1  "
        ::= { kudosConv1CtrlEntries 10102 }


    i1ARCOutputSignallingConfigVIPassData OBJECT-TYPE
        SYNTAX            INTEGER { disable(0), enable(1)  }
        MAX-ACCESS        read-write
        STATUS            current
        DESCRIPTION
                "CMNT: - 
                 TYPE: - Checkbox
                 PAGE: - ARC
                    VI Pass Data  cmdID= 10103  "
        ::= { kudosConv1CtrlEntries 10103 }


    i1ARCOutputSignallingConfigL23Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10099
                    Auto  value= 0
                    Pass  value= 1
                    Force  value= 2
                    Delete  value= 3  "
        ::= { kudosConv1CtrlEntries 10099 }


    i1ARCOutputSignallingConfigL23OutputFormat OBJECT-TYPE
        SYNTAX            INTEGER {
                            valETSI(0),
                            valAFD(1)
                            }
        MAX-ACCESS        read-write
        STATUS            current
        DESCRIPTION
                "CMNT: - 
                 TYPE: - RadiobuttonList
                 PAGE: - Output Signalling Config
                    Output Format  cmdID= 10100
                    ETSI  value= 0
                    AFD  value= 1  "
        ::= { kudosConv1CtrlEntries 10100 }


    i1ARCOutputSignallingConfigL23InputLine OBJECT-TYPE
        SYNTAX            INTEGER
        MAX-ACCESS        read-write
        STATUS            current
        DESCRIPTION
                "CMNT: - 
                 TYPE: - Number
                 PAGE: - Output Signalling Config
                    Input Line  cmdID= 10097
                    min= 10  max= 23  step= 1  format= %0.0f  div_scale= 1  preset= 23
                    Min = 10  Max = 23  Step = 1  Preset = 23  "
        ::= { kudosConv1CtrlEntries 10097 }


    i1ARCOutputSignallingConfigL23OutputLine OBJECT-TYPE
        SYNTAX            INTEGER
        MAX-ACCESS        read-write
        STATUS            current
        DESCRIPTION
                "CMNT: - 
                 TYPE: - Number
                 PAGE: - Output Signalling Config
                    Output Line  cmdID= 10098
                    min= 10  max= 23  step= 1  format= %0.0f  div_scale= 1  preset= 23
                    Min = 10  Max = 23  Step = 1  Preset = 23  "
        ::= { kudosConv1CtrlEntries 10098 }


    i1ARCOutputSignallingConfigL23OutputLineStatus OBJECT-TYPE
        SYNTAX            RollCallString
        MAX-ACCESS        read-only
        STATUS            current
        DESCRIPTION
                "CMNT: - 
                 TYPE: - Display
                 PAGE: - Output Signalling Config
                    Output Line Status  cmdID= 10339  "
        ::= { kudosConv1CtrlEntries 10339 }


    i1ARCL23AFDUserBitsForceUserBitsValue OBJECT-TYPE
        SYNTAX            INTEGER { disable(0), enable(1)  }
        MAX-ACCESS        read-write
        STATUS            current
        DESCRIPTION
                "CMNT: - 
                 TYPE: - Checkbox
                 PAGE: - L23
                    Force User Bits Value  cmdID= 10336  "
        ::= { kudosConv1CtrlEntries 10336 }


    i1ARCL23AFDUserBitsUserBitsValue OBJECT-TYPE
        SYNTAX            INTEGER
        MAX-ACCESS        read-write
        STATUS            current
        DESCRIPTION
                "CMNT: - 
                 TYPE: - Number
                 PAGE: - L23
                    User Bits Value  cmdID= 10111
                    min= 0  max= 15  step= 1  format= %0.0f  div_scale= 1  preset= 0
                    Min = 0  Max = 15  Step = 1  Preset = 0  "
        ::= { kudosConv1CtrlEntries 10111 }


    i1ARCOutputSignallingConfigForceModeConfigSMPTE2016 OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val43AFD8(8),
                            val43AFD9(9),
                            val43AFD10(10),
                            val43AFD11(11),
                            val43AFD12(12),
                            val43AFD13(13),
                            val43AFD14(14),
                            val43AFD15(15),
                            val169AFD0(16),
                            val169AFD1(17),
                            val169AFD2(18),
                            val169AFD3(19),
                            val169AFD4(20),
                            val169AFD5(21),
                            val169AFD6(22),
                            val169AFD7(23),
                            val169AFD8(24),
                            val169AFD9(25),
                            val169AFD10(26),
                            val169AFD11(27),
                            val169AFD12(28),
                            val169AFD13(29),
                            val169AFD14(30),
                            val169AFD15(31)
                            }
        MAX-ACCESS        read-write
        STATUS            current
        DESCRIPTION
                "CMNT: - 
                 TYPE: - RadiobuttonList
                 PAGE: - Output Signalling Config
                    SMPTE 2016  cmdID= 10107
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    4:3 AFD 8  value= 8
                    4:3 AFD 9  value= 9
                    4:3 AFD 10  value= 10
                    4:3 AFD 11  value= 11
                    4:3 AFD 12  value= 12
                    4:3 AFD 13  value= 13
                    4:3 AFD 14  value= 14
                    4:3 AFD 15  value= 15
                    16:9 AFD 0  value= 16
                    16:9 AFD 1  value= 17
                    16:9 AFD 2  value= 18
                    16:9 AFD 3  value= 19
                    16:9 AFD 4  value= 20
                    16:9 AFD 5  value= 21
                    16:9 AFD 6  value= 22
                    16:9 AFD 7  value= 23
                    16:9 AFD 8  value= 24
                    16:9 AFD 9  value= 25
                    16:9 AFD 10  value= 26
                    16:9 AFD 11  value= 27
                    16:9 AFD 12  value= 28
                    16:9 AFD 13  value= 29
                    16:9 AFD 14  value= 30
                    16:9 AFD 15  value= 31  "
        ::= { kudosConv1CtrlEntries 10107 }


    i1ARCOutputSignallingConfigForceModeConfigSMPTERP186 OBJECT-TYPE
        SYNTAX            INTEGER {
                            val43(0),
                            val169(1)
                            }
        MAX-ACCESS        read-write
        STATUS            current
        DESCRIPTION
                "CMNT: - 
                 TYPE: - RadiobuttonList
                 PAGE: - Output Signalling Config
                    SMPTE RP186  cmdID= 10108
                    4:3  value= 0
                    16:9  value= 1  "
        ::= { kudosConv1CtrlEntries 10108 }


    i1ARCOutputSignallingConfigForceModeConfigAFD OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val169AFD0(8),
                            val169AFD1(9),
                            val169AFD2(10),
                            val169AFD3(11),
                            val169AFD4(12),
                            val169AFD5(13),
                            val169AFD6(14),
                            val169AFD7(15)
                            }
        MAX-ACCESS        read-write
        STATUS            current
        DESCRIPTION
                "CMNT: - 
                 TYPE: - RadiobuttonList
                 PAGE: - Output Signalling Config
                    AFD  cmdID= 10105
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    16:9 AFD 0  value= 8
                    16:9 AFD 1  value= 9
                    16:9 AFD 2  value= 10
                    16:9 AFD 3  value= 11
                    16:9 AFD 4  value= 12
                    16:9 AFD 5  value= 13
                    16:9 AFD 6  value= 14
                    16:9 AFD 7  value= 15  "
        ::= { kudosConv1CtrlEntries 10105 }


    i1ARCOutputSignallingConfigForceModeConfigETSI OBJECT-TYPE
        SYNTAX            INTEGER {
                            val43FF(0),
                            val149Centre(1),
                            val149Top(2),
                            val169Centre(3),
                            val169Top(4),
                            valGr169Centre(5),
                            val43SP149(6),
                            val169FF(7)
                            }
        MAX-ACCESS        read-write
        STATUS            current
        DESCRIPTION
                "CMNT: - 
                 TYPE: - RadiobuttonList
                 PAGE: - Output Signalling Config
                    ETSI  cmdID= 10106
                    4:3 FF  value= 0
                    14:9 Centre  value= 1
                    14:9 Top  value= 2
                    16:9 Centre  value= 3
                    16:9 Top  value= 4
                    Gr 16:9 Centre  value= 5
                    4:3 SP 14:9  value= 6
                    16:9 FF  value= 7  "
        ::= { kudosConv1CtrlEntries 10106 }


    i1AudioRoutingInputPairsStatusEmbedded1 OBJECT-TYPE
        SYNTAX            RollCallString
        MAX-ACCESS        read-only
        STATUS            current
        DESCRIPTION
                "CMNT: - 
                 TYPE: - Display
                 PAGE: - Routing
                    Embedded 1  cmdID= 10282  "
        ::= { kudosConv1CtrlEntries 10282 }


    i1AudioRoutingInputPairsStatusEmbedded2 OBJECT-TYPE
        SYNTAX            RollCallString
        MAX-ACCESS        read-only
        STATUS            current
        DESCRIPTION
                "CMNT: - 
                 TYPE: - Display
                 PAGE: - Routing
                    Embedded 2  cmdID= 10283  "
        ::= { kudosConv1CtrlEntries 10283 }


    i1AudioRoutingInputPairsStatusEmbedded3 OBJECT-TYPE
        SYNTAX            RollCallString
        MAX-ACCESS        read-only
        STATUS            current
        DESCRIPTION
                "CMNT: - 
                 TYPE: - Display
                 PAGE: - Routing
                    Embedded 3  cmdID= 10284  "
        ::= { kudosConv1CtrlEntries 10284 }


    i1AudioRoutingInputPairsStatusEmbedded4 OBJECT-TYPE
        SYNTAX            RollCallString
        MAX-ACCESS        read-only
        STATUS            current
        DESCRIPTION
                "CMNT: - 
                 TYPE: - Display
                 PAGE: - Routing
                    Embedded 4  cmdID= 10285  "
        ::= { kudosConv1CtrlEntries 10285 }


    i1AudioRoutingInputPairsStatusEmbedded5 OBJECT-TYPE
        SYNTAX            RollCallString
        MAX-ACCESS        read-only
        STATUS            current
        DESCRIPTION
                "CMNT: - 
                 TYPE: - Display
                 PAGE: - Routing
                    Embedded 5  cmdID= 10286  "
        ::= { kudosConv1CtrlEntries 10286 }


    i1AudioRoutingInputPairsStatusEmbedded6 OBJECT-TYPE
        SYNTAX            RollCallString
        MAX-ACCESS        read-only
        STATUS            current
        DESCRIPTION
                "CMNT: - 
                 TYPE: - Display
                 PAGE: - Routing
                    Embedded 6  cmdID= 10287  "
        ::= { kudosConv1CtrlEntries 10287 }


    i1AudioRoutingInputPairsStatusEmbedded7 OBJECT-TYPE
        SYNTAX            RollCallString
        MAX-ACCESS        read-only
        STATUS            current
        DESCRIPTION
                "CMNT: - 
                 TYPE: - Display
                 PAGE: - Routing
                    Embedded 7  cmdID= 10288  "
        ::= { kudosConv1CtrlEntries 10288 }


    i1AudioRoutingInputPairsStatusEmbedded8 OBJECT-TYPE
        SYNTAX            RollCallString
        MAX-ACCESS        read-only
        STATUS            current
        DESCRIPTION
                "CMNT: - 
                 TYPE: - Display
                 PAGE: - Routing
                    Embedded 8  cmdID= 10289  "
        ::= { kudosConv1CtrlEntries 10289 }


    i1AudioRoutingInputPairsStatusAES1 OBJECT-TYPE
        SYNTAX            RollCallString
        MAX-ACCESS        read-only
        STATUS            current
        DESCRIPTION
                "CMNT: - 
                 TYPE: - Display
                 PAGE: - Routing
                    AES 1  cmdID= 10290  "
        ::= { kudosConv1CtrlEntries 10290 }


    i1AudioRoutingInputPairsStatusAES2 OBJECT-TYPE
        SYNTAX            RollCallString
        MAX-ACCESS        read-only
        STATUS            current
        DESCRIPTION
                "CMNT: - 
                 TYPE: - Display
                 PAGE: - Routing
                    AES 2  cmdID= 10291  "
        ::= { kudosConv1CtrlEntries 10291 }


    i1AudioRoutingInputPairsStatusAES3 OBJECT-TYPE
        SYNTAX            RollCallString
        MAX-ACCESS        read-only
        STATUS            current
        DESCRIPTION
                "CMNT: - 
                 TYPE: - Display
                 PAGE: - Routing
                    AES 3  cmdID= 10292  "
        ::= { kudosConv1CtrlEntries 10292 }


    i1AudioRoutingInputPairsStatusAES4 OBJECT-TYPE
        SYNTAX            RollCallString
        MAX-ACCESS        read-only
        STATUS            current
        DESCRIPTION
                "CMNT: - 
                 TYPE: - Display
                 PAGE: - Routing
                    AES 4  cmdID= 10293  "
        ::= { kudosConv1CtrlEntries 10293 }


    i1AudioRoutingInputPairsStatusAnalog1 OBJECT-TYPE
        SYNTAX            RollCallString
        MAX-ACCESS        read-only
        STATUS            current
        DESCRIPTION
                "CMNT: - 
                 TYPE: - Display
                 PAGE: - Routing
                    Analog 1  cmdID= 10294  "
        ::= { kudosConv1CtrlEntries 10294 }


    i1AudioRoutingInputPairsStatusAnalog2 OBJECT-TYPE
        SYNTAX            RollCallString
        MAX-ACCESS        read-only
        STATUS            current
        DESCRIPTION
                "CMNT: - 
                 TYPE: - Display
                 PAGE: - Routing
                    Analog 2  cmdID= 10295  "
        ::= { kudosConv1CtrlEntries 10295 }


    i1AudioRoutingInputPairsStatusAnalog3 OBJECT-TYPE
        SYNTAX            RollCallString
        MAX-ACCESS        read-only
        STATUS            current
        DESCRIPTION
                "CMNT: - 
                 TYPE: - Display
                 PAGE: - Routing
                    Analog 3  cmdID= 10296  "
        ::= { kudosConv1CtrlEntries 10296 }


    i1AudioRoutingInputPairsStatusAnalog4 OBJECT-TYPE
        SYNTAX            RollCallString
        MAX-ACCESS        read-only
        STATUS            current
        DESCRIPTION
                "CMNT: - 
                 TYPE: - Display
                 PAGE: - Routing
                    Analog 4  cmdID= 10297  "
        ::= { kudosConv1CtrlEntries 10297 }


    i1AudioRoutingInputPairsStatusDolbyDecoder1 OBJECT-TYPE
        SYNTAX            RollCallString
        MAX-ACCESS        read-only
        STATUS            current
        DESCRIPTION
                "CMNT: - 
                 TYPE: - Display
                 PAGE: - Routing
                    Dolby Decoder 1  cmdID= 10298  "
        ::= { kudosConv1CtrlEntries 10298 }


    i1AudioRoutingInputPairsStatusDolbyDecoder2 OBJECT-TYPE
        SYNTAX            RollCallString
        MAX-ACCESS        read-only
        STATUS            current
        DESCRIPTION
                "CMNT: - 
                 TYPE: - Display
                 PAGE: - Routing
                    Dolby Decoder 2  cmdID= 10299  "
        ::= { kudosConv1CtrlEntries 10299 }


    i1AudioRoutingInputPairsStatusDolbyDecoder3 OBJECT-TYPE
        SYNTAX            RollCallString
        MAX-ACCESS        read-only
        STATUS            current
        DESCRIPTION
                "CMNT: - 
                 TYPE: - Display
                 PAGE: - Routing
                    Dolby Decoder 3  cmdID= 10300  "
        ::= { kudosConv1CtrlEntries 10300 }


    i1AudioRoutingInputPairsStatusDolbyDecoder4 OBJECT-TYPE
        SYNTAX            RollCallString
        MAX-ACCESS        read-only
        STATUS            current
        DESCRIPTION
                "CMNT: - 
                 TYPE: - Display
                 PAGE: - Routing
                    Dolby Decoder 4  cmdID= 10301  "
        ::= { kudosConv1CtrlEntries 10301 }


    i1AudioRoutingInputPairsStatusDolbyDownmix OBJECT-TYPE
        SYNTAX            RollCallString
        MAX-ACCESS        read-only
        STATUS            current
        DESCRIPTION
                "CMNT: - 
                 TYPE: - Display
                 PAGE: - Routing
                    Dolby Downmix  cmdID= 10302  "
        ::= { kudosConv1CtrlEntries 10302 }


    i1AudioRoutingInputPairsStatusDolbyEncoder OBJECT-TYPE
        SYNTAX            RollCallString
        MAX-ACCESS        read-only
        STATUS            current
        DESCRIPTION
                "CMNT: - 
                 TYPE: - Display
                 PAGE: - Routing
                    Dolby Encoder  cmdID= 10303  "
        ::= { kudosConv1CtrlEntries 10303 }


    i1AudioRoutingProcessPair1InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10112
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv1CtrlEntries 10112 }


    i1AudioRoutingProcessPair2InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10113
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv1CtrlEntries 10113 }


    i1AudioRoutingProcessPair3InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10114
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv1CtrlEntries 10114 }


    i1AudioRoutingProcessPair4InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10115
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv1CtrlEntries 10115 }


    i1AudioRoutingProcessPair5InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10116
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv1CtrlEntries 10116 }


    i1AudioRoutingProcessPair6InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10117
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv1CtrlEntries 10117 }


    i1AudioRoutingProcessPair7InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10118
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv1CtrlEntries 10118 }


    i1AudioRoutingProcessPair8InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10119
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv1CtrlEntries 10119 }


    i1AudioRoutingProcessPairs18StatusPair1 OBJECT-TYPE
        SYNTAX            RollCallString
        MAX-ACCESS        read-only
        STATUS            current
        DESCRIPTION
                "CMNT: - 
                 TYPE: - Display
                 PAGE: - Routing
                    Pair 1  cmdID= 10304  "
        ::= { kudosConv1CtrlEntries 10304 }


    i1AudioRoutingProcessPairs18StatusPair2 OBJECT-TYPE
        SYNTAX            RollCallString
        MAX-ACCESS        read-only
        STATUS            current
        DESCRIPTION
                "CMNT: - 
                 TYPE: - Display
                 PAGE: - Routing
                    Pair 2  cmdID= 10305  "
        ::= { kudosConv1CtrlEntries 10305 }


    i1AudioRoutingProcessPairs18StatusPair3 OBJECT-TYPE
        SYNTAX            RollCallString
        MAX-ACCESS        read-only
        STATUS            current
        DESCRIPTION
                "CMNT: - 
                 TYPE: - Display
                 PAGE: - Routing
                    Pair 3  cmdID= 10306  "
        ::= { kudosConv1CtrlEntries 10306 }


    i1AudioRoutingProcessPairs18StatusPair4 OBJECT-TYPE
        SYNTAX            RollCallString
        MAX-ACCESS        read-only
        STATUS            current
        DESCRIPTION
                "CMNT: - 
                 TYPE: - Display
                 PAGE: - Routing
                    Pair 4  cmdID= 10307  "
        ::= { kudosConv1CtrlEntries 10307 }


    i1AudioRoutingProcessPairs18StatusPair5 OBJECT-TYPE
        SYNTAX            RollCallString
        MAX-ACCESS        read-only
        STATUS            current
        DESCRIPTION
                "CMNT: - 
                 TYPE: - Display
                 PAGE: - Routing
                    Pair 5  cmdID= 10308  "
        ::= { kudosConv1CtrlEntries 10308 }


    i1AudioRoutingProcessPairs18StatusPair6 OBJECT-TYPE
        SYNTAX            RollCallString
        MAX-ACCESS        read-only
        STATUS            current
        DESCRIPTION
                "CMNT: - 
                 TYPE: - Display
                 PAGE: - Routing
                    Pair 6  cmdID= 10309  "
        ::= { kudosConv1CtrlEntries 10309 }


    i1AudioRoutingProcessPairs18StatusPair7 OBJECT-TYPE
        SYNTAX            RollCallString
        MAX-ACCESS        read-only
        STATUS            current
        DESCRIPTION
                "CMNT: - 
                 TYPE: - Display
                 PAGE: - Routing
                    Pair 7  cmdID= 10310  "
        ::= { kudosConv1CtrlEntries 10310 }


    i1AudioRoutingProcessPairs18StatusPair8 OBJECT-TYPE
        SYNTAX            RollCallString
        MAX-ACCESS        read-only
        STATUS            current
        DESCRIPTION
                "CMNT: - 
                 TYPE: - Display
                 PAGE: - Routing
                    Pair 8  cmdID= 10311  "
        ::= { kudosConv1CtrlEntries 10311 }


    i1AudioControlGainPair1L OBJECT-TYPE
        SYNTAX            INTEGER
        MAX-ACCESS        read-write
        STATUS            current
        DESCRIPTION
                "CMNT: - 
                 TYPE: - Number
                 PAGE: - Control
                    Pair 1 L  cmdID= 10120
                    min= -180  max= 180  step= 1  format= %0.1fdB  div_scale= 10  preset= 0
                    Min = -18.0dB  Max = 18.0dB  Step = 0.1dB  Preset = 0.0dB  "
        ::= { kudosConv1CtrlEntries 10120 }


    i1AudioControlGainPair1R OBJECT-TYPE
        SYNTAX            INTEGER
        MAX-ACCESS        read-write
        STATUS            current
        DESCRIPTION
                "CMNT: - 
                 TYPE: - Number
                 PAGE: - Control
                    Pair 1 R  cmdID= 10121
                    min= -180  max= 180  step= 1  format= %0.1fdB  div_scale= 10  preset= 0
                    Min = -18.0dB  Max = 18.0dB  Step = 0.1dB  Preset = 0.0dB  "
        ::= { kudosConv1CtrlEntries 10121 }


    i1AudioControlGainPair2L OBJECT-TYPE
        SYNTAX            INTEGER
        MAX-ACCESS        read-write
        STATUS            current
        DESCRIPTION
                "CMNT: - 
                 TYPE: - Number
                 PAGE: - Control
                    Pair 2 L  cmdID= 10122
                    min= -180  max= 180  step= 1  format= %0.1fdB  div_scale= 10  preset= 0
                    Min = -18.0dB  Max = 18.0dB  Step = 0.1dB  Preset = 0.0dB  "
        ::= { kudosConv1CtrlEntries 10122 }


    i1AudioControlGainPair2R OBJECT-TYPE
        SYNTAX            INTEGER
        MAX-ACCESS        read-write
        STATUS            current
        DESCRIPTION
                "CMNT: - 
                 TYPE: - Number
                 PAGE: - Control
                    Pair 2 R  cmdID= 10123
                    min= -180  max= 180  step= 1  format= %0.1fdB  div_scale= 10  preset= 0
                    Min = -18.0dB  Max = 18.0dB  Step = 0.1dB  Preset = 0.0dB  "
        ::= { kudosConv1CtrlEntries 10123 }


    i1AudioControlGainPair3L OBJECT-TYPE
        SYNTAX            INTEGER
        MAX-ACCESS        read-write
        STATUS            current
        DESCRIPTION
                "CMNT: - 
                 TYPE: - Number
                 PAGE: - Control
                    Pair 3 L  cmdID= 10124
                    min= -180  max= 180  step= 1  format= %0.1fdB  div_scale= 10  preset= 0
                    Min = -18.0dB  Max = 18.0dB  Step = 0.1dB  Preset = 0.0dB  "
        ::= { kudosConv1CtrlEntries 10124 }


    i1AudioControlGainPair3R OBJECT-TYPE
        SYNTAX            INTEGER
        MAX-ACCESS        read-write
        STATUS            current
        DESCRIPTION
                "CMNT: - 
                 TYPE: - Number
                 PAGE: - Control
                    Pair 3 R  cmdID= 10125
                    min= -180  max= 180  step= 1  format= %0.1fdB  div_scale= 10  preset= 0
                    Min = -18.0dB  Max = 18.0dB  Step = 0.1dB  Preset = 0.0dB  "
        ::= { kudosConv1CtrlEntries 10125 }


    i1AudioControlGainPair4L OBJECT-TYPE
        SYNTAX            INTEGER
        MAX-ACCESS        read-write
        STATUS            current
        DESCRIPTION
                "CMNT: - 
                 TYPE: - Number
                 PAGE: - Control
                    Pair 4 L  cmdID= 10126
                    min= -180  max= 180  step= 1  format= %0.1fdB  div_scale= 10  preset= 0
                    Min = -18.0dB  Max = 18.0dB  Step = 0.1dB  Preset = 0.0dB  "
        ::= { kudosConv1CtrlEntries 10126 }


    i1AudioControlGainPair4R OBJECT-TYPE
        SYNTAX            INTEGER
        MAX-ACCESS        read-write
        STATUS            current
        DESCRIPTION
                "CMNT: - 
                 TYPE: - Number
                 PAGE: - Control
                    Pair 4 R  cmdID= 10127
                    min= -180  max= 180  step= 1  format= %0.1fdB  div_scale= 10  preset= 0
                    Min = -18.0dB  Max = 18.0dB  Step = 0.1dB  Preset = 0.0dB  "
        ::= { kudosConv1CtrlEntries 10127 }


    i1AudioControlGainPair5L OBJECT-TYPE
        SYNTAX            INTEGER
        MAX-ACCESS        read-write
        STATUS            current
        DESCRIPTION
                "CMNT: - 
                 TYPE: - Number
                 PAGE: - Control
                    Pair 5 L  cmdID= 10128
                    min= -180  max= 180  step= 1  format= %0.1fdB  div_scale= 10  preset= 0
                    Min = -18.0dB  Max = 18.0dB  Step = 0.1dB  Preset = 0.0dB  "
        ::= { kudosConv1CtrlEntries 10128 }


    i1AudioControlGainPair5R OBJECT-TYPE
        SYNTAX            INTEGER
        MAX-ACCESS        read-write
        STATUS            current
        DESCRIPTION
                "CMNT: - 
                 TYPE: - Number
                 PAGE: - Control
                    Pair 5 R  cmdID= 10129
                    min= -180  max= 180  step= 1  format= %0.1fdB  div_scale= 10  preset= 0
                    Min = -18.0dB  Max = 18.0dB  Step = 0.1dB  Preset = 0.0dB  "
        ::= { kudosConv1CtrlEntries 10129 }


    i1AudioControlGainPair6L OBJECT-TYPE
        SYNTAX            INTEGER
        MAX-ACCESS        read-write
        STATUS            current
        DESCRIPTION
                "CMNT: - 
                 TYPE: - Number
                 PAGE: - Control
                    Pair 6 L  cmdID= 10130
                    min= -180  max= 180  step= 1  format= %0.1fdB  div_scale= 10  preset= 0
                    Min = -18.0dB  Max = 18.0dB  Step = 0.1dB  Preset = 0.0dB  "
        ::= { kudosConv1CtrlEntries 10130 }


    i1AudioControlGainPair6R OBJECT-TYPE
        SYNTAX            INTEGER
        MAX-ACCESS        read-write
        STATUS            current
        DESCRIPTION
                "CMNT: - 
                 TYPE: - Number
                 PAGE: - Control
                    Pair 6 R  cmdID= 10131
                    min= -180  max= 180  step= 1  format= %0.1fdB  div_scale= 10  preset= 0
                    Min = -18.0dB  Max = 18.0dB  Step = 0.1dB  Preset = 0.0dB  "
        ::= { kudosConv1CtrlEntries 10131 }


    i1AudioControlGainPair7L OBJECT-TYPE
        SYNTAX            INTEGER
        MAX-ACCESS        read-write
        STATUS            current
        DESCRIPTION
                "CMNT: - 
                 TYPE: - Number
                 PAGE: - Control
                    Pair 7 L  cmdID= 10132
                    min= -180  max= 180  step= 1  format= %0.1fdB  div_scale= 10  preset= 0
                    Min = -18.0dB  Max = 18.0dB  Step = 0.1dB  Preset = 0.0dB  "
        ::= { kudosConv1CtrlEntries 10132 }


    i1AudioControlGainPair7R OBJECT-TYPE
        SYNTAX            INTEGER
        MAX-ACCESS        read-write
        STATUS            current
        DESCRIPTION
                "CMNT: - 
                 TYPE: - Number
                 PAGE: - Control
                    Pair 7 R  cmdID= 10133
                    min= -180  max= 180  step= 1  format= %0.1fdB  div_scale= 10  preset= 0
                    Min = -18.0dB  Max = 18.0dB  Step = 0.1dB  Preset = 0.0dB  "
        ::= { kudosConv1CtrlEntries 10133 }


    i1AudioControlGainPair8L OBJECT-TYPE
        SYNTAX            INTEGER
        MAX-ACCESS        read-write
        STATUS            current
        DESCRIPTION
                "CMNT: - 
                 TYPE: - Number
                 PAGE: - Control
                    Pair 8 L  cmdID= 10134
                    min= -180  max= 180  step= 1  format= %0.1fdB  div_scale= 10  preset= 0
                    Min = -18.0dB  Max = 18.0dB  Step = 0.1dB  Preset = 0.0dB  "
        ::= { kudosConv1CtrlEntries 10134 }


    i1AudioControlGainPair8R OBJECT-TYPE
        SYNTAX            INTEGER
        MAX-ACCESS        read-write
        STATUS            current
        DESCRIPTION
                "CMNT: - 
                 TYPE: - Number
                 PAGE: - Control
                    Pair 8 R  cmdID= 10135
                    min= -180  max= 180  step= 1  format= %0.1fdB  div_scale= 10  preset= 0
                    Min = -18.0dB  Max = 18.0dB  Step = 0.1dB  Preset = 0.0dB  "
        ::= { kudosConv1CtrlEntries 10135 }


    i1AudioControlToneFrequency OBJECT-TYPE
        SYNTAX            INTEGER
        MAX-ACCESS        read-write
        STATUS            current
        DESCRIPTION
                "CMNT: - 
                 TYPE: - Number
                 PAGE: - Audio
                    Tone Frequency  cmdID= 10152
                    min= 100  max= 10000  step= 100  format= %0.1f KHz  div_scale= 1000  preset= 1000
                    Min = 0.1 KHz  Max = 10.0 KHz  Step = 0.1 KHz  Preset = 1.0 KHz  "
        ::= { kudosConv1CtrlEntries 10152 }


    i1AudioControlDolbyEAlignmentOffset OBJECT-TYPE
        SYNTAX            INTEGER
        MAX-ACCESS        read-write
        STATUS            current
        DESCRIPTION
                "CMNT: - 
                 TYPE: - Number
                 PAGE: - Audio
                    Dolby E Alignment Offset  cmdID= 10154
                    min= -10  max= 10  step= 1  format= %0.0f Lines  div_scale= 1  preset= 0
                    Min = -10 Lines  Max = 10 Lines  Step = 1 Lines  Preset = 0 Lines  "
        ::= { kudosConv1CtrlEntries 10154 }


    i1AudioDelayGlobalDelayPairOffsetsPair1 OBJECT-TYPE
        SYNTAX            INTEGER
        MAX-ACCESS        read-write
        STATUS            current
        DESCRIPTION
                "CMNT: - 
                 TYPE: - Number
                 PAGE: - Delay
                    Pair 1  cmdID= 10155
                    min= -40  max= 200  step= 1  format= %0.0f ms  div_scale= 1  preset= 0
                    Min = -40 ms  Max = 200 ms  Step = 1 ms  Preset = 0 ms  "
        ::= { kudosConv1CtrlEntries 10155 }


    i1AudioDelayGlobalDelayPairOffsetsPair1Total OBJECT-TYPE
        SYNTAX            RollCallString
        MAX-ACCESS        read-only
        STATUS            current
        DESCRIPTION
                "CMNT: - 
                 TYPE: - Display
                 PAGE: - Delay
                    Pair 1 Total  cmdID= 10164  "
        ::= { kudosConv1CtrlEntries 10164 }


    i1AudioDelayGlobalDelayPairOffsetsPair2 OBJECT-TYPE
        SYNTAX            INTEGER
        MAX-ACCESS        read-write
        STATUS            current
        DESCRIPTION
                "CMNT: - 
                 TYPE: - Number
                 PAGE: - Delay
                    Pair 2  cmdID= 10156
                    min= -40  max= 200  step= 1  format= %0.0f ms  div_scale= 1  preset= 0
                    Min = -40 ms  Max = 200 ms  Step = 1 ms  Preset = 0 ms  "
        ::= { kudosConv1CtrlEntries 10156 }


    i1AudioDelayGlobalDelayPairOffsetsPair2Total OBJECT-TYPE
        SYNTAX            RollCallString
        MAX-ACCESS        read-only
        STATUS            current
        DESCRIPTION
                "CMNT: - 
                 TYPE: - Display
                 PAGE: - Delay
                    Pair 2 Total  cmdID= 10165  "
        ::= { kudosConv1CtrlEntries 10165 }


    i1AudioDelayGlobalDelayPairOffsetsPair3 OBJECT-TYPE
        SYNTAX            INTEGER
        MAX-ACCESS        read-write
        STATUS            current
        DESCRIPTION
                "CMNT: - 
                 TYPE: - Number
                 PAGE: - Delay
                    Pair 3  cmdID= 10157
                    min= -40  max= 200  step= 1  format= %0.0f ms  div_scale= 1  preset= 0
                    Min = -40 ms  Max = 200 ms  Step = 1 ms  Preset = 0 ms  "
        ::= { kudosConv1CtrlEntries 10157 }


    i1AudioDelayGlobalDelayPairOffsetsPair3Total OBJECT-TYPE
        SYNTAX            RollCallString
        MAX-ACCESS        read-only
        STATUS            current
        DESCRIPTION
                "CMNT: - 
                 TYPE: - Display
                 PAGE: - Delay
                    Pair 3 Total  cmdID= 10166  "
        ::= { kudosConv1CtrlEntries 10166 }


    i1AudioDelayGlobalDelayPairOffsetsPair4 OBJECT-TYPE
        SYNTAX            INTEGER
        MAX-ACCESS        read-write
        STATUS            current
        DESCRIPTION
                "CMNT: - 
                 TYPE: - Number
                 PAGE: - Delay
                    Pair 4  cmdID= 10158
                    min= -40  max= 200  step= 1  format= %0.0f ms  div_scale= 1  preset= 0
                    Min = -40 ms  Max = 200 ms  Step = 1 ms  Preset = 0 ms  "
        ::= { kudosConv1CtrlEntries 10158 }


    i1AudioDelayGlobalDelayPairOffsetsPair4Total OBJECT-TYPE
        SYNTAX            RollCallString
        MAX-ACCESS        read-only
        STATUS            current
        DESCRIPTION
                "CMNT: - 
                 TYPE: - Display
                 PAGE: - Delay
                    Pair 4 Total  cmdID= 10167  "
        ::= { kudosConv1CtrlEntries 10167 }


    i1AudioDelayGlobalDelayPairOffsetsPair5 OBJECT-TYPE
        SYNTAX            INTEGER
        MAX-ACCESS        read-write
        STATUS            current
        DESCRIPTION
                "CMNT: - 
                 TYPE: - Number
                 PAGE: - Delay
                    Pair 5  cmdID= 10159
                    min= -40  max= 200  step= 1  format= %0.0f ms  div_scale= 1  preset= 0
                    Min = -40 ms  Max = 200 ms  Step = 1 ms  Preset = 0 ms  "
        ::= { kudosConv1CtrlEntries 10159 }


    i1AudioDelayGlobalDelayPairOffsetsPair5Total OBJECT-TYPE
        SYNTAX            RollCallString
        MAX-ACCESS        read-only
        STATUS            current
        DESCRIPTION
                "CMNT: - 
                 TYPE: - Display
                 PAGE: - Delay
                    Pair 5 Total  cmdID= 10168  "
        ::= { kudosConv1CtrlEntries 10168 }


    i1AudioDelayGlobalDelayPairOffsetsPair6 OBJECT-TYPE
        SYNTAX            INTEGER
        MAX-ACCESS        read-write
        STATUS            current
        DESCRIPTION
                "CMNT: - 
                 TYPE: - Number
                 PAGE: - Delay
                    Pair 6  cmdID= 10160
                    min= -40  max= 200  step= 1  format= %0.0f ms  div_scale= 1  preset= 0
                    Min = -40 ms  Max = 200 ms  Step = 1 ms  Preset = 0 ms  "
        ::= { kudosConv1CtrlEntries 10160 }


    i1AudioDelayGlobalDelayPairOffsetsPair6Total OBJECT-TYPE
        SYNTAX            RollCallString
        MAX-ACCESS        read-only
        STATUS            current
        DESCRIPTION
                "CMNT: - 
                 TYPE: - Display
                 PAGE: - Delay
                    Pair 6 Total  cmdID= 10169  "
        ::= { kudosConv1CtrlEntries 10169 }


    i1AudioDelayGlobalDelayPairOffsetsPair7 OBJECT-TYPE
        SYNTAX            INTEGER
        MAX-ACCESS        read-write
        STATUS            current
        DESCRIPTION
                "CMNT: - 
                 TYPE: - Number
                 PAGE: - Delay
                    Pair 7  cmdID= 10161
                    min= -40  max= 200  step= 1  format= %0.0f ms  div_scale= 1  preset= 0
                    Min = -40 ms  Max = 200 ms  Step = 1 ms  Preset = 0 ms  "
        ::= { kudosConv1CtrlEntries 10161 }


    i1AudioDelayGlobalDelayPairOffsetsPair7Total OBJECT-TYPE
        SYNTAX            RollCallString
        MAX-ACCESS        read-only
        STATUS            current
        DESCRIPTION
                "CMNT: - 
                 TYPE: - Display
                 PAGE: - Delay
                    Pair 7 Total  cmdID= 10170  "
        ::= { kudosConv1CtrlEntries 10170 }


    i1AudioDelayGlobalDelayPairOffsetsPair8 OBJECT-TYPE
        SYNTAX            INTEGER
        MAX-ACCESS        read-write
        STATUS            current
        DESCRIPTION
                "CMNT: - 
                 TYPE: - Number
                 PAGE: - Delay
                    Pair 8  cmdID= 10162
                    min= -40  max= 200  step= 1  format= %0.0f ms  div_scale= 1  preset= 0
                    Min = -40 ms  Max = 200 ms  Step = 1 ms  Preset = 0 ms  "
        ::= { kudosConv1CtrlEntries 10162 }


    i1AudioDelayGlobalDelayPairOffsetsPair8Total OBJECT-TYPE
        SYNTAX            RollCallString
        MAX-ACCESS        read-only
        STATUS            current
        DESCRIPTION
                "CMNT: - 
                 TYPE: - Display
                 PAGE: - Delay
                    Pair 8 Total  cmdID= 10171  "
        ::= { kudosConv1CtrlEntries 10171 }


    i1AudioDelayGlobalDelayAudio OBJECT-TYPE
        SYNTAX            INTEGER
        MAX-ACCESS        read-write
        STATUS            current
        DESCRIPTION
                "CMNT: - 
                 TYPE: - Number
                 PAGE: - Delay
                    Audio  cmdID= 10163
                    min= -40  max= 200  step= 1  format= %0.0f ms  div_scale= 1  preset= 0
                    Min = -40 ms  Max = 200 ms  Step = 1 ms  Preset = 0 ms  "
        ::= { kudosConv1CtrlEntries 10163 }


    i1AudioDelayGlobalDelayAudioTotal OBJECT-TYPE
        SYNTAX            RollCallString
        MAX-ACCESS        read-only
        STATUS            current
        DESCRIPTION
                "CMNT: - 
                 TYPE: - Display
                 PAGE: - Delay
                    Audio Total  cmdID= 10172  "
        ::= { kudosConv1CtrlEntries 10172 }


    i1AudioDelayGlobalDelayVideoTotal OBJECT-TYPE
        SYNTAX            RollCallString
        MAX-ACCESS        read-only
        STATUS            current
        DESCRIPTION
                "CMNT: - 
                 TYPE: - Display
                 PAGE: - Delay
                    Video Total  cmdID= 10173  "
        ::= { kudosConv1CtrlEntries 10173 }


    i1AudioShuffleOutputPair1LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10182
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10182 }


    i1AudioShuffleOutputPair1LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10198  "
        ::= { kudosConv1CtrlEntries 10198 }


    i1AudioShuffleOutputPair1LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10214
                    Use Routing  value= 0
                    Tone  value= 1
                    Silence  value= 2  "
        ::= { kudosConv1CtrlEntries 10214 }


    i1AudioShuffleOutputPair1RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10190
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10190 }


    i1AudioShuffleOutputPair1RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10206  "
        ::= { kudosConv1CtrlEntries 10206 }


    i1AudioShuffleOutputPair1RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10222
                    Use Routing  value= 0
                    Tone  value= 1
                    Silence  value= 2  "
        ::= { kudosConv1CtrlEntries 10222 }


    i1AudioShuffleOutputPair2LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10183
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10183 }


    i1AudioShuffleOutputPair2LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10199  "
        ::= { kudosConv1CtrlEntries 10199 }


    i1AudioShuffleOutputPair2LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10215
                    Use Routing  value= 0
                    Tone  value= 1
                    Silence  value= 2  "
        ::= { kudosConv1CtrlEntries 10215 }


    i1AudioShuffleOutputPair2RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10191
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10191 }


    i1AudioShuffleOutputPair2RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10207  "
        ::= { kudosConv1CtrlEntries 10207 }


    i1AudioShuffleOutputPair2RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10223
                    Use Routing  value= 0
                    Tone  value= 1
                    Silence  value= 2  "
        ::= { kudosConv1CtrlEntries 10223 }


    i1AudioShuffleOutputPair3LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10184
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10184 }


    i1AudioShuffleOutputPair3LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10200  "
        ::= { kudosConv1CtrlEntries 10200 }


    i1AudioShuffleOutputPair3LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10216
                    Use Routing  value= 0
                    Tone  value= 1
                    Silence  value= 2  "
        ::= { kudosConv1CtrlEntries 10216 }


    i1AudioShuffleOutputPair3RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10192
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10192 }


    i1AudioShuffleOutputPair3RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10208  "
        ::= { kudosConv1CtrlEntries 10208 }


    i1AudioShuffleOutputPair3RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10224
                    Use Routing  value= 0
                    Tone  value= 1
                    Silence  value= 2  "
        ::= { kudosConv1CtrlEntries 10224 }


    i1AudioShuffleOutputPair4LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10185
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10185 }


    i1AudioShuffleOutputPair4LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10201  "
        ::= { kudosConv1CtrlEntries 10201 }


    i1AudioShuffleOutputPair4LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10217
                    Use Routing  value= 0
                    Tone  value= 1
                    Silence  value= 2  "
        ::= { kudosConv1CtrlEntries 10217 }


    i1AudioShuffleOutputPair4RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10193
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10193 }


    i1AudioShuffleOutputPair4RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10209  "
        ::= { kudosConv1CtrlEntries 10209 }


    i1AudioShuffleOutputPair4RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10225
                    Use Routing  value= 0
                    Tone  value= 1
                    Silence  value= 2  "
        ::= { kudosConv1CtrlEntries 10225 }


    i1AudioShuffleOutputPair5LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10186
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10186 }


    i1AudioShuffleOutputPair5LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10202  "
        ::= { kudosConv1CtrlEntries 10202 }


    i1AudioShuffleOutputPair5LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10218
                    Use Routing  value= 0
                    Tone  value= 1
                    Silence  value= 2  "
        ::= { kudosConv1CtrlEntries 10218 }


    i1AudioShuffleOutputPair5RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10194
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10194 }


    i1AudioShuffleOutputPair5RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10210  "
        ::= { kudosConv1CtrlEntries 10210 }


    i1AudioShuffleOutputPair5RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10226
                    Use Routing  value= 0
                    Tone  value= 1
                    Silence  value= 2  "
        ::= { kudosConv1CtrlEntries 10226 }


    i1AudioShuffleOutputPair6LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10187
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10187 }


    i1AudioShuffleOutputPair6LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10203  "
        ::= { kudosConv1CtrlEntries 10203 }


    i1AudioShuffleOutputPair6LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10219
                    Use Routing  value= 0
                    Tone  value= 1
                    Silence  value= 2  "
        ::= { kudosConv1CtrlEntries 10219 }


    i1AudioShuffleOutputPair6RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10195
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10195 }


    i1AudioShuffleOutputPair6RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10211  "
        ::= { kudosConv1CtrlEntries 10211 }


    i1AudioShuffleOutputPair6RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10227
                    Use Routing  value= 0
                    Tone  value= 1
                    Silence  value= 2  "
        ::= { kudosConv1CtrlEntries 10227 }


    i1AudioShuffleOutputPair7LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10188
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10188 }


    i1AudioShuffleOutputPair7LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10204  "
        ::= { kudosConv1CtrlEntries 10204 }


    i1AudioShuffleOutputPair7LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10220
                    Use Routing  value= 0
                    Tone  value= 1
                    Silence  value= 2  "
        ::= { kudosConv1CtrlEntries 10220 }


    i1AudioShuffleOutputPair7RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10196
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10196 }


    i1AudioShuffleOutputPair7RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10212  "
        ::= { kudosConv1CtrlEntries 10212 }


    i1AudioShuffleOutputPair7RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10228
                    Use Routing  value= 0
                    Tone  value= 1
                    Silence  value= 2  "
        ::= { kudosConv1CtrlEntries 10228 }


    i1AudioShuffleOutputPair8LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10189
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10189 }


    i1AudioShuffleOutputPair8LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10205  "
        ::= { kudosConv1CtrlEntries 10205 }


    i1AudioShuffleOutputPair8LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10221
                    Use Routing  value= 0
                    Tone  value= 1
                    Silence  value= 2  "
        ::= { kudosConv1CtrlEntries 10221 }


    i1AudioShuffleOutputPair8RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10197
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv1CtrlEntries 10197 }


    i1AudioShuffleOutputPair8RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10213  "
        ::= { kudosConv1CtrlEntries 10213 }


    i1AudioShuffleOutputPair8RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10229
                    Use Routing  value= 0
                    Tone  value= 1
                    Silence  value= 2  "
        ::= { kudosConv1CtrlEntries 10229 }


    i1AudioShuffleOutputPairs18StatusPair1 OBJECT-TYPE
        SYNTAX            RollCallString
        MAX-ACCESS        read-only
        STATUS            current
        DESCRIPTION
                "CMNT: - 
                 TYPE: - Display
                 PAGE: - Shuffle
                    Pair 1  cmdID= 10174  "
        ::= { kudosConv1CtrlEntries 10174 }


    i1AudioShuffleOutputPairs18StatusPair2 OBJECT-TYPE
        SYNTAX            RollCallString
        MAX-ACCESS        read-only
        STATUS            current
        DESCRIPTION
                "CMNT: - 
                 TYPE: - Display
                 PAGE: - Shuffle
                    Pair 2  cmdID= 10175  "
        ::= { kudosConv1CtrlEntries 10175 }


    i1AudioShuffleOutputPairs18StatusPair3 OBJECT-TYPE
        SYNTAX            RollCallString
        MAX-ACCESS        read-only
        STATUS            current
        DESCRIPTION
                "CMNT: - 
                 TYPE: - Display
                 PAGE: - Shuffle
                    Pair 3  cmdID= 10176  "
        ::= { kudosConv1CtrlEntries 10176 }


    i1AudioShuffleOutputPairs18StatusPair4 OBJECT-TYPE
        SYNTAX            RollCallString
        MAX-ACCESS        read-only
        STATUS            current
        DESCRIPTION
                "CMNT: - 
                 TYPE: - Display
                 PAGE: - Shuffle
                    Pair 4  cmdID= 10177  "
        ::= { kudosConv1CtrlEntries 10177 }


    i1AudioShuffleOutputPairs18StatusPair5 OBJECT-TYPE
        SYNTAX            RollCallString
        MAX-ACCESS        read-only
        STATUS            current
        DESCRIPTION
                "CMNT: - 
                 TYPE: - Display
                 PAGE: - Shuffle
                    Pair 5  cmdID= 10178  "
        ::= { kudosConv1CtrlEntries 10178 }


    i1AudioShuffleOutputPairs18StatusPair6 OBJECT-TYPE
        SYNTAX            RollCallString
        MAX-ACCESS        read-only
        STATUS            current
        DESCRIPTION
                "CMNT: - 
                 TYPE: - Display
                 PAGE: - Shuffle
                    Pair 6  cmdID= 10179  "
        ::= { kudosConv1CtrlEntries 10179 }


    i1AudioShuffleOutputPairs18StatusPair7 OBJECT-TYPE
        SYNTAX            RollCallString
        MAX-ACCESS        read-only
        STATUS            current
        DESCRIPTION
                "CMNT: - 
                 TYPE: - Display
                 PAGE: - Shuffle
                    Pair 7  cmdID= 10180  "
        ::= { kudosConv1CtrlEntries 10180 }


    i1AudioShuffleOutputPairs18StatusPair8 OBJECT-TYPE
        SYNTAX            RollCallString
        MAX-ACCESS        read-only
        STATUS            current
        DESCRIPTION
                "CMNT: - 
                 TYPE: - Display
                 PAGE: - Shuffle
                    Pair 8  cmdID= 10181  "
        ::= { kudosConv1CtrlEntries 10181 }


    i1TimecodeSourceHD OBJECT-TYPE
        SYNTAX            INTEGER {
                            valLTC(0),
                            valVITC(1)
                            }
        MAX-ACCESS        read-write
        STATUS            current
        DESCRIPTION
                "CMNT: - 
                 TYPE: - RadiobuttonList
                 PAGE: - Timecode
                    Source (HD)  cmdID= 10230
                    LTC  value= 0
                    VITC  value= 1  "
        ::= { kudosConv1CtrlEntries 10230 }


    i1TimecodeSourceSD OBJECT-TYPE
        SYNTAX            INTEGER {
                            valVITC(0),
                            valATCLTC(1),
                            valATCVITC(2)
                            }
        MAX-ACCESS        read-write
        STATUS            current
        DESCRIPTION
                "CMNT: - 
                 TYPE: - RadiobuttonList
                 PAGE: - Timecode
                    Source (SD)  cmdID= 10231
                    VITC  value= 0
                    ATC LTC  value= 1
                    ATC VITC  value= 2  "
        ::= { kudosConv1CtrlEntries 10231 }


    i1TimecodeStatus OBJECT-TYPE
        SYNTAX            RollCallString
        MAX-ACCESS        read-only
        STATUS            current
        DESCRIPTION
                "CMNT: - 
                 TYPE: - Display
                 PAGE: - Timecode
                    Status  cmdID= 10239  "
        ::= { kudosConv1CtrlEntries 10239 }


    i1TimecodeMode OBJECT-TYPE
        SYNTAX            INTEGER {
                            valFollowInput(0),
                            valGenerate(1),
                            valInputTrigger(2)
                            }
        MAX-ACCESS        read-write
        STATUS            current
        DESCRIPTION
                "CMNT: - 
                 TYPE: - RadiobuttonList
                 PAGE: - Timecode
                    Mode  cmdID= 10232
                    Follow Input  value= 0
                    Generate  value= 1
                    Input Trigger  value= 2  "
        ::= { kudosConv1CtrlEntries 10232 }


    i1TimecodeVITCEnable OBJECT-TYPE
        SYNTAX            INTEGER { disable(0), enable(1)  }
        MAX-ACCESS        read-write
        STATUS            current
        DESCRIPTION
                "CMNT: - 
                 TYPE: - Checkbox
                 PAGE: - Timecode
                    VITC Enable  cmdID= 10238  "
        ::= { kudosConv1CtrlEntries 10238 }


    i1TimecodeOutputLine525 OBJECT-TYPE
        SYNTAX            INTEGER
        MAX-ACCESS        read-write
        STATUS            current
        DESCRIPTION
                "CMNT: - 
                 TYPE: - Number
                 PAGE: - Timecode
                    Output Line (525)  cmdID= 10233
                    min= 11  max= 17  step= 1  format= %0.0f  div_scale= 1  preset= 14
                    Min = 11  Max = 17  Step = 1  Preset = 14  "
        ::= { kudosConv1CtrlEntries 10233 }


    i1TimecodeOutputLine625 OBJECT-TYPE
        SYNTAX            INTEGER
        MAX-ACCESS        read-write
        STATUS            current
        DESCRIPTION
                "CMNT: - 
                 TYPE: - Number
                 PAGE: - Timecode
                    Output Line (625)  cmdID= 10234
                    min= 7  max= 20  step= 1  format= %0.0f  div_scale= 1  preset= 19
                    Min = 7  Max = 20  Step = 1  Preset = 19  "
        ::= { kudosConv1CtrlEntries 10234 }


    i1TimecodeOutputLineStatus OBJECT-TYPE
        SYNTAX            RollCallString
        MAX-ACCESS        read-only
        STATUS            current
        DESCRIPTION
                "CMNT: - 
                 TYPE: - Display
                 PAGE: - Timecode
                    Output Line Status  cmdID= 10338  "
        ::= { kudosConv1CtrlEntries 10338 }


    i1TimecodeInputTriggerEntry OBJECT-TYPE
        SYNTAX            RollCallString
        MAX-ACCESS        read-write
        STATUS            current
        DESCRIPTION
                "CMNT: - 
                 TYPE: - Editstring
                 PAGE: - Timecode
                    Input Trigger Entry  cmdID= 10240
                    preset= 00:00:00:00"
        ::= { kudosConv1CtrlEntries 10240 }


    i1TimecodeOutputTimecodeEntry OBJECT-TYPE
        SYNTAX            RollCallString
        MAX-ACCESS        read-write
        STATUS            current
        DESCRIPTION
                "CMNT: - 
                 TYPE: - Editstring
                 PAGE: - Timecode
                    Output Timecode Entry  cmdID= 10241
                    preset= 00:00:00:00"
        ::= { kudosConv1CtrlEntries 10241 }


    i1TimecodeEntry OBJECT-TYPE
        SYNTAX            RollCallString
        MAX-ACCESS        read-write
        STATUS            current
        DESCRIPTION
                "CMNT: - 
                 TYPE: - Editstring
                 PAGE: - Timecode
                    Timecode Entry  cmdID= 10237
                    preset= 00:00:00:00"
        ::= { kudosConv1CtrlEntries 10237 }


    i1TimecodeLoad OBJECT-TYPE
        SYNTAX            INTEGER { noAction(0),valTimecodeLoad(1) }
        MAX-ACCESS        read-write
        STATUS            current
        DESCRIPTION
                "CMNT: - 
                 TYPE: - Button
                 PAGE: - Timecode
                    Timecode Load  cmdID= 10316
                    value= 1  "
        ::= { kudosConv1CtrlEntries 10316 }


    i1TimecodeOnTimecodeLoss OBJECT-TYPE
        SYNTAX            INTEGER {
                            valFreeze(0),
                            valFreeRun(1)
                            }
        MAX-ACCESS        read-write
        STATUS            current
        DESCRIPTION
                "CMNT: - 
                 TYPE: - RadiobuttonList
                 PAGE: - Timecode
                    On Timecode Loss  cmdID= 10235
                    Freeze  value= 0
                    Free Run  value= 1  "
        ::= { kudosConv1CtrlEntries 10235 }


    i1TimecodeNondropFrame OBJECT-TYPE
        SYNTAX            INTEGER { disable(0), enable(1)  }
        MAX-ACCESS        read-write
        STATUS            current
        DESCRIPTION
                "CMNT: - 
                 TYPE: - Checkbox
                 PAGE: - Timecode
                    Non-drop Frame  cmdID= 10236  "
        ::= { kudosConv1CtrlEntries 10236 }


    i1MetadataClosedCaptionsInputStatus OBJECT-TYPE
        SYNTAX            RollCallString
        MAX-ACCESS        read-only
        STATUS            current
        DESCRIPTION
                "CMNT: - 
                 TYPE: - Display
                 PAGE: - Metadata
                    Input Status  cmdID= 10250  "
        ::= { kudosConv1CtrlEntries 10250 }


    i1MetadataClosedCaptionsCEA608OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-608 Output Enable  cmdID= 10242
                    Off  value= 0
                    On  value= 1  "
        ::= { kudosConv1CtrlEntries 10242 }


    i1MetadataClosedCaptionsCEA708OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-708 Output Enable  cmdID= 10243
                    Off  value= 0
                    On  value= 1  "
        ::= { kudosConv1CtrlEntries 10243 }


    i1MetadataClosedCaptionsCEA708OutputLine OBJECT-TYPE
        SYNTAX            INTEGER
        MAX-ACCESS        read-write
        STATUS            current
        DESCRIPTION
                "CMNT: - 
                 TYPE: - Number
                 PAGE: - Metadata
                    CEA-708 Output Line  cmdID= 10244
                    min= 8  max= 20  step= 1  format= %0.0f  div_scale= 1  preset= 10
                    Min = 8  Max = 20  Step = 1  Preset = 10  "
        ::= { kudosConv1CtrlEntries 10244 }


    i1MetadataClosedCaptionsCEA708OutputLineStatus OBJECT-TYPE
        SYNTAX            RollCallString
        MAX-ACCESS        read-only
        STATUS            current
        DESCRIPTION
                "CMNT: - 
                 TYPE: - Display
                 PAGE: - Metadata
                    CEA-708 Output Line Status  cmdID= 10252  "
        ::= { kudosConv1CtrlEntries 10252 }


    i1MetadataTeletext625CaptionsSource OBJECT-TYPE
        SYNTAX            INTEGER {
                            valWST(0),
                            valCEAn608(1)
                            }
        MAX-ACCESS        read-write
        STATUS            current
        DESCRIPTION
                "CMNT: - 
                 TYPE: - RadiobuttonList
                 PAGE: - Metadata
                    625 Captions Source  cmdID= 10337
                    WST  value= 0
                    CEA-608  value= 1  "
        ::= { kudosConv1CtrlEntries 10337 }


    i1MetadataTeletextPresentStatus OBJECT-TYPE
        SYNTAX            RollCallString
        MAX-ACCESS        read-only
        STATUS            current
        DESCRIPTION
                "CMNT: - 
                 TYPE: - Display
                 PAGE: - Metadata
                    Teletext Present Status  cmdID= 10251  "
        ::= { kudosConv1CtrlEntries 10251 }


    i1MetadataTeletextWSTInputLine OBJECT-TYPE
        SYNTAX            INTEGER
        MAX-ACCESS        read-write
        STATUS            current
        DESCRIPTION
                "CMNT: - 
                 TYPE: - Number
                 PAGE: - Metadata
                    WST Input Line  cmdID= 10245
                    min= 7  max= 22  step= 1  format= %0.0f  div_scale= 1  preset= 10
                    Min = 7  Max = 22  Step = 1  Preset = 10  "
        ::= { kudosConv1CtrlEntries 10245 }


    i1MetadataTeletextWSTOutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    WST Output Enable  cmdID= 10246
                    Off  value= 0
                    On  value= 1  "
        ::= { kudosConv1CtrlEntries 10246 }


    i1MetadataTeletextWSTOutputLine OBJECT-TYPE
        SYNTAX            INTEGER
        MAX-ACCESS        read-write
        STATUS            current
        DESCRIPTION
                "CMNT: - 
                 TYPE: - Number
                 PAGE: - Metadata
                    WST Output Line  cmdID= 10253
                    min= 7  max= 22  step= 1  format= %0.0f  div_scale= 1  preset= 10
                    Min = 7  Max = 22  Step = 1  Preset = 10  "
        ::= { kudosConv1CtrlEntries 10253 }


    i1MetadataTeletextWSTOutputLineStatus OBJECT-TYPE
        SYNTAX            RollCallString
        MAX-ACCESS        read-only
        STATUS            current
        DESCRIPTION
                "CMNT: - 
                 TYPE: - Display
                 PAGE: - Metadata
                    WST Output Line Status  cmdID= 10341  "
        ::= { kudosConv1CtrlEntries 10341 }


    i1MetadataTeletextRDD08InputLine OBJECT-TYPE
        SYNTAX            INTEGER
        MAX-ACCESS        read-write
        STATUS            current
        DESCRIPTION
                "CMNT: - 
                 TYPE: - Number
                 PAGE: - Metadata
                    RDD-08 Input Line  cmdID= 10248
                    min= 8  max= 20  step= 1  format= %0.0f  div_scale= 1  preset= 10
                    Min = 8  Max = 20  Step = 1  Preset = 10  "
        ::= { kudosConv1CtrlEntries 10248 }


    i1MetadataTeletextRDD08OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    RDD-08 Output Enable  cmdID= 10247
                    Off  value= 0
                    On  value= 1  "
        ::= { kudosConv1CtrlEntries 10247 }


    i1MetadataTeletextRDD08OutputLine OBJECT-TYPE
        SYNTAX            INTEGER
        MAX-ACCESS        read-write
        STATUS            current
        DESCRIPTION
                "CMNT: - 
                 TYPE: - Number
                 PAGE: - Metadata
                    RDD-08 Output Line  cmdID= 10249
                    min= 8  max= 20  step= 1  format= %0.0f  div_scale= 1  preset= 10
                    Min = 8  Max = 20  Step = 1  Preset = 10  "
        ::= { kudosConv1CtrlEntries 10249 }


    i1MetadataTeletextRDD08OutputLineStatus OBJECT-TYPE
        SYNTAX            RollCallString
        MAX-ACCESS        read-only
        STATUS            current
        DESCRIPTION
                "CMNT: - 
                 TYPE: - Display
                 PAGE: - Metadata
                    RDD-08 Output Line Status  cmdID= 10340  "
        ::= { kudosConv1CtrlEntries 10340 }


    i1MemorySelect OBJECT-TYPE
        SYNTAX            INTEGER {
                            valMemory1(1),
                            valMemory2(2),
                            valMemory3(3),
                            valMemory4(4),
                            valMemory5(5),
                            valMemory6(6),
                            valMemory7(7),
                            valMemory8(8)
                            }
        MAX-ACCESS        read-write
        STATUS            current
        DESCRIPTION
                "CMNT: - 
                 TYPE: - RadiobuttonList
                 PAGE: - Memory
                    Memory Select  cmdID= 10254
                    Memory 1  value= 1
                    Memory 2  value= 2
                    Memory 3  value= 3
                    Memory 4  value= 4
                    Memory 5  value= 5
                    Memory 6  value= 6
                    Memory 7  value= 7
                    Memory 8  value= 8  "
        ::= { kudosConv1CtrlEntries 10254 }


    i1MemorySaveMemory OBJECT-TYPE
        SYNTAX            INTEGER { noAction(0),valSaveMemory(1) }
        MAX-ACCESS        read-write
        STATUS            current
        DESCRIPTION
                "CMNT: - 
                 TYPE: - Button
                 PAGE: - Memory
                    Save Memory  cmdID= 10255
                    value= 1  "
        ::= { kudosConv1CtrlEntries 10255 }


    i1MemoryRecallMemory OBJECT-TYPE
        SYNTAX            INTEGER { noAction(0),valRecallMemory(1) }
        MAX-ACCESS        read-write
        STATUS            current
        DESCRIPTION
                "CMNT: - 
                 TYPE: - Button
                 PAGE: - Memory
                    Recall Memory  cmdID= 10256
                    value= 1  "
        ::= { kudosConv1CtrlEntries 10256 }


    i1MemoryResettoDefaults OBJECT-TYPE
        SYNTAX            INTEGER { noAction(0),valResettoDefaults(1) }
        MAX-ACCESS        read-write
        STATUS            current
        DESCRIPTION
                "CMNT: - 
                 TYPE: - Button
                 PAGE: - Memory
                    Reset to Defaults  cmdID= 10258
                    value= 1  "
        ::= { kudosConv1CtrlEntries 10258 }


    i1MemoryNameChangeName OBJECT-TYPE
        SYNTAX            RollCallString
        MAX-ACCESS        read-write
        STATUS            current
        DESCRIPTION
                "CMNT: - 
                 TYPE: - Editstring
                 PAGE: - Memory
                    Change Name  cmdID= 10257
                    preset= "
        ::= { kudosConv1CtrlEntries 10257 }


    i1RollCallUnitName OBJECT-TYPE
        SYNTAX            RollCallString
        MAX-ACCESS        read-write
        STATUS            current
        DESCRIPTION
                "CMNT: - 
                 TYPE: - Editstring
                 PAGE: - RollCall
                    Unit Name  cmdID= 10312
                    preset= IQP"
        ::= { kudosConv1CtrlEntries 10312 }


    i1SNMPControlEnable OBJECT-TYPE
        SYNTAX            INTEGER { disable(0), enable(1)  }
        MAX-ACCESS        read-write
        STATUS            current
        DESCRIPTION
                "CMNT: - 
                 TYPE: - Checkbox
                 PAGE: - SNMP
                    Control Enable  cmdID= 10342  "
        ::= { kudosConv1CtrlEntries 10342 }


    i1SNMPTrapsEnable OBJECT-TYPE
        SYNTAX            INTEGER { disable(0), enable(1)  }
        MAX-ACCESS        read-write
        STATUS            current
        DESCRIPTION
                "CMNT: - 
                 TYPE: - Checkbox
                 PAGE: - SNMP
                    Traps Enable  cmdID= 10343  "
        ::= { kudosConv1CtrlEntries 10343 }


    i1SNMPResendTraps OBJECT-TYPE
        SYNTAX            INTEGER { noAction(0),valResendTraps(1) }
        MAX-ACCESS        read-write
        STATUS            current
        DESCRIPTION
                "CMNT: - 
                 TYPE: - Button
                 PAGE: - SNMP
                    Resend Traps  cmdID= 10344
                    value= 1  "
        ::= { kudosConv1CtrlEntries 10344 }


    i1LoggingInputIdentEnable OBJECT-TYPE
        SYNTAX            INTEGER { disable(0), enable(1)  }
        MAX-ACCESS        read-write
        STATUS            current
        DESCRIPTION
                "CMNT: - 
                 TYPE: - Checkbox
                 PAGE: - Logging
                    Input Ident Enable  cmdID= 10261  "
        ::= { kudosConv1CtrlEntries 10261 }


    i1LoggingInputStandardEnable OBJECT-TYPE
        SYNTAX            INTEGER { disable(0), enable(1)  }
        MAX-ACCESS        read-write
        STATUS            current
        DESCRIPTION
                "CMNT: - 
                 TYPE: - Checkbox
                 PAGE: - Logging
                    Input Standard Enable  cmdID= 10259  "
        ::= { kudosConv1CtrlEntries 10259 }


    i1LoggingInputStateEnable OBJECT-TYPE
        SYNTAX            INTEGER { disable(0), enable(1)  }
        MAX-ACCESS        read-write
        STATUS            current
        DESCRIPTION
                "CMNT: - 
                 TYPE: - Checkbox
                 PAGE: - Logging
                    Input State Enable  cmdID= 10263  "
        ::= { kudosConv1CtrlEntries 10263 }


    i1LoggingOutputStandardEnable OBJECT-TYPE
        SYNTAX            INTEGER { disable(0), enable(1)  }
        MAX-ACCESS        read-write
        STATUS            current
        DESCRIPTION
                "CMNT: - 
                 TYPE: - Checkbox
                 PAGE: - Logging
                    Output Standard Enable  cmdID= 10267  "
        ::= { kudosConv1CtrlEntries 10267 }


    i1LoggingOutputIdentEnable OBJECT-TYPE
        SYNTAX            INTEGER { disable(0), enable(1)  }
        MAX-ACCESS        read-write
        STATUS            current
        DESCRIPTION
                "CMNT: - 
                 TYPE: - Checkbox
                 PAGE: - Logging
                    Output Ident Enable  cmdID= 10265  "
        ::= { kudosConv1CtrlEntries 10265 }


    i1LoggingTimecodeEnable OBJECT-TYPE
        SYNTAX            INTEGER { disable(0), enable(1)  }
        MAX-ACCESS        read-write
        STATUS            current
        DESCRIPTION
                "CMNT: - 
                 TYPE: - Checkbox
                 PAGE: - Logging
                    Timecode Enable  cmdID= 10346  "
        ::= { kudosConv1CtrlEntries 10346 }


    i1LoggingClosedCaptionInputEnable OBJECT-TYPE
        SYNTAX            INTEGER { disable(0), enable(1)  }
        MAX-ACCESS        read-write
        STATUS            current
        DESCRIPTION
                "CMNT: - 
                 TYPE: - Checkbox
                 PAGE: - Logging
                    Closed Caption Input Enable  cmdID= 10348  "
        ::= { kudosConv1CtrlEntries 10348 }


    i1LoggingWSTEnable OBJECT-TYPE
        SYNTAX            INTEGER { disable(0), enable(1)  }
        MAX-ACCESS        read-write
        STATUS            current
        DESCRIPTION
                "CMNT: - 
                 TYPE: - Checkbox
                 PAGE: - Logging
                    WST Enable  cmdID= 10350  "
        ::= { kudosConv1CtrlEntries 10350 }


    i1LoggingRDD08Enable OBJECT-TYPE
        SYNTAX            INTEGER { disable(0), enable(1)  }
        MAX-ACCESS        read-write
        STATUS            current
        DESCRIPTION
                "CMNT: - 
                 TYPE: - Checkbox
                 PAGE: - Logging
                    RDD08 Enable  cmdID= 10352  "
        ::= { kudosConv1CtrlEntries 10352 }


    i1LoggingCEA708Enable OBJECT-TYPE
        SYNTAX            INTEGER { disable(0), enable(1)  }
        MAX-ACCESS        read-write
        STATUS            current
        DESCRIPTION
                "CMNT: - 
                 TYPE: - Checkbox
                 PAGE: - Logging
                    CEA-708 Enable  cmdID= 10354  "
        ::= { kudosConv1CtrlEntries 10354 }


    i1LoggingSMPTE2016Enable OBJECT-TYPE
        SYNTAX            INTEGER { disable(0), enable(1)  }
        MAX-ACCESS        read-write
        STATUS            current
        DESCRIPTION
                "CMNT: - 
                 TYPE: - Checkbox
                 PAGE: - Logging
                    SMPTE 2016 Enable  cmdID= 10356  "
        ::= { kudosConv1CtrlEntries 10356 }


    i1LoggingSMPTEL23Enable OBJECT-TYPE
        SYNTAX            INTEGER { disable(0), enable(1)  }
        MAX-ACCESS        read-write
        STATUS            current
        DESCRIPTION
                "CMNT: - 
                 TYPE: - Checkbox
                 PAGE: - Logging
                    SMPTE L23 Enable  cmdID= 10358  "
        ::= { kudosConv1CtrlEntries 10358 }


    i1LoggingSignallingEnable OBJECT-TYPE
        SYNTAX            INTEGER { disable(0), enable(1)  }
        MAX-ACCESS        read-write
        STATUS            current
        DESCRIPTION
                "CMNT: - 
                 TYPE: - Checkbox
                 PAGE: - Logging
                    Signalling Enable  cmdID= 10360  "
        ::= { kudosConv1CtrlEntries 10360 }
    kudosConv1StatEntries OBJECT IDENTIFIER ::= { kudosIQP 6 }


    i1LoggingInputIdentStatus OBJECT-TYPE
        SYNTAX            RollCallString
        MAX-ACCESS        read-only
        STATUS            current
        DESCRIPTION
                "CMNT: - Channel Name
                 TYPE: - Display
                 PAGE: - Logging
                    Input Ident Status  cmdID= 10262  "
        ::= { kudosConv1StatEntries 10262 }


    i1LoggingInputStandardStatus OBJECT-TYPE
        SYNTAX            RollCallString
        MAX-ACCESS        read-only
        STATUS            current
        DESCRIPTION
                "CMNT: - WARN: or format
                 TYPE: - Display
                 PAGE: - Logging
                    Input Standard Status  cmdID= 10260  "
        ::= { kudosConv1StatEntries 10260 }


    i1LoggingInputStateStatus OBJECT-TYPE
        SYNTAX            RollCallString
        MAX-ACCESS        read-only
        STATUS            current
        DESCRIPTION
                "CMNT: - WARN: or OK
                 TYPE: - Display
                 PAGE: - Logging
                    Input State Status  cmdID= 10264  "
        ::= { kudosConv1StatEntries 10264 }


    i1LoggingOutputStandardStatus OBJECT-TYPE
        SYNTAX            RollCallString
        MAX-ACCESS        read-only
        STATUS            current
        DESCRIPTION
                "CMNT: - WARN: or format
                 TYPE: - Display
                 PAGE: - Logging
                    Output Standard Status  cmdID= 10268  "
        ::= { kudosConv1StatEntries 10268 }


    i1LoggingOutputIdentStatus OBJECT-TYPE
        SYNTAX            RollCallString
        MAX-ACCESS        read-only
        STATUS            current
        DESCRIPTION
                "CMNT: - Channel Name
                 TYPE: - Display
                 PAGE: - Logging
                    Output Ident Status  cmdID= 10266  "
        ::= { kudosConv1StatEntries 10266 }


    i1LoggingTimeCodeStatus OBJECT-TYPE
        SYNTAX            RollCallString
        MAX-ACCESS        read-only
        STATUS            current
        DESCRIPTION
                "CMNT: - LOST or OK
                 TYPE: - Display
                 PAGE: - Logging
                    TimeCode Status  cmdID= 10347  "
        ::= { kudosConv1StatEntries 10347 }


    i1LoggingClosedCaptionInputStatus OBJECT-TYPE
        SYNTAX            RollCallString
        MAX-ACCESS        read-only
        STATUS            current
        DESCRIPTION
                "CMNT: - LOST or OK
                 TYPE: - Display
                 PAGE: - Logging
                    Closed Caption Input Status  cmdID= 10349  "
        ::= { kudosConv1StatEntries 10349 }


    i1LoggingWSTOutputLineStatus OBJECT-TYPE
        SYNTAX            RollCallString
        MAX-ACCESS        read-only
        STATUS            current
        DESCRIPTION
                "CMNT: - off or line number
                 TYPE: - Display
                 PAGE: - Logging
                    WST Output Line Status  cmdID= 10351  "
        ::= { kudosConv1StatEntries 10351 }


    i1LoggingRDD08OutputLineStatus OBJECT-TYPE
        SYNTAX            RollCallString
        MAX-ACCESS        read-only
        STATUS            current
        DESCRIPTION
                "CMNT: - off or line number
                 TYPE: - Display
                 PAGE: - Logging
                    RDD08 Output Line Status  cmdID= 10353  "
        ::= { kudosConv1StatEntries 10353 }


    i1LoggingCEA708OutputLineStatus OBJECT-TYPE
        SYNTAX            RollCallString
        MAX-ACCESS        read-only
        STATUS            current
        DESCRIPTION
                "CMNT: - off or line number
                 TYPE: - Display
                 PAGE: - Logging
                    CEA-708 Output Line Status  cmdID= 10355  "
        ::= { kudosConv1StatEntries 10355 }


    i1Logging2016OutputLineStatus OBJECT-TYPE
        SYNTAX            RollCallString
        MAX-ACCESS        read-only
        STATUS            current
        DESCRIPTION
                "CMNT: - off or line number
                 TYPE: - Display
                 PAGE: - Logging
                    2016 Output Line Status  cmdID= 10357  "
        ::= { kudosConv1StatEntries 10357 }


    i1LoggingL23OutputLineStatus OBJECT-TYPE
        SYNTAX            RollCallString
        MAX-ACCESS        read-only
        STATUS            current
        DESCRIPTION
                "CMNT: - off or line number
                 TYPE: - Display
                 PAGE: - Logging
                    L23 Output Line Status  cmdID= 10359  "
        ::= { kudosConv1StatEntries 10359 }


    i1LoggingSignallingStatus OBJECT-TYPE
        SYNTAX            RollCallString
        MAX-ACCESS        read-only
        STATUS            current
        DESCRIPTION
                "CMNT: - NONE or OK
                 TYPE: - Display
                 PAGE: - Logging
                    Signalling Status  cmdID= 10361  "
        ::= { kudosConv1StatEntries 10361 }


    i1LoggingMSGStatus OBJECT-TYPE
        SYNTAX            RollCallString
        MAX-ACCESS        read-only
        STATUS            current
        DESCRIPTION
                "CMNT: - 
                 TYPE: - Display
                 PAGE: - Logging
                    MSG Status  cmdID= 10269  "
        ::= { kudosConv1StatEntries 10269 }
    kudosConv2NoteEntries OBJECT IDENTIFIER ::= { kudosIQP 7 }


    i2InputIdentStatus NOTIFICATION-TYPE
        OBJECTS            { i2LoggingInputIdentStatus } 
        STATUS            current
        DESCRIPTION
                "CMNT: - Channel Name
                 TYPE: - Display
                 PAGE: - Logging
                    Input Ident Status  cmdID= 5000  "
        ::= { kudosConv2NoteEntries 5000 }


    i2InputStandardStatus NOTIFICATION-TYPE
        OBJECTS            { i2LoggingInputStandardStatus } 
        STATUS            current
        DESCRIPTION
                "CMNT: - WARN: or format
                 TYPE: - Display
                 PAGE: - Logging
                    Input Standard Status  cmdID= 5001  "
        ::= { kudosConv2NoteEntries 5001 }


    i2InputStateStatus NOTIFICATION-TYPE
        OBJECTS            { i2LoggingInputStateStatus } 
        STATUS            current
        DESCRIPTION
                "CMNT: - WARN: or OK
                 TYPE: - Display
                 PAGE: - Logging
                    Input State Status  cmdID= 5002  "
        ::= { kudosConv2NoteEntries 5002 }


    i2OutputStandardStatus NOTIFICATION-TYPE
        OBJECTS            { i2LoggingOutputStandardStatus } 
        STATUS            current
        DESCRIPTION
                "CMNT: - WARN: or format
                 TYPE: - Display
                 PAGE: - Logging
                    Output Standard Status  cmdID= 5003  "
        ::= { kudosConv2NoteEntries 5003 }


    i2OutputIdentStatus NOTIFICATION-TYPE
        OBJECTS            { i2LoggingOutputIdentStatus } 
        STATUS            current
        DESCRIPTION
                "CMNT: - Channel Name
                 TYPE: - Display
                 PAGE: - Logging
                    Output Ident Status  cmdID= 5004  "
        ::= { kudosConv2NoteEntries 5004 }


    i2TimeCodeStatus NOTIFICATION-TYPE
        OBJECTS            { i2LoggingTimeCodeStatus } 
        STATUS            current
        DESCRIPTION
                "CMNT: - LOST or OK
                 TYPE: - Display
                 PAGE: - Logging
                    TimeCode Status  cmdID= 5005  "
        ::= { kudosConv2NoteEntries 5005 }


    i2ClosedCaptionInputStatus NOTIFICATION-TYPE
        OBJECTS            { i2LoggingClosedCaptionInputStatus } 
        STATUS            current
        DESCRIPTION
                "CMNT: - LOST or OK
                 TYPE: - Display
                 PAGE: - Logging
                    Closed Caption Input Status  cmdID= 5006  "
        ::= { kudosConv2NoteEntries 5006 }


    i2WSTOutputLineStatus NOTIFICATION-TYPE
        OBJECTS            { i2LoggingWSTOutputLineStatus } 
        STATUS            current
        DESCRIPTION
                "CMNT: - off or line number
                 TYPE: - Display
                 PAGE: - Logging
                    WST Output Line Status  cmdID= 5007  "
        ::= { kudosConv2NoteEntries 5007 }


    i2RDD08OutputLineStatus NOTIFICATION-TYPE
        OBJECTS            { i2LoggingRDD08OutputLineStatus } 
        STATUS            current
        DESCRIPTION
                "CMNT: - off or line number
                 TYPE: - Display
                 PAGE: - Logging
                    RDD08 Output Line Status  cmdID= 5008  "
        ::= { kudosConv2NoteEntries 5008 }


    i2CEA708OutputLineStatus NOTIFICATION-TYPE
        OBJECTS            { i2LoggingCEA708OutputLineStatus } 
        STATUS            current
        DESCRIPTION
                "CMNT: - off or line number
                 TYPE: - Display
                 PAGE: - Logging
                    CEA-708 Output Line Status  cmdID= 5009  "
        ::= { kudosConv2NoteEntries 5009 }


    i22016OutputLineStatus NOTIFICATION-TYPE
        OBJECTS            { i2Logging2016OutputLineStatus } 
        STATUS            current
        DESCRIPTION
                "CMNT: - off or line number
                 TYPE: - Display
                 PAGE: - Logging
                    2016 Output Line Status  cmdID= 5010  "
        ::= { kudosConv2NoteEntries 5010 }


    i2L23OutputLineStatus NOTIFICATION-TYPE
        OBJECTS            { i2LoggingL23OutputLineStatus } 
        STATUS            current
        DESCRIPTION
                "CMNT: - off or line number
                 TYPE: - Display
                 PAGE: - Logging
                    L23 Output Line Status  cmdID= 5011  "
        ::= { kudosConv2NoteEntries 5011 }


    i2SignallingStatus NOTIFICATION-TYPE
        OBJECTS            { i2LoggingSignallingStatus } 
        STATUS            current
        DESCRIPTION
                "CMNT: - NONE or OK
                 TYPE: - Display
                 PAGE: - Logging
                    Signalling Status  cmdID= 5012  "
        ::= { kudosConv2NoteEntries 5012 }


    i2MSGStatus NOTIFICATION-TYPE
        OBJECTS            { i2LoggingMSGStatus } 
        STATUS            current
        DESCRIPTION
                "CMNT: - 
                 TYPE: - Display
                 PAGE: - Logging
                    MSG Status  cmdID= 5013  "
        ::= { kudosConv2NoteEntries 5013 }
    kudosConv2CtrlEntries OBJECT IDENTIFIER ::= { kudosIQP 8 }


    i2InputSelect OBJECT-TYPE
        SYNTAX            INTEGER {
                            valSDI1(0),
                            valSDI2(1),
                            valSDI3(2),
                            valSDI4(3),
                            valCVBSA(4),
                            valCVBSB(5),
                            valCVBSC(6),
                            valCVBSD(7),
                            valSFPA1(8),
                            valSFPA2(9),
                            valSFPB1(10),
                            valSFPB2(11)
                            }
        MAX-ACCESS        read-write
        STATUS            current
        DESCRIPTION
                "CMNT: - 
                 TYPE: - RadiobuttonList
                 PAGE: - Input
                    Input Select  cmdID= 10020
                    SDI 1  value= 0
                    SDI 2  value= 1
                    SDI 3  value= 2
                    SDI 4  value= 3
                    CVBS A  value= 4
                    CVBS B  value= 5
                    CVBS C  value= 6
                    CVBS D  value= 7
                    SFP A1  value= 8
                    SFP A2  value= 9
                    SFP B1  value= 10
                    SFP B2  value= 11  "
        ::= { kudosConv2CtrlEntries 10020 }


    i2InputStatusSDI1 OBJECT-TYPE
        SYNTAX            RollCallString
        MAX-ACCESS        read-only
        STATUS            current
        DESCRIPTION
                "CMNT: - 
                 TYPE: - Display
                 PAGE: - Input
                    SDI 1  cmdID= 10270  "
        ::= { kudosConv2CtrlEntries 10270 }


    i2InputStatusSDI2 OBJECT-TYPE
        SYNTAX            RollCallString
        MAX-ACCESS        read-only
        STATUS            current
        DESCRIPTION
                "CMNT: - 
                 TYPE: - Display
                 PAGE: - Input
                    SDI 2  cmdID= 10271  "
        ::= { kudosConv2CtrlEntries 10271 }


    i2InputStatusSDI3 OBJECT-TYPE
        SYNTAX            RollCallString
        MAX-ACCESS        read-only
        STATUS            current
        DESCRIPTION
                "CMNT: - 
                 TYPE: - Display
                 PAGE: - Input
                    SDI 3  cmdID= 10272  "
        ::= { kudosConv2CtrlEntries 10272 }


    i2InputStatusSDI4 OBJECT-TYPE
        SYNTAX            RollCallString
        MAX-ACCESS        read-only
        STATUS            current
        DESCRIPTION
                "CMNT: - 
                 TYPE: - Display
                 PAGE: - Input
                    SDI 4  cmdID= 10273  "
        ::= { kudosConv2CtrlEntries 10273 }


    i2InputStatusCVBS1 OBJECT-TYPE
        SYNTAX            RollCallString
        MAX-ACCESS        read-only
        STATUS            current
        DESCRIPTION
                "CMNT: - 
                 TYPE: - Display
                 PAGE: - Input
                    CVBS 1  cmdID= 10274  "
        ::= { kudosConv2CtrlEntries 10274 }


    i2InputStatusCVBS2 OBJECT-TYPE
        SYNTAX            RollCallString
        MAX-ACCESS        read-only
        STATUS            current
        DESCRIPTION
                "CMNT: - 
                 TYPE: - Display
                 PAGE: - Input
                    CVBS 2  cmdID= 10275  "
        ::= { kudosConv2CtrlEntries 10275 }


    i2InputStatusCVBS3 OBJECT-TYPE
        SYNTAX            RollCallString
        MAX-ACCESS        read-only
        STATUS            current
        DESCRIPTION
                "CMNT: - 
                 TYPE: - Display
                 PAGE: - Input
                    CVBS 3  cmdID= 10276  "
        ::= { kudosConv2CtrlEntries 10276 }


    i2InputStatusCVBS4 OBJECT-TYPE
        SYNTAX            RollCallString
        MAX-ACCESS        read-only
        STATUS            current
        DESCRIPTION
                "CMNT: - 
                 TYPE: - Display
                 PAGE: - Input
                    CVBS 4  cmdID= 10277  "
        ::= { kudosConv2CtrlEntries 10277 }


    i2InputStatusSFP1 OBJECT-TYPE
        SYNTAX            RollCallString
        MAX-ACCESS        read-only
        STATUS            current
        DESCRIPTION
                "CMNT: - 
                 TYPE: - Display
                 PAGE: - Input
                    SFP 1  cmdID= 10278  "
        ::= { kudosConv2CtrlEntries 10278 }


    i2InputStatusSFP2 OBJECT-TYPE
        SYNTAX            RollCallString
        MAX-ACCESS        read-only
        STATUS            current
        DESCRIPTION
                "CMNT: - 
                 TYPE: - Display
                 PAGE: - Input
                    SFP 2  cmdID= 10279  "
        ::= { kudosConv2CtrlEntries 10279 }


    i2InputStatusSFP3 OBJECT-TYPE
        SYNTAX            RollCallString
        MAX-ACCESS        read-only
        STATUS            current
        DESCRIPTION
                "CMNT: - 
                 TYPE: - Display
                 PAGE: - Input
                    SFP 3  cmdID= 10280  "
        ::= { kudosConv2CtrlEntries 10280 }


    i2InputStatusSFP4 OBJECT-TYPE
        SYNTAX            RollCallString
        MAX-ACCESS        read-only
        STATUS            current
        DESCRIPTION
                "CMNT: - 
                 TYPE: - Display
                 PAGE: - Input
                    SFP 4  cmdID= 10281  "
        ::= { kudosConv2CtrlEntries 10281 }


    i2InputStatusCurrentInputStandard OBJECT-TYPE
        SYNTAX            RollCallString
        MAX-ACCESS        read-only
        STATUS            current
        DESCRIPTION
                "CMNT: - 
                 TYPE: - Display
                 PAGE: - Input
                    Current Input Standard  cmdID= 10313  "
        ::= { kudosConv2CtrlEntries 10313 }


    i2OutputFormat OBJECT-TYPE
        SYNTAX            INTEGER {
                            val525625(0),
                            val720p(1),
                            val1080i(2),
                            val1080pnA(3),
                            val1080pnB(4)
                            }
        MAX-ACCESS        read-write
        STATUS            current
        DESCRIPTION
                "CMNT: - 
                 TYPE: - RadiobuttonList
                 PAGE: - Output
                    Output Format  cmdID= 10025
                    525/625  value= 0
                    720p  value= 1
                    1080i  value= 2
                    1080p-A  value= 3
                    1080p-B  value= 4  "
        ::= { kudosConv2CtrlEntries 10025 }


    i2OutputDefaultFieldRate OBJECT-TYPE
        SYNTAX            INTEGER {
                            valLastValidInput(0),
                            val23Hz(1),
                            val24Hz(2),
                            val25Hz(3),
                            val29Hz(4),
                            val30Hz(5),
                            val50Hz(6),
                            val59Hz(7),
                            val60Hz(8)
                            }
        MAX-ACCESS        read-write
        STATUS            current
        DESCRIPTION
                "CMNT: - 
                 TYPE: - RadiobuttonList
                 PAGE: - Output
                    Default Field Rate  cmdID= 10026
                    Last Valid Input  value= 0
                    23 Hz  value= 1
                    24 Hz  value= 2
                    25 Hz  value= 3
                    29 Hz  value= 4
                    30 Hz  value= 5
                    50 Hz  value= 6
                    59 Hz  value= 7
                    60 Hz  value= 8  "
        ::= { kudosConv2CtrlEntries 10026 }


    i2OutputStandard OBJECT-TYPE
        SYNTAX            INTEGER {
                            val62550i(2),
                            val52559i(3),
                            val72023p(4),
                            val72024p(5),
                            val72025p(6),
                            val72029p(7),
                            val72030p(8),
                            val72050p(9),
                            val72059p(10),
                            val72060p(11),
                            val108023p(12),
                            val108024p(13),
                            val108025p(14),
                            val108029p(15),
                            val108030p(16),
                            val108050i(17),
                            val108059i(18),
                            val108060i(19),
                            val108023psf(20),
                            val108024psf(21),
                            val108025psf(50),
                            val108029psf(51),
                            val108050pnA(22),
                            val108059pnA(23),
                            val108060pnA(24),
                            val108050pnB(25),
                            val108059pnB(26),
                            val108060pnB(27)
                            }
        MAX-ACCESS        read-write
        STATUS            current
        DESCRIPTION
                "CMNT: - 
                 TYPE: - RadiobuttonList
                 PAGE: - Output
                    Output Standard  cmdID= 10024
                    625 50i  value= 2
                    525 59i  value= 3
                    720 23p  value= 4
                    720 24p  value= 5
                    720 25p  value= 6
                    720 29p  value= 7
                    720 30p  value= 8
                    720 50p  value= 9
                    720 59p  value= 10
                    720 60p  value= 11
                    1080 23p  value= 12
                    1080 24p  value= 13
                    1080 25p  value= 14
                    1080 29p  value= 15
                    1080 30p  value= 16
                    1080 50i  value= 17
                    1080 59i  value= 18
                    1080 60i  value= 19
                    1080 23psf  value= 20
                    1080 24psf  value= 21
                    1080 25psf  value= 50
                    1080 29psf  value= 51
                    1080 50p-A  value= 22
                    1080 59p-A  value= 23
                    1080 60p-A  value= 24
                    1080 50p-B  value= 25
                    1080 59p-B  value= 26
                    1080 60p-B  value= 27  "
        ::= { kudosConv2CtrlEntries 10024 }


    i2OutputCurrentOutputStandard OBJECT-TYPE
        SYNTAX            RollCallString
        MAX-ACCESS        read-only
        STATUS            current
        DESCRIPTION
                "CMNT: - 
                 TYPE: - Display
                 PAGE: - Output
                    Current Output Standard  cmdID= 10314  "
        ::= { kudosConv2CtrlEntries 10314 }


    i2OutputBlankingEmbeddedAudio OBJECT-TYPE
        SYNTAX            INTEGER {
                            valEnable(0),
                            valBlank(1)
                            }
        MAX-ACCESS        read-write
        STATUS            current
        DESCRIPTION
                "CMNT: - 
                 TYPE: - RadiobuttonList
                 PAGE: - Output
                    Embedded Audio  cmdID= 10021
                    Enable  value= 0
                    Blank  value= 1  "
        ::= { kudosConv2CtrlEntries 10021 }


    i2OutputBlankingVAncillaryData OBJECT-TYPE
        SYNTAX            INTEGER {
                            valPass(0),
                            valStrip(1)
                            }
        MAX-ACCESS        read-write
        STATUS            current
        DESCRIPTION
                "CMNT: - 
                 TYPE: - RadiobuttonList
                 PAGE: - Output
                    V Ancillary Data  cmdID= 10022
                    Pass  value= 0
                    Strip  value= 1  "
        ::= { kudosConv2CtrlEntries 10022 }


    i2OutputBlankingSDHalfLine OBJECT-TYPE
        SYNTAX            INTEGER {
                            valPass(0),
                            valBlank(1)
                            }
        MAX-ACCESS        read-write
        STATUS            current
        DESCRIPTION
                "CMNT: - 
                 TYPE: - RadiobuttonList
                 PAGE: - Output
                    SD Half Line  cmdID= 10023
                    Pass  value= 0
                    Blank  value= 1  "
        ::= { kudosConv2CtrlEntries 10023 }


    i2OutputTestPatterns OBJECT-TYPE
        SYNTAX            INTEGER {
                            valOff(0),
                            valBlack(1),
                            valRamp(2),
                            valBars(3)
                            }
        MAX-ACCESS        read-write
        STATUS            current
        DESCRIPTION
                "CMNT: - 
                 TYPE: - RadiobuttonList
                 PAGE: - Output
                    Test Patterns  cmdID= 10054
                    Off  value= 0
                    Black  value= 1
                    Ramp  value= 2
                    Bars  value= 3  "
        ::= { kudosConv2CtrlEntries 10054 }


    i2OutputScrollingCaptionGeneratorCaptionEntry OBJECT-TYPE
        SYNTAX            RollCallString
        MAX-ACCESS        read-write
        STATUS            current
        DESCRIPTION
                "CMNT: - 
                 TYPE: - Editstring
                 PAGE: - Output
                    Caption Entry  cmdID= 10050
                    preset= Channel Number"
        ::= { kudosConv2CtrlEntries 10050 }


    i2OutputScrollingCaptionGeneratorCaptionScroll OBJECT-TYPE
        SYNTAX            INTEGER { disable(0), enable(1)  }
        MAX-ACCESS        read-write
        STATUS            current
        DESCRIPTION
                "CMNT: - 
                 TYPE: - Checkbox
                 PAGE: - Output
                    Caption Scroll  cmdID= 10052  "
        ::= { kudosConv2CtrlEntries 10052 }


    i2OutputScrollingCaptionGeneratorCaptionEnable OBJECT-TYPE
        SYNTAX            INTEGER { disable(0), enable(1)  }
        MAX-ACCESS        read-write
        STATUS            current
        DESCRIPTION
                "CMNT: - 
                 TYPE: - Checkbox
                 PAGE: - Output
                    Caption Enable  cmdID= 10051  "
        ::= { kudosConv2CtrlEntries 10051 }


    i2OutputFreeze OBJECT-TYPE
        SYNTAX            INTEGER { disable(0), enable(1)  }
        MAX-ACCESS        read-write
        STATUS            current
        DESCRIPTION
                "CMNT: - 
                 TYPE: - Checkbox
                 PAGE: - Output
                    Freeze  cmdID= 10053  "
        ::= { kudosConv2CtrlEntries 10053 }


    i2OutputLegalization OBJECT-TYPE
        SYNTAX            INTEGER {
                            valOff(0),
                            val700mV(1),
                            val721mV(2),
                            val735mV(3),
                            val746mV(4)
                            }
        MAX-ACCESS        read-write
        STATUS            current
        DESCRIPTION
                "CMNT: - 
                 TYPE: - RadiobuttonList
                 PAGE: - Output
                    Legalization  cmdID= 10049
                    Off  value= 0
                    700mV  value= 1
                    721mV  value= 2
                    735mV  value= 3
                    746mV  value= 4  "
        ::= { kudosConv2CtrlEntries 10049 }


    i2OutputLogoControlPreShaped OBJECT-TYPE
        SYNTAX            INTEGER { disable(0), enable(1)  }
        MAX-ACCESS        read-write
        STATUS            current
        DESCRIPTION
                "CMNT: - 
                 TYPE: - Checkbox
                 PAGE: - Output
                    Pre-Shaped  cmdID= 10055  "
        ::= { kudosConv2CtrlEntries 10055 }


    i2OutputLogoControlTake OBJECT-TYPE
        SYNTAX            INTEGER { disable(0), enable(1)  }
        MAX-ACCESS        read-write
        STATUS            current
        DESCRIPTION
                "CMNT: - 
                 TYPE: - Checkbox
                 PAGE: - Output
                    Take  cmdID= 10056  "
        ::= { kudosConv2CtrlEntries 10056 }


    i2OutputLogoControlHPosition OBJECT-TYPE
        SYNTAX            INTEGER
        MAX-ACCESS        read-write
        STATUS            current
        DESCRIPTION
                "CMNT: - 
                 TYPE: - Number
                 PAGE: - Output
                    H Position  cmdID= 10057
                    min= 0  max= 100  step= 1  format= %0.0f  div_scale= 1  preset= 10
                    Min = 0  Max = 100  Step = 1  Preset = 10  "
        ::= { kudosConv2CtrlEntries 10057 }


    i2OutputLogoControlVPosition OBJECT-TYPE
        SYNTAX            INTEGER
        MAX-ACCESS        read-write
        STATUS            current
        DESCRIPTION
                "CMNT: - 
                 TYPE: - Number
                 PAGE: - Output
                    V Position  cmdID= 10058
                    min= 0  max= 100  step= 1  format= %0.0f  div_scale= 1  preset= 10
                    Min = 0  Max = 100  Step = 1  Preset = 10  "
        ::= { kudosConv2CtrlEntries 10058 }


    i2OutputLogoControlTransparency OBJECT-TYPE
        SYNTAX            INTEGER
        MAX-ACCESS        read-write
        STATUS            current
        DESCRIPTION
                "CMNT: - 
                 TYPE: - Number
                 PAGE: - Output
                    Transparency  cmdID= 10059
                    min= 0  max= 100  step= 1  format= %0.0f  div_scale= 1  preset= 10
                    Min = 0  Max = 100  Step = 1  Preset = 10  "
        ::= { kudosConv2CtrlEntries 10059 }


    i2OutputLogoControlDelete OBJECT-TYPE
        SYNTAX            INTEGER { noAction(0),valDelete(1) }
        MAX-ACCESS        read-write
        STATUS            current
        DESCRIPTION
                "CMNT: - 
                 TYPE: - Button
                 PAGE: - Output
                    Delete  cmdID= 10060
                    value= 1  "
        ::= { kudosConv2CtrlEntries 10060 }


    i2OutputLogoControlCurrentSelectedLogo OBJECT-TYPE
        SYNTAX            RollCallString
        MAX-ACCESS        read-only
        STATUS            current
        DESCRIPTION
                "CMNT: - 
                 TYPE: - Display
                 PAGE: - Output
                    Current Selected Logo  cmdID= 10062  "
        ::= { kudosConv2CtrlEntries 10062 }


    i2OutputLogoControlLogoStatus OBJECT-TYPE
        SYNTAX            RollCallString
        MAX-ACCESS        read-only
        STATUS            current
        DESCRIPTION
                "CMNT: - 
                 TYPE: - Display
                 PAGE: - Output
                    Logo Status  cmdID= 15001  "
        ::= { kudosConv2CtrlEntries 15001 }


    i2OutputLogoControlLogoState OBJECT-TYPE
        SYNTAX            RollCallString
        MAX-ACCESS        read-only
        STATUS            current
        DESCRIPTION
                "CMNT: - 
                 TYPE: - Display
                 PAGE: - Output
                    Logo State  cmdID= 10063  "
        ::= { kudosConv2CtrlEntries 10063 }


    i2OutputLogoControlNewLogo OBJECT-TYPE
        SYNTAX            RollCallString
        MAX-ACCESS        read-write
        STATUS            current
        DESCRIPTION
                "CMNT: - 
                 TYPE: - Editstring
                 PAGE: - Output
                    New Logo  cmdID= 15000
                    preset= startupqwerty"
        ::= { kudosConv2CtrlEntries 15000 }


    i2OutputLogoControlLogoSelect OBJECT-TYPE
        SYNTAX            INTEGER {
                            valNoneSelected(-1),
                            valLogo1(1),
                            valLogo2(2),
                            valLogo3(3),
                            valLogo4(4),
                            valLogo5(5),
                            valLogo6(6),
                            valLogo7(7),
                            valLogo8(8),
                            valLogo9(9),
                            valLogo10(10),
                            valLogo11(11),
                            valLogo12(12),
                            valLogo13(13),
                            valLogo14(14),
                            valLogo15(15),
                            valLogo16(16),
                            valLogo17(17),
                            valLogo18(18),
                            valLogo19(19),
                            valLogo20(20),
                            valLogo21(21),
                            valLogo22(22),
                            valLogo23(23),
                            valLogo24(24),
                            valLogo25(25),
                            valLogo26(26),
                            valLogo27(27),
                            valLogo28(28),
                            valLogo29(29),
                            valLogo30(30),
                            valLogo31(31),
                            valLogo32(32),
                            valLogo33(33),
                            valLogo34(34),
                            valLogo35(35),
                            valLogo36(36),
                            valLogo37(37),
                            valLogo38(38),
                            valLogo39(39),
                            valLogo40(40),
                            valLogo41(41),
                            valLogo42(42),
                            valLogo43(43),
                            valLogo44(44),
                            valLogo45(45),
                            valLogo46(46),
                            valLogo47(47),
                            valLogo48(48),
                            valLogo49(49),
                            valLogo50(50),
                            valLogo51(51),
                            valLogo52(52),
                            valLogo53(53),
                            valLogo54(54),
                            valLogo55(55),
                            valLogo56(56),
                            valLogo57(57),
                            valLogo58(58),
                            valLogo59(59),
                            valLogo60(60),
                            valLogo61(61),
                            valLogo62(62),
                            valLogo63(63),
                            valLogo64(64)
                            }
        MAX-ACCESS        read-write
        STATUS            current
        DESCRIPTION
                "CMNT: - 
                 TYPE: - RadiobuttonList
                 PAGE: - Output
                    Logo Select  cmdID= 10061
                    None Selected  value= -1
                    Logo 1  value= 1
                    Logo 2  value= 2
                    Logo 3  value= 3
                    Logo 4  value= 4
                    Logo 5  value= 5
                    Logo 6  value= 6
                    Logo 7  value= 7
                    Logo 8  value= 8
                    Logo 9  value= 9
                    Logo 10  value= 10
                    Logo 11  value= 11
                    Logo 12  value= 12
                    Logo 13  value= 13
                    Logo 14  value= 14
                    Logo 15  value= 15
                    Logo 16  value= 16
                    Logo 17  value= 17
                    Logo 18  value= 18
                    Logo 19  value= 19
                    Logo 20  value= 20
                    Logo 21  value= 21
                    Logo 22  value= 22
                    Logo 23  value= 23
                    Logo 24  value= 24
                    Logo 25  value= 25
                    Logo 26  value= 26
                    Logo 27  value= 27
                    Logo 28  value= 28
                    Logo 29  value= 29
                    Logo 30  value= 30
                    Logo 31  value= 31
                    Logo 32  value= 32
                    Logo 33  value= 33
                    Logo 34  value= 34
                    Logo 35  value= 35
                    Logo 36  value= 36
                    Logo 37  value= 37
                    Logo 38  value= 38
                    Logo 39  value= 39
                    Logo 40  value= 40
                    Logo 41  value= 41
                    Logo 42  value= 42
                    Logo 43  value= 43
                    Logo 44  value= 44
                    Logo 45  value= 45
                    Logo 46  value= 46
                    Logo 47  value= 47
                    Logo 48  value= 48
                    Logo 49  value= 49
                    Logo 50  value= 50
                    Logo 51  value= 51
                    Logo 52  value= 52
                    Logo 53  value= 53
                    Logo 54  value= 54
                    Logo 55  value= 55
                    Logo 56  value= 56
                    Logo 57  value= 57
                    Logo 58  value= 58
                    Logo 59  value= 59
                    Logo 60  value= 60
                    Logo 61  value= 61
                    Logo 62  value= 62
                    Logo 63  value= 63
                    Logo 64  value= 64  "
        ::= { kudosConv2CtrlEntries 10061 }


    i2VideoProcAmpEnable OBJECT-TYPE
        SYNTAX            INTEGER { disable(0), enable(1)  }
        MAX-ACCESS        read-write
        STATUS            current
        DESCRIPTION
                "CMNT: - 
                 TYPE: - Checkbox
                 PAGE: - Video
                    Enable  cmdID= 10047  "
        ::= { kudosConv2CtrlEntries 10047 }


    i2VideoProcAmpContrast OBJECT-TYPE
        SYNTAX            INTEGER
        MAX-ACCESS        read-write
        STATUS            current
        DESCRIPTION
                "CMNT: - 
                 TYPE: - Number
                 PAGE: - Video
                    Contrast  cmdID= 10043
                    min= -60  max= 60  step= 2  format= %0.1fdB  div_scale= 10  preset= 0
                    Min = -6.0dB  Max = 6.0dB  Step = 0.2dB  Preset = 0.0dB  "
        ::= { kudosConv2CtrlEntries 10043 }


    i2VideoProcAmpSaturation OBJECT-TYPE
        SYNTAX            INTEGER
        MAX-ACCESS        read-write
        STATUS            current
        DESCRIPTION
                "CMNT: - 
                 TYPE: - Number
                 PAGE: - Video
                    Saturation  cmdID= 10044
                    min= -60  max= 60  step= 2  format= %0.1fdB  div_scale= 10  preset= 0
                    Min = -6.0dB  Max = 6.0dB  Step = 0.2dB  Preset = 0.0dB  "
        ::= { kudosConv2CtrlEntries 10044 }


    i2VideoProcAmpBlackLevel OBJECT-TYPE
        SYNTAX            INTEGER
        MAX-ACCESS        read-write
        STATUS            current
        DESCRIPTION
                "CMNT: - 
                 TYPE: - Number
                 PAGE: - Video
                    Black Level  cmdID= 10045
                    min= -1000  max= 1000  step= 8  format= %0.1fmV  div_scale= 10  preset= 0
                    Min = -100.0mV  Max = 100.0mV  Step = 0.8mV  Preset = 0.0mV  "
        ::= { kudosConv2CtrlEntries 10045 }


    i2VideoProcAmpGamma OBJECT-TYPE
        SYNTAX            INTEGER
        MAX-ACCESS        read-write
        STATUS            current
        DESCRIPTION
                "CMNT: - 
                 TYPE: - Number
                 PAGE: - Video
                    Gamma  cmdID= 10046
                    min= 4  max= 17  step= 1  format= %0.1f  div_scale= 10  preset= 10
                    Min = 0.4  Max = 1.7  Step = 0.1  Preset = 1.0  "
        ::= { kudosConv2CtrlEntries 10046 }


    i2VideoProcAmpYCOffset OBJECT-TYPE
        SYNTAX            INTEGER
        MAX-ACCESS        read-write
        STATUS            current
        DESCRIPTION
                "CMNT: - 
                 TYPE: - Number
                 PAGE: - Video
                    YC Offset  cmdID= 10048
                    min= -20  max= 20  step= 2  format= %0.0f  div_scale= 1  preset= 0
                    Min = -20  Max = 20  Step = 2  Preset = 0  "
        ::= { kudosConv2CtrlEntries 10048 }


    i2VideoEnhanceNonlinearEnhancerEnable OBJECT-TYPE
        SYNTAX            INTEGER { disable(0), enable(1)  }
        MAX-ACCESS        read-write
        STATUS            current
        DESCRIPTION
                "CMNT: - 
                 TYPE: - Checkbox
                 PAGE: - Enhance
                    Enable  cmdID= 10036  "
        ::= { kudosConv2CtrlEntries 10036 }


    i2VideoEnhanceNonlinearEnhancerLevel OBJECT-TYPE
        SYNTAX            INTEGER
        MAX-ACCESS        read-write
        STATUS            current
        DESCRIPTION
                "CMNT: - 
                 TYPE: - Number
                 PAGE: - Enhance
                    Level  cmdID= 10039
                    min= 0  max= 192  step= 1  format= %0.0f  div_scale= 1  preset= 0
                    Min = 0  Max = 192  Step = 1  Preset = 0  "
        ::= { kudosConv2CtrlEntries 10039 }


    i2VideoEnhanceNonlinearEnhancerMode OBJECT-TYPE
        SYNTAX            INTEGER {
                            valLow(0),
                            valMedium(1),
                            valHigh(2),
                            valSuper(3),
                            valManual(4)
                            }
        MAX-ACCESS        read-write
        STATUS            current
        DESCRIPTION
                "CMNT: - 
                 TYPE: - RadiobuttonList
                 PAGE: - Enhance
                    Mode  cmdID= 10037
                    Low  value= 0
                    Medium  value= 1
                    High  value= 2
                    Super  value= 3
                    Manual  value= 4  "
        ::= { kudosConv2CtrlEntries 10037 }


    i2VideoEnhanceNonlinearEnhancerFrequencyBand OBJECT-TYPE
        SYNTAX            INTEGER {
                            valLow(0),
                            valMedium(1),
                            valHigh(2)
                            }
        MAX-ACCESS        read-write
        STATUS            current
        DESCRIPTION
                "CMNT: - 
                 TYPE: - RadiobuttonList
                 PAGE: - Enhance
                    Frequency Band  cmdID= 10038
                    Low  value= 0
                    Medium  value= 1
                    High  value= 2  "
        ::= { kudosConv2CtrlEntries 10038 }


    i2VideoEnhanceNonlinearEnhancerNoiseRejection OBJECT-TYPE
        SYNTAX            INTEGER
        MAX-ACCESS        read-write
        STATUS            current
        DESCRIPTION
                "CMNT: - 
                 TYPE: - Number
                 PAGE: - Enhance
                    Noise Rejection  cmdID= 10040
                    min= 0  max= 100  step= 1  format= %0.0f  div_scale= 1  preset= 0
                    Min = 0  Max = 100  Step = 1  Preset = 0  "
        ::= { kudosConv2CtrlEntries 10040 }


    i2VideoEnhanceConversionAperturePreset OBJECT-TYPE
        SYNTAX            INTEGER { noAction(0),valPreset(1) }
        MAX-ACCESS        read-write
        STATUS            current
        DESCRIPTION
                "CMNT: - 
                 TYPE: - Button
                 PAGE: - Enhance
                    Preset  cmdID= 10335
                    value= 1  "
        ::= { kudosConv2CtrlEntries 10335 }


    i2VideoConversionApertureHorizontalSharpness OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Conversion Aperture
                    Sharpness  cmdID= 10072
                    Soft 2  value= 0
                    Soft 1  value= 1
                    Normal  value= 2
                    Sharp 1  value= 3
                    Sharp 2  value= 4  "
        ::= { kudosConv2CtrlEntries 10072 }


    i2VideoConversionApertureHorizontalDetail OBJECT-TYPE
        SYNTAX            INTEGER {
                            valLow2(0),
                            valLow1(1),
                            valNormal(2),
                            valHigh1(3),
                            valHigh2(4)
                            }
        MAX-ACCESS        read-write
        STATUS            current
        DESCRIPTION
                "CMNT: - 
                 TYPE: - RadiobuttonList
                 PAGE: - Conversion Aperture
                    Detail  cmdID= 10073
                    Low 2  value= 0
                    Low 1  value= 1
                    Normal  value= 2
                    High 1  value= 3
                    High 2  value= 4  "
        ::= { kudosConv2CtrlEntries 10073 }


    i2VideoConversionApertureVerticalLevel OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Conversion Aperture
                    Level  cmdID= 10042
                    Soft 2  value= 0
                    Soft 1  value= 1
                    Normal  value= 2
                    Sharp 1  value= 3
                    Sharp 2  value= 4  "
        ::= { kudosConv2CtrlEntries 10042 }


    i2VideoConversionApertureVerticalFrequencyBand OBJECT-TYPE
        SYNTAX            INTEGER {
                            valLow(0),
                            valMedium(1),
                            valHigh(2)
                            }
        MAX-ACCESS        read-write
        STATUS            current
        DESCRIPTION
                "CMNT: - 
                 TYPE: - RadiobuttonList
                 PAGE: - Conversion Aperture
                    Frequency Band  cmdID= 10041
                    Low  value= 0
                    Medium  value= 1
                    High  value= 2  "
        ::= { kudosConv2CtrlEntries 10041 }


    i2VideoNoiseReductionEnable OBJECT-TYPE
        SYNTAX            INTEGER { disable(0), enable(1)  }
        MAX-ACCESS        read-write
        STATUS            current
        DESCRIPTION
                "CMNT: - 
                 TYPE: - Checkbox
                 PAGE: - Video
                    Enable  cmdID= 10031  "
        ::= { kudosConv2CtrlEntries 10031 }


    i2VideoNoiseReductionRecursiveLuma OBJECT-TYPE
        SYNTAX            INTEGER
        MAX-ACCESS        read-write
        STATUS            current
        DESCRIPTION
                "CMNT: - 
                 TYPE: - Number
                 PAGE: - Noise Reduction
                    Luma  cmdID= 10027
                    min= 0  max= 7  step= 1  format= %0.0f  div_scale= 1  preset= 0
                    Min = 0  Max = 7  Step = 1  Preset = 0  "
        ::= { kudosConv2CtrlEntries 10027 }


    i2VideoNoiseReductionRecursiveChroma OBJECT-TYPE
        SYNTAX            INTEGER
        MAX-ACCESS        read-write
        STATUS            current
        DESCRIPTION
                "CMNT: - 
                 TYPE: - Number
                 PAGE: - Noise Reduction
                    Chroma  cmdID= 10028
                    min= 0  max= 7  step= 1  format= %0.0f  div_scale= 1  preset= 0
                    Min = 0  Max = 7  Step = 1  Preset = 0  "
        ::= { kudosConv2CtrlEntries 10028 }


    i2VideoNoiseReductionRecursiveMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10029
                    Auto  value= 0
                    Manual  value= 1  "
        ::= { kudosConv2CtrlEntries 10029 }


    i2VideoNoiseReductionRecursiveThreshold OBJECT-TYPE
        SYNTAX            INTEGER
        MAX-ACCESS        read-write
        STATUS            current
        DESCRIPTION
                "CMNT: - 
                 TYPE: - Number
                 PAGE: - Noise Reduction
                    Threshold  cmdID= 10030
                    min= 0  max= 7  step= 1  format= %0.0f  div_scale= 1  preset= 0
                    Min = 0  Max = 7  Step = 1  Preset = 0  "
        ::= { kudosConv2CtrlEntries 10030 }


    i2VideoNoiseReductionSpatialLevel OBJECT-TYPE
        SYNTAX            INTEGER
        MAX-ACCESS        read-write
        STATUS            current
        DESCRIPTION
                "CMNT: - 
                 TYPE: - Number
                 PAGE: - Noise Reduction
                    Level  cmdID= 10033
                    min= 0  max= 7  step= 1  format= %0.0f  div_scale= 1  preset= 0
                    Min = 0  Max = 7  Step = 1  Preset = 0  "
        ::= { kudosConv2CtrlEntries 10033 }


    i2VideoNoiseReductionSpatialMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10032
                    Auto  value= 0
                    Manual  value= 1  "
        ::= { kudosConv2CtrlEntries 10032 }


    i2VideoNoiseReductionSpatialThreshold OBJECT-TYPE
        SYNTAX            INTEGER
        MAX-ACCESS        read-write
        STATUS            current
        DESCRIPTION
                "CMNT: - 
                 TYPE: - Number
                 PAGE: - Noise Reduction
                    Threshold  cmdID= 10034
                    min= 1  max= 4  step= 1  format= %0.0f  div_scale= 1  preset= 1
                    Min = 1  Max = 4  Step = 1  Preset = 1  "
        ::= { kudosConv2CtrlEntries 10034 }


    i2VideoNoiseReductionSplitScreen OBJECT-TYPE
        SYNTAX            INTEGER { disable(0), enable(1)  }
        MAX-ACCESS        read-write
        STATUS            current
        DESCRIPTION
                "CMNT: - 
                 TYPE: - Checkbox
                 PAGE: - Video
                    Split Screen  cmdID= 10035  "
        ::= { kudosConv2CtrlEntries 10035 }


    i2ConvertUpConversionCleanEdgeUpconversion OBJECT-TYPE
        SYNTAX            INTEGER { disable(0), enable(1)  }
        MAX-ACCESS        read-write
        STATUS            current
        DESCRIPTION
                "CMNT: - 
                 TYPE: - Checkbox
                 PAGE: - Convert
                    Clean Edge Upconversion  cmdID= 10069  "
        ::= { kudosConv2CtrlEntries 10069 }


    i2ConvertMotionProcessingMotionProcess OBJECT-TYPE
        SYNTAX            INTEGER { disable(0), enable(1)  }
        MAX-ACCESS        read-write
        STATUS            current
        DESCRIPTION
                "CMNT: - 
                 TYPE: - Checkbox
                 PAGE: - Convert
                    Motion Process  cmdID= 10064  "
        ::= { kudosConv2CtrlEntries 10064 }


    i2ConvertMotionProcessingEnhancedMotion OBJECT-TYPE
        SYNTAX            INTEGER { disable(0), enable(1)  }
        MAX-ACCESS        read-write
        STATUS            current
        DESCRIPTION
                "CMNT: - 
                 TYPE: - Checkbox
                 PAGE: - Convert
                    Enhanced Motion  cmdID= 10065  "
        ::= { kudosConv2CtrlEntries 10065 }


    i2ConvertMotionProcessingStillProcess OBJECT-TYPE
        SYNTAX            INTEGER { disable(0), enable(1)  }
        MAX-ACCESS        read-write
        STATUS            current
        DESCRIPTION
                "CMNT: - 
                 TYPE: - Checkbox
                 PAGE: - Convert
                    Still Process  cmdID= 10066  "
        ::= { kudosConv2CtrlEntries 10066 }


    i2ConvertMotionProcessingEnhancedStill OBJECT-TYPE
        SYNTAX            INTEGER { disable(0), enable(1)  }
        MAX-ACCESS        read-write
        STATUS            current
        DESCRIPTION
                "CMNT: - 
                 TYPE: - Checkbox
                 PAGE: - Convert
                    Enhanced Still  cmdID= 10067  "
        ::= { kudosConv2CtrlEntries 10067 }


    i2ConvertMotionProcessingEnhancedFilm OBJECT-TYPE
        SYNTAX            INTEGER { disable(0), enable(1)  }
        MAX-ACCESS        read-write
        STATUS            current
        DESCRIPTION
                "CMNT: - 
                 TYPE: - Checkbox
                 PAGE: - Convert
                    Enhanced Film  cmdID= 10068  "
        ::= { kudosConv2CtrlEntries 10068 }


    i2ConvertMotionProcessingEnhancedDeinterlace OBJECT-TYPE
        SYNTAX            INTEGER { disable(0), enable(1)  }
        MAX-ACCESS        read-write
        STATUS            current
        DESCRIPTION
                "CMNT: - 
                 TYPE: - Checkbox
                 PAGE: - Convert
                    Enhanced De-interlace  cmdID= 10071  "
        ::= { kudosConv2CtrlEntries 10071 }


    i2ConvertMotionProcessingCleanCut OBJECT-TYPE
        SYNTAX            INTEGER { disable(0), enable(1)  }
        MAX-ACCESS        read-write
        STATUS            current
        DESCRIPTION
                "CMNT: - 
                 TYPE: - Checkbox
                 PAGE: - Convert
                    Clean Cut  cmdID= 10070  "
        ::= { kudosConv2CtrlEntries 10070 }


    i2ConvertInputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10323  "
        ::= { kudosConv2CtrlEntries 10323 }


    i2ConvertInputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10324
                    2:3  value= 0
                    2:2 (psf)  value= 1  "
        ::= { kudosConv2CtrlEntries 10324 }


    i2ConvertInputCadence23Source OBJECT-TYPE
        SYNTAX            INTEGER {
                            valAutomatic(0),
                            valInputTimecode(1)
                            }
        MAX-ACCESS        read-write
        STATUS            current
        DESCRIPTION
                "CMNT: - 
                 TYPE: - RadiobuttonList
                 PAGE: - Convert
                    2:3 Source  cmdID= 10325
                    Automatic  value= 0
                    Input Timecode  value= 1  "
        ::= { kudosConv2CtrlEntries 10325 }


    i2ConvertInputCadence23StartHour OBJECT-TYPE
        SYNTAX            INTEGER
        MAX-ACCESS        read-write
        STATUS            current
        DESCRIPTION
                "CMNT: - 
                 TYPE: - Number
                 PAGE: - Convert
                    2:3 Start Hour  cmdID= 10326
                    min= 0  max= 23  step= 1  format= %0.0f  div_scale= 1  preset= 1
                    Min = 0  Max = 23  Step = 1  Preset = 1  "
        ::= { kudosConv2CtrlEntries 10326 }


    i2ConvertOutputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10327  "
        ::= { kudosConv2CtrlEntries 10327 }


    i2ConvertOutputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10328
                    2:3  value= 0
                    2:2 (psf)  value= 1  "
        ::= { kudosConv2CtrlEntries 10328 }


    i2ConvertOutputCadence23Source OBJECT-TYPE
        SYNTAX            INTEGER {
                            valFreeRun(0),
                            valOutputTimecode(1)
                            }
        MAX-ACCESS        read-write
        STATUS            current
        DESCRIPTION
                "CMNT: - 
                 TYPE: - RadiobuttonList
                 PAGE: - Convert
                    2:3 Source  cmdID= 10329
                    Free Run  value= 0
                    Output Timecode  value= 1  "
        ::= { kudosConv2CtrlEntries 10329 }


    i2ConvertOutputCadence23StartHour OBJECT-TYPE
        SYNTAX            INTEGER
        MAX-ACCESS        read-write
        STATUS            current
        DESCRIPTION
                "CMNT: - 
                 TYPE: - Number
                 PAGE: - Convert
                    2:3 Start Hour  cmdID= 10330
                    min= 0  max= 23  step= 1  format= %0.0f  div_scale= 1  preset= 1
                    Min = 0  Max = 23  Step = 1  Preset = 1  "
        ::= { kudosConv2CtrlEntries 10330 }


    i2ARCSyncMode OBJECT-TYPE
        SYNTAX            INTEGER { disable(0), enable(1)  }
        MAX-ACCESS        read-write
        STATUS            current
        DESCRIPTION
                "CMNT: - 
                 TYPE: - Checkbox
                 PAGE: - ARC
                    Sync Mode  cmdID= 10079  "
        ::= { kudosConv2CtrlEntries 10079 }


    i2ARCSignalingDetected OBJECT-TYPE
        SYNTAX            RollCallString
        MAX-ACCESS        read-only
        STATUS            current
        DESCRIPTION
                "CMNT: - 
                 TYPE: - Display
                 PAGE: - ARC
                    Signaling Detected  cmdID= 10315  "
        ::= { kudosConv2CtrlEntries 10315 }


    i2ARCSidebarKeyingOutputCropMode OBJECT-TYPE
        SYNTAX            INTEGER {
                            valOff(0),
                            valOutputCrop(1),
                            valSidebarKey(2)
                            }
        MAX-ACCESS        read-write
        STATUS            current
        DESCRIPTION
                "CMNT: - 
                 TYPE: - RadiobuttonList
                 PAGE: - ARC
                    Mode  cmdID= 10091
                    Off  value= 0
                    Output Crop  value= 1
                    Sidebar Key  value= 2  "
        ::= { kudosConv2CtrlEntries 10091 }


    i2ARCSidebarKeyingOutputCropSidebarKeySource OBJECT-TYPE
        SYNTAX            INTEGER {
                            valSDI1(0),
                            valSDI2(1),
                            valSDI3(2),
                            valSDI4(3),
                            valCVBSA(4),
                            valCVBSB(5),
                            valCVBSC(6),
                            valCVBSD(7),
                            valSFPA1(8),
                            valSFPA2(9),
                            valSFPA3(10),
                            valSFPA4(11),
                            valOutput(20)
                            }
        MAX-ACCESS        read-write
        STATUS            current
        DESCRIPTION
                "CMNT: - 
                 TYPE: - RadiobuttonList
                 PAGE: - ARC
                    Sidebar Key Source  cmdID= 10092
                    SDI 1  value= 0
                    SDI 2  value= 1
                    SDI 3  value= 2
                    SDI 4  value= 3
                    CVBS A  value= 4
                    CVBS B  value= 5
                    CVBS C  value= 6
                    CVBS D  value= 7
                    SFP A1  value= 8
                    SFP A2  value= 9
                    SFP A3  value= 10
                    SFP A4  value= 11
                    Output  value= 20  "
        ::= { kudosConv2CtrlEntries 10092 }


    i2ARCSidebarKeyingOutputCropOutputCropPositionTop OBJECT-TYPE
        SYNTAX            INTEGER
        MAX-ACCESS        read-write
        STATUS            current
        DESCRIPTION
                "CMNT: - 
                 TYPE: - Number
                 PAGE: - Sidebar Keying & Output Crop
                    Top  cmdID= 10093
                    min= 0  max= 99  step= 1  format= %0.0f%%  div_scale= 1  preset= 0
                    Min = 0%  Max = 99%  Step = 1%  Preset = 0%  "
        ::= { kudosConv2CtrlEntries 10093 }


    i2ARCSidebarKeyingOutputCropOutputCropPositionBottom OBJECT-TYPE
        SYNTAX            INTEGER
        MAX-ACCESS        read-write
        STATUS            current
        DESCRIPTION
                "CMNT: - 
                 TYPE: - Number
                 PAGE: - Sidebar Keying & Output Crop
                    Bottom  cmdID= 10094
                    min= 0  max= 99  step= 1  format= %0.0f%%  div_scale= 1  preset= 0
                    Min = 0%  Max = 99%  Step = 1%  Preset = 0%  "
        ::= { kudosConv2CtrlEntries 10094 }


    i2ARCSidebarKeyingOutputCropOutputCropPositionLeft OBJECT-TYPE
        SYNTAX            INTEGER
        MAX-ACCESS        read-write
        STATUS            current
        DESCRIPTION
                "CMNT: - 
                 TYPE: - Number
                 PAGE: - Sidebar Keying & Output Crop
                    Left  cmdID= 10095
                    min= 0  max= 99  step= 1  format= %0.0f%%  div_scale= 1  preset= 0
                    Min = 0%  Max = 99%  Step = 1%  Preset = 0%  "
        ::= { kudosConv2CtrlEntries 10095 }


    i2ARCSidebarKeyingOutputCropOutputCropPositionRight OBJECT-TYPE
        SYNTAX            INTEGER
        MAX-ACCESS        read-write
        STATUS            current
        DESCRIPTION
                "CMNT: - 
                 TYPE: - Number
                 PAGE: - Sidebar Keying & Output Crop
                    Right  cmdID= 10096
                    min= 0  max= 99  step= 1  format= %0.0f%%  div_scale= 1  preset= 0
                    Min = 0%  Max = 99%  Step = 1%  Preset = 0%  "
        ::= { kudosConv2CtrlEntries 10096 }


    i2ARCPostScalingControlPostScalingEnable OBJECT-TYPE
        SYNTAX            INTEGER { disable(0), enable(1)  }
        MAX-ACCESS        read-write
        STATUS            current
        DESCRIPTION
                "CMNT: - 
                 TYPE: - Checkbox
                 PAGE: - ARC
                    Post Scaling Enable  cmdID= 10078  "
        ::= { kudosConv2CtrlEntries 10078 }


    i2ARCPostScalingControlSize OBJECT-TYPE
        SYNTAX            INTEGER
        MAX-ACCESS        read-write
        STATUS            current
        DESCRIPTION
                "CMNT: - 
                 TYPE: - Number
                 PAGE: - ARC
                    Size  cmdID= 10074
                    min= 80  max= 120  step= 1  format= %0.0f%%  div_scale= 1  preset= 100
                    Min = 80%  Max = 120%  Step = 1%  Preset = 100%  "
        ::= { kudosConv2CtrlEntries 10074 }


    i2ARCPostScalingControlAspect OBJECT-TYPE
        SYNTAX            INTEGER
        MAX-ACCESS        read-write
        STATUS            current
        DESCRIPTION
                "CMNT: - 
                 TYPE: - Number
                 PAGE: - ARC
                    Aspect  cmdID= 10075
                    min= 70  max= 150  step= 1  format= %0.0f%%  div_scale= 1  preset= 100
                    Min = 70%  Max = 150%  Step = 1%  Preset = 100%  "
        ::= { kudosConv2CtrlEntries 10075 }


    i2ARCPostScalingControlPan OBJECT-TYPE
        SYNTAX            INTEGER
        MAX-ACCESS        read-write
        STATUS            current
        DESCRIPTION
                "CMNT: - 
                 TYPE: - Number
                 PAGE: - ARC
                    Pan  cmdID= 10076
                    min= -50  max= 50  step= 1  format= %0.0f%  div_scale= 1  preset= 0
                    Min = -50  Max = 50  Step = 1  Preset = 0  "
        ::= { kudosConv2CtrlEntries 10076 }


    i2ARCPostScalingControlTilt OBJECT-TYPE
        SYNTAX            INTEGER
        MAX-ACCESS        read-write
        STATUS            current
        DESCRIPTION
                "CMNT: - 
                 TYPE: - Number
                 PAGE: - ARC
                    Tilt  cmdID= 10077
                    min= -50  max= 50  step= 1  format= %0.0f%  div_scale= 1  preset= 0
                    Min = -50  Max = 50  Step = 1  Preset = 0  "
        ::= { kudosConv2CtrlEntries 10077 }


    i2ARCScalerConfigUsePresets OBJECT-TYPE
        SYNTAX            INTEGER { disable(0), enable(1)  }
        MAX-ACCESS        read-write
        STATUS            current
        DESCRIPTION
                "CMNT: - 
                 TYPE: - Checkbox
                 PAGE: - ARC
                    Use Presets  cmdID= 10110  "
        ::= { kudosConv2CtrlEntries 10110 }


    i2ARCScalerConfigPresetsSDInputis702 OBJECT-TYPE
        SYNTAX            INTEGER { disable(0), enable(1)  }
        MAX-ACCESS        read-write
        STATUS            current
        DESCRIPTION
                "CMNT: - 
                 TYPE: - Checkbox
                 PAGE: - Scaler Config
                    SD Input is 702  cmdID= 10080  "
        ::= { kudosConv2CtrlEntries 10080 }


    i2ARCScalerConfigPresetsSDOutputis702 OBJECT-TYPE
        SYNTAX            INTEGER { disable(0), enable(1)  }
        MAX-ACCESS        read-write
        STATUS            current
        DESCRIPTION
                "CMNT: - 
                 TYPE: - Checkbox
                 PAGE: - Scaler Config
                    SD Output is 702  cmdID= 10081  "
        ::= { kudosConv2CtrlEntries 10081 }


    i2ARCPresetsSDCrossConversionSelectStdPreset OBJECT-TYPE
        SYNTAX            INTEGER {
                            valNone(0),
                            val169LB43HC(1),
                            val169LB169Ana(2),
                            val169LB149LB(3),
                            val169Ana43HC(4),
                            val169Ana169LB(5),
                            val169Ana149LB(6)
                            }
        MAX-ACCESS        read-write
        STATUS            current
        DESCRIPTION
                "CMNT: - 
                 TYPE: - RadiobuttonList
                 PAGE: - Presets
                    Select Std Preset  cmdID= 10082
                    None  value= 0
                    16:9 LB > 4:3 HC  value= 1
                    16:9 LB > 16:9 Ana  value= 2
                    16:9 LB > 14:9 LB  value= 3
                    16:9 Ana > 4:3 HC  value= 4
                    16:9 Ana > 16:9 LB  value= 5
                    16:9 Ana > 14:9 LB  value= 6  "
        ::= { kudosConv2CtrlEntries 10082 }


    i2ARCPresetsHDCrossConversionSelectStdPreset OBJECT-TYPE
        SYNTAX            INTEGER {
                            valNone(0),
                            val149PB169VC(1),
                            val43PB169VC(2),
                            val43PB149PBVC(3)
                            }
        MAX-ACCESS        read-write
        STATUS            current
        DESCRIPTION
                "CMNT: - 
                 TYPE: - RadiobuttonList
                 PAGE: - Presets
                    Select Std Preset  cmdID= 10083
                    None  value= 0
                    14:9 PB > 16:9 VC  value= 1
                    4:3 PB > 16:9 VC  value= 2
                    4:3 PB > 14:9 PB VC  value= 3  "
        ::= { kudosConv2CtrlEntries 10083 }


    i2ARCPresetsUpConversionSelectStdPreset OBJECT-TYPE
        SYNTAX            INTEGER {
                            val43169VC(0),
                            val4343PB(1),
                            val169LB169(2),
                            val169Ana169(3),
                            val149LB149PB(4)
                            }
        MAX-ACCESS        read-write
        STATUS            current
        DESCRIPTION
                "CMNT: - 
                 TYPE: - RadiobuttonList
                 PAGE: - Presets
                    Select Std Preset  cmdID= 10084
                    4:3 > 16:9 VC  value= 0
                    4:3 > 4:3 PB  value= 1
                    16:9 LB > 16:9  value= 2
                    16:9 Ana > 16:9  value= 3
                    14:9 LB > 14:9 PB  value= 4  "
        ::= { kudosConv2CtrlEntries 10084 }


    i2ARCPresetsDownConversionSelectStdPreset OBJECT-TYPE
        SYNTAX            INTEGER {
                            val16943HC(0),
                            val169169LB(1),
                            val169169Ana(2),
                            val43PB43(3),
                            val149PB149LB(4)
                            }
        MAX-ACCESS        read-write
        STATUS            current
        DESCRIPTION
                "CMNT: - 
                 TYPE: - RadiobuttonList
                 PAGE: - Presets
                    Select Std Preset  cmdID= 10085
                    16:9 > 4:3 HC  value= 0
                    16:9 > 16:9 LB  value= 1
                    16:9 > 16:9 Ana  value= 2
                    4:3 PB > 4:3  value= 3
                    14:9 PB > 14:9 LB  value= 4  "
        ::= { kudosConv2CtrlEntries 10085 }


    i2ARCScalerConfigInputConfigInputSignallingSource OBJECT-TYPE
        SYNTAX            INTEGER {
                            valSMPTE2016(0),
                            valL23ETSI(1),
                            valL23AFD(2),
                            valVISMPTE(3),
                            valVIAFD(4)
                            }
        MAX-ACCESS        read-write
        STATUS            current
        DESCRIPTION
                "CMNT: - 
                 TYPE: - RadiobuttonList
                 PAGE: - Scaler Config
                    Input Signalling Source  cmdID= 10090
                    SMPTE 2016  value= 0
                    L23 ETSI  value= 1
                    L23 AFD  value= 2
                    VI SMPTE  value= 3
                    VI AFD  value= 4  "
        ::= { kudosConv2CtrlEntries 10090 }


    i2ARCInputConfigIfInputSignallingNotPresentForceInputFormat OBJECT-TYPE
        SYNTAX            INTEGER { disable(0), enable(1)  }
        MAX-ACCESS        read-write
        STATUS            current
        DESCRIPTION
                "CMNT: - 
                 TYPE: - Checkbox
                 PAGE: - Input Config
                    Force Input Format  cmdID= 10109  "
        ::= { kudosConv2CtrlEntries 10109 }


    i2ARCInputConfigIfInputSignallingNotPresentSDInputFormat OBJECT-TYPE
        SYNTAX            INTEGER {
                            valNormal(0),
                            valAnamorphic(1),
                            val169Letterbox(2),
                            val149Letterbox(3)
                            }
        MAX-ACCESS        read-write
        STATUS            current
        DESCRIPTION
                "CMNT: - 
                 TYPE: - RadiobuttonList
                 PAGE: - Input Config
                    SD Input Format  cmdID= 10086
                    Normal  value= 0
                    Anamorphic  value= 1
                    16:9 Letterbox  value= 2
                    14:9 Letterbox  value= 3  "
        ::= { kudosConv2CtrlEntries 10086 }


    i2ARCInputConfigIfInputSignallingNotPresentHDInputFormat OBJECT-TYPE
        SYNTAX            INTEGER {
                            valNormal(0),
                            val149Pillarbox(1),
                            val43Pillarbox(2)
                            }
        MAX-ACCESS        read-write
        STATUS            current
        DESCRIPTION
                "CMNT: - 
                 TYPE: - RadiobuttonList
                 PAGE: - Input Config
                    HD Input Format  cmdID= 10087
                    Normal  value= 0
                    14:9 Pillarbox  value= 1
                    4:3 Pillarbox  value= 2  "
        ::= { kudosConv2CtrlEntries 10087 }


    i2ARCScalerConfigOutputConfigConversionScaling OBJECT-TYPE
        SYNTAX            INTEGER {
                            valFittoHeight(0),
                            valFittoWidth(1),
                            val149(2)
                            }
        MAX-ACCESS        read-write
        STATUS            current
        DESCRIPTION
                "CMNT: - 
                 TYPE: - RadiobuttonList
                 PAGE: - Scaler Config
                    Conversion Scaling  cmdID= 10089
                    Fit to Height  value= 0
                    Fit to Width  value= 1
                    14:9  value= 2  "
        ::= { kudosConv2CtrlEntries 10089 }


    i2ARCScalerConfigOutputConfigSDOutputFormat OBJECT-TYPE
        SYNTAX            INTEGER {
                            valNormal(0),
                            valAnamorphic(1)
                            }
        MAX-ACCESS        read-write
        STATUS            current
        DESCRIPTION
                "CMNT: - 
                 TYPE: - RadiobuttonList
                 PAGE: - Scaler Config
                    SD Output Format  cmdID= 10088
                    Normal  value= 0
                    Anamorphic  value= 1  "
        ::= { kudosConv2CtrlEntries 10088 }


    i2ARCOutputSignallingConfigSMPTE2016Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10104
                    Auto  value= 0
                    Pass  value= 1
                    Force  value= 2
                    Delete  value= 3  "
        ::= { kudosConv2CtrlEntries 10104 }


    i2ARCOutputSignallingConfigSMPTE2016OutputLinePAL OBJECT-TYPE
        SYNTAX            INTEGER
        MAX-ACCESS        read-write
        STATUS            current
        DESCRIPTION
                "CMNT: - 
                 TYPE: - Number
                 PAGE: - Output Signalling Config
                    Output Line PAL  cmdID= 10332
                    min= 7  max= 22  step= 1  format= %0.0f  div_scale= 1  preset= 12
                    Min = 7  Max = 22  Step = 1  Preset = 12  "
        ::= { kudosConv2CtrlEntries 10332 }


    i2ARCOutputSignallingConfigSMPTE2016OutputLineNTSC OBJECT-TYPE
        SYNTAX            INTEGER
        MAX-ACCESS        read-write
        STATUS            current
        DESCRIPTION
                "CMNT: - 
                 TYPE: - Number
                 PAGE: - Output Signalling Config
                    Output Line NTSC  cmdID= 10333
                    min= 11  max= 19  step= 1  format= %0.0f  div_scale= 1  preset= 11
                    Min = 11  Max = 19  Step = 1  Preset = 11  "
        ::= { kudosConv2CtrlEntries 10333 }


    i2ARCOutputSignallingConfigSMPTE2016OutputLineHD OBJECT-TYPE
        SYNTAX            INTEGER
        MAX-ACCESS        read-write
        STATUS            current
        DESCRIPTION
                "CMNT: - 
                 TYPE: - Number
                 PAGE: - Output Signalling Config
                    Output Line HD  cmdID= 10331
                    min= 9  max= 20  step= 1  format= %0.0f  div_scale= 1  preset= 11
                    Min = 9  Max = 20  Step = 1  Preset = 11  "
        ::= { kudosConv2CtrlEntries 10331 }


    i2ARCOutputSignallingConfigSMPTE2016OutputLineStatus OBJECT-TYPE
        SYNTAX            RollCallString
        MAX-ACCESS        read-only
        STATUS            current
        DESCRIPTION
                "CMNT: - 
                 TYPE: - Display
                 PAGE: - Output Signalling Config
                    Output Line Status  cmdID= 10334  "
        ::= { kudosConv2CtrlEntries 10334 }


    i2ARCOutputSignallingConfigVIMode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10101
                    Auto  value= 0
                    Pass  value= 1
                    Force  value= 2
                    Delete  value= 3  "
        ::= { kudosConv2CtrlEntries 10101 }


    i2ARCOutputSignallingConfigVIOutputFormat OBJECT-TYPE
        SYNTAX            INTEGER {
                            valSMPTE(0),
                            valAFD(1)
                            }
        MAX-ACCESS        read-write
        STATUS            current
        DESCRIPTION
                "CMNT: - 
                 TYPE: - RadiobuttonList
                 PAGE: - Output Signalling Config
                    Output Format  cmdID= 10102
                    SMPTE  value= 0
                    AFD  value= 1  "
        ::= { kudosConv2CtrlEntries 10102 }


    i2ARCOutputSignallingConfigVIPassData OBJECT-TYPE
        SYNTAX            INTEGER { disable(0), enable(1)  }
        MAX-ACCESS        read-write
        STATUS            current
        DESCRIPTION
                "CMNT: - 
                 TYPE: - Checkbox
                 PAGE: - ARC
                    VI Pass Data  cmdID= 10103  "
        ::= { kudosConv2CtrlEntries 10103 }


    i2ARCOutputSignallingConfigL23Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10099
                    Auto  value= 0
                    Pass  value= 1
                    Force  value= 2
                    Delete  value= 3  "
        ::= { kudosConv2CtrlEntries 10099 }


    i2ARCOutputSignallingConfigL23OutputFormat OBJECT-TYPE
        SYNTAX            INTEGER {
                            valETSI(0),
                            valAFD(1)
                            }
        MAX-ACCESS        read-write
        STATUS            current
        DESCRIPTION
                "CMNT: - 
                 TYPE: - RadiobuttonList
                 PAGE: - Output Signalling Config
                    Output Format  cmdID= 10100
                    ETSI  value= 0
                    AFD  value= 1  "
        ::= { kudosConv2CtrlEntries 10100 }


    i2ARCOutputSignallingConfigL23InputLine OBJECT-TYPE
        SYNTAX            INTEGER
        MAX-ACCESS        read-write
        STATUS            current
        DESCRIPTION
                "CMNT: - 
                 TYPE: - Number
                 PAGE: - Output Signalling Config
                    Input Line  cmdID= 10097
                    min= 10  max= 23  step= 1  format= %0.0f  div_scale= 1  preset= 23
                    Min = 10  Max = 23  Step = 1  Preset = 23  "
        ::= { kudosConv2CtrlEntries 10097 }


    i2ARCOutputSignallingConfigL23OutputLine OBJECT-TYPE
        SYNTAX            INTEGER
        MAX-ACCESS        read-write
        STATUS            current
        DESCRIPTION
                "CMNT: - 
                 TYPE: - Number
                 PAGE: - Output Signalling Config
                    Output Line  cmdID= 10098
                    min= 10  max= 23  step= 1  format= %0.0f  div_scale= 1  preset= 23
                    Min = 10  Max = 23  Step = 1  Preset = 23  "
        ::= { kudosConv2CtrlEntries 10098 }


    i2ARCOutputSignallingConfigL23OutputLineStatus OBJECT-TYPE
        SYNTAX            RollCallString
        MAX-ACCESS        read-only
        STATUS            current
        DESCRIPTION
                "CMNT: - 
                 TYPE: - Display
                 PAGE: - Output Signalling Config
                    Output Line Status  cmdID= 10339  "
        ::= { kudosConv2CtrlEntries 10339 }


    i2ARCL23AFDUserBitsForceUserBitsValue OBJECT-TYPE
        SYNTAX            INTEGER { disable(0), enable(1)  }
        MAX-ACCESS        read-write
        STATUS            current
        DESCRIPTION
                "CMNT: - 
                 TYPE: - Checkbox
                 PAGE: - L23
                    Force User Bits Value  cmdID= 10336  "
        ::= { kudosConv2CtrlEntries 10336 }


    i2ARCL23AFDUserBitsUserBitsValue OBJECT-TYPE
        SYNTAX            INTEGER
        MAX-ACCESS        read-write
        STATUS            current
        DESCRIPTION
                "CMNT: - 
                 TYPE: - Number
                 PAGE: - L23
                    User Bits Value  cmdID= 10111
                    min= 0  max= 15  step= 1  format= %0.0f  div_scale= 1  preset= 0
                    Min = 0  Max = 15  Step = 1  Preset = 0  "
        ::= { kudosConv2CtrlEntries 10111 }


    i2ARCOutputSignallingConfigForceModeConfigSMPTE2016 OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val43AFD8(8),
                            val43AFD9(9),
                            val43AFD10(10),
                            val43AFD11(11),
                            val43AFD12(12),
                            val43AFD13(13),
                            val43AFD14(14),
                            val43AFD15(15),
                            val169AFD0(16),
                            val169AFD1(17),
                            val169AFD2(18),
                            val169AFD3(19),
                            val169AFD4(20),
                            val169AFD5(21),
                            val169AFD6(22),
                            val169AFD7(23),
                            val169AFD8(24),
                            val169AFD9(25),
                            val169AFD10(26),
                            val169AFD11(27),
                            val169AFD12(28),
                            val169AFD13(29),
                            val169AFD14(30),
                            val169AFD15(31)
                            }
        MAX-ACCESS        read-write
        STATUS            current
        DESCRIPTION
                "CMNT: - 
                 TYPE: - RadiobuttonList
                 PAGE: - Output Signalling Config
                    SMPTE 2016  cmdID= 10107
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    4:3 AFD 8  value= 8
                    4:3 AFD 9  value= 9
                    4:3 AFD 10  value= 10
                    4:3 AFD 11  value= 11
                    4:3 AFD 12  value= 12
                    4:3 AFD 13  value= 13
                    4:3 AFD 14  value= 14
                    4:3 AFD 15  value= 15
                    16:9 AFD 0  value= 16
                    16:9 AFD 1  value= 17
                    16:9 AFD 2  value= 18
                    16:9 AFD 3  value= 19
                    16:9 AFD 4  value= 20
                    16:9 AFD 5  value= 21
                    16:9 AFD 6  value= 22
                    16:9 AFD 7  value= 23
                    16:9 AFD 8  value= 24
                    16:9 AFD 9  value= 25
                    16:9 AFD 10  value= 26
                    16:9 AFD 11  value= 27
                    16:9 AFD 12  value= 28
                    16:9 AFD 13  value= 29
                    16:9 AFD 14  value= 30
                    16:9 AFD 15  value= 31  "
        ::= { kudosConv2CtrlEntries 10107 }


    i2ARCOutputSignallingConfigForceModeConfigSMPTERP186 OBJECT-TYPE
        SYNTAX            INTEGER {
                            val43(0),
                            val169(1)
                            }
        MAX-ACCESS        read-write
        STATUS            current
        DESCRIPTION
                "CMNT: - 
                 TYPE: - RadiobuttonList
                 PAGE: - Output Signalling Config
                    SMPTE RP186  cmdID= 10108
                    4:3  value= 0
                    16:9  value= 1  "
        ::= { kudosConv2CtrlEntries 10108 }


    i2ARCOutputSignallingConfigForceModeConfigAFD OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val169AFD0(8),
                            val169AFD1(9),
                            val169AFD2(10),
                            val169AFD3(11),
                            val169AFD4(12),
                            val169AFD5(13),
                            val169AFD6(14),
                            val169AFD7(15)
                            }
        MAX-ACCESS        read-write
        STATUS            current
        DESCRIPTION
                "CMNT: - 
                 TYPE: - RadiobuttonList
                 PAGE: - Output Signalling Config
                    AFD  cmdID= 10105
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    16:9 AFD 0  value= 8
                    16:9 AFD 1  value= 9
                    16:9 AFD 2  value= 10
                    16:9 AFD 3  value= 11
                    16:9 AFD 4  value= 12
                    16:9 AFD 5  value= 13
                    16:9 AFD 6  value= 14
                    16:9 AFD 7  value= 15  "
        ::= { kudosConv2CtrlEntries 10105 }


    i2ARCOutputSignallingConfigForceModeConfigETSI OBJECT-TYPE
        SYNTAX            INTEGER {
                            val43FF(0),
                            val149Centre(1),
                            val149Top(2),
                            val169Centre(3),
                            val169Top(4),
                            valGr169Centre(5),
                            val43SP149(6),
                            val169FF(7)
                            }
        MAX-ACCESS        read-write
        STATUS            current
        DESCRIPTION
                "CMNT: - 
                 TYPE: - RadiobuttonList
                 PAGE: - Output Signalling Config
                    ETSI  cmdID= 10106
                    4:3 FF  value= 0
                    14:9 Centre  value= 1
                    14:9 Top  value= 2
                    16:9 Centre  value= 3
                    16:9 Top  value= 4
                    Gr 16:9 Centre  value= 5
                    4:3 SP 14:9  value= 6
                    16:9 FF  value= 7  "
        ::= { kudosConv2CtrlEntries 10106 }


    i2AudioRoutingInputPairsStatusEmbedded1 OBJECT-TYPE
        SYNTAX            RollCallString
        MAX-ACCESS        read-only
        STATUS            current
        DESCRIPTION
                "CMNT: - 
                 TYPE: - Display
                 PAGE: - Routing
                    Embedded 1  cmdID= 10282  "
        ::= { kudosConv2CtrlEntries 10282 }


    i2AudioRoutingInputPairsStatusEmbedded2 OBJECT-TYPE
        SYNTAX            RollCallString
        MAX-ACCESS        read-only
        STATUS            current
        DESCRIPTION
                "CMNT: - 
                 TYPE: - Display
                 PAGE: - Routing
                    Embedded 2  cmdID= 10283  "
        ::= { kudosConv2CtrlEntries 10283 }


    i2AudioRoutingInputPairsStatusEmbedded3 OBJECT-TYPE
        SYNTAX            RollCallString
        MAX-ACCESS        read-only
        STATUS            current
        DESCRIPTION
                "CMNT: - 
                 TYPE: - Display
                 PAGE: - Routing
                    Embedded 3  cmdID= 10284  "
        ::= { kudosConv2CtrlEntries 10284 }


    i2AudioRoutingInputPairsStatusEmbedded4 OBJECT-TYPE
        SYNTAX            RollCallString
        MAX-ACCESS        read-only
        STATUS            current
        DESCRIPTION
                "CMNT: - 
                 TYPE: - Display
                 PAGE: - Routing
                    Embedded 4  cmdID= 10285  "
        ::= { kudosConv2CtrlEntries 10285 }


    i2AudioRoutingInputPairsStatusEmbedded5 OBJECT-TYPE
        SYNTAX            RollCallString
        MAX-ACCESS        read-only
        STATUS            current
        DESCRIPTION
                "CMNT: - 
                 TYPE: - Display
                 PAGE: - Routing
                    Embedded 5  cmdID= 10286  "
        ::= { kudosConv2CtrlEntries 10286 }


    i2AudioRoutingInputPairsStatusEmbedded6 OBJECT-TYPE
        SYNTAX            RollCallString
        MAX-ACCESS        read-only
        STATUS            current
        DESCRIPTION
                "CMNT: - 
                 TYPE: - Display
                 PAGE: - Routing
                    Embedded 6  cmdID= 10287  "
        ::= { kudosConv2CtrlEntries 10287 }


    i2AudioRoutingInputPairsStatusEmbedded7 OBJECT-TYPE
        SYNTAX            RollCallString
        MAX-ACCESS        read-only
        STATUS            current
        DESCRIPTION
                "CMNT: - 
                 TYPE: - Display
                 PAGE: - Routing
                    Embedded 7  cmdID= 10288  "
        ::= { kudosConv2CtrlEntries 10288 }


    i2AudioRoutingInputPairsStatusEmbedded8 OBJECT-TYPE
        SYNTAX            RollCallString
        MAX-ACCESS        read-only
        STATUS            current
        DESCRIPTION
                "CMNT: - 
                 TYPE: - Display
                 PAGE: - Routing
                    Embedded 8  cmdID= 10289  "
        ::= { kudosConv2CtrlEntries 10289 }


    i2AudioRoutingInputPairsStatusAES1 OBJECT-TYPE
        SYNTAX            RollCallString
        MAX-ACCESS        read-only
        STATUS            current
        DESCRIPTION
                "CMNT: - 
                 TYPE: - Display
                 PAGE: - Routing
                    AES 1  cmdID= 10290  "
        ::= { kudosConv2CtrlEntries 10290 }


    i2AudioRoutingInputPairsStatusAES2 OBJECT-TYPE
        SYNTAX            RollCallString
        MAX-ACCESS        read-only
        STATUS            current
        DESCRIPTION
                "CMNT: - 
                 TYPE: - Display
                 PAGE: - Routing
                    AES 2  cmdID= 10291  "
        ::= { kudosConv2CtrlEntries 10291 }


    i2AudioRoutingInputPairsStatusAES3 OBJECT-TYPE
        SYNTAX            RollCallString
        MAX-ACCESS        read-only
        STATUS            current
        DESCRIPTION
                "CMNT: - 
                 TYPE: - Display
                 PAGE: - Routing
                    AES 3  cmdID= 10292  "
        ::= { kudosConv2CtrlEntries 10292 }


    i2AudioRoutingInputPairsStatusAES4 OBJECT-TYPE
        SYNTAX            RollCallString
        MAX-ACCESS        read-only
        STATUS            current
        DESCRIPTION
                "CMNT: - 
                 TYPE: - Display
                 PAGE: - Routing
                    AES 4  cmdID= 10293  "
        ::= { kudosConv2CtrlEntries 10293 }


    i2AudioRoutingInputPairsStatusAnalog1 OBJECT-TYPE
        SYNTAX            RollCallString
        MAX-ACCESS        read-only
        STATUS            current
        DESCRIPTION
                "CMNT: - 
                 TYPE: - Display
                 PAGE: - Routing
                    Analog 1  cmdID= 10294  "
        ::= { kudosConv2CtrlEntries 10294 }


    i2AudioRoutingInputPairsStatusAnalog2 OBJECT-TYPE
        SYNTAX            RollCallString
        MAX-ACCESS        read-only
        STATUS            current
        DESCRIPTION
                "CMNT: - 
                 TYPE: - Display
                 PAGE: - Routing
                    Analog 2  cmdID= 10295  "
        ::= { kudosConv2CtrlEntries 10295 }


    i2AudioRoutingInputPairsStatusAnalog3 OBJECT-TYPE
        SYNTAX            RollCallString
        MAX-ACCESS        read-only
        STATUS            current
        DESCRIPTION
                "CMNT: - 
                 TYPE: - Display
                 PAGE: - Routing
                    Analog 3  cmdID= 10296  "
        ::= { kudosConv2CtrlEntries 10296 }


    i2AudioRoutingInputPairsStatusAnalog4 OBJECT-TYPE
        SYNTAX            RollCallString
        MAX-ACCESS        read-only
        STATUS            current
        DESCRIPTION
                "CMNT: - 
                 TYPE: - Display
                 PAGE: - Routing
                    Analog 4  cmdID= 10297  "
        ::= { kudosConv2CtrlEntries 10297 }


    i2AudioRoutingInputPairsStatusDolbyDecoder1 OBJECT-TYPE
        SYNTAX            RollCallString
        MAX-ACCESS        read-only
        STATUS            current
        DESCRIPTION
                "CMNT: - 
                 TYPE: - Display
                 PAGE: - Routing
                    Dolby Decoder 1  cmdID= 10298  "
        ::= { kudosConv2CtrlEntries 10298 }


    i2AudioRoutingInputPairsStatusDolbyDecoder2 OBJECT-TYPE
        SYNTAX            RollCallString
        MAX-ACCESS        read-only
        STATUS            current
        DESCRIPTION
                "CMNT: - 
                 TYPE: - Display
                 PAGE: - Routing
                    Dolby Decoder 2  cmdID= 10299  "
        ::= { kudosConv2CtrlEntries 10299 }


    i2AudioRoutingInputPairsStatusDolbyDecoder3 OBJECT-TYPE
        SYNTAX            RollCallString
        MAX-ACCESS        read-only
        STATUS            current
        DESCRIPTION
                "CMNT: - 
                 TYPE: - Display
                 PAGE: - Routing
                    Dolby Decoder 3  cmdID= 10300  "
        ::= { kudosConv2CtrlEntries 10300 }


    i2AudioRoutingInputPairsStatusDolbyDecoder4 OBJECT-TYPE
        SYNTAX            RollCallString
        MAX-ACCESS        read-only
        STATUS            current
        DESCRIPTION
                "CMNT: - 
                 TYPE: - Display
                 PAGE: - Routing
                    Dolby Decoder 4  cmdID= 10301  "
        ::= { kudosConv2CtrlEntries 10301 }


    i2AudioRoutingInputPairsStatusDolbyDownmix OBJECT-TYPE
        SYNTAX            RollCallString
        MAX-ACCESS        read-only
        STATUS            current
        DESCRIPTION
                "CMNT: - 
                 TYPE: - Display
                 PAGE: - Routing
                    Dolby Downmix  cmdID= 10302  "
        ::= { kudosConv2CtrlEntries 10302 }


    i2AudioRoutingInputPairsStatusDolbyEncoder OBJECT-TYPE
        SYNTAX            RollCallString
        MAX-ACCESS        read-only
        STATUS            current
        DESCRIPTION
                "CMNT: - 
                 TYPE: - Display
                 PAGE: - Routing
                    Dolby Encoder  cmdID= 10303  "
        ::= { kudosConv2CtrlEntries 10303 }


    i2AudioRoutingProcessPair1InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10112
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv2CtrlEntries 10112 }


    i2AudioRoutingProcessPair2InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10113
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv2CtrlEntries 10113 }


    i2AudioRoutingProcessPair3InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10114
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv2CtrlEntries 10114 }


    i2AudioRoutingProcessPair4InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10115
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv2CtrlEntries 10115 }


    i2AudioRoutingProcessPair5InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10116
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv2CtrlEntries 10116 }


    i2AudioRoutingProcessPair6InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10117
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv2CtrlEntries 10117 }


    i2AudioRoutingProcessPair7InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10118
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv2CtrlEntries 10118 }


    i2AudioRoutingProcessPair8InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10119
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv2CtrlEntries 10119 }


    i2AudioRoutingProcessPairs18StatusPair1 OBJECT-TYPE
        SYNTAX            RollCallString
        MAX-ACCESS        read-only
        STATUS            current
        DESCRIPTION
                "CMNT: - 
                 TYPE: - Display
                 PAGE: - Routing
                    Pair 1  cmdID= 10304  "
        ::= { kudosConv2CtrlEntries 10304 }


    i2AudioRoutingProcessPairs18StatusPair2 OBJECT-TYPE
        SYNTAX            RollCallString
        MAX-ACCESS        read-only
        STATUS            current
        DESCRIPTION
                "CMNT: - 
                 TYPE: - Display
                 PAGE: - Routing
                    Pair 2  cmdID= 10305  "
        ::= { kudosConv2CtrlEntries 10305 }


    i2AudioRoutingProcessPairs18StatusPair3 OBJECT-TYPE
        SYNTAX            RollCallString
        MAX-ACCESS        read-only
        STATUS            current
        DESCRIPTION
                "CMNT: - 
                 TYPE: - Display
                 PAGE: - Routing
                    Pair 3  cmdID= 10306  "
        ::= { kudosConv2CtrlEntries 10306 }


    i2AudioRoutingProcessPairs18StatusPair4 OBJECT-TYPE
        SYNTAX            RollCallString
        MAX-ACCESS        read-only
        STATUS            current
        DESCRIPTION
                "CMNT: - 
                 TYPE: - Display
                 PAGE: - Routing
                    Pair 4  cmdID= 10307  "
        ::= { kudosConv2CtrlEntries 10307 }


    i2AudioRoutingProcessPairs18StatusPair5 OBJECT-TYPE
        SYNTAX            RollCallString
        MAX-ACCESS        read-only
        STATUS            current
        DESCRIPTION
                "CMNT: - 
                 TYPE: - Display
                 PAGE: - Routing
                    Pair 5  cmdID= 10308  "
        ::= { kudosConv2CtrlEntries 10308 }


    i2AudioRoutingProcessPairs18StatusPair6 OBJECT-TYPE
        SYNTAX            RollCallString
        MAX-ACCESS        read-only
        STATUS            current
        DESCRIPTION
                "CMNT: - 
                 TYPE: - Display
                 PAGE: - Routing
                    Pair 6  cmdID= 10309  "
        ::= { kudosConv2CtrlEntries 10309 }


    i2AudioRoutingProcessPairs18StatusPair7 OBJECT-TYPE
        SYNTAX            RollCallString
        MAX-ACCESS        read-only
        STATUS            current
        DESCRIPTION
                "CMNT: - 
                 TYPE: - Display
                 PAGE: - Routing
                    Pair 7  cmdID= 10310  "
        ::= { kudosConv2CtrlEntries 10310 }


    i2AudioRoutingProcessPairs18StatusPair8 OBJECT-TYPE
        SYNTAX            RollCallString
        MAX-ACCESS        read-only
        STATUS            current
        DESCRIPTION
                "CMNT: - 
                 TYPE: - Display
                 PAGE: - Routing
                    Pair 8  cmdID= 10311  "
        ::= { kudosConv2CtrlEntries 10311 }


    i2AudioControlGainPair1L OBJECT-TYPE
        SYNTAX            INTEGER
        MAX-ACCESS        read-write
        STATUS            current
        DESCRIPTION
                "CMNT: - 
                 TYPE: - Number
                 PAGE: - Control
                    Pair 1 L  cmdID= 10120
                    min= -180  max= 180  step= 1  format= %0.1fdB  div_scale= 10  preset= 0
                    Min = -18.0dB  Max = 18.0dB  Step = 0.1dB  Preset = 0.0dB  "
        ::= { kudosConv2CtrlEntries 10120 }


    i2AudioControlGainPair1R OBJECT-TYPE
        SYNTAX            INTEGER
        MAX-ACCESS        read-write
        STATUS            current
        DESCRIPTION
                "CMNT: - 
                 TYPE: - Number
                 PAGE: - Control
                    Pair 1 R  cmdID= 10121
                    min= -180  max= 180  step= 1  format= %0.1fdB  div_scale= 10  preset= 0
                    Min = -18.0dB  Max = 18.0dB  Step = 0.1dB  Preset = 0.0dB  "
        ::= { kudosConv2CtrlEntries 10121 }


    i2AudioControlGainPair2L OBJECT-TYPE
        SYNTAX            INTEGER
        MAX-ACCESS        read-write
        STATUS            current
        DESCRIPTION
                "CMNT: - 
                 TYPE: - Number
                 PAGE: - Control
                    Pair 2 L  cmdID= 10122
                    min= -180  max= 180  step= 1  format= %0.1fdB  div_scale= 10  preset= 0
                    Min = -18.0dB  Max = 18.0dB  Step = 0.1dB  Preset = 0.0dB  "
        ::= { kudosConv2CtrlEntries 10122 }


    i2AudioControlGainPair2R OBJECT-TYPE
        SYNTAX            INTEGER
        MAX-ACCESS        read-write
        STATUS            current
        DESCRIPTION
                "CMNT: - 
                 TYPE: - Number
                 PAGE: - Control
                    Pair 2 R  cmdID= 10123
                    min= -180  max= 180  step= 1  format= %0.1fdB  div_scale= 10  preset= 0
                    Min = -18.0dB  Max = 18.0dB  Step = 0.1dB  Preset = 0.0dB  "
        ::= { kudosConv2CtrlEntries 10123 }


    i2AudioControlGainPair3L OBJECT-TYPE
        SYNTAX            INTEGER
        MAX-ACCESS        read-write
        STATUS            current
        DESCRIPTION
                "CMNT: - 
                 TYPE: - Number
                 PAGE: - Control
                    Pair 3 L  cmdID= 10124
                    min= -180  max= 180  step= 1  format= %0.1fdB  div_scale= 10  preset= 0
                    Min = -18.0dB  Max = 18.0dB  Step = 0.1dB  Preset = 0.0dB  "
        ::= { kudosConv2CtrlEntries 10124 }


    i2AudioControlGainPair3R OBJECT-TYPE
        SYNTAX            INTEGER
        MAX-ACCESS        read-write
        STATUS            current
        DESCRIPTION
                "CMNT: - 
                 TYPE: - Number
                 PAGE: - Control
                    Pair 3 R  cmdID= 10125
                    min= -180  max= 180  step= 1  format= %0.1fdB  div_scale= 10  preset= 0
                    Min = -18.0dB  Max = 18.0dB  Step = 0.1dB  Preset = 0.0dB  "
        ::= { kudosConv2CtrlEntries 10125 }


    i2AudioControlGainPair4L OBJECT-TYPE
        SYNTAX            INTEGER
        MAX-ACCESS        read-write
        STATUS            current
        DESCRIPTION
                "CMNT: - 
                 TYPE: - Number
                 PAGE: - Control
                    Pair 4 L  cmdID= 10126
                    min= -180  max= 180  step= 1  format= %0.1fdB  div_scale= 10  preset= 0
                    Min = -18.0dB  Max = 18.0dB  Step = 0.1dB  Preset = 0.0dB  "
        ::= { kudosConv2CtrlEntries 10126 }


    i2AudioControlGainPair4R OBJECT-TYPE
        SYNTAX            INTEGER
        MAX-ACCESS        read-write
        STATUS            current
        DESCRIPTION
                "CMNT: - 
                 TYPE: - Number
                 PAGE: - Control
                    Pair 4 R  cmdID= 10127
                    min= -180  max= 180  step= 1  format= %0.1fdB  div_scale= 10  preset= 0
                    Min = -18.0dB  Max = 18.0dB  Step = 0.1dB  Preset = 0.0dB  "
        ::= { kudosConv2CtrlEntries 10127 }


    i2AudioControlGainPair5L OBJECT-TYPE
        SYNTAX            INTEGER
        MAX-ACCESS        read-write
        STATUS            current
        DESCRIPTION
                "CMNT: - 
                 TYPE: - Number
                 PAGE: - Control
                    Pair 5 L  cmdID= 10128
                    min= -180  max= 180  step= 1  format= %0.1fdB  div_scale= 10  preset= 0
                    Min = -18.0dB  Max = 18.0dB  Step = 0.1dB  Preset = 0.0dB  "
        ::= { kudosConv2CtrlEntries 10128 }


    i2AudioControlGainPair5R OBJECT-TYPE
        SYNTAX            INTEGER
        MAX-ACCESS        read-write
        STATUS            current
        DESCRIPTION
                "CMNT: - 
                 TYPE: - Number
                 PAGE: - Control
                    Pair 5 R  cmdID= 10129
                    min= -180  max= 180  step= 1  format= %0.1fdB  div_scale= 10  preset= 0
                    Min = -18.0dB  Max = 18.0dB  Step = 0.1dB  Preset = 0.0dB  "
        ::= { kudosConv2CtrlEntries 10129 }


    i2AudioControlGainPair6L OBJECT-TYPE
        SYNTAX            INTEGER
        MAX-ACCESS        read-write
        STATUS            current
        DESCRIPTION
                "CMNT: - 
                 TYPE: - Number
                 PAGE: - Control
                    Pair 6 L  cmdID= 10130
                    min= -180  max= 180  step= 1  format= %0.1fdB  div_scale= 10  preset= 0
                    Min = -18.0dB  Max = 18.0dB  Step = 0.1dB  Preset = 0.0dB  "
        ::= { kudosConv2CtrlEntries 10130 }


    i2AudioControlGainPair6R OBJECT-TYPE
        SYNTAX            INTEGER
        MAX-ACCESS        read-write
        STATUS            current
        DESCRIPTION
                "CMNT: - 
                 TYPE: - Number
                 PAGE: - Control
                    Pair 6 R  cmdID= 10131
                    min= -180  max= 180  step= 1  format= %0.1fdB  div_scale= 10  preset= 0
                    Min = -18.0dB  Max = 18.0dB  Step = 0.1dB  Preset = 0.0dB  "
        ::= { kudosConv2CtrlEntries 10131 }


    i2AudioControlGainPair7L OBJECT-TYPE
        SYNTAX            INTEGER
        MAX-ACCESS        read-write
        STATUS            current
        DESCRIPTION
                "CMNT: - 
                 TYPE: - Number
                 PAGE: - Control
                    Pair 7 L  cmdID= 10132
                    min= -180  max= 180  step= 1  format= %0.1fdB  div_scale= 10  preset= 0
                    Min = -18.0dB  Max = 18.0dB  Step = 0.1dB  Preset = 0.0dB  "
        ::= { kudosConv2CtrlEntries 10132 }


    i2AudioControlGainPair7R OBJECT-TYPE
        SYNTAX            INTEGER
        MAX-ACCESS        read-write
        STATUS            current
        DESCRIPTION
                "CMNT: - 
                 TYPE: - Number
                 PAGE: - Control
                    Pair 7 R  cmdID= 10133
                    min= -180  max= 180  step= 1  format= %0.1fdB  div_scale= 10  preset= 0
                    Min = -18.0dB  Max = 18.0dB  Step = 0.1dB  Preset = 0.0dB  "
        ::= { kudosConv2CtrlEntries 10133 }


    i2AudioControlGainPair8L OBJECT-TYPE
        SYNTAX            INTEGER
        MAX-ACCESS        read-write
        STATUS            current
        DESCRIPTION
                "CMNT: - 
                 TYPE: - Number
                 PAGE: - Control
                    Pair 8 L  cmdID= 10134
                    min= -180  max= 180  step= 1  format= %0.1fdB  div_scale= 10  preset= 0
                    Min = -18.0dB  Max = 18.0dB  Step = 0.1dB  Preset = 0.0dB  "
        ::= { kudosConv2CtrlEntries 10134 }


    i2AudioControlGainPair8R OBJECT-TYPE
        SYNTAX            INTEGER
        MAX-ACCESS        read-write
        STATUS            current
        DESCRIPTION
                "CMNT: - 
                 TYPE: - Number
                 PAGE: - Control
                    Pair 8 R  cmdID= 10135
                    min= -180  max= 180  step= 1  format= %0.1fdB  div_scale= 10  preset= 0
                    Min = -18.0dB  Max = 18.0dB  Step = 0.1dB  Preset = 0.0dB  "
        ::= { kudosConv2CtrlEntries 10135 }


    i2AudioControlToneFrequency OBJECT-TYPE
        SYNTAX            INTEGER
        MAX-ACCESS        read-write
        STATUS            current
        DESCRIPTION
                "CMNT: - 
                 TYPE: - Number
                 PAGE: - Audio
                    Tone Frequency  cmdID= 10152
                    min= 100  max= 10000  step= 100  format= %0.1f KHz  div_scale= 1000  preset= 1000
                    Min = 0.1 KHz  Max = 10.0 KHz  Step = 0.1 KHz  Preset = 1.0 KHz  "
        ::= { kudosConv2CtrlEntries 10152 }


    i2AudioControlDolbyEAlignmentOffset OBJECT-TYPE
        SYNTAX            INTEGER
        MAX-ACCESS        read-write
        STATUS            current
        DESCRIPTION
                "CMNT: - 
                 TYPE: - Number
                 PAGE: - Audio
                    Dolby E Alignment Offset  cmdID= 10154
                    min= -10  max= 10  step= 1  format= %0.0f Lines  div_scale= 1  preset= 0
                    Min = -10 Lines  Max = 10 Lines  Step = 1 Lines  Preset = 0 Lines  "
        ::= { kudosConv2CtrlEntries 10154 }


    i2AudioDelayGlobalDelayPairOffsetsPair1 OBJECT-TYPE
        SYNTAX            INTEGER
        MAX-ACCESS        read-write
        STATUS            current
        DESCRIPTION
                "CMNT: - 
                 TYPE: - Number
                 PAGE: - Delay
                    Pair 1  cmdID= 10155
                    min= -40  max= 200  step= 1  format= %0.0f ms  div_scale= 1  preset= 0
                    Min = -40 ms  Max = 200 ms  Step = 1 ms  Preset = 0 ms  "
        ::= { kudosConv2CtrlEntries 10155 }


    i2AudioDelayGlobalDelayPairOffsetsPair1Total OBJECT-TYPE
        SYNTAX            RollCallString
        MAX-ACCESS        read-only
        STATUS            current
        DESCRIPTION
                "CMNT: - 
                 TYPE: - Display
                 PAGE: - Delay
                    Pair 1 Total  cmdID= 10164  "
        ::= { kudosConv2CtrlEntries 10164 }


    i2AudioDelayGlobalDelayPairOffsetsPair2 OBJECT-TYPE
        SYNTAX            INTEGER
        MAX-ACCESS        read-write
        STATUS            current
        DESCRIPTION
                "CMNT: - 
                 TYPE: - Number
                 PAGE: - Delay
                    Pair 2  cmdID= 10156
                    min= -40  max= 200  step= 1  format= %0.0f ms  div_scale= 1  preset= 0
                    Min = -40 ms  Max = 200 ms  Step = 1 ms  Preset = 0 ms  "
        ::= { kudosConv2CtrlEntries 10156 }


    i2AudioDelayGlobalDelayPairOffsetsPair2Total OBJECT-TYPE
        SYNTAX            RollCallString
        MAX-ACCESS        read-only
        STATUS            current
        DESCRIPTION
                "CMNT: - 
                 TYPE: - Display
                 PAGE: - Delay
                    Pair 2 Total  cmdID= 10165  "
        ::= { kudosConv2CtrlEntries 10165 }


    i2AudioDelayGlobalDelayPairOffsetsPair3 OBJECT-TYPE
        SYNTAX            INTEGER
        MAX-ACCESS        read-write
        STATUS            current
        DESCRIPTION
                "CMNT: - 
                 TYPE: - Number
                 PAGE: - Delay
                    Pair 3  cmdID= 10157
                    min= -40  max= 200  step= 1  format= %0.0f ms  div_scale= 1  preset= 0
                    Min = -40 ms  Max = 200 ms  Step = 1 ms  Preset = 0 ms  "
        ::= { kudosConv2CtrlEntries 10157 }


    i2AudioDelayGlobalDelayPairOffsetsPair3Total OBJECT-TYPE
        SYNTAX            RollCallString
        MAX-ACCESS        read-only
        STATUS            current
        DESCRIPTION
                "CMNT: - 
                 TYPE: - Display
                 PAGE: - Delay
                    Pair 3 Total  cmdID= 10166  "
        ::= { kudosConv2CtrlEntries 10166 }


    i2AudioDelayGlobalDelayPairOffsetsPair4 OBJECT-TYPE
        SYNTAX            INTEGER
        MAX-ACCESS        read-write
        STATUS            current
        DESCRIPTION
                "CMNT: - 
                 TYPE: - Number
                 PAGE: - Delay
                    Pair 4  cmdID= 10158
                    min= -40  max= 200  step= 1  format= %0.0f ms  div_scale= 1  preset= 0
                    Min = -40 ms  Max = 200 ms  Step = 1 ms  Preset = 0 ms  "
        ::= { kudosConv2CtrlEntries 10158 }


    i2AudioDelayGlobalDelayPairOffsetsPair4Total OBJECT-TYPE
        SYNTAX            RollCallString
        MAX-ACCESS        read-only
        STATUS            current
        DESCRIPTION
                "CMNT: - 
                 TYPE: - Display
                 PAGE: - Delay
                    Pair 4 Total  cmdID= 10167  "
        ::= { kudosConv2CtrlEntries 10167 }


    i2AudioDelayGlobalDelayPairOffsetsPair5 OBJECT-TYPE
        SYNTAX            INTEGER
        MAX-ACCESS        read-write
        STATUS            current
        DESCRIPTION
                "CMNT: - 
                 TYPE: - Number
                 PAGE: - Delay
                    Pair 5  cmdID= 10159
                    min= -40  max= 200  step= 1  format= %0.0f ms  div_scale= 1  preset= 0
                    Min = -40 ms  Max = 200 ms  Step = 1 ms  Preset = 0 ms  "
        ::= { kudosConv2CtrlEntries 10159 }


    i2AudioDelayGlobalDelayPairOffsetsPair5Total OBJECT-TYPE
        SYNTAX            RollCallString
        MAX-ACCESS        read-only
        STATUS            current
        DESCRIPTION
                "CMNT: - 
                 TYPE: - Display
                 PAGE: - Delay
                    Pair 5 Total  cmdID= 10168  "
        ::= { kudosConv2CtrlEntries 10168 }


    i2AudioDelayGlobalDelayPairOffsetsPair6 OBJECT-TYPE
        SYNTAX            INTEGER
        MAX-ACCESS        read-write
        STATUS            current
        DESCRIPTION
                "CMNT: - 
                 TYPE: - Number
                 PAGE: - Delay
                    Pair 6  cmdID= 10160
                    min= -40  max= 200  step= 1  format= %0.0f ms  div_scale= 1  preset= 0
                    Min = -40 ms  Max = 200 ms  Step = 1 ms  Preset = 0 ms  "
        ::= { kudosConv2CtrlEntries 10160 }


    i2AudioDelayGlobalDelayPairOffsetsPair6Total OBJECT-TYPE
        SYNTAX            RollCallString
        MAX-ACCESS        read-only
        STATUS            current
        DESCRIPTION
                "CMNT: - 
                 TYPE: - Display
                 PAGE: - Delay
                    Pair 6 Total  cmdID= 10169  "
        ::= { kudosConv2CtrlEntries 10169 }


    i2AudioDelayGlobalDelayPairOffsetsPair7 OBJECT-TYPE
        SYNTAX            INTEGER
        MAX-ACCESS        read-write
        STATUS            current
        DESCRIPTION
                "CMNT: - 
                 TYPE: - Number
                 PAGE: - Delay
                    Pair 7  cmdID= 10161
                    min= -40  max= 200  step= 1  format= %0.0f ms  div_scale= 1  preset= 0
                    Min = -40 ms  Max = 200 ms  Step = 1 ms  Preset = 0 ms  "
        ::= { kudosConv2CtrlEntries 10161 }


    i2AudioDelayGlobalDelayPairOffsetsPair7Total OBJECT-TYPE
        SYNTAX            RollCallString
        MAX-ACCESS        read-only
        STATUS            current
        DESCRIPTION
                "CMNT: - 
                 TYPE: - Display
                 PAGE: - Delay
                    Pair 7 Total  cmdID= 10170  "
        ::= { kudosConv2CtrlEntries 10170 }


    i2AudioDelayGlobalDelayPairOffsetsPair8 OBJECT-TYPE
        SYNTAX            INTEGER
        MAX-ACCESS        read-write
        STATUS            current
        DESCRIPTION
                "CMNT: - 
                 TYPE: - Number
                 PAGE: - Delay
                    Pair 8  cmdID= 10162
                    min= -40  max= 200  step= 1  format= %0.0f ms  div_scale= 1  preset= 0
                    Min = -40 ms  Max = 200 ms  Step = 1 ms  Preset = 0 ms  "
        ::= { kudosConv2CtrlEntries 10162 }


    i2AudioDelayGlobalDelayPairOffsetsPair8Total OBJECT-TYPE
        SYNTAX            RollCallString
        MAX-ACCESS        read-only
        STATUS            current
        DESCRIPTION
                "CMNT: - 
                 TYPE: - Display
                 PAGE: - Delay
                    Pair 8 Total  cmdID= 10171  "
        ::= { kudosConv2CtrlEntries 10171 }


    i2AudioDelayGlobalDelayAudio OBJECT-TYPE
        SYNTAX            INTEGER
        MAX-ACCESS        read-write
        STATUS            current
        DESCRIPTION
                "CMNT: - 
                 TYPE: - Number
                 PAGE: - Delay
                    Audio  cmdID= 10163
                    min= -40  max= 200  step= 1  format= %0.0f ms  div_scale= 1  preset= 0
                    Min = -40 ms  Max = 200 ms  Step = 1 ms  Preset = 0 ms  "
        ::= { kudosConv2CtrlEntries 10163 }


    i2AudioDelayGlobalDelayAudioTotal OBJECT-TYPE
        SYNTAX            RollCallString
        MAX-ACCESS        read-only
        STATUS            current
        DESCRIPTION
                "CMNT: - 
                 TYPE: - Display
                 PAGE: - Delay
                    Audio Total  cmdID= 10172  "
        ::= { kudosConv2CtrlEntries 10172 }


    i2AudioDelayGlobalDelayVideoTotal OBJECT-TYPE
        SYNTAX            RollCallString
        MAX-ACCESS        read-only
        STATUS            current
        DESCRIPTION
                "CMNT: - 
                 TYPE: - Display
                 PAGE: - Delay
                    Video Total  cmdID= 10173  "
        ::= { kudosConv2CtrlEntries 10173 }


    i2AudioShuffleOutputPair1LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10182
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10182 }


    i2AudioShuffleOutputPair1LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10198  "
        ::= { kudosConv2CtrlEntries 10198 }


    i2AudioShuffleOutputPair1LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10214
                    Use Routing  value= 0
                    Tone  value= 1
                    Silence  value= 2  "
        ::= { kudosConv2CtrlEntries 10214 }


    i2AudioShuffleOutputPair1RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10190
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10190 }


    i2AudioShuffleOutputPair1RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10206  "
        ::= { kudosConv2CtrlEntries 10206 }


    i2AudioShuffleOutputPair1RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10222
                    Use Routing  value= 0
                    Tone  value= 1
                    Silence  value= 2  "
        ::= { kudosConv2CtrlEntries 10222 }


    i2AudioShuffleOutputPair2LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10183
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10183 }


    i2AudioShuffleOutputPair2LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10199  "
        ::= { kudosConv2CtrlEntries 10199 }


    i2AudioShuffleOutputPair2LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10215
                    Use Routing  value= 0
                    Tone  value= 1
                    Silence  value= 2  "
        ::= { kudosConv2CtrlEntries 10215 }


    i2AudioShuffleOutputPair2RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10191
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10191 }


    i2AudioShuffleOutputPair2RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10207  "
        ::= { kudosConv2CtrlEntries 10207 }


    i2AudioShuffleOutputPair2RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10223
                    Use Routing  value= 0
                    Tone  value= 1
                    Silence  value= 2  "
        ::= { kudosConv2CtrlEntries 10223 }


    i2AudioShuffleOutputPair3LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10184
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10184 }


    i2AudioShuffleOutputPair3LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10200  "
        ::= { kudosConv2CtrlEntries 10200 }


    i2AudioShuffleOutputPair3LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10216
                    Use Routing  value= 0
                    Tone  value= 1
                    Silence  value= 2  "
        ::= { kudosConv2CtrlEntries 10216 }


    i2AudioShuffleOutputPair3RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10192
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10192 }


    i2AudioShuffleOutputPair3RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10208  "
        ::= { kudosConv2CtrlEntries 10208 }


    i2AudioShuffleOutputPair3RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10224
                    Use Routing  value= 0
                    Tone  value= 1
                    Silence  value= 2  "
        ::= { kudosConv2CtrlEntries 10224 }


    i2AudioShuffleOutputPair4LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10185
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10185 }


    i2AudioShuffleOutputPair4LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10201  "
        ::= { kudosConv2CtrlEntries 10201 }


    i2AudioShuffleOutputPair4LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10217
                    Use Routing  value= 0
                    Tone  value= 1
                    Silence  value= 2  "
        ::= { kudosConv2CtrlEntries 10217 }


    i2AudioShuffleOutputPair4RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10193
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10193 }


    i2AudioShuffleOutputPair4RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10209  "
        ::= { kudosConv2CtrlEntries 10209 }


    i2AudioShuffleOutputPair4RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10225
                    Use Routing  value= 0
                    Tone  value= 1
                    Silence  value= 2  "
        ::= { kudosConv2CtrlEntries 10225 }


    i2AudioShuffleOutputPair5LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10186
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10186 }


    i2AudioShuffleOutputPair5LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10202  "
        ::= { kudosConv2CtrlEntries 10202 }


    i2AudioShuffleOutputPair5LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10218
                    Use Routing  value= 0
                    Tone  value= 1
                    Silence  value= 2  "
        ::= { kudosConv2CtrlEntries 10218 }


    i2AudioShuffleOutputPair5RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10194
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10194 }


    i2AudioShuffleOutputPair5RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10210  "
        ::= { kudosConv2CtrlEntries 10210 }


    i2AudioShuffleOutputPair5RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10226
                    Use Routing  value= 0
                    Tone  value= 1
                    Silence  value= 2  "
        ::= { kudosConv2CtrlEntries 10226 }


    i2AudioShuffleOutputPair6LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10187
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10187 }


    i2AudioShuffleOutputPair6LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10203  "
        ::= { kudosConv2CtrlEntries 10203 }


    i2AudioShuffleOutputPair6LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10219
                    Use Routing  value= 0
                    Tone  value= 1
                    Silence  value= 2  "
        ::= { kudosConv2CtrlEntries 10219 }


    i2AudioShuffleOutputPair6RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10195
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10195 }


    i2AudioShuffleOutputPair6RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10211  "
        ::= { kudosConv2CtrlEntries 10211 }


    i2AudioShuffleOutputPair6RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10227
                    Use Routing  value= 0
                    Tone  value= 1
                    Silence  value= 2  "
        ::= { kudosConv2CtrlEntries 10227 }


    i2AudioShuffleOutputPair7LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10188
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10188 }


    i2AudioShuffleOutputPair7LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10204  "
        ::= { kudosConv2CtrlEntries 10204 }


    i2AudioShuffleOutputPair7LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10220
                    Use Routing  value= 0
                    Tone  value= 1
                    Silence  value= 2  "
        ::= { kudosConv2CtrlEntries 10220 }


    i2AudioShuffleOutputPair7RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10196
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10196 }


    i2AudioShuffleOutputPair7RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10212  "
        ::= { kudosConv2CtrlEntries 10212 }


    i2AudioShuffleOutputPair7RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10228
                    Use Routing  value= 0
                    Tone  value= 1
                    Silence  value= 2  "
        ::= { kudosConv2CtrlEntries 10228 }


    i2AudioShuffleOutputPair8LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10189
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10189 }


    i2AudioShuffleOutputPair8LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10205  "
        ::= { kudosConv2CtrlEntries 10205 }


    i2AudioShuffleOutputPair8LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10221
                    Use Routing  value= 0
                    Tone  value= 1
                    Silence  value= 2  "
        ::= { kudosConv2CtrlEntries 10221 }


    i2AudioShuffleOutputPair8RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10197
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv2CtrlEntries 10197 }


    i2AudioShuffleOutputPair8RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10213  "
        ::= { kudosConv2CtrlEntries 10213 }


    i2AudioShuffleOutputPair8RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10229
                    Use Routing  value= 0
                    Tone  value= 1
                    Silence  value= 2  "
        ::= { kudosConv2CtrlEntries 10229 }


    i2AudioShuffleOutputPairs18StatusPair1 OBJECT-TYPE
        SYNTAX            RollCallString
        MAX-ACCESS        read-only
        STATUS            current
        DESCRIPTION
                "CMNT: - 
                 TYPE: - Display
                 PAGE: - Shuffle
                    Pair 1  cmdID= 10174  "
        ::= { kudosConv2CtrlEntries 10174 }


    i2AudioShuffleOutputPairs18StatusPair2 OBJECT-TYPE
        SYNTAX            RollCallString
        MAX-ACCESS        read-only
        STATUS            current
        DESCRIPTION
                "CMNT: - 
                 TYPE: - Display
                 PAGE: - Shuffle
                    Pair 2  cmdID= 10175  "
        ::= { kudosConv2CtrlEntries 10175 }


    i2AudioShuffleOutputPairs18StatusPair3 OBJECT-TYPE
        SYNTAX            RollCallString
        MAX-ACCESS        read-only
        STATUS            current
        DESCRIPTION
                "CMNT: - 
                 TYPE: - Display
                 PAGE: - Shuffle
                    Pair 3  cmdID= 10176  "
        ::= { kudosConv2CtrlEntries 10176 }


    i2AudioShuffleOutputPairs18StatusPair4 OBJECT-TYPE
        SYNTAX            RollCallString
        MAX-ACCESS        read-only
        STATUS            current
        DESCRIPTION
                "CMNT: - 
                 TYPE: - Display
                 PAGE: - Shuffle
                    Pair 4  cmdID= 10177  "
        ::= { kudosConv2CtrlEntries 10177 }


    i2AudioShuffleOutputPairs18StatusPair5 OBJECT-TYPE
        SYNTAX            RollCallString
        MAX-ACCESS        read-only
        STATUS            current
        DESCRIPTION
                "CMNT: - 
                 TYPE: - Display
                 PAGE: - Shuffle
                    Pair 5  cmdID= 10178  "
        ::= { kudosConv2CtrlEntries 10178 }


    i2AudioShuffleOutputPairs18StatusPair6 OBJECT-TYPE
        SYNTAX            RollCallString
        MAX-ACCESS        read-only
        STATUS            current
        DESCRIPTION
                "CMNT: - 
                 TYPE: - Display
                 PAGE: - Shuffle
                    Pair 6  cmdID= 10179  "
        ::= { kudosConv2CtrlEntries 10179 }


    i2AudioShuffleOutputPairs18StatusPair7 OBJECT-TYPE
        SYNTAX            RollCallString
        MAX-ACCESS        read-only
        STATUS            current
        DESCRIPTION
                "CMNT: - 
                 TYPE: - Display
                 PAGE: - Shuffle
                    Pair 7  cmdID= 10180  "
        ::= { kudosConv2CtrlEntries 10180 }


    i2AudioShuffleOutputPairs18StatusPair8 OBJECT-TYPE
        SYNTAX            RollCallString
        MAX-ACCESS        read-only
        STATUS            current
        DESCRIPTION
                "CMNT: - 
                 TYPE: - Display
                 PAGE: - Shuffle
                    Pair 8  cmdID= 10181  "
        ::= { kudosConv2CtrlEntries 10181 }


    i2TimecodeSourceHD OBJECT-TYPE
        SYNTAX            INTEGER {
                            valLTC(0),
                            valVITC(1)
                            }
        MAX-ACCESS        read-write
        STATUS            current
        DESCRIPTION
                "CMNT: - 
                 TYPE: - RadiobuttonList
                 PAGE: - Timecode
                    Source (HD)  cmdID= 10230
                    LTC  value= 0
                    VITC  value= 1  "
        ::= { kudosConv2CtrlEntries 10230 }


    i2TimecodeSourceSD OBJECT-TYPE
        SYNTAX            INTEGER {
                            valVITC(0),
                            valATCLTC(1),
                            valATCVITC(2)
                            }
        MAX-ACCESS        read-write
        STATUS            current
        DESCRIPTION
                "CMNT: - 
                 TYPE: - RadiobuttonList
                 PAGE: - Timecode
                    Source (SD)  cmdID= 10231
                    VITC  value= 0
                    ATC LTC  value= 1
                    ATC VITC  value= 2  "
        ::= { kudosConv2CtrlEntries 10231 }


    i2TimecodeStatus OBJECT-TYPE
        SYNTAX            RollCallString
        MAX-ACCESS        read-only
        STATUS            current
        DESCRIPTION
                "CMNT: - 
                 TYPE: - Display
                 PAGE: - Timecode
                    Status  cmdID= 10239  "
        ::= { kudosConv2CtrlEntries 10239 }


    i2TimecodeMode OBJECT-TYPE
        SYNTAX            INTEGER {
                            valFollowInput(0),
                            valGenerate(1),
                            valInputTrigger(2)
                            }
        MAX-ACCESS        read-write
        STATUS            current
        DESCRIPTION
                "CMNT: - 
                 TYPE: - RadiobuttonList
                 PAGE: - Timecode
                    Mode  cmdID= 10232
                    Follow Input  value= 0
                    Generate  value= 1
                    Input Trigger  value= 2  "
        ::= { kudosConv2CtrlEntries 10232 }


    i2TimecodeVITCEnable OBJECT-TYPE
        SYNTAX            INTEGER { disable(0), enable(1)  }
        MAX-ACCESS        read-write
        STATUS            current
        DESCRIPTION
                "CMNT: - 
                 TYPE: - Checkbox
                 PAGE: - Timecode
                    VITC Enable  cmdID= 10238  "
        ::= { kudosConv2CtrlEntries 10238 }


    i2TimecodeOutputLine525 OBJECT-TYPE
        SYNTAX            INTEGER
        MAX-ACCESS        read-write
        STATUS            current
        DESCRIPTION
                "CMNT: - 
                 TYPE: - Number
                 PAGE: - Timecode
                    Output Line (525)  cmdID= 10233
                    min= 11  max= 17  step= 1  format= %0.0f  div_scale= 1  preset= 14
                    Min = 11  Max = 17  Step = 1  Preset = 14  "
        ::= { kudosConv2CtrlEntries 10233 }


    i2TimecodeOutputLine625 OBJECT-TYPE
        SYNTAX            INTEGER
        MAX-ACCESS        read-write
        STATUS            current
        DESCRIPTION
                "CMNT: - 
                 TYPE: - Number
                 PAGE: - Timecode
                    Output Line (625)  cmdID= 10234
                    min= 7  max= 20  step= 1  format= %0.0f  div_scale= 1  preset= 19
                    Min = 7  Max = 20  Step = 1  Preset = 19  "
        ::= { kudosConv2CtrlEntries 10234 }


    i2TimecodeOutputLineStatus OBJECT-TYPE
        SYNTAX            RollCallString
        MAX-ACCESS        read-only
        STATUS            current
        DESCRIPTION
                "CMNT: - 
                 TYPE: - Display
                 PAGE: - Timecode
                    Output Line Status  cmdID= 10338  "
        ::= { kudosConv2CtrlEntries 10338 }


    i2TimecodeInputTriggerEntry OBJECT-TYPE
        SYNTAX            RollCallString
        MAX-ACCESS        read-write
        STATUS            current
        DESCRIPTION
                "CMNT: - 
                 TYPE: - Editstring
                 PAGE: - Timecode
                    Input Trigger Entry  cmdID= 10240
                    preset= 00:00:00:00"
        ::= { kudosConv2CtrlEntries 10240 }


    i2TimecodeOutputTimecodeEntry OBJECT-TYPE
        SYNTAX            RollCallString
        MAX-ACCESS        read-write
        STATUS            current
        DESCRIPTION
                "CMNT: - 
                 TYPE: - Editstring
                 PAGE: - Timecode
                    Output Timecode Entry  cmdID= 10241
                    preset= 00:00:00:00"
        ::= { kudosConv2CtrlEntries 10241 }


    i2TimecodeEntry OBJECT-TYPE
        SYNTAX            RollCallString
        MAX-ACCESS        read-write
        STATUS            current
        DESCRIPTION
                "CMNT: - 
                 TYPE: - Editstring
                 PAGE: - Timecode
                    Timecode Entry  cmdID= 10237
                    preset= 00:00:00:00"
        ::= { kudosConv2CtrlEntries 10237 }


    i2TimecodeLoad OBJECT-TYPE
        SYNTAX            INTEGER { noAction(0),valTimecodeLoad(1) }
        MAX-ACCESS        read-write
        STATUS            current
        DESCRIPTION
                "CMNT: - 
                 TYPE: - Button
                 PAGE: - Timecode
                    Timecode Load  cmdID= 10316
                    value= 1  "
        ::= { kudosConv2CtrlEntries 10316 }


    i2TimecodeOnTimecodeLoss OBJECT-TYPE
        SYNTAX            INTEGER {
                            valFreeze(0),
                            valFreeRun(1)
                            }
        MAX-ACCESS        read-write
        STATUS            current
        DESCRIPTION
                "CMNT: - 
                 TYPE: - RadiobuttonList
                 PAGE: - Timecode
                    On Timecode Loss  cmdID= 10235
                    Freeze  value= 0
                    Free Run  value= 1  "
        ::= { kudosConv2CtrlEntries 10235 }


    i2TimecodeNondropFrame OBJECT-TYPE
        SYNTAX            INTEGER { disable(0), enable(1)  }
        MAX-ACCESS        read-write
        STATUS            current
        DESCRIPTION
                "CMNT: - 
                 TYPE: - Checkbox
                 PAGE: - Timecode
                    Non-drop Frame  cmdID= 10236  "
        ::= { kudosConv2CtrlEntries 10236 }


    i2MetadataClosedCaptionsInputStatus OBJECT-TYPE
        SYNTAX            RollCallString
        MAX-ACCESS        read-only
        STATUS            current
        DESCRIPTION
                "CMNT: - 
                 TYPE: - Display
                 PAGE: - Metadata
                    Input Status  cmdID= 10250  "
        ::= { kudosConv2CtrlEntries 10250 }


    i2MetadataClosedCaptionsCEA608OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-608 Output Enable  cmdID= 10242
                    Off  value= 0
                    On  value= 1  "
        ::= { kudosConv2CtrlEntries 10242 }


    i2MetadataClosedCaptionsCEA708OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-708 Output Enable  cmdID= 10243
                    Off  value= 0
                    On  value= 1  "
        ::= { kudosConv2CtrlEntries 10243 }


    i2MetadataClosedCaptionsCEA708OutputLine OBJECT-TYPE
        SYNTAX            INTEGER
        MAX-ACCESS        read-write
        STATUS            current
        DESCRIPTION
                "CMNT: - 
                 TYPE: - Number
                 PAGE: - Metadata
                    CEA-708 Output Line  cmdID= 10244
                    min= 8  max= 20  step= 1  format= %0.0f  div_scale= 1  preset= 10
                    Min = 8  Max = 20  Step = 1  Preset = 10  "
        ::= { kudosConv2CtrlEntries 10244 }


    i2MetadataClosedCaptionsCEA708OutputLineStatus OBJECT-TYPE
        SYNTAX            RollCallString
        MAX-ACCESS        read-only
        STATUS            current
        DESCRIPTION
                "CMNT: - 
                 TYPE: - Display
                 PAGE: - Metadata
                    CEA-708 Output Line Status  cmdID= 10252  "
        ::= { kudosConv2CtrlEntries 10252 }


    i2MetadataTeletext625CaptionsSource OBJECT-TYPE
        SYNTAX            INTEGER {
                            valWST(0),
                            valCEAn608(1)
                            }
        MAX-ACCESS        read-write
        STATUS            current
        DESCRIPTION
                "CMNT: - 
                 TYPE: - RadiobuttonList
                 PAGE: - Metadata
                    625 Captions Source  cmdID= 10337
                    WST  value= 0
                    CEA-608  value= 1  "
        ::= { kudosConv2CtrlEntries 10337 }


    i2MetadataTeletextPresentStatus OBJECT-TYPE
        SYNTAX            RollCallString
        MAX-ACCESS        read-only
        STATUS            current
        DESCRIPTION
                "CMNT: - 
                 TYPE: - Display
                 PAGE: - Metadata
                    Teletext Present Status  cmdID= 10251  "
        ::= { kudosConv2CtrlEntries 10251 }


    i2MetadataTeletextWSTInputLine OBJECT-TYPE
        SYNTAX            INTEGER
        MAX-ACCESS        read-write
        STATUS            current
        DESCRIPTION
                "CMNT: - 
                 TYPE: - Number
                 PAGE: - Metadata
                    WST Input Line  cmdID= 10245
                    min= 7  max= 22  step= 1  format= %0.0f  div_scale= 1  preset= 10
                    Min = 7  Max = 22  Step = 1  Preset = 10  "
        ::= { kudosConv2CtrlEntries 10245 }


    i2MetadataTeletextWSTOutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    WST Output Enable  cmdID= 10246
                    Off  value= 0
                    On  value= 1  "
        ::= { kudosConv2CtrlEntries 10246 }


    i2MetadataTeletextWSTOutputLine OBJECT-TYPE
        SYNTAX            INTEGER
        MAX-ACCESS        read-write
        STATUS            current
        DESCRIPTION
                "CMNT: - 
                 TYPE: - Number
                 PAGE: - Metadata
                    WST Output Line  cmdID= 10253
                    min= 7  max= 22  step= 1  format= %0.0f  div_scale= 1  preset= 10
                    Min = 7  Max = 22  Step = 1  Preset = 10  "
        ::= { kudosConv2CtrlEntries 10253 }


    i2MetadataTeletextWSTOutputLineStatus OBJECT-TYPE
        SYNTAX            RollCallString
        MAX-ACCESS        read-only
        STATUS            current
        DESCRIPTION
                "CMNT: - 
                 TYPE: - Display
                 PAGE: - Metadata
                    WST Output Line Status  cmdID= 10341  "
        ::= { kudosConv2CtrlEntries 10341 }


    i2MetadataTeletextRDD08InputLine OBJECT-TYPE
        SYNTAX            INTEGER
        MAX-ACCESS        read-write
        STATUS            current
        DESCRIPTION
                "CMNT: - 
                 TYPE: - Number
                 PAGE: - Metadata
                    RDD-08 Input Line  cmdID= 10248
                    min= 8  max= 20  step= 1  format= %0.0f  div_scale= 1  preset= 10
                    Min = 8  Max = 20  Step = 1  Preset = 10  "
        ::= { kudosConv2CtrlEntries 10248 }


    i2MetadataTeletextRDD08OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    RDD-08 Output Enable  cmdID= 10247
                    Off  value= 0
                    On  value= 1  "
        ::= { kudosConv2CtrlEntries 10247 }


    i2MetadataTeletextRDD08OutputLine OBJECT-TYPE
        SYNTAX            INTEGER
        MAX-ACCESS        read-write
        STATUS            current
        DESCRIPTION
                "CMNT: - 
                 TYPE: - Number
                 PAGE: - Metadata
                    RDD-08 Output Line  cmdID= 10249
                    min= 8  max= 20  step= 1  format= %0.0f  div_scale= 1  preset= 10
                    Min = 8  Max = 20  Step = 1  Preset = 10  "
        ::= { kudosConv2CtrlEntries 10249 }


    i2MetadataTeletextRDD08OutputLineStatus OBJECT-TYPE
        SYNTAX            RollCallString
        MAX-ACCESS        read-only
        STATUS            current
        DESCRIPTION
                "CMNT: - 
                 TYPE: - Display
                 PAGE: - Metadata
                    RDD-08 Output Line Status  cmdID= 10340  "
        ::= { kudosConv2CtrlEntries 10340 }


    i2MemorySelect OBJECT-TYPE
        SYNTAX            INTEGER {
                            valMemory1(1),
                            valMemory2(2),
                            valMemory3(3),
                            valMemory4(4),
                            valMemory5(5),
                            valMemory6(6),
                            valMemory7(7),
                            valMemory8(8)
                            }
        MAX-ACCESS        read-write
        STATUS            current
        DESCRIPTION
                "CMNT: - 
                 TYPE: - RadiobuttonList
                 PAGE: - Memory
                    Memory Select  cmdID= 10254
                    Memory 1  value= 1
                    Memory 2  value= 2
                    Memory 3  value= 3
                    Memory 4  value= 4
                    Memory 5  value= 5
                    Memory 6  value= 6
                    Memory 7  value= 7
                    Memory 8  value= 8  "
        ::= { kudosConv2CtrlEntries 10254 }


    i2MemorySaveMemory OBJECT-TYPE
        SYNTAX            INTEGER { noAction(0),valSaveMemory(1) }
        MAX-ACCESS        read-write
        STATUS            current
        DESCRIPTION
                "CMNT: - 
                 TYPE: - Button
                 PAGE: - Memory
                    Save Memory  cmdID= 10255
                    value= 1  "
        ::= { kudosConv2CtrlEntries 10255 }


    i2MemoryRecallMemory OBJECT-TYPE
        SYNTAX            INTEGER { noAction(0),valRecallMemory(1) }
        MAX-ACCESS        read-write
        STATUS            current
        DESCRIPTION
                "CMNT: - 
                 TYPE: - Button
                 PAGE: - Memory
                    Recall Memory  cmdID= 10256
                    value= 1  "
        ::= { kudosConv2CtrlEntries 10256 }


    i2MemoryResettoDefaults OBJECT-TYPE
        SYNTAX            INTEGER { noAction(0),valResettoDefaults(1) }
        MAX-ACCESS        read-write
        STATUS            current
        DESCRIPTION
                "CMNT: - 
                 TYPE: - Button
                 PAGE: - Memory
                    Reset to Defaults  cmdID= 10258
                    value= 1  "
        ::= { kudosConv2CtrlEntries 10258 }


    i2MemoryNameChangeName OBJECT-TYPE
        SYNTAX            RollCallString
        MAX-ACCESS        read-write
        STATUS            current
        DESCRIPTION
                "CMNT: - 
                 TYPE: - Editstring
                 PAGE: - Memory
                    Change Name  cmdID= 10257
                    preset= "
        ::= { kudosConv2CtrlEntries 10257 }


    i2RollCallUnitName OBJECT-TYPE
        SYNTAX            RollCallString
        MAX-ACCESS        read-write
        STATUS            current
        DESCRIPTION
                "CMNT: - 
                 TYPE: - Editstring
                 PAGE: - RollCall
                    Unit Name  cmdID= 10312
                    preset= IQP"
        ::= { kudosConv2CtrlEntries 10312 }


    i2SNMPControlEnable OBJECT-TYPE
        SYNTAX            INTEGER { disable(0), enable(1)  }
        MAX-ACCESS        read-write
        STATUS            current
        DESCRIPTION
                "CMNT: - 
                 TYPE: - Checkbox
                 PAGE: - SNMP
                    Control Enable  cmdID= 10342  "
        ::= { kudosConv2CtrlEntries 10342 }


    i2SNMPTrapsEnable OBJECT-TYPE
        SYNTAX            INTEGER { disable(0), enable(1)  }
        MAX-ACCESS        read-write
        STATUS            current
        DESCRIPTION
                "CMNT: - 
                 TYPE: - Checkbox
                 PAGE: - SNMP
                    Traps Enable  cmdID= 10343  "
        ::= { kudosConv2CtrlEntries 10343 }


    i2SNMPResendTraps OBJECT-TYPE
        SYNTAX            INTEGER { noAction(0),valResendTraps(1) }
        MAX-ACCESS        read-write
        STATUS            current
        DESCRIPTION
                "CMNT: - 
                 TYPE: - Button
                 PAGE: - SNMP
                    Resend Traps  cmdID= 10344
                    value= 1  "
        ::= { kudosConv2CtrlEntries 10344 }


    i2LoggingInputIdentEnable OBJECT-TYPE
        SYNTAX            INTEGER { disable(0), enable(1)  }
        MAX-ACCESS        read-write
        STATUS            current
        DESCRIPTION
                "CMNT: - 
                 TYPE: - Checkbox
                 PAGE: - Logging
                    Input Ident Enable  cmdID= 10261  "
        ::= { kudosConv2CtrlEntries 10261 }


    i2LoggingInputStandardEnable OBJECT-TYPE
        SYNTAX            INTEGER { disable(0), enable(1)  }
        MAX-ACCESS        read-write
        STATUS            current
        DESCRIPTION
                "CMNT: - 
                 TYPE: - Checkbox
                 PAGE: - Logging
                    Input Standard Enable  cmdID= 10259  "
        ::= { kudosConv2CtrlEntries 10259 }


    i2LoggingInputStateEnable OBJECT-TYPE
        SYNTAX            INTEGER { disable(0), enable(1)  }
        MAX-ACCESS        read-write
        STATUS            current
        DESCRIPTION
                "CMNT: - 
                 TYPE: - Checkbox
                 PAGE: - Logging
                    Input State Enable  cmdID= 10263  "
        ::= { kudosConv2CtrlEntries 10263 }


    i2LoggingOutputStandardEnable OBJECT-TYPE
        SYNTAX            INTEGER { disable(0), enable(1)  }
        MAX-ACCESS        read-write
        STATUS            current
        DESCRIPTION
                "CMNT: - 
                 TYPE: - Checkbox
                 PAGE: - Logging
                    Output Standard Enable  cmdID= 10267  "
        ::= { kudosConv2CtrlEntries 10267 }


    i2LoggingOutputIdentEnable OBJECT-TYPE
        SYNTAX            INTEGER { disable(0), enable(1)  }
        MAX-ACCESS        read-write
        STATUS            current
        DESCRIPTION
                "CMNT: - 
                 TYPE: - Checkbox
                 PAGE: - Logging
                    Output Ident Enable  cmdID= 10265  "
        ::= { kudosConv2CtrlEntries 10265 }


    i2LoggingTimecodeEnable OBJECT-TYPE
        SYNTAX            INTEGER { disable(0), enable(1)  }
        MAX-ACCESS        read-write
        STATUS            current
        DESCRIPTION
                "CMNT: - 
                 TYPE: - Checkbox
                 PAGE: - Logging
                    Timecode Enable  cmdID= 10346  "
        ::= { kudosConv2CtrlEntries 10346 }


    i2LoggingClosedCaptionInputEnable OBJECT-TYPE
        SYNTAX            INTEGER { disable(0), enable(1)  }
        MAX-ACCESS        read-write
        STATUS            current
        DESCRIPTION
                "CMNT: - 
                 TYPE: - Checkbox
                 PAGE: - Logging
                    Closed Caption Input Enable  cmdID= 10348  "
        ::= { kudosConv2CtrlEntries 10348 }


    i2LoggingWSTEnable OBJECT-TYPE
        SYNTAX            INTEGER { disable(0), enable(1)  }
        MAX-ACCESS        read-write
        STATUS            current
        DESCRIPTION
                "CMNT: - 
                 TYPE: - Checkbox
                 PAGE: - Logging
                    WST Enable  cmdID= 10350  "
        ::= { kudosConv2CtrlEntries 10350 }


    i2LoggingRDD08Enable OBJECT-TYPE
        SYNTAX            INTEGER { disable(0), enable(1)  }
        MAX-ACCESS        read-write
        STATUS            current
        DESCRIPTION
                "CMNT: - 
                 TYPE: - Checkbox
                 PAGE: - Logging
                    RDD08 Enable  cmdID= 10352  "
        ::= { kudosConv2CtrlEntries 10352 }


    i2LoggingCEA708Enable OBJECT-TYPE
        SYNTAX            INTEGER { disable(0), enable(1)  }
        MAX-ACCESS        read-write
        STATUS            current
        DESCRIPTION
                "CMNT: - 
                 TYPE: - Checkbox
                 PAGE: - Logging
                    CEA-708 Enable  cmdID= 10354  "
        ::= { kudosConv2CtrlEntries 10354 }


    i2LoggingSMPTE2016Enable OBJECT-TYPE
        SYNTAX            INTEGER { disable(0), enable(1)  }
        MAX-ACCESS        read-write
        STATUS            current
        DESCRIPTION
                "CMNT: - 
                 TYPE: - Checkbox
                 PAGE: - Logging
                    SMPTE 2016 Enable  cmdID= 10356  "
        ::= { kudosConv2CtrlEntries 10356 }


    i2LoggingSMPTEL23Enable OBJECT-TYPE
        SYNTAX            INTEGER { disable(0), enable(1)  }
        MAX-ACCESS        read-write
        STATUS            current
        DESCRIPTION
                "CMNT: - 
                 TYPE: - Checkbox
                 PAGE: - Logging
                    SMPTE L23 Enable  cmdID= 10358  "
        ::= { kudosConv2CtrlEntries 10358 }


    i2LoggingSignallingEnable OBJECT-TYPE
        SYNTAX            INTEGER { disable(0), enable(1)  }
        MAX-ACCESS        read-write
        STATUS            current
        DESCRIPTION
                "CMNT: - 
                 TYPE: - Checkbox
                 PAGE: - Logging
                    Signalling Enable  cmdID= 10360  "
        ::= { kudosConv2CtrlEntries 10360 }
    kudosConv2StatEntries OBJECT IDENTIFIER ::= { kudosIQP 9 }


    i2LoggingInputIdentStatus OBJECT-TYPE
        SYNTAX            RollCallString
        MAX-ACCESS        read-only
        STATUS            current
        DESCRIPTION
                "CMNT: - Channel Name
                 TYPE: - Display
                 PAGE: - Logging
                    Input Ident Status  cmdID= 10262  "
        ::= { kudosConv2StatEntries 10262 }


    i2LoggingInputStandardStatus OBJECT-TYPE
        SYNTAX            RollCallString
        MAX-ACCESS        read-only
        STATUS            current
        DESCRIPTION
                "CMNT: - WARN: or format
                 TYPE: - Display
                 PAGE: - Logging
                    Input Standard Status  cmdID= 10260  "
        ::= { kudosConv2StatEntries 10260 }


    i2LoggingInputStateStatus OBJECT-TYPE
        SYNTAX            RollCallString
        MAX-ACCESS        read-only
        STATUS            current
        DESCRIPTION
                "CMNT: - WARN: or OK
                 TYPE: - Display
                 PAGE: - Logging
                    Input State Status  cmdID= 10264  "
        ::= { kudosConv2StatEntries 10264 }


    i2LoggingOutputStandardStatus OBJECT-TYPE
        SYNTAX            RollCallString
        MAX-ACCESS        read-only
        STATUS            current
        DESCRIPTION
                "CMNT: - WARN: or format
                 TYPE: - Display
                 PAGE: - Logging
                    Output Standard Status  cmdID= 10268  "
        ::= { kudosConv2StatEntries 10268 }


    i2LoggingOutputIdentStatus OBJECT-TYPE
        SYNTAX            RollCallString
        MAX-ACCESS        read-only
        STATUS            current
        DESCRIPTION
                "CMNT: - Channel Name
                 TYPE: - Display
                 PAGE: - Logging
                    Output Ident Status  cmdID= 10266  "
        ::= { kudosConv2StatEntries 10266 }


    i2LoggingTimeCodeStatus OBJECT-TYPE
        SYNTAX            RollCallString
        MAX-ACCESS        read-only
        STATUS            current
        DESCRIPTION
                "CMNT: - LOST or OK
                 TYPE: - Display
                 PAGE: - Logging
                    TimeCode Status  cmdID= 10347  "
        ::= { kudosConv2StatEntries 10347 }


    i2LoggingClosedCaptionInputStatus OBJECT-TYPE
        SYNTAX            RollCallString
        MAX-ACCESS        read-only
        STATUS            current
        DESCRIPTION
                "CMNT: - LOST or OK
                 TYPE: - Display
                 PAGE: - Logging
                    Closed Caption Input Status  cmdID= 10349  "
        ::= { kudosConv2StatEntries 10349 }


    i2LoggingWSTOutputLineStatus OBJECT-TYPE
        SYNTAX            RollCallString
        MAX-ACCESS        read-only
        STATUS            current
        DESCRIPTION
                "CMNT: - off or line number
                 TYPE: - Display
                 PAGE: - Logging
                    WST Output Line Status  cmdID= 10351  "
        ::= { kudosConv2StatEntries 10351 }


    i2LoggingRDD08OutputLineStatus OBJECT-TYPE
        SYNTAX            RollCallString
        MAX-ACCESS        read-only
        STATUS            current
        DESCRIPTION
                "CMNT: - off or line number
                 TYPE: - Display
                 PAGE: - Logging
                    RDD08 Output Line Status  cmdID= 10353  "
        ::= { kudosConv2StatEntries 10353 }


    i2LoggingCEA708OutputLineStatus OBJECT-TYPE
        SYNTAX            RollCallString
        MAX-ACCESS        read-only
        STATUS            current
        DESCRIPTION
                "CMNT: - off or line number
                 TYPE: - Display
                 PAGE: - Logging
                    CEA-708 Output Line Status  cmdID= 10355  "
        ::= { kudosConv2StatEntries 10355 }


    i2Logging2016OutputLineStatus OBJECT-TYPE
        SYNTAX            RollCallString
        MAX-ACCESS        read-only
        STATUS            current
        DESCRIPTION
                "CMNT: - off or line number
                 TYPE: - Display
                 PAGE: - Logging
                    2016 Output Line Status  cmdID= 10357  "
        ::= { kudosConv2StatEntries 10357 }


    i2LoggingL23OutputLineStatus OBJECT-TYPE
        SYNTAX            RollCallString
        MAX-ACCESS        read-only
        STATUS            current
        DESCRIPTION
                "CMNT: - off or line number
                 TYPE: - Display
                 PAGE: - Logging
                    L23 Output Line Status  cmdID= 10359  "
        ::= { kudosConv2StatEntries 10359 }


    i2LoggingSignallingStatus OBJECT-TYPE
        SYNTAX            RollCallString
        MAX-ACCESS        read-only
        STATUS            current
        DESCRIPTION
                "CMNT: - NONE or OK
                 TYPE: - Display
                 PAGE: - Logging
                    Signalling Status  cmdID= 10361  "
        ::= { kudosConv2StatEntries 10361 }


    i2LoggingMSGStatus OBJECT-TYPE
        SYNTAX            RollCallString
        MAX-ACCESS        read-only
        STATUS            current
        DESCRIPTION
                "CMNT: - 
                 TYPE: - Display
                 PAGE: - Logging
                    MSG Status  cmdID= 10269  "
        ::= { kudosConv2StatEntries 10269 }
    kudosConv3NoteEntries OBJECT IDENTIFIER ::= { kudosIQP 10 }


    i3InputIdentStatus NOTIFICATION-TYPE
        OBJECTS            { i3LoggingInputIdentStatus } 
        STATUS            current
        DESCRIPTION
                "CMNT: - Channel Name
                 TYPE: - Display
                 PAGE: - Logging
                    Input Ident Status  cmdID= 5000  "
        ::= { kudosConv3NoteEntries 5000 }


    i3InputStandardStatus NOTIFICATION-TYPE
        OBJECTS            { i3LoggingInputStandardStatus } 
        STATUS            current
        DESCRIPTION
                "CMNT: - WARN: or format
                 TYPE: - Display
                 PAGE: - Logging
                    Input Standard Status  cmdID= 5001  "
        ::= { kudosConv3NoteEntries 5001 }


    i3InputStateStatus NOTIFICATION-TYPE
        OBJECTS            { i3LoggingInputStateStatus } 
        STATUS            current
        DESCRIPTION
                "CMNT: - WARN: or OK
                 TYPE: - Display
                 PAGE: - Logging
                    Input State Status  cmdID= 5002  "
        ::= { kudosConv3NoteEntries 5002 }


    i3OutputStandardStatus NOTIFICATION-TYPE
        OBJECTS            { i3LoggingOutputStandardStatus } 
        STATUS            current
        DESCRIPTION
                "CMNT: - WARN: or format
                 TYPE: - Display
                 PAGE: - Logging
                    Output Standard Status  cmdID= 5003  "
        ::= { kudosConv3NoteEntries 5003 }


    i3OutputIdentStatus NOTIFICATION-TYPE
        OBJECTS            { i3LoggingOutputIdentStatus } 
        STATUS            current
        DESCRIPTION
                "CMNT: - Channel Name
                 TYPE: - Display
                 PAGE: - Logging
                    Output Ident Status  cmdID= 5004  "
        ::= { kudosConv3NoteEntries 5004 }


    i3TimeCodeStatus NOTIFICATION-TYPE
        OBJECTS            { i3LoggingTimeCodeStatus } 
        STATUS            current
        DESCRIPTION
                "CMNT: - LOST or OK
                 TYPE: - Display
                 PAGE: - Logging
                    TimeCode Status  cmdID= 5005  "
        ::= { kudosConv3NoteEntries 5005 }


    i3ClosedCaptionInputStatus NOTIFICATION-TYPE
        OBJECTS            { i3LoggingClosedCaptionInputStatus } 
        STATUS            current
        DESCRIPTION
                "CMNT: - LOST or OK
                 TYPE: - Display
                 PAGE: - Logging
                    Closed Caption Input Status  cmdID= 5006  "
        ::= { kudosConv3NoteEntries 5006 }


    i3WSTOutputLineStatus NOTIFICATION-TYPE
        OBJECTS            { i3LoggingWSTOutputLineStatus } 
        STATUS            current
        DESCRIPTION
                "CMNT: - off or line number
                 TYPE: - Display
                 PAGE: - Logging
                    WST Output Line Status  cmdID= 5007  "
        ::= { kudosConv3NoteEntries 5007 }


    i3RDD08OutputLineStatus NOTIFICATION-TYPE
        OBJECTS            { i3LoggingRDD08OutputLineStatus } 
        STATUS            current
        DESCRIPTION
                "CMNT: - off or line number
                 TYPE: - Display
                 PAGE: - Logging
                    RDD08 Output Line Status  cmdID= 5008  "
        ::= { kudosConv3NoteEntries 5008 }


    i3CEA708OutputLineStatus NOTIFICATION-TYPE
        OBJECTS            { i3LoggingCEA708OutputLineStatus } 
        STATUS            current
        DESCRIPTION
                "CMNT: - off or line number
                 TYPE: - Display
                 PAGE: - Logging
                    CEA-708 Output Line Status  cmdID= 5009  "
        ::= { kudosConv3NoteEntries 5009 }


    i32016OutputLineStatus NOTIFICATION-TYPE
        OBJECTS            { i3Logging2016OutputLineStatus } 
        STATUS            current
        DESCRIPTION
                "CMNT: - off or line number
                 TYPE: - Display
                 PAGE: - Logging
                    2016 Output Line Status  cmdID= 5010  "
        ::= { kudosConv3NoteEntries 5010 }


    i3L23OutputLineStatus NOTIFICATION-TYPE
        OBJECTS            { i3LoggingL23OutputLineStatus } 
        STATUS            current
        DESCRIPTION
                "CMNT: - off or line number
                 TYPE: - Display
                 PAGE: - Logging
                    L23 Output Line Status  cmdID= 5011  "
        ::= { kudosConv3NoteEntries 5011 }


    i3SignallingStatus NOTIFICATION-TYPE
        OBJECTS            { i3LoggingSignallingStatus } 
        STATUS            current
        DESCRIPTION
                "CMNT: - NONE or OK
                 TYPE: - Display
                 PAGE: - Logging
                    Signalling Status  cmdID= 5012  "
        ::= { kudosConv3NoteEntries 5012 }


    i3MSGStatus NOTIFICATION-TYPE
        OBJECTS            { i3LoggingMSGStatus } 
        STATUS            current
        DESCRIPTION
                "CMNT: - 
                 TYPE: - Display
                 PAGE: - Logging
                    MSG Status  cmdID= 5013  "
        ::= { kudosConv3NoteEntries 5013 }
    kudosConv3CtrlEntries OBJECT IDENTIFIER ::= { kudosIQP 11 }


    i3InputSelect OBJECT-TYPE
        SYNTAX            INTEGER {
                            valSDI1(0),
                            valSDI2(1),
                            valSDI3(2),
                            valSDI4(3),
                            valCVBSA(4),
                            valCVBSB(5),
                            valCVBSC(6),
                            valCVBSD(7),
                            valSFPA1(8),
                            valSFPA2(9),
                            valSFPB1(10),
                            valSFPB2(11)
                            }
        MAX-ACCESS        read-write
        STATUS            current
        DESCRIPTION
                "CMNT: - 
                 TYPE: - RadiobuttonList
                 PAGE: - Input
                    Input Select  cmdID= 10020
                    SDI 1  value= 0
                    SDI 2  value= 1
                    SDI 3  value= 2
                    SDI 4  value= 3
                    CVBS A  value= 4
                    CVBS B  value= 5
                    CVBS C  value= 6
                    CVBS D  value= 7
                    SFP A1  value= 8
                    SFP A2  value= 9
                    SFP B1  value= 10
                    SFP B2  value= 11  "
        ::= { kudosConv3CtrlEntries 10020 }


    i3InputStatusSDI1 OBJECT-TYPE
        SYNTAX            RollCallString
        MAX-ACCESS        read-only
        STATUS            current
        DESCRIPTION
                "CMNT: - 
                 TYPE: - Display
                 PAGE: - Input
                    SDI 1  cmdID= 10270  "
        ::= { kudosConv3CtrlEntries 10270 }


    i3InputStatusSDI2 OBJECT-TYPE
        SYNTAX            RollCallString
        MAX-ACCESS        read-only
        STATUS            current
        DESCRIPTION
                "CMNT: - 
                 TYPE: - Display
                 PAGE: - Input
                    SDI 2  cmdID= 10271  "
        ::= { kudosConv3CtrlEntries 10271 }


    i3InputStatusSDI3 OBJECT-TYPE
        SYNTAX            RollCallString
        MAX-ACCESS        read-only
        STATUS            current
        DESCRIPTION
                "CMNT: - 
                 TYPE: - Display
                 PAGE: - Input
                    SDI 3  cmdID= 10272  "
        ::= { kudosConv3CtrlEntries 10272 }


    i3InputStatusSDI4 OBJECT-TYPE
        SYNTAX            RollCallString
        MAX-ACCESS        read-only
        STATUS            current
        DESCRIPTION
                "CMNT: - 
                 TYPE: - Display
                 PAGE: - Input
                    SDI 4  cmdID= 10273  "
        ::= { kudosConv3CtrlEntries 10273 }


    i3InputStatusCVBS1 OBJECT-TYPE
        SYNTAX            RollCallString
        MAX-ACCESS        read-only
        STATUS            current
        DESCRIPTION
                "CMNT: - 
                 TYPE: - Display
                 PAGE: - Input
                    CVBS 1  cmdID= 10274  "
        ::= { kudosConv3CtrlEntries 10274 }


    i3InputStatusCVBS2 OBJECT-TYPE
        SYNTAX            RollCallString
        MAX-ACCESS        read-only
        STATUS            current
        DESCRIPTION
                "CMNT: - 
                 TYPE: - Display
                 PAGE: - Input
                    CVBS 2  cmdID= 10275  "
        ::= { kudosConv3CtrlEntries 10275 }


    i3InputStatusCVBS3 OBJECT-TYPE
        SYNTAX            RollCallString
        MAX-ACCESS        read-only
        STATUS            current
        DESCRIPTION
                "CMNT: - 
                 TYPE: - Display
                 PAGE: - Input
                    CVBS 3  cmdID= 10276  "
        ::= { kudosConv3CtrlEntries 10276 }


    i3InputStatusCVBS4 OBJECT-TYPE
        SYNTAX            RollCallString
        MAX-ACCESS        read-only
        STATUS            current
        DESCRIPTION
                "CMNT: - 
                 TYPE: - Display
                 PAGE: - Input
                    CVBS 4  cmdID= 10277  "
        ::= { kudosConv3CtrlEntries 10277 }


    i3InputStatusSFP1 OBJECT-TYPE
        SYNTAX            RollCallString
        MAX-ACCESS        read-only
        STATUS            current
        DESCRIPTION
                "CMNT: - 
                 TYPE: - Display
                 PAGE: - Input
                    SFP 1  cmdID= 10278  "
        ::= { kudosConv3CtrlEntries 10278 }


    i3InputStatusSFP2 OBJECT-TYPE
        SYNTAX            RollCallString
        MAX-ACCESS        read-only
        STATUS            current
        DESCRIPTION
                "CMNT: - 
                 TYPE: - Display
                 PAGE: - Input
                    SFP 2  cmdID= 10279  "
        ::= { kudosConv3CtrlEntries 10279 }


    i3InputStatusSFP3 OBJECT-TYPE
        SYNTAX            RollCallString
        MAX-ACCESS        read-only
        STATUS            current
        DESCRIPTION
                "CMNT: - 
                 TYPE: - Display
                 PAGE: - Input
                    SFP 3  cmdID= 10280  "
        ::= { kudosConv3CtrlEntries 10280 }


    i3InputStatusSFP4 OBJECT-TYPE
        SYNTAX            RollCallString
        MAX-ACCESS        read-only
        STATUS            current
        DESCRIPTION
                "CMNT: - 
                 TYPE: - Display
                 PAGE: - Input
                    SFP 4  cmdID= 10281  "
        ::= { kudosConv3CtrlEntries 10281 }


    i3InputStatusCurrentInputStandard OBJECT-TYPE
        SYNTAX            RollCallString
        MAX-ACCESS        read-only
        STATUS            current
        DESCRIPTION
                "CMNT: - 
                 TYPE: - Display
                 PAGE: - Input
                    Current Input Standard  cmdID= 10313  "
        ::= { kudosConv3CtrlEntries 10313 }


    i3OutputFormat OBJECT-TYPE
        SYNTAX            INTEGER {
                            val525625(0),
                            val720p(1),
                            val1080i(2),
                            val1080pnA(3),
                            val1080pnB(4)
                            }
        MAX-ACCESS        read-write
        STATUS            current
        DESCRIPTION
                "CMNT: - 
                 TYPE: - RadiobuttonList
                 PAGE: - Output
                    Output Format  cmdID= 10025
                    525/625  value= 0
                    720p  value= 1
                    1080i  value= 2
                    1080p-A  value= 3
                    1080p-B  value= 4  "
        ::= { kudosConv3CtrlEntries 10025 }


    i3OutputDefaultFieldRate OBJECT-TYPE
        SYNTAX            INTEGER {
                            valLastValidInput(0),
                            val23Hz(1),
                            val24Hz(2),
                            val25Hz(3),
                            val29Hz(4),
                            val30Hz(5),
                            val50Hz(6),
                            val59Hz(7),
                            val60Hz(8)
                            }
        MAX-ACCESS        read-write
        STATUS            current
        DESCRIPTION
                "CMNT: - 
                 TYPE: - RadiobuttonList
                 PAGE: - Output
                    Default Field Rate  cmdID= 10026
                    Last Valid Input  value= 0
                    23 Hz  value= 1
                    24 Hz  value= 2
                    25 Hz  value= 3
                    29 Hz  value= 4
                    30 Hz  value= 5
                    50 Hz  value= 6
                    59 Hz  value= 7
                    60 Hz  value= 8  "
        ::= { kudosConv3CtrlEntries 10026 }


    i3OutputStandard OBJECT-TYPE
        SYNTAX            INTEGER {
                            val62550i(2),
                            val52559i(3),
                            val72023p(4),
                            val72024p(5),
                            val72025p(6),
                            val72029p(7),
                            val72030p(8),
                            val72050p(9),
                            val72059p(10),
                            val72060p(11),
                            val108023p(12),
                            val108024p(13),
                            val108025p(14),
                            val108029p(15),
                            val108030p(16),
                            val108050i(17),
                            val108059i(18),
                            val108060i(19),
                            val108023psf(20),
                            val108024psf(21),
                            val108025psf(50),
                            val108029psf(51),
                            val108050pnA(22),
                            val108059pnA(23),
                            val108060pnA(24),
                            val108050pnB(25),
                            val108059pnB(26),
                            val108060pnB(27)
                            }
        MAX-ACCESS        read-write
        STATUS            current
        DESCRIPTION
                "CMNT: - 
                 TYPE: - RadiobuttonList
                 PAGE: - Output
                    Output Standard  cmdID= 10024
                    625 50i  value= 2
                    525 59i  value= 3
                    720 23p  value= 4
                    720 24p  value= 5
                    720 25p  value= 6
                    720 29p  value= 7
                    720 30p  value= 8
                    720 50p  value= 9
                    720 59p  value= 10
                    720 60p  value= 11
                    1080 23p  value= 12
                    1080 24p  value= 13
                    1080 25p  value= 14
                    1080 29p  value= 15
                    1080 30p  value= 16
                    1080 50i  value= 17
                    1080 59i  value= 18
                    1080 60i  value= 19
                    1080 23psf  value= 20
                    1080 24psf  value= 21
                    1080 25psf  value= 50
                    1080 29psf  value= 51
                    1080 50p-A  value= 22
                    1080 59p-A  value= 23
                    1080 60p-A  value= 24
                    1080 50p-B  value= 25
                    1080 59p-B  value= 26
                    1080 60p-B  value= 27  "
        ::= { kudosConv3CtrlEntries 10024 }


    i3OutputCurrentOutputStandard OBJECT-TYPE
        SYNTAX            RollCallString
        MAX-ACCESS        read-only
        STATUS            current
        DESCRIPTION
                "CMNT: - 
                 TYPE: - Display
                 PAGE: - Output
                    Current Output Standard  cmdID= 10314  "
        ::= { kudosConv3CtrlEntries 10314 }


    i3OutputBlankingEmbeddedAudio OBJECT-TYPE
        SYNTAX            INTEGER {
                            valEnable(0),
                            valBlank(1)
                            }
        MAX-ACCESS        read-write
        STATUS            current
        DESCRIPTION
                "CMNT: - 
                 TYPE: - RadiobuttonList
                 PAGE: - Output
                    Embedded Audio  cmdID= 10021
                    Enable  value= 0
                    Blank  value= 1  "
        ::= { kudosConv3CtrlEntries 10021 }


    i3OutputBlankingVAncillaryData OBJECT-TYPE
        SYNTAX            INTEGER {
                            valPass(0),
                            valStrip(1)
                            }
        MAX-ACCESS        read-write
        STATUS            current
        DESCRIPTION
                "CMNT: - 
                 TYPE: - RadiobuttonList
                 PAGE: - Output
                    V Ancillary Data  cmdID= 10022
                    Pass  value= 0
                    Strip  value= 1  "
        ::= { kudosConv3CtrlEntries 10022 }


    i3OutputBlankingSDHalfLine OBJECT-TYPE
        SYNTAX            INTEGER {
                            valPass(0),
                            valBlank(1)
                            }
        MAX-ACCESS        read-write
        STATUS            current
        DESCRIPTION
                "CMNT: - 
                 TYPE: - RadiobuttonList
                 PAGE: - Output
                    SD Half Line  cmdID= 10023
                    Pass  value= 0
                    Blank  value= 1  "
        ::= { kudosConv3CtrlEntries 10023 }


    i3OutputTestPatterns OBJECT-TYPE
        SYNTAX            INTEGER {
                            valOff(0),
                            valBlack(1),
                            valRamp(2),
                            valBars(3)
                            }
        MAX-ACCESS        read-write
        STATUS            current
        DESCRIPTION
                "CMNT: - 
                 TYPE: - RadiobuttonList
                 PAGE: - Output
                    Test Patterns  cmdID= 10054
                    Off  value= 0
                    Black  value= 1
                    Ramp  value= 2
                    Bars  value= 3  "
        ::= { kudosConv3CtrlEntries 10054 }


    i3OutputScrollingCaptionGeneratorCaptionEntry OBJECT-TYPE
        SYNTAX            RollCallString
        MAX-ACCESS        read-write
        STATUS            current
        DESCRIPTION
                "CMNT: - 
                 TYPE: - Editstring
                 PAGE: - Output
                    Caption Entry  cmdID= 10050
                    preset= Channel Number"
        ::= { kudosConv3CtrlEntries 10050 }


    i3OutputScrollingCaptionGeneratorCaptionScroll OBJECT-TYPE
        SYNTAX            INTEGER { disable(0), enable(1)  }
        MAX-ACCESS        read-write
        STATUS            current
        DESCRIPTION
                "CMNT: - 
                 TYPE: - Checkbox
                 PAGE: - Output
                    Caption Scroll  cmdID= 10052  "
        ::= { kudosConv3CtrlEntries 10052 }


    i3OutputScrollingCaptionGeneratorCaptionEnable OBJECT-TYPE
        SYNTAX            INTEGER { disable(0), enable(1)  }
        MAX-ACCESS        read-write
        STATUS            current
        DESCRIPTION
                "CMNT: - 
                 TYPE: - Checkbox
                 PAGE: - Output
                    Caption Enable  cmdID= 10051  "
        ::= { kudosConv3CtrlEntries 10051 }


    i3OutputFreeze OBJECT-TYPE
        SYNTAX            INTEGER { disable(0), enable(1)  }
        MAX-ACCESS        read-write
        STATUS            current
        DESCRIPTION
                "CMNT: - 
                 TYPE: - Checkbox
                 PAGE: - Output
                    Freeze  cmdID= 10053  "
        ::= { kudosConv3CtrlEntries 10053 }


    i3OutputLegalization OBJECT-TYPE
        SYNTAX            INTEGER {
                            valOff(0),
                            val700mV(1),
                            val721mV(2),
                            val735mV(3),
                            val746mV(4)
                            }
        MAX-ACCESS        read-write
        STATUS            current
        DESCRIPTION
                "CMNT: - 
                 TYPE: - RadiobuttonList
                 PAGE: - Output
                    Legalization  cmdID= 10049
                    Off  value= 0
                    700mV  value= 1
                    721mV  value= 2
                    735mV  value= 3
                    746mV  value= 4  "
        ::= { kudosConv3CtrlEntries 10049 }


    i3OutputLogoControlPreShaped OBJECT-TYPE
        SYNTAX            INTEGER { disable(0), enable(1)  }
        MAX-ACCESS        read-write
        STATUS            current
        DESCRIPTION
                "CMNT: - 
                 TYPE: - Checkbox
                 PAGE: - Output
                    Pre-Shaped  cmdID= 10055  "
        ::= { kudosConv3CtrlEntries 10055 }


    i3OutputLogoControlTake OBJECT-TYPE
        SYNTAX            INTEGER { disable(0), enable(1)  }
        MAX-ACCESS        read-write
        STATUS            current
        DESCRIPTION
                "CMNT: - 
                 TYPE: - Checkbox
                 PAGE: - Output
                    Take  cmdID= 10056  "
        ::= { kudosConv3CtrlEntries 10056 }


    i3OutputLogoControlHPosition OBJECT-TYPE
        SYNTAX            INTEGER
        MAX-ACCESS        read-write
        STATUS            current
        DESCRIPTION
                "CMNT: - 
                 TYPE: - Number
                 PAGE: - Output
                    H Position  cmdID= 10057
                    min= 0  max= 100  step= 1  format= %0.0f  div_scale= 1  preset= 10
                    Min = 0  Max = 100  Step = 1  Preset = 10  "
        ::= { kudosConv3CtrlEntries 10057 }


    i3OutputLogoControlVPosition OBJECT-TYPE
        SYNTAX            INTEGER
        MAX-ACCESS        read-write
        STATUS            current
        DESCRIPTION
                "CMNT: - 
                 TYPE: - Number
                 PAGE: - Output
                    V Position  cmdID= 10058
                    min= 0  max= 100  step= 1  format= %0.0f  div_scale= 1  preset= 10
                    Min = 0  Max = 100  Step = 1  Preset = 10  "
        ::= { kudosConv3CtrlEntries 10058 }


    i3OutputLogoControlTransparency OBJECT-TYPE
        SYNTAX            INTEGER
        MAX-ACCESS        read-write
        STATUS            current
        DESCRIPTION
                "CMNT: - 
                 TYPE: - Number
                 PAGE: - Output
                    Transparency  cmdID= 10059
                    min= 0  max= 100  step= 1  format= %0.0f  div_scale= 1  preset= 10
                    Min = 0  Max = 100  Step = 1  Preset = 10  "
        ::= { kudosConv3CtrlEntries 10059 }


    i3OutputLogoControlDelete OBJECT-TYPE
        SYNTAX            INTEGER { noAction(0),valDelete(1) }
        MAX-ACCESS        read-write
        STATUS            current
        DESCRIPTION
                "CMNT: - 
                 TYPE: - Button
                 PAGE: - Output
                    Delete  cmdID= 10060
                    value= 1  "
        ::= { kudosConv3CtrlEntries 10060 }


    i3OutputLogoControlCurrentSelectedLogo OBJECT-TYPE
        SYNTAX            RollCallString
        MAX-ACCESS        read-only
        STATUS            current
        DESCRIPTION
                "CMNT: - 
                 TYPE: - Display
                 PAGE: - Output
                    Current Selected Logo  cmdID= 10062  "
        ::= { kudosConv3CtrlEntries 10062 }


    i3OutputLogoControlLogoStatus OBJECT-TYPE
        SYNTAX            RollCallString
        MAX-ACCESS        read-only
        STATUS            current
        DESCRIPTION
                "CMNT: - 
                 TYPE: - Display
                 PAGE: - Output
                    Logo Status  cmdID= 15001  "
        ::= { kudosConv3CtrlEntries 15001 }


    i3OutputLogoControlLogoState OBJECT-TYPE
        SYNTAX            RollCallString
        MAX-ACCESS        read-only
        STATUS            current
        DESCRIPTION
                "CMNT: - 
                 TYPE: - Display
                 PAGE: - Output
                    Logo State  cmdID= 10063  "
        ::= { kudosConv3CtrlEntries 10063 }


    i3OutputLogoControlNewLogo OBJECT-TYPE
        SYNTAX            RollCallString
        MAX-ACCESS        read-write
        STATUS            current
        DESCRIPTION
                "CMNT: - 
                 TYPE: - Editstring
                 PAGE: - Output
                    New Logo  cmdID= 15000
                    preset= startupqwerty"
        ::= { kudosConv3CtrlEntries 15000 }


    i3OutputLogoControlLogoSelect OBJECT-TYPE
        SYNTAX            INTEGER {
                            valNoneSelected(-1),
                            valLogo1(1),
                            valLogo2(2),
                            valLogo3(3),
                            valLogo4(4),
                            valLogo5(5),
                            valLogo6(6),
                            valLogo7(7),
                            valLogo8(8),
                            valLogo9(9),
                            valLogo10(10),
                            valLogo11(11),
                            valLogo12(12),
                            valLogo13(13),
                            valLogo14(14),
                            valLogo15(15),
                            valLogo16(16),
                            valLogo17(17),
                            valLogo18(18),
                            valLogo19(19),
                            valLogo20(20),
                            valLogo21(21),
                            valLogo22(22),
                            valLogo23(23),
                            valLogo24(24),
                            valLogo25(25),
                            valLogo26(26),
                            valLogo27(27),
                            valLogo28(28),
                            valLogo29(29),
                            valLogo30(30),
                            valLogo31(31),
                            valLogo32(32),
                            valLogo33(33),
                            valLogo34(34),
                            valLogo35(35),
                            valLogo36(36),
                            valLogo37(37),
                            valLogo38(38),
                            valLogo39(39),
                            valLogo40(40),
                            valLogo41(41),
                            valLogo42(42),
                            valLogo43(43),
                            valLogo44(44),
                            valLogo45(45),
                            valLogo46(46),
                            valLogo47(47),
                            valLogo48(48),
                            valLogo49(49),
                            valLogo50(50),
                            valLogo51(51),
                            valLogo52(52),
                            valLogo53(53),
                            valLogo54(54),
                            valLogo55(55),
                            valLogo56(56),
                            valLogo57(57),
                            valLogo58(58),
                            valLogo59(59),
                            valLogo60(60),
                            valLogo61(61),
                            valLogo62(62),
                            valLogo63(63),
                            valLogo64(64)
                            }
        MAX-ACCESS        read-write
        STATUS            current
        DESCRIPTION
                "CMNT: - 
                 TYPE: - RadiobuttonList
                 PAGE: - Output
                    Logo Select  cmdID= 10061
                    None Selected  value= -1
                    Logo 1  value= 1
                    Logo 2  value= 2
                    Logo 3  value= 3
                    Logo 4  value= 4
                    Logo 5  value= 5
                    Logo 6  value= 6
                    Logo 7  value= 7
                    Logo 8  value= 8
                    Logo 9  value= 9
                    Logo 10  value= 10
                    Logo 11  value= 11
                    Logo 12  value= 12
                    Logo 13  value= 13
                    Logo 14  value= 14
                    Logo 15  value= 15
                    Logo 16  value= 16
                    Logo 17  value= 17
                    Logo 18  value= 18
                    Logo 19  value= 19
                    Logo 20  value= 20
                    Logo 21  value= 21
                    Logo 22  value= 22
                    Logo 23  value= 23
                    Logo 24  value= 24
                    Logo 25  value= 25
                    Logo 26  value= 26
                    Logo 27  value= 27
                    Logo 28  value= 28
                    Logo 29  value= 29
                    Logo 30  value= 30
                    Logo 31  value= 31
                    Logo 32  value= 32
                    Logo 33  value= 33
                    Logo 34  value= 34
                    Logo 35  value= 35
                    Logo 36  value= 36
                    Logo 37  value= 37
                    Logo 38  value= 38
                    Logo 39  value= 39
                    Logo 40  value= 40
                    Logo 41  value= 41
                    Logo 42  value= 42
                    Logo 43  value= 43
                    Logo 44  value= 44
                    Logo 45  value= 45
                    Logo 46  value= 46
                    Logo 47  value= 47
                    Logo 48  value= 48
                    Logo 49  value= 49
                    Logo 50  value= 50
                    Logo 51  value= 51
                    Logo 52  value= 52
                    Logo 53  value= 53
                    Logo 54  value= 54
                    Logo 55  value= 55
                    Logo 56  value= 56
                    Logo 57  value= 57
                    Logo 58  value= 58
                    Logo 59  value= 59
                    Logo 60  value= 60
                    Logo 61  value= 61
                    Logo 62  value= 62
                    Logo 63  value= 63
                    Logo 64  value= 64  "
        ::= { kudosConv3CtrlEntries 10061 }


    i3VideoProcAmpEnable OBJECT-TYPE
        SYNTAX            INTEGER { disable(0), enable(1)  }
        MAX-ACCESS        read-write
        STATUS            current
        DESCRIPTION
                "CMNT: - 
                 TYPE: - Checkbox
                 PAGE: - Video
                    Enable  cmdID= 10047  "
        ::= { kudosConv3CtrlEntries 10047 }


    i3VideoProcAmpContrast OBJECT-TYPE
        SYNTAX            INTEGER
        MAX-ACCESS        read-write
        STATUS            current
        DESCRIPTION
                "CMNT: - 
                 TYPE: - Number
                 PAGE: - Video
                    Contrast  cmdID= 10043
                    min= -60  max= 60  step= 2  format= %0.1fdB  div_scale= 10  preset= 0
                    Min = -6.0dB  Max = 6.0dB  Step = 0.2dB  Preset = 0.0dB  "
        ::= { kudosConv3CtrlEntries 10043 }


    i3VideoProcAmpSaturation OBJECT-TYPE
        SYNTAX            INTEGER
        MAX-ACCESS        read-write
        STATUS            current
        DESCRIPTION
                "CMNT: - 
                 TYPE: - Number
                 PAGE: - Video
                    Saturation  cmdID= 10044
                    min= -60  max= 60  step= 2  format= %0.1fdB  div_scale= 10  preset= 0
                    Min = -6.0dB  Max = 6.0dB  Step = 0.2dB  Preset = 0.0dB  "
        ::= { kudosConv3CtrlEntries 10044 }


    i3VideoProcAmpBlackLevel OBJECT-TYPE
        SYNTAX            INTEGER
        MAX-ACCESS        read-write
        STATUS            current
        DESCRIPTION
                "CMNT: - 
                 TYPE: - Number
                 PAGE: - Video
                    Black Level  cmdID= 10045
                    min= -1000  max= 1000  step= 8  format= %0.1fmV  div_scale= 10  preset= 0
                    Min = -100.0mV  Max = 100.0mV  Step = 0.8mV  Preset = 0.0mV  "
        ::= { kudosConv3CtrlEntries 10045 }


    i3VideoProcAmpGamma OBJECT-TYPE
        SYNTAX            INTEGER
        MAX-ACCESS        read-write
        STATUS            current
        DESCRIPTION
                "CMNT: - 
                 TYPE: - Number
                 PAGE: - Video
                    Gamma  cmdID= 10046
                    min= 4  max= 17  step= 1  format= %0.1f  div_scale= 10  preset= 10
                    Min = 0.4  Max = 1.7  Step = 0.1  Preset = 1.0  "
        ::= { kudosConv3CtrlEntries 10046 }


    i3VideoProcAmpYCOffset OBJECT-TYPE
        SYNTAX            INTEGER
        MAX-ACCESS        read-write
        STATUS            current
        DESCRIPTION
                "CMNT: - 
                 TYPE: - Number
                 PAGE: - Video
                    YC Offset  cmdID= 10048
                    min= -20  max= 20  step= 2  format= %0.0f  div_scale= 1  preset= 0
                    Min = -20  Max = 20  Step = 2  Preset = 0  "
        ::= { kudosConv3CtrlEntries 10048 }


    i3VideoEnhanceNonlinearEnhancerEnable OBJECT-TYPE
        SYNTAX            INTEGER { disable(0), enable(1)  }
        MAX-ACCESS        read-write
        STATUS            current
        DESCRIPTION
                "CMNT: - 
                 TYPE: - Checkbox
                 PAGE: - Enhance
                    Enable  cmdID= 10036  "
        ::= { kudosConv3CtrlEntries 10036 }


    i3VideoEnhanceNonlinearEnhancerLevel OBJECT-TYPE
        SYNTAX            INTEGER
        MAX-ACCESS        read-write
        STATUS            current
        DESCRIPTION
                "CMNT: - 
                 TYPE: - Number
                 PAGE: - Enhance
                    Level  cmdID= 10039
                    min= 0  max= 192  step= 1  format= %0.0f  div_scale= 1  preset= 0
                    Min = 0  Max = 192  Step = 1  Preset = 0  "
        ::= { kudosConv3CtrlEntries 10039 }


    i3VideoEnhanceNonlinearEnhancerMode OBJECT-TYPE
        SYNTAX            INTEGER {
                            valLow(0),
                            valMedium(1),
                            valHigh(2),
                            valSuper(3),
                            valManual(4)
                            }
        MAX-ACCESS        read-write
        STATUS            current
        DESCRIPTION
                "CMNT: - 
                 TYPE: - RadiobuttonList
                 PAGE: - Enhance
                    Mode  cmdID= 10037
                    Low  value= 0
                    Medium  value= 1
                    High  value= 2
                    Super  value= 3
                    Manual  value= 4  "
        ::= { kudosConv3CtrlEntries 10037 }


    i3VideoEnhanceNonlinearEnhancerFrequencyBand OBJECT-TYPE
        SYNTAX            INTEGER {
                            valLow(0),
                            valMedium(1),
                            valHigh(2)
                            }
        MAX-ACCESS        read-write
        STATUS            current
        DESCRIPTION
                "CMNT: - 
                 TYPE: - RadiobuttonList
                 PAGE: - Enhance
                    Frequency Band  cmdID= 10038
                    Low  value= 0
                    Medium  value= 1
                    High  value= 2  "
        ::= { kudosConv3CtrlEntries 10038 }


    i3VideoEnhanceNonlinearEnhancerNoiseRejection OBJECT-TYPE
        SYNTAX            INTEGER
        MAX-ACCESS        read-write
        STATUS            current
        DESCRIPTION
                "CMNT: - 
                 TYPE: - Number
                 PAGE: - Enhance
                    Noise Rejection  cmdID= 10040
                    min= 0  max= 100  step= 1  format= %0.0f  div_scale= 1  preset= 0
                    Min = 0  Max = 100  Step = 1  Preset = 0  "
        ::= { kudosConv3CtrlEntries 10040 }


    i3VideoEnhanceConversionAperturePreset OBJECT-TYPE
        SYNTAX            INTEGER { noAction(0),valPreset(1) }
        MAX-ACCESS        read-write
        STATUS            current
        DESCRIPTION
                "CMNT: - 
                 TYPE: - Button
                 PAGE: - Enhance
                    Preset  cmdID= 10335
                    value= 1  "
        ::= { kudosConv3CtrlEntries 10335 }


    i3VideoConversionApertureHorizontalSharpness OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Conversion Aperture
                    Sharpness  cmdID= 10072
                    Soft 2  value= 0
                    Soft 1  value= 1
                    Normal  value= 2
                    Sharp 1  value= 3
                    Sharp 2  value= 4  "
        ::= { kudosConv3CtrlEntries 10072 }


    i3VideoConversionApertureHorizontalDetail OBJECT-TYPE
        SYNTAX            INTEGER {
                            valLow2(0),
                            valLow1(1),
                            valNormal(2),
                            valHigh1(3),
                            valHigh2(4)
                            }
        MAX-ACCESS        read-write
        STATUS            current
        DESCRIPTION
                "CMNT: - 
                 TYPE: - RadiobuttonList
                 PAGE: - Conversion Aperture
                    Detail  cmdID= 10073
                    Low 2  value= 0
                    Low 1  value= 1
                    Normal  value= 2
                    High 1  value= 3
                    High 2  value= 4  "
        ::= { kudosConv3CtrlEntries 10073 }


    i3VideoConversionApertureVerticalLevel OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Conversion Aperture
                    Level  cmdID= 10042
                    Soft 2  value= 0
                    Soft 1  value= 1
                    Normal  value= 2
                    Sharp 1  value= 3
                    Sharp 2  value= 4  "
        ::= { kudosConv3CtrlEntries 10042 }


    i3VideoConversionApertureVerticalFrequencyBand OBJECT-TYPE
        SYNTAX            INTEGER {
                            valLow(0),
                            valMedium(1),
                            valHigh(2)
                            }
        MAX-ACCESS        read-write
        STATUS            current
        DESCRIPTION
                "CMNT: - 
                 TYPE: - RadiobuttonList
                 PAGE: - Conversion Aperture
                    Frequency Band  cmdID= 10041
                    Low  value= 0
                    Medium  value= 1
                    High  value= 2  "
        ::= { kudosConv3CtrlEntries 10041 }


    i3VideoNoiseReductionEnable OBJECT-TYPE
        SYNTAX            INTEGER { disable(0), enable(1)  }
        MAX-ACCESS        read-write
        STATUS            current
        DESCRIPTION
                "CMNT: - 
                 TYPE: - Checkbox
                 PAGE: - Video
                    Enable  cmdID= 10031  "
        ::= { kudosConv3CtrlEntries 10031 }


    i3VideoNoiseReductionRecursiveLuma OBJECT-TYPE
        SYNTAX            INTEGER
        MAX-ACCESS        read-write
        STATUS            current
        DESCRIPTION
                "CMNT: - 
                 TYPE: - Number
                 PAGE: - Noise Reduction
                    Luma  cmdID= 10027
                    min= 0  max= 7  step= 1  format= %0.0f  div_scale= 1  preset= 0
                    Min = 0  Max = 7  Step = 1  Preset = 0  "
        ::= { kudosConv3CtrlEntries 10027 }


    i3VideoNoiseReductionRecursiveChroma OBJECT-TYPE
        SYNTAX            INTEGER
        MAX-ACCESS        read-write
        STATUS            current
        DESCRIPTION
                "CMNT: - 
                 TYPE: - Number
                 PAGE: - Noise Reduction
                    Chroma  cmdID= 10028
                    min= 0  max= 7  step= 1  format= %0.0f  div_scale= 1  preset= 0
                    Min = 0  Max = 7  Step = 1  Preset = 0  "
        ::= { kudosConv3CtrlEntries 10028 }


    i3VideoNoiseReductionRecursiveMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10029
                    Auto  value= 0
                    Manual  value= 1  "
        ::= { kudosConv3CtrlEntries 10029 }


    i3VideoNoiseReductionRecursiveThreshold OBJECT-TYPE
        SYNTAX            INTEGER
        MAX-ACCESS        read-write
        STATUS            current
        DESCRIPTION
                "CMNT: - 
                 TYPE: - Number
                 PAGE: - Noise Reduction
                    Threshold  cmdID= 10030
                    min= 0  max= 7  step= 1  format= %0.0f  div_scale= 1  preset= 0
                    Min = 0  Max = 7  Step = 1  Preset = 0  "
        ::= { kudosConv3CtrlEntries 10030 }


    i3VideoNoiseReductionSpatialLevel OBJECT-TYPE
        SYNTAX            INTEGER
        MAX-ACCESS        read-write
        STATUS            current
        DESCRIPTION
                "CMNT: - 
                 TYPE: - Number
                 PAGE: - Noise Reduction
                    Level  cmdID= 10033
                    min= 0  max= 7  step= 1  format= %0.0f  div_scale= 1  preset= 0
                    Min = 0  Max = 7  Step = 1  Preset = 0  "
        ::= { kudosConv3CtrlEntries 10033 }


    i3VideoNoiseReductionSpatialMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10032
                    Auto  value= 0
                    Manual  value= 1  "
        ::= { kudosConv3CtrlEntries 10032 }


    i3VideoNoiseReductionSpatialThreshold OBJECT-TYPE
        SYNTAX            INTEGER
        MAX-ACCESS        read-write
        STATUS            current
        DESCRIPTION
                "CMNT: - 
                 TYPE: - Number
                 PAGE: - Noise Reduction
                    Threshold  cmdID= 10034
                    min= 1  max= 4  step= 1  format= %0.0f  div_scale= 1  preset= 1
                    Min = 1  Max = 4  Step = 1  Preset = 1  "
        ::= { kudosConv3CtrlEntries 10034 }


    i3VideoNoiseReductionSplitScreen OBJECT-TYPE
        SYNTAX            INTEGER { disable(0), enable(1)  }
        MAX-ACCESS        read-write
        STATUS            current
        DESCRIPTION
                "CMNT: - 
                 TYPE: - Checkbox
                 PAGE: - Video
                    Split Screen  cmdID= 10035  "
        ::= { kudosConv3CtrlEntries 10035 }


    i3ConvertUpConversionCleanEdgeUpconversion OBJECT-TYPE
        SYNTAX            INTEGER { disable(0), enable(1)  }
        MAX-ACCESS        read-write
        STATUS            current
        DESCRIPTION
                "CMNT: - 
                 TYPE: - Checkbox
                 PAGE: - Convert
                    Clean Edge Upconversion  cmdID= 10069  "
        ::= { kudosConv3CtrlEntries 10069 }


    i3ConvertMotionProcessingMotionProcess OBJECT-TYPE
        SYNTAX            INTEGER { disable(0), enable(1)  }
        MAX-ACCESS        read-write
        STATUS            current
        DESCRIPTION
                "CMNT: - 
                 TYPE: - Checkbox
                 PAGE: - Convert
                    Motion Process  cmdID= 10064  "
        ::= { kudosConv3CtrlEntries 10064 }


    i3ConvertMotionProcessingEnhancedMotion OBJECT-TYPE
        SYNTAX            INTEGER { disable(0), enable(1)  }
        MAX-ACCESS        read-write
        STATUS            current
        DESCRIPTION
                "CMNT: - 
                 TYPE: - Checkbox
                 PAGE: - Convert
                    Enhanced Motion  cmdID= 10065  "
        ::= { kudosConv3CtrlEntries 10065 }


    i3ConvertMotionProcessingStillProcess OBJECT-TYPE
        SYNTAX            INTEGER { disable(0), enable(1)  }
        MAX-ACCESS        read-write
        STATUS            current
        DESCRIPTION
                "CMNT: - 
                 TYPE: - Checkbox
                 PAGE: - Convert
                    Still Process  cmdID= 10066  "
        ::= { kudosConv3CtrlEntries 10066 }


    i3ConvertMotionProcessingEnhancedStill OBJECT-TYPE
        SYNTAX            INTEGER { disable(0), enable(1)  }
        MAX-ACCESS        read-write
        STATUS            current
        DESCRIPTION
                "CMNT: - 
                 TYPE: - Checkbox
                 PAGE: - Convert
                    Enhanced Still  cmdID= 10067  "
        ::= { kudosConv3CtrlEntries 10067 }


    i3ConvertMotionProcessingEnhancedFilm OBJECT-TYPE
        SYNTAX            INTEGER { disable(0), enable(1)  }
        MAX-ACCESS        read-write
        STATUS            current
        DESCRIPTION
                "CMNT: - 
                 TYPE: - Checkbox
                 PAGE: - Convert
                    Enhanced Film  cmdID= 10068  "
        ::= { kudosConv3CtrlEntries 10068 }


    i3ConvertMotionProcessingEnhancedDeinterlace OBJECT-TYPE
        SYNTAX            INTEGER { disable(0), enable(1)  }
        MAX-ACCESS        read-write
        STATUS            current
        DESCRIPTION
                "CMNT: - 
                 TYPE: - Checkbox
                 PAGE: - Convert
                    Enhanced De-interlace  cmdID= 10071  "
        ::= { kudosConv3CtrlEntries 10071 }


    i3ConvertMotionProcessingCleanCut OBJECT-TYPE
        SYNTAX            INTEGER { disable(0), enable(1)  }
        MAX-ACCESS        read-write
        STATUS            current
        DESCRIPTION
                "CMNT: - 
                 TYPE: - Checkbox
                 PAGE: - Convert
                    Clean Cut  cmdID= 10070  "
        ::= { kudosConv3CtrlEntries 10070 }


    i3ConvertInputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10323  "
        ::= { kudosConv3CtrlEntries 10323 }


    i3ConvertInputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10324
                    2:3  value= 0
                    2:2 (psf)  value= 1  "
        ::= { kudosConv3CtrlEntries 10324 }


    i3ConvertInputCadence23Source OBJECT-TYPE
        SYNTAX            INTEGER {
                            valAutomatic(0),
                            valInputTimecode(1)
                            }
        MAX-ACCESS        read-write
        STATUS            current
        DESCRIPTION
                "CMNT: - 
                 TYPE: - RadiobuttonList
                 PAGE: - Convert
                    2:3 Source  cmdID= 10325
                    Automatic  value= 0
                    Input Timecode  value= 1  "
        ::= { kudosConv3CtrlEntries 10325 }


    i3ConvertInputCadence23StartHour OBJECT-TYPE
        SYNTAX            INTEGER
        MAX-ACCESS        read-write
        STATUS            current
        DESCRIPTION
                "CMNT: - 
                 TYPE: - Number
                 PAGE: - Convert
                    2:3 Start Hour  cmdID= 10326
                    min= 0  max= 23  step= 1  format= %0.0f  div_scale= 1  preset= 1
                    Min = 0  Max = 23  Step = 1  Preset = 1  "
        ::= { kudosConv3CtrlEntries 10326 }


    i3ConvertOutputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10327  "
        ::= { kudosConv3CtrlEntries 10327 }


    i3ConvertOutputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10328
                    2:3  value= 0
                    2:2 (psf)  value= 1  "
        ::= { kudosConv3CtrlEntries 10328 }


    i3ConvertOutputCadence23Source OBJECT-TYPE
        SYNTAX            INTEGER {
                            valFreeRun(0),
                            valOutputTimecode(1)
                            }
        MAX-ACCESS        read-write
        STATUS            current
        DESCRIPTION
                "CMNT: - 
                 TYPE: - RadiobuttonList
                 PAGE: - Convert
                    2:3 Source  cmdID= 10329
                    Free Run  value= 0
                    Output Timecode  value= 1  "
        ::= { kudosConv3CtrlEntries 10329 }


    i3ConvertOutputCadence23StartHour OBJECT-TYPE
        SYNTAX            INTEGER
        MAX-ACCESS        read-write
        STATUS            current
        DESCRIPTION
                "CMNT: - 
                 TYPE: - Number
                 PAGE: - Convert
                    2:3 Start Hour  cmdID= 10330
                    min= 0  max= 23  step= 1  format= %0.0f  div_scale= 1  preset= 1
                    Min = 0  Max = 23  Step = 1  Preset = 1  "
        ::= { kudosConv3CtrlEntries 10330 }


    i3ARCSyncMode OBJECT-TYPE
        SYNTAX            INTEGER { disable(0), enable(1)  }
        MAX-ACCESS        read-write
        STATUS            current
        DESCRIPTION
                "CMNT: - 
                 TYPE: - Checkbox
                 PAGE: - ARC
                    Sync Mode  cmdID= 10079  "
        ::= { kudosConv3CtrlEntries 10079 }


    i3ARCSignalingDetected OBJECT-TYPE
        SYNTAX            RollCallString
        MAX-ACCESS        read-only
        STATUS            current
        DESCRIPTION
                "CMNT: - 
                 TYPE: - Display
                 PAGE: - ARC
                    Signaling Detected  cmdID= 10315  "
        ::= { kudosConv3CtrlEntries 10315 }


    i3ARCSidebarKeyingOutputCropMode OBJECT-TYPE
        SYNTAX            INTEGER {
                            valOff(0),
                            valOutputCrop(1),
                            valSidebarKey(2)
                            }
        MAX-ACCESS        read-write
        STATUS            current
        DESCRIPTION
                "CMNT: - 
                 TYPE: - RadiobuttonList
                 PAGE: - ARC
                    Mode  cmdID= 10091
                    Off  value= 0
                    Output Crop  value= 1
                    Sidebar Key  value= 2  "
        ::= { kudosConv3CtrlEntries 10091 }


    i3ARCSidebarKeyingOutputCropSidebarKeySource OBJECT-TYPE
        SYNTAX            INTEGER {
                            valSDI1(0),
                            valSDI2(1),
                            valSDI3(2),
                            valSDI4(3),
                            valCVBSA(4),
                            valCVBSB(5),
                            valCVBSC(6),
                            valCVBSD(7),
                            valSFPA1(8),
                            valSFPA2(9),
                            valSFPA3(10),
                            valSFPA4(11),
                            valOutput(20)
                            }
        MAX-ACCESS        read-write
        STATUS            current
        DESCRIPTION
                "CMNT: - 
                 TYPE: - RadiobuttonList
                 PAGE: - ARC
                    Sidebar Key Source  cmdID= 10092
                    SDI 1  value= 0
                    SDI 2  value= 1
                    SDI 3  value= 2
                    SDI 4  value= 3
                    CVBS A  value= 4
                    CVBS B  value= 5
                    CVBS C  value= 6
                    CVBS D  value= 7
                    SFP A1  value= 8
                    SFP A2  value= 9
                    SFP A3  value= 10
                    SFP A4  value= 11
                    Output  value= 20  "
        ::= { kudosConv3CtrlEntries 10092 }


    i3ARCSidebarKeyingOutputCropOutputCropPositionTop OBJECT-TYPE
        SYNTAX            INTEGER
        MAX-ACCESS        read-write
        STATUS            current
        DESCRIPTION
                "CMNT: - 
                 TYPE: - Number
                 PAGE: - Sidebar Keying & Output Crop
                    Top  cmdID= 10093
                    min= 0  max= 99  step= 1  format= %0.0f%%  div_scale= 1  preset= 0
                    Min = 0%  Max = 99%  Step = 1%  Preset = 0%  "
        ::= { kudosConv3CtrlEntries 10093 }


    i3ARCSidebarKeyingOutputCropOutputCropPositionBottom OBJECT-TYPE
        SYNTAX            INTEGER
        MAX-ACCESS        read-write
        STATUS            current
        DESCRIPTION
                "CMNT: - 
                 TYPE: - Number
                 PAGE: - Sidebar Keying & Output Crop
                    Bottom  cmdID= 10094
                    min= 0  max= 99  step= 1  format= %0.0f%%  div_scale= 1  preset= 0
                    Min = 0%  Max = 99%  Step = 1%  Preset = 0%  "
        ::= { kudosConv3CtrlEntries 10094 }


    i3ARCSidebarKeyingOutputCropOutputCropPositionLeft OBJECT-TYPE
        SYNTAX            INTEGER
        MAX-ACCESS        read-write
        STATUS            current
        DESCRIPTION
                "CMNT: - 
                 TYPE: - Number
                 PAGE: - Sidebar Keying & Output Crop
                    Left  cmdID= 10095
                    min= 0  max= 99  step= 1  format= %0.0f%%  div_scale= 1  preset= 0
                    Min = 0%  Max = 99%  Step = 1%  Preset = 0%  "
        ::= { kudosConv3CtrlEntries 10095 }


    i3ARCSidebarKeyingOutputCropOutputCropPositionRight OBJECT-TYPE
        SYNTAX            INTEGER
        MAX-ACCESS        read-write
        STATUS            current
        DESCRIPTION
                "CMNT: - 
                 TYPE: - Number
                 PAGE: - Sidebar Keying & Output Crop
                    Right  cmdID= 10096
                    min= 0  max= 99  step= 1  format= %0.0f%%  div_scale= 1  preset= 0
                    Min = 0%  Max = 99%  Step = 1%  Preset = 0%  "
        ::= { kudosConv3CtrlEntries 10096 }


    i3ARCPostScalingControlPostScalingEnable OBJECT-TYPE
        SYNTAX            INTEGER { disable(0), enable(1)  }
        MAX-ACCESS        read-write
        STATUS            current
        DESCRIPTION
                "CMNT: - 
                 TYPE: - Checkbox
                 PAGE: - ARC
                    Post Scaling Enable  cmdID= 10078  "
        ::= { kudosConv3CtrlEntries 10078 }


    i3ARCPostScalingControlSize OBJECT-TYPE
        SYNTAX            INTEGER
        MAX-ACCESS        read-write
        STATUS            current
        DESCRIPTION
                "CMNT: - 
                 TYPE: - Number
                 PAGE: - ARC
                    Size  cmdID= 10074
                    min= 80  max= 120  step= 1  format= %0.0f%%  div_scale= 1  preset= 100
                    Min = 80%  Max = 120%  Step = 1%  Preset = 100%  "
        ::= { kudosConv3CtrlEntries 10074 }


    i3ARCPostScalingControlAspect OBJECT-TYPE
        SYNTAX            INTEGER
        MAX-ACCESS        read-write
        STATUS            current
        DESCRIPTION
                "CMNT: - 
                 TYPE: - Number
                 PAGE: - ARC
                    Aspect  cmdID= 10075
                    min= 70  max= 150  step= 1  format= %0.0f%%  div_scale= 1  preset= 100
                    Min = 70%  Max = 150%  Step = 1%  Preset = 100%  "
        ::= { kudosConv3CtrlEntries 10075 }


    i3ARCPostScalingControlPan OBJECT-TYPE
        SYNTAX            INTEGER
        MAX-ACCESS        read-write
        STATUS            current
        DESCRIPTION
                "CMNT: - 
                 TYPE: - Number
                 PAGE: - ARC
                    Pan  cmdID= 10076
                    min= -50  max= 50  step= 1  format= %0.0f%  div_scale= 1  preset= 0
                    Min = -50  Max = 50  Step = 1  Preset = 0  "
        ::= { kudosConv3CtrlEntries 10076 }


    i3ARCPostScalingControlTilt OBJECT-TYPE
        SYNTAX            INTEGER
        MAX-ACCESS        read-write
        STATUS            current
        DESCRIPTION
                "CMNT: - 
                 TYPE: - Number
                 PAGE: - ARC
                    Tilt  cmdID= 10077
                    min= -50  max= 50  step= 1  format= %0.0f%  div_scale= 1  preset= 0
                    Min = -50  Max = 50  Step = 1  Preset = 0  "
        ::= { kudosConv3CtrlEntries 10077 }


    i3ARCScalerConfigUsePresets OBJECT-TYPE
        SYNTAX            INTEGER { disable(0), enable(1)  }
        MAX-ACCESS        read-write
        STATUS            current
        DESCRIPTION
                "CMNT: - 
                 TYPE: - Checkbox
                 PAGE: - ARC
                    Use Presets  cmdID= 10110  "
        ::= { kudosConv3CtrlEntries 10110 }


    i3ARCScalerConfigPresetsSDInputis702 OBJECT-TYPE
        SYNTAX            INTEGER { disable(0), enable(1)  }
        MAX-ACCESS        read-write
        STATUS            current
        DESCRIPTION
                "CMNT: - 
                 TYPE: - Checkbox
                 PAGE: - Scaler Config
                    SD Input is 702  cmdID= 10080  "
        ::= { kudosConv3CtrlEntries 10080 }


    i3ARCScalerConfigPresetsSDOutputis702 OBJECT-TYPE
        SYNTAX            INTEGER { disable(0), enable(1)  }
        MAX-ACCESS        read-write
        STATUS            current
        DESCRIPTION
                "CMNT: - 
                 TYPE: - Checkbox
                 PAGE: - Scaler Config
                    SD Output is 702  cmdID= 10081  "
        ::= { kudosConv3CtrlEntries 10081 }


    i3ARCPresetsSDCrossConversionSelectStdPreset OBJECT-TYPE
        SYNTAX            INTEGER {
                            valNone(0),
                            val169LB43HC(1),
                            val169LB169Ana(2),
                            val169LB149LB(3),
                            val169Ana43HC(4),
                            val169Ana169LB(5),
                            val169Ana149LB(6)
                            }
        MAX-ACCESS        read-write
        STATUS            current
        DESCRIPTION
                "CMNT: - 
                 TYPE: - RadiobuttonList
                 PAGE: - Presets
                    Select Std Preset  cmdID= 10082
                    None  value= 0
                    16:9 LB > 4:3 HC  value= 1
                    16:9 LB > 16:9 Ana  value= 2
                    16:9 LB > 14:9 LB  value= 3
                    16:9 Ana > 4:3 HC  value= 4
                    16:9 Ana > 16:9 LB  value= 5
                    16:9 Ana > 14:9 LB  value= 6  "
        ::= { kudosConv3CtrlEntries 10082 }


    i3ARCPresetsHDCrossConversionSelectStdPreset OBJECT-TYPE
        SYNTAX            INTEGER {
                            valNone(0),
                            val149PB169VC(1),
                            val43PB169VC(2),
                            val43PB149PBVC(3)
                            }
        MAX-ACCESS        read-write
        STATUS            current
        DESCRIPTION
                "CMNT: - 
                 TYPE: - RadiobuttonList
                 PAGE: - Presets
                    Select Std Preset  cmdID= 10083
                    None  value= 0
                    14:9 PB > 16:9 VC  value= 1
                    4:3 PB > 16:9 VC  value= 2
                    4:3 PB > 14:9 PB VC  value= 3  "
        ::= { kudosConv3CtrlEntries 10083 }


    i3ARCPresetsUpConversionSelectStdPreset OBJECT-TYPE
        SYNTAX            INTEGER {
                            val43169VC(0),
                            val4343PB(1),
                            val169LB169(2),
                            val169Ana169(3),
                            val149LB149PB(4)
                            }
        MAX-ACCESS        read-write
        STATUS            current
        DESCRIPTION
                "CMNT: - 
                 TYPE: - RadiobuttonList
                 PAGE: - Presets
                    Select Std Preset  cmdID= 10084
                    4:3 > 16:9 VC  value= 0
                    4:3 > 4:3 PB  value= 1
                    16:9 LB > 16:9  value= 2
                    16:9 Ana > 16:9  value= 3
                    14:9 LB > 14:9 PB  value= 4  "
        ::= { kudosConv3CtrlEntries 10084 }


    i3ARCPresetsDownConversionSelectStdPreset OBJECT-TYPE
        SYNTAX            INTEGER {
                            val16943HC(0),
                            val169169LB(1),
                            val169169Ana(2),
                            val43PB43(3),
                            val149PB149LB(4)
                            }
        MAX-ACCESS        read-write
        STATUS            current
        DESCRIPTION
                "CMNT: - 
                 TYPE: - RadiobuttonList
                 PAGE: - Presets
                    Select Std Preset  cmdID= 10085
                    16:9 > 4:3 HC  value= 0
                    16:9 > 16:9 LB  value= 1
                    16:9 > 16:9 Ana  value= 2
                    4:3 PB > 4:3  value= 3
                    14:9 PB > 14:9 LB  value= 4  "
        ::= { kudosConv3CtrlEntries 10085 }


    i3ARCScalerConfigInputConfigInputSignallingSource OBJECT-TYPE
        SYNTAX            INTEGER {
                            valSMPTE2016(0),
                            valL23ETSI(1),
                            valL23AFD(2),
                            valVISMPTE(3),
                            valVIAFD(4)
                            }
        MAX-ACCESS        read-write
        STATUS            current
        DESCRIPTION
                "CMNT: - 
                 TYPE: - RadiobuttonList
                 PAGE: - Scaler Config
                    Input Signalling Source  cmdID= 10090
                    SMPTE 2016  value= 0
                    L23 ETSI  value= 1
                    L23 AFD  value= 2
                    VI SMPTE  value= 3
                    VI AFD  value= 4  "
        ::= { kudosConv3CtrlEntries 10090 }


    i3ARCInputConfigIfInputSignallingNotPresentForceInputFormat OBJECT-TYPE
        SYNTAX            INTEGER { disable(0), enable(1)  }
        MAX-ACCESS        read-write
        STATUS            current
        DESCRIPTION
                "CMNT: - 
                 TYPE: - Checkbox
                 PAGE: - Input Config
                    Force Input Format  cmdID= 10109  "
        ::= { kudosConv3CtrlEntries 10109 }


    i3ARCInputConfigIfInputSignallingNotPresentSDInputFormat OBJECT-TYPE
        SYNTAX            INTEGER {
                            valNormal(0),
                            valAnamorphic(1),
                            val169Letterbox(2),
                            val149Letterbox(3)
                            }
        MAX-ACCESS        read-write
        STATUS            current
        DESCRIPTION
                "CMNT: - 
                 TYPE: - RadiobuttonList
                 PAGE: - Input Config
                    SD Input Format  cmdID= 10086
                    Normal  value= 0
                    Anamorphic  value= 1
                    16:9 Letterbox  value= 2
                    14:9 Letterbox  value= 3  "
        ::= { kudosConv3CtrlEntries 10086 }


    i3ARCInputConfigIfInputSignallingNotPresentHDInputFormat OBJECT-TYPE
        SYNTAX            INTEGER {
                            valNormal(0),
                            val149Pillarbox(1),
                            val43Pillarbox(2)
                            }
        MAX-ACCESS        read-write
        STATUS            current
        DESCRIPTION
                "CMNT: - 
                 TYPE: - RadiobuttonList
                 PAGE: - Input Config
                    HD Input Format  cmdID= 10087
                    Normal  value= 0
                    14:9 Pillarbox  value= 1
                    4:3 Pillarbox  value= 2  "
        ::= { kudosConv3CtrlEntries 10087 }


    i3ARCScalerConfigOutputConfigConversionScaling OBJECT-TYPE
        SYNTAX            INTEGER {
                            valFittoHeight(0),
                            valFittoWidth(1),
                            val149(2)
                            }
        MAX-ACCESS        read-write
        STATUS            current
        DESCRIPTION
                "CMNT: - 
                 TYPE: - RadiobuttonList
                 PAGE: - Scaler Config
                    Conversion Scaling  cmdID= 10089
                    Fit to Height  value= 0
                    Fit to Width  value= 1
                    14:9  value= 2  "
        ::= { kudosConv3CtrlEntries 10089 }


    i3ARCScalerConfigOutputConfigSDOutputFormat OBJECT-TYPE
        SYNTAX            INTEGER {
                            valNormal(0),
                            valAnamorphic(1)
                            }
        MAX-ACCESS        read-write
        STATUS            current
        DESCRIPTION
                "CMNT: - 
                 TYPE: - RadiobuttonList
                 PAGE: - Scaler Config
                    SD Output Format  cmdID= 10088
                    Normal  value= 0
                    Anamorphic  value= 1  "
        ::= { kudosConv3CtrlEntries 10088 }


    i3ARCOutputSignallingConfigSMPTE2016Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10104
                    Auto  value= 0
                    Pass  value= 1
                    Force  value= 2
                    Delete  value= 3  "
        ::= { kudosConv3CtrlEntries 10104 }


    i3ARCOutputSignallingConfigSMPTE2016OutputLinePAL OBJECT-TYPE
        SYNTAX            INTEGER
        MAX-ACCESS        read-write
        STATUS            current
        DESCRIPTION
                "CMNT: - 
                 TYPE: - Number
                 PAGE: - Output Signalling Config
                    Output Line PAL  cmdID= 10332
                    min= 7  max= 22  step= 1  format= %0.0f  div_scale= 1  preset= 12
                    Min = 7  Max = 22  Step = 1  Preset = 12  "
        ::= { kudosConv3CtrlEntries 10332 }


    i3ARCOutputSignallingConfigSMPTE2016OutputLineNTSC OBJECT-TYPE
        SYNTAX            INTEGER
        MAX-ACCESS        read-write
        STATUS            current
        DESCRIPTION
                "CMNT: - 
                 TYPE: - Number
                 PAGE: - Output Signalling Config
                    Output Line NTSC  cmdID= 10333
                    min= 11  max= 19  step= 1  format= %0.0f  div_scale= 1  preset= 11
                    Min = 11  Max = 19  Step = 1  Preset = 11  "
        ::= { kudosConv3CtrlEntries 10333 }


    i3ARCOutputSignallingConfigSMPTE2016OutputLineHD OBJECT-TYPE
        SYNTAX            INTEGER
        MAX-ACCESS        read-write
        STATUS            current
        DESCRIPTION
                "CMNT: - 
                 TYPE: - Number
                 PAGE: - Output Signalling Config
                    Output Line HD  cmdID= 10331
                    min= 9  max= 20  step= 1  format= %0.0f  div_scale= 1  preset= 11
                    Min = 9  Max = 20  Step = 1  Preset = 11  "
        ::= { kudosConv3CtrlEntries 10331 }


    i3ARCOutputSignallingConfigSMPTE2016OutputLineStatus OBJECT-TYPE
        SYNTAX            RollCallString
        MAX-ACCESS        read-only
        STATUS            current
        DESCRIPTION
                "CMNT: - 
                 TYPE: - Display
                 PAGE: - Output Signalling Config
                    Output Line Status  cmdID= 10334  "
        ::= { kudosConv3CtrlEntries 10334 }


    i3ARCOutputSignallingConfigVIMode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10101
                    Auto  value= 0
                    Pass  value= 1
                    Force  value= 2
                    Delete  value= 3  "
        ::= { kudosConv3CtrlEntries 10101 }


    i3ARCOutputSignallingConfigVIOutputFormat OBJECT-TYPE
        SYNTAX            INTEGER {
                            valSMPTE(0),
                            valAFD(1)
                            }
        MAX-ACCESS        read-write
        STATUS            current
        DESCRIPTION
                "CMNT: - 
                 TYPE: - RadiobuttonList
                 PAGE: - Output Signalling Config
                    Output Format  cmdID= 10102
                    SMPTE  value= 0
                    AFD  value= 1  "
        ::= { kudosConv3CtrlEntries 10102 }


    i3ARCOutputSignallingConfigVIPassData OBJECT-TYPE
        SYNTAX            INTEGER { disable(0), enable(1)  }
        MAX-ACCESS        read-write
        STATUS            current
        DESCRIPTION
                "CMNT: - 
                 TYPE: - Checkbox
                 PAGE: - ARC
                    VI Pass Data  cmdID= 10103  "
        ::= { kudosConv3CtrlEntries 10103 }


    i3ARCOutputSignallingConfigL23Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10099
                    Auto  value= 0
                    Pass  value= 1
                    Force  value= 2
                    Delete  value= 3  "
        ::= { kudosConv3CtrlEntries 10099 }


    i3ARCOutputSignallingConfigL23OutputFormat OBJECT-TYPE
        SYNTAX            INTEGER {
                            valETSI(0),
                            valAFD(1)
                            }
        MAX-ACCESS        read-write
        STATUS            current
        DESCRIPTION
                "CMNT: - 
                 TYPE: - RadiobuttonList
                 PAGE: - Output Signalling Config
                    Output Format  cmdID= 10100
                    ETSI  value= 0
                    AFD  value= 1  "
        ::= { kudosConv3CtrlEntries 10100 }


    i3ARCOutputSignallingConfigL23InputLine OBJECT-TYPE
        SYNTAX            INTEGER
        MAX-ACCESS        read-write
        STATUS            current
        DESCRIPTION
                "CMNT: - 
                 TYPE: - Number
                 PAGE: - Output Signalling Config
                    Input Line  cmdID= 10097
                    min= 10  max= 23  step= 1  format= %0.0f  div_scale= 1  preset= 23
                    Min = 10  Max = 23  Step = 1  Preset = 23  "
        ::= { kudosConv3CtrlEntries 10097 }


    i3ARCOutputSignallingConfigL23OutputLine OBJECT-TYPE
        SYNTAX            INTEGER
        MAX-ACCESS        read-write
        STATUS            current
        DESCRIPTION
                "CMNT: - 
                 TYPE: - Number
                 PAGE: - Output Signalling Config
                    Output Line  cmdID= 10098
                    min= 10  max= 23  step= 1  format= %0.0f  div_scale= 1  preset= 23
                    Min = 10  Max = 23  Step = 1  Preset = 23  "
        ::= { kudosConv3CtrlEntries 10098 }


    i3ARCOutputSignallingConfigL23OutputLineStatus OBJECT-TYPE
        SYNTAX            RollCallString
        MAX-ACCESS        read-only
        STATUS            current
        DESCRIPTION
                "CMNT: - 
                 TYPE: - Display
                 PAGE: - Output Signalling Config
                    Output Line Status  cmdID= 10339  "
        ::= { kudosConv3CtrlEntries 10339 }


    i3ARCL23AFDUserBitsForceUserBitsValue OBJECT-TYPE
        SYNTAX            INTEGER { disable(0), enable(1)  }
        MAX-ACCESS        read-write
        STATUS            current
        DESCRIPTION
                "CMNT: - 
                 TYPE: - Checkbox
                 PAGE: - L23
                    Force User Bits Value  cmdID= 10336  "
        ::= { kudosConv3CtrlEntries 10336 }


    i3ARCL23AFDUserBitsUserBitsValue OBJECT-TYPE
        SYNTAX            INTEGER
        MAX-ACCESS        read-write
        STATUS            current
        DESCRIPTION
                "CMNT: - 
                 TYPE: - Number
                 PAGE: - L23
                    User Bits Value  cmdID= 10111
                    min= 0  max= 15  step= 1  format= %0.0f  div_scale= 1  preset= 0
                    Min = 0  Max = 15  Step = 1  Preset = 0  "
        ::= { kudosConv3CtrlEntries 10111 }


    i3ARCOutputSignallingConfigForceModeConfigSMPTE2016 OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val43AFD8(8),
                            val43AFD9(9),
                            val43AFD10(10),
                            val43AFD11(11),
                            val43AFD12(12),
                            val43AFD13(13),
                            val43AFD14(14),
                            val43AFD15(15),
                            val169AFD0(16),
                            val169AFD1(17),
                            val169AFD2(18),
                            val169AFD3(19),
                            val169AFD4(20),
                            val169AFD5(21),
                            val169AFD6(22),
                            val169AFD7(23),
                            val169AFD8(24),
                            val169AFD9(25),
                            val169AFD10(26),
                            val169AFD11(27),
                            val169AFD12(28),
                            val169AFD13(29),
                            val169AFD14(30),
                            val169AFD15(31)
                            }
        MAX-ACCESS        read-write
        STATUS            current
        DESCRIPTION
                "CMNT: - 
                 TYPE: - RadiobuttonList
                 PAGE: - Output Signalling Config
                    SMPTE 2016  cmdID= 10107
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    4:3 AFD 8  value= 8
                    4:3 AFD 9  value= 9
                    4:3 AFD 10  value= 10
                    4:3 AFD 11  value= 11
                    4:3 AFD 12  value= 12
                    4:3 AFD 13  value= 13
                    4:3 AFD 14  value= 14
                    4:3 AFD 15  value= 15
                    16:9 AFD 0  value= 16
                    16:9 AFD 1  value= 17
                    16:9 AFD 2  value= 18
                    16:9 AFD 3  value= 19
                    16:9 AFD 4  value= 20
                    16:9 AFD 5  value= 21
                    16:9 AFD 6  value= 22
                    16:9 AFD 7  value= 23
                    16:9 AFD 8  value= 24
                    16:9 AFD 9  value= 25
                    16:9 AFD 10  value= 26
                    16:9 AFD 11  value= 27
                    16:9 AFD 12  value= 28
                    16:9 AFD 13  value= 29
                    16:9 AFD 14  value= 30
                    16:9 AFD 15  value= 31  "
        ::= { kudosConv3CtrlEntries 10107 }


    i3ARCOutputSignallingConfigForceModeConfigSMPTERP186 OBJECT-TYPE
        SYNTAX            INTEGER {
                            val43(0),
                            val169(1)
                            }
        MAX-ACCESS        read-write
        STATUS            current
        DESCRIPTION
                "CMNT: - 
                 TYPE: - RadiobuttonList
                 PAGE: - Output Signalling Config
                    SMPTE RP186  cmdID= 10108
                    4:3  value= 0
                    16:9  value= 1  "
        ::= { kudosConv3CtrlEntries 10108 }


    i3ARCOutputSignallingConfigForceModeConfigAFD OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val169AFD0(8),
                            val169AFD1(9),
                            val169AFD2(10),
                            val169AFD3(11),
                            val169AFD4(12),
                            val169AFD5(13),
                            val169AFD6(14),
                            val169AFD7(15)
                            }
        MAX-ACCESS        read-write
        STATUS            current
        DESCRIPTION
                "CMNT: - 
                 TYPE: - RadiobuttonList
                 PAGE: - Output Signalling Config
                    AFD  cmdID= 10105
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    16:9 AFD 0  value= 8
                    16:9 AFD 1  value= 9
                    16:9 AFD 2  value= 10
                    16:9 AFD 3  value= 11
                    16:9 AFD 4  value= 12
                    16:9 AFD 5  value= 13
                    16:9 AFD 6  value= 14
                    16:9 AFD 7  value= 15  "
        ::= { kudosConv3CtrlEntries 10105 }


    i3ARCOutputSignallingConfigForceModeConfigETSI OBJECT-TYPE
        SYNTAX            INTEGER {
                            val43FF(0),
                            val149Centre(1),
                            val149Top(2),
                            val169Centre(3),
                            val169Top(4),
                            valGr169Centre(5),
                            val43SP149(6),
                            val169FF(7)
                            }
        MAX-ACCESS        read-write
        STATUS            current
        DESCRIPTION
                "CMNT: - 
                 TYPE: - RadiobuttonList
                 PAGE: - Output Signalling Config
                    ETSI  cmdID= 10106
                    4:3 FF  value= 0
                    14:9 Centre  value= 1
                    14:9 Top  value= 2
                    16:9 Centre  value= 3
                    16:9 Top  value= 4
                    Gr 16:9 Centre  value= 5
                    4:3 SP 14:9  value= 6
                    16:9 FF  value= 7  "
        ::= { kudosConv3CtrlEntries 10106 }


    i3AudioRoutingInputPairsStatusEmbedded1 OBJECT-TYPE
        SYNTAX            RollCallString
        MAX-ACCESS        read-only
        STATUS            current
        DESCRIPTION
                "CMNT: - 
                 TYPE: - Display
                 PAGE: - Routing
                    Embedded 1  cmdID= 10282  "
        ::= { kudosConv3CtrlEntries 10282 }


    i3AudioRoutingInputPairsStatusEmbedded2 OBJECT-TYPE
        SYNTAX            RollCallString
        MAX-ACCESS        read-only
        STATUS            current
        DESCRIPTION
                "CMNT: - 
                 TYPE: - Display
                 PAGE: - Routing
                    Embedded 2  cmdID= 10283  "
        ::= { kudosConv3CtrlEntries 10283 }


    i3AudioRoutingInputPairsStatusEmbedded3 OBJECT-TYPE
        SYNTAX            RollCallString
        MAX-ACCESS        read-only
        STATUS            current
        DESCRIPTION
                "CMNT: - 
                 TYPE: - Display
                 PAGE: - Routing
                    Embedded 3  cmdID= 10284  "
        ::= { kudosConv3CtrlEntries 10284 }


    i3AudioRoutingInputPairsStatusEmbedded4 OBJECT-TYPE
        SYNTAX            RollCallString
        MAX-ACCESS        read-only
        STATUS            current
        DESCRIPTION
                "CMNT: - 
                 TYPE: - Display
                 PAGE: - Routing
                    Embedded 4  cmdID= 10285  "
        ::= { kudosConv3CtrlEntries 10285 }


    i3AudioRoutingInputPairsStatusEmbedded5 OBJECT-TYPE
        SYNTAX            RollCallString
        MAX-ACCESS        read-only
        STATUS            current
        DESCRIPTION
                "CMNT: - 
                 TYPE: - Display
                 PAGE: - Routing
                    Embedded 5  cmdID= 10286  "
        ::= { kudosConv3CtrlEntries 10286 }


    i3AudioRoutingInputPairsStatusEmbedded6 OBJECT-TYPE
        SYNTAX            RollCallString
        MAX-ACCESS        read-only
        STATUS            current
        DESCRIPTION
                "CMNT: - 
                 TYPE: - Display
                 PAGE: - Routing
                    Embedded 6  cmdID= 10287  "
        ::= { kudosConv3CtrlEntries 10287 }


    i3AudioRoutingInputPairsStatusEmbedded7 OBJECT-TYPE
        SYNTAX            RollCallString
        MAX-ACCESS        read-only
        STATUS            current
        DESCRIPTION
                "CMNT: - 
                 TYPE: - Display
                 PAGE: - Routing
                    Embedded 7  cmdID= 10288  "
        ::= { kudosConv3CtrlEntries 10288 }


    i3AudioRoutingInputPairsStatusEmbedded8 OBJECT-TYPE
        SYNTAX            RollCallString
        MAX-ACCESS        read-only
        STATUS            current
        DESCRIPTION
                "CMNT: - 
                 TYPE: - Display
                 PAGE: - Routing
                    Embedded 8  cmdID= 10289  "
        ::= { kudosConv3CtrlEntries 10289 }


    i3AudioRoutingInputPairsStatusAES1 OBJECT-TYPE
        SYNTAX            RollCallString
        MAX-ACCESS        read-only
        STATUS            current
        DESCRIPTION
                "CMNT: - 
                 TYPE: - Display
                 PAGE: - Routing
                    AES 1  cmdID= 10290  "
        ::= { kudosConv3CtrlEntries 10290 }


    i3AudioRoutingInputPairsStatusAES2 OBJECT-TYPE
        SYNTAX            RollCallString
        MAX-ACCESS        read-only
        STATUS            current
        DESCRIPTION
                "CMNT: - 
                 TYPE: - Display
                 PAGE: - Routing
                    AES 2  cmdID= 10291  "
        ::= { kudosConv3CtrlEntries 10291 }


    i3AudioRoutingInputPairsStatusAES3 OBJECT-TYPE
        SYNTAX            RollCallString
        MAX-ACCESS        read-only
        STATUS            current
        DESCRIPTION
                "CMNT: - 
                 TYPE: - Display
                 PAGE: - Routing
                    AES 3  cmdID= 10292  "
        ::= { kudosConv3CtrlEntries 10292 }


    i3AudioRoutingInputPairsStatusAES4 OBJECT-TYPE
        SYNTAX            RollCallString
        MAX-ACCESS        read-only
        STATUS            current
        DESCRIPTION
                "CMNT: - 
                 TYPE: - Display
                 PAGE: - Routing
                    AES 4  cmdID= 10293  "
        ::= { kudosConv3CtrlEntries 10293 }


    i3AudioRoutingInputPairsStatusAnalog1 OBJECT-TYPE
        SYNTAX            RollCallString
        MAX-ACCESS        read-only
        STATUS            current
        DESCRIPTION
                "CMNT: - 
                 TYPE: - Display
                 PAGE: - Routing
                    Analog 1  cmdID= 10294  "
        ::= { kudosConv3CtrlEntries 10294 }


    i3AudioRoutingInputPairsStatusAnalog2 OBJECT-TYPE
        SYNTAX            RollCallString
        MAX-ACCESS        read-only
        STATUS            current
        DESCRIPTION
                "CMNT: - 
                 TYPE: - Display
                 PAGE: - Routing
                    Analog 2  cmdID= 10295  "
        ::= { kudosConv3CtrlEntries 10295 }


    i3AudioRoutingInputPairsStatusAnalog3 OBJECT-TYPE
        SYNTAX            RollCallString
        MAX-ACCESS        read-only
        STATUS            current
        DESCRIPTION
                "CMNT: - 
                 TYPE: - Display
                 PAGE: - Routing
                    Analog 3  cmdID= 10296  "
        ::= { kudosConv3CtrlEntries 10296 }


    i3AudioRoutingInputPairsStatusAnalog4 OBJECT-TYPE
        SYNTAX            RollCallString
        MAX-ACCESS        read-only
        STATUS            current
        DESCRIPTION
                "CMNT: - 
                 TYPE: - Display
                 PAGE: - Routing
                    Analog 4  cmdID= 10297  "
        ::= { kudosConv3CtrlEntries 10297 }


    i3AudioRoutingInputPairsStatusDolbyDecoder1 OBJECT-TYPE
        SYNTAX            RollCallString
        MAX-ACCESS        read-only
        STATUS            current
        DESCRIPTION
                "CMNT: - 
                 TYPE: - Display
                 PAGE: - Routing
                    Dolby Decoder 1  cmdID= 10298  "
        ::= { kudosConv3CtrlEntries 10298 }


    i3AudioRoutingInputPairsStatusDolbyDecoder2 OBJECT-TYPE
        SYNTAX            RollCallString
        MAX-ACCESS        read-only
        STATUS            current
        DESCRIPTION
                "CMNT: - 
                 TYPE: - Display
                 PAGE: - Routing
                    Dolby Decoder 2  cmdID= 10299  "
        ::= { kudosConv3CtrlEntries 10299 }


    i3AudioRoutingInputPairsStatusDolbyDecoder3 OBJECT-TYPE
        SYNTAX            RollCallString
        MAX-ACCESS        read-only
        STATUS            current
        DESCRIPTION
                "CMNT: - 
                 TYPE: - Display
                 PAGE: - Routing
                    Dolby Decoder 3  cmdID= 10300  "
        ::= { kudosConv3CtrlEntries 10300 }


    i3AudioRoutingInputPairsStatusDolbyDecoder4 OBJECT-TYPE
        SYNTAX            RollCallString
        MAX-ACCESS        read-only
        STATUS            current
        DESCRIPTION
                "CMNT: - 
                 TYPE: - Display
                 PAGE: - Routing
                    Dolby Decoder 4  cmdID= 10301  "
        ::= { kudosConv3CtrlEntries 10301 }


    i3AudioRoutingInputPairsStatusDolbyDownmix OBJECT-TYPE
        SYNTAX            RollCallString
        MAX-ACCESS        read-only
        STATUS            current
        DESCRIPTION
                "CMNT: - 
                 TYPE: - Display
                 PAGE: - Routing
                    Dolby Downmix  cmdID= 10302  "
        ::= { kudosConv3CtrlEntries 10302 }


    i3AudioRoutingInputPairsStatusDolbyEncoder OBJECT-TYPE
        SYNTAX            RollCallString
        MAX-ACCESS        read-only
        STATUS            current
        DESCRIPTION
                "CMNT: - 
                 TYPE: - Display
                 PAGE: - Routing
                    Dolby Encoder  cmdID= 10303  "
        ::= { kudosConv3CtrlEntries 10303 }


    i3AudioRoutingProcessPair1InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10112
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv3CtrlEntries 10112 }


    i3AudioRoutingProcessPair2InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10113
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv3CtrlEntries 10113 }


    i3AudioRoutingProcessPair3InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10114
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv3CtrlEntries 10114 }


    i3AudioRoutingProcessPair4InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10115
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv3CtrlEntries 10115 }


    i3AudioRoutingProcessPair5InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10116
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv3CtrlEntries 10116 }


    i3AudioRoutingProcessPair6InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10117
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv3CtrlEntries 10117 }


    i3AudioRoutingProcessPair7InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10118
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv3CtrlEntries 10118 }


    i3AudioRoutingProcessPair8InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10119
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv3CtrlEntries 10119 }


    i3AudioRoutingProcessPairs18StatusPair1 OBJECT-TYPE
        SYNTAX            RollCallString
        MAX-ACCESS        read-only
        STATUS            current
        DESCRIPTION
                "CMNT: - 
                 TYPE: - Display
                 PAGE: - Routing
                    Pair 1  cmdID= 10304  "
        ::= { kudosConv3CtrlEntries 10304 }


    i3AudioRoutingProcessPairs18StatusPair2 OBJECT-TYPE
        SYNTAX            RollCallString
        MAX-ACCESS        read-only
        STATUS            current
        DESCRIPTION
                "CMNT: - 
                 TYPE: - Display
                 PAGE: - Routing
                    Pair 2  cmdID= 10305  "
        ::= { kudosConv3CtrlEntries 10305 }


    i3AudioRoutingProcessPairs18StatusPair3 OBJECT-TYPE
        SYNTAX            RollCallString
        MAX-ACCESS        read-only
        STATUS            current
        DESCRIPTION
                "CMNT: - 
                 TYPE: - Display
                 PAGE: - Routing
                    Pair 3  cmdID= 10306  "
        ::= { kudosConv3CtrlEntries 10306 }


    i3AudioRoutingProcessPairs18StatusPair4 OBJECT-TYPE
        SYNTAX            RollCallString
        MAX-ACCESS        read-only
        STATUS            current
        DESCRIPTION
                "CMNT: - 
                 TYPE: - Display
                 PAGE: - Routing
                    Pair 4  cmdID= 10307  "
        ::= { kudosConv3CtrlEntries 10307 }


    i3AudioRoutingProcessPairs18StatusPair5 OBJECT-TYPE
        SYNTAX            RollCallString
        MAX-ACCESS        read-only
        STATUS            current
        DESCRIPTION
                "CMNT: - 
                 TYPE: - Display
                 PAGE: - Routing
                    Pair 5  cmdID= 10308  "
        ::= { kudosConv3CtrlEntries 10308 }


    i3AudioRoutingProcessPairs18StatusPair6 OBJECT-TYPE
        SYNTAX            RollCallString
        MAX-ACCESS        read-only
        STATUS            current
        DESCRIPTION
                "CMNT: - 
                 TYPE: - Display
                 PAGE: - Routing
                    Pair 6  cmdID= 10309  "
        ::= { kudosConv3CtrlEntries 10309 }


    i3AudioRoutingProcessPairs18StatusPair7 OBJECT-TYPE
        SYNTAX            RollCallString
        MAX-ACCESS        read-only
        STATUS            current
        DESCRIPTION
                "CMNT: - 
                 TYPE: - Display
                 PAGE: - Routing
                    Pair 7  cmdID= 10310  "
        ::= { kudosConv3CtrlEntries 10310 }


    i3AudioRoutingProcessPairs18StatusPair8 OBJECT-TYPE
        SYNTAX            RollCallString
        MAX-ACCESS        read-only
        STATUS            current
        DESCRIPTION
                "CMNT: - 
                 TYPE: - Display
                 PAGE: - Routing
                    Pair 8  cmdID= 10311  "
        ::= { kudosConv3CtrlEntries 10311 }


    i3AudioControlGainPair1L OBJECT-TYPE
        SYNTAX            INTEGER
        MAX-ACCESS        read-write
        STATUS            current
        DESCRIPTION
                "CMNT: - 
                 TYPE: - Number
                 PAGE: - Control
                    Pair 1 L  cmdID= 10120
                    min= -180  max= 180  step= 1  format= %0.1fdB  div_scale= 10  preset= 0
                    Min = -18.0dB  Max = 18.0dB  Step = 0.1dB  Preset = 0.0dB  "
        ::= { kudosConv3CtrlEntries 10120 }


    i3AudioControlGainPair1R OBJECT-TYPE
        SYNTAX            INTEGER
        MAX-ACCESS        read-write
        STATUS            current
        DESCRIPTION
                "CMNT: - 
                 TYPE: - Number
                 PAGE: - Control
                    Pair 1 R  cmdID= 10121
                    min= -180  max= 180  step= 1  format= %0.1fdB  div_scale= 10  preset= 0
                    Min = -18.0dB  Max = 18.0dB  Step = 0.1dB  Preset = 0.0dB  "
        ::= { kudosConv3CtrlEntries 10121 }


    i3AudioControlGainPair2L OBJECT-TYPE
        SYNTAX            INTEGER
        MAX-ACCESS        read-write
        STATUS            current
        DESCRIPTION
                "CMNT: - 
                 TYPE: - Number
                 PAGE: - Control
                    Pair 2 L  cmdID= 10122
                    min= -180  max= 180  step= 1  format= %0.1fdB  div_scale= 10  preset= 0
                    Min = -18.0dB  Max = 18.0dB  Step = 0.1dB  Preset = 0.0dB  "
        ::= { kudosConv3CtrlEntries 10122 }


    i3AudioControlGainPair2R OBJECT-TYPE
        SYNTAX            INTEGER
        MAX-ACCESS        read-write
        STATUS            current
        DESCRIPTION
                "CMNT: - 
                 TYPE: - Number
                 PAGE: - Control
                    Pair 2 R  cmdID= 10123
                    min= -180  max= 180  step= 1  format= %0.1fdB  div_scale= 10  preset= 0
                    Min = -18.0dB  Max = 18.0dB  Step = 0.1dB  Preset = 0.0dB  "
        ::= { kudosConv3CtrlEntries 10123 }


    i3AudioControlGainPair3L OBJECT-TYPE
        SYNTAX            INTEGER
        MAX-ACCESS        read-write
        STATUS            current
        DESCRIPTION
                "CMNT: - 
                 TYPE: - Number
                 PAGE: - Control
                    Pair 3 L  cmdID= 10124
                    min= -180  max= 180  step= 1  format= %0.1fdB  div_scale= 10  preset= 0
                    Min = -18.0dB  Max = 18.0dB  Step = 0.1dB  Preset = 0.0dB  "
        ::= { kudosConv3CtrlEntries 10124 }


    i3AudioControlGainPair3R OBJECT-TYPE
        SYNTAX            INTEGER
        MAX-ACCESS        read-write
        STATUS            current
        DESCRIPTION
                "CMNT: - 
                 TYPE: - Number
                 PAGE: - Control
                    Pair 3 R  cmdID= 10125
                    min= -180  max= 180  step= 1  format= %0.1fdB  div_scale= 10  preset= 0
                    Min = -18.0dB  Max = 18.0dB  Step = 0.1dB  Preset = 0.0dB  "
        ::= { kudosConv3CtrlEntries 10125 }


    i3AudioControlGainPair4L OBJECT-TYPE
        SYNTAX            INTEGER
        MAX-ACCESS        read-write
        STATUS            current
        DESCRIPTION
                "CMNT: - 
                 TYPE: - Number
                 PAGE: - Control
                    Pair 4 L  cmdID= 10126
                    min= -180  max= 180  step= 1  format= %0.1fdB  div_scale= 10  preset= 0
                    Min = -18.0dB  Max = 18.0dB  Step = 0.1dB  Preset = 0.0dB  "
        ::= { kudosConv3CtrlEntries 10126 }


    i3AudioControlGainPair4R OBJECT-TYPE
        SYNTAX            INTEGER
        MAX-ACCESS        read-write
        STATUS            current
        DESCRIPTION
                "CMNT: - 
                 TYPE: - Number
                 PAGE: - Control
                    Pair 4 R  cmdID= 10127
                    min= -180  max= 180  step= 1  format= %0.1fdB  div_scale= 10  preset= 0
                    Min = -18.0dB  Max = 18.0dB  Step = 0.1dB  Preset = 0.0dB  "
        ::= { kudosConv3CtrlEntries 10127 }


    i3AudioControlGainPair5L OBJECT-TYPE
        SYNTAX            INTEGER
        MAX-ACCESS        read-write
        STATUS            current
        DESCRIPTION
                "CMNT: - 
                 TYPE: - Number
                 PAGE: - Control
                    Pair 5 L  cmdID= 10128
                    min= -180  max= 180  step= 1  format= %0.1fdB  div_scale= 10  preset= 0
                    Min = -18.0dB  Max = 18.0dB  Step = 0.1dB  Preset = 0.0dB  "
        ::= { kudosConv3CtrlEntries 10128 }


    i3AudioControlGainPair5R OBJECT-TYPE
        SYNTAX            INTEGER
        MAX-ACCESS        read-write
        STATUS            current
        DESCRIPTION
                "CMNT: - 
                 TYPE: - Number
                 PAGE: - Control
                    Pair 5 R  cmdID= 10129
                    min= -180  max= 180  step= 1  format= %0.1fdB  div_scale= 10  preset= 0
                    Min = -18.0dB  Max = 18.0dB  Step = 0.1dB  Preset = 0.0dB  "
        ::= { kudosConv3CtrlEntries 10129 }


    i3AudioControlGainPair6L OBJECT-TYPE
        SYNTAX            INTEGER
        MAX-ACCESS        read-write
        STATUS            current
        DESCRIPTION
                "CMNT: - 
                 TYPE: - Number
                 PAGE: - Control
                    Pair 6 L  cmdID= 10130
                    min= -180  max= 180  step= 1  format= %0.1fdB  div_scale= 10  preset= 0
                    Min = -18.0dB  Max = 18.0dB  Step = 0.1dB  Preset = 0.0dB  "
        ::= { kudosConv3CtrlEntries 10130 }


    i3AudioControlGainPair6R OBJECT-TYPE
        SYNTAX            INTEGER
        MAX-ACCESS        read-write
        STATUS            current
        DESCRIPTION
                "CMNT: - 
                 TYPE: - Number
                 PAGE: - Control
                    Pair 6 R  cmdID= 10131
                    min= -180  max= 180  step= 1  format= %0.1fdB  div_scale= 10  preset= 0
                    Min = -18.0dB  Max = 18.0dB  Step = 0.1dB  Preset = 0.0dB  "
        ::= { kudosConv3CtrlEntries 10131 }


    i3AudioControlGainPair7L OBJECT-TYPE
        SYNTAX            INTEGER
        MAX-ACCESS        read-write
        STATUS            current
        DESCRIPTION
                "CMNT: - 
                 TYPE: - Number
                 PAGE: - Control
                    Pair 7 L  cmdID= 10132
                    min= -180  max= 180  step= 1  format= %0.1fdB  div_scale= 10  preset= 0
                    Min = -18.0dB  Max = 18.0dB  Step = 0.1dB  Preset = 0.0dB  "
        ::= { kudosConv3CtrlEntries 10132 }


    i3AudioControlGainPair7R OBJECT-TYPE
        SYNTAX            INTEGER
        MAX-ACCESS        read-write
        STATUS            current
        DESCRIPTION
                "CMNT: - 
                 TYPE: - Number
                 PAGE: - Control
                    Pair 7 R  cmdID= 10133
                    min= -180  max= 180  step= 1  format= %0.1fdB  div_scale= 10  preset= 0
                    Min = -18.0dB  Max = 18.0dB  Step = 0.1dB  Preset = 0.0dB  "
        ::= { kudosConv3CtrlEntries 10133 }


    i3AudioControlGainPair8L OBJECT-TYPE
        SYNTAX            INTEGER
        MAX-ACCESS        read-write
        STATUS            current
        DESCRIPTION
                "CMNT: - 
                 TYPE: - Number
                 PAGE: - Control
                    Pair 8 L  cmdID= 10134
                    min= -180  max= 180  step= 1  format= %0.1fdB  div_scale= 10  preset= 0
                    Min = -18.0dB  Max = 18.0dB  Step = 0.1dB  Preset = 0.0dB  "
        ::= { kudosConv3CtrlEntries 10134 }


    i3AudioControlGainPair8R OBJECT-TYPE
        SYNTAX            INTEGER
        MAX-ACCESS        read-write
        STATUS            current
        DESCRIPTION
                "CMNT: - 
                 TYPE: - Number
                 PAGE: - Control
                    Pair 8 R  cmdID= 10135
                    min= -180  max= 180  step= 1  format= %0.1fdB  div_scale= 10  preset= 0
                    Min = -18.0dB  Max = 18.0dB  Step = 0.1dB  Preset = 0.0dB  "
        ::= { kudosConv3CtrlEntries 10135 }


    i3AudioControlToneFrequency OBJECT-TYPE
        SYNTAX            INTEGER
        MAX-ACCESS        read-write
        STATUS            current
        DESCRIPTION
                "CMNT: - 
                 TYPE: - Number
                 PAGE: - Audio
                    Tone Frequency  cmdID= 10152
                    min= 100  max= 10000  step= 100  format= %0.1f KHz  div_scale= 1000  preset= 1000
                    Min = 0.1 KHz  Max = 10.0 KHz  Step = 0.1 KHz  Preset = 1.0 KHz  "
        ::= { kudosConv3CtrlEntries 10152 }


    i3AudioControlDolbyEAlignmentOffset OBJECT-TYPE
        SYNTAX            INTEGER
        MAX-ACCESS        read-write
        STATUS            current
        DESCRIPTION
                "CMNT: - 
                 TYPE: - Number
                 PAGE: - Audio
                    Dolby E Alignment Offset  cmdID= 10154
                    min= -10  max= 10  step= 1  format= %0.0f Lines  div_scale= 1  preset= 0
                    Min = -10 Lines  Max = 10 Lines  Step = 1 Lines  Preset = 0 Lines  "
        ::= { kudosConv3CtrlEntries 10154 }


    i3AudioDelayGlobalDelayPairOffsetsPair1 OBJECT-TYPE
        SYNTAX            INTEGER
        MAX-ACCESS        read-write
        STATUS            current
        DESCRIPTION
                "CMNT: - 
                 TYPE: - Number
                 PAGE: - Delay
                    Pair 1  cmdID= 10155
                    min= -40  max= 200  step= 1  format= %0.0f ms  div_scale= 1  preset= 0
                    Min = -40 ms  Max = 200 ms  Step = 1 ms  Preset = 0 ms  "
        ::= { kudosConv3CtrlEntries 10155 }


    i3AudioDelayGlobalDelayPairOffsetsPair1Total OBJECT-TYPE
        SYNTAX            RollCallString
        MAX-ACCESS        read-only
        STATUS            current
        DESCRIPTION
                "CMNT: - 
                 TYPE: - Display
                 PAGE: - Delay
                    Pair 1 Total  cmdID= 10164  "
        ::= { kudosConv3CtrlEntries 10164 }


    i3AudioDelayGlobalDelayPairOffsetsPair2 OBJECT-TYPE
        SYNTAX            INTEGER
        MAX-ACCESS        read-write
        STATUS            current
        DESCRIPTION
                "CMNT: - 
                 TYPE: - Number
                 PAGE: - Delay
                    Pair 2  cmdID= 10156
                    min= -40  max= 200  step= 1  format= %0.0f ms  div_scale= 1  preset= 0
                    Min = -40 ms  Max = 200 ms  Step = 1 ms  Preset = 0 ms  "
        ::= { kudosConv3CtrlEntries 10156 }


    i3AudioDelayGlobalDelayPairOffsetsPair2Total OBJECT-TYPE
        SYNTAX            RollCallString
        MAX-ACCESS        read-only
        STATUS            current
        DESCRIPTION
                "CMNT: - 
                 TYPE: - Display
                 PAGE: - Delay
                    Pair 2 Total  cmdID= 10165  "
        ::= { kudosConv3CtrlEntries 10165 }


    i3AudioDelayGlobalDelayPairOffsetsPair3 OBJECT-TYPE
        SYNTAX            INTEGER
        MAX-ACCESS        read-write
        STATUS            current
        DESCRIPTION
                "CMNT: - 
                 TYPE: - Number
                 PAGE: - Delay
                    Pair 3  cmdID= 10157
                    min= -40  max= 200  step= 1  format= %0.0f ms  div_scale= 1  preset= 0
                    Min = -40 ms  Max = 200 ms  Step = 1 ms  Preset = 0 ms  "
        ::= { kudosConv3CtrlEntries 10157 }


    i3AudioDelayGlobalDelayPairOffsetsPair3Total OBJECT-TYPE
        SYNTAX            RollCallString
        MAX-ACCESS        read-only
        STATUS            current
        DESCRIPTION
                "CMNT: - 
                 TYPE: - Display
                 PAGE: - Delay
                    Pair 3 Total  cmdID= 10166  "
        ::= { kudosConv3CtrlEntries 10166 }


    i3AudioDelayGlobalDelayPairOffsetsPair4 OBJECT-TYPE
        SYNTAX            INTEGER
        MAX-ACCESS        read-write
        STATUS            current
        DESCRIPTION
                "CMNT: - 
                 TYPE: - Number
                 PAGE: - Delay
                    Pair 4  cmdID= 10158
                    min= -40  max= 200  step= 1  format= %0.0f ms  div_scale= 1  preset= 0
                    Min = -40 ms  Max = 200 ms  Step = 1 ms  Preset = 0 ms  "
        ::= { kudosConv3CtrlEntries 10158 }


    i3AudioDelayGlobalDelayPairOffsetsPair4Total OBJECT-TYPE
        SYNTAX            RollCallString
        MAX-ACCESS        read-only
        STATUS            current
        DESCRIPTION
                "CMNT: - 
                 TYPE: - Display
                 PAGE: - Delay
                    Pair 4 Total  cmdID= 10167  "
        ::= { kudosConv3CtrlEntries 10167 }


    i3AudioDelayGlobalDelayPairOffsetsPair5 OBJECT-TYPE
        SYNTAX            INTEGER
        MAX-ACCESS        read-write
        STATUS            current
        DESCRIPTION
                "CMNT: - 
                 TYPE: - Number
                 PAGE: - Delay
                    Pair 5  cmdID= 10159
                    min= -40  max= 200  step= 1  format= %0.0f ms  div_scale= 1  preset= 0
                    Min = -40 ms  Max = 200 ms  Step = 1 ms  Preset = 0 ms  "
        ::= { kudosConv3CtrlEntries 10159 }


    i3AudioDelayGlobalDelayPairOffsetsPair5Total OBJECT-TYPE
        SYNTAX            RollCallString
        MAX-ACCESS        read-only
        STATUS            current
        DESCRIPTION
                "CMNT: - 
                 TYPE: - Display
                 PAGE: - Delay
                    Pair 5 Total  cmdID= 10168  "
        ::= { kudosConv3CtrlEntries 10168 }


    i3AudioDelayGlobalDelayPairOffsetsPair6 OBJECT-TYPE
        SYNTAX            INTEGER
        MAX-ACCESS        read-write
        STATUS            current
        DESCRIPTION
                "CMNT: - 
                 TYPE: - Number
                 PAGE: - Delay
                    Pair 6  cmdID= 10160
                    min= -40  max= 200  step= 1  format= %0.0f ms  div_scale= 1  preset= 0
                    Min = -40 ms  Max = 200 ms  Step = 1 ms  Preset = 0 ms  "
        ::= { kudosConv3CtrlEntries 10160 }


    i3AudioDelayGlobalDelayPairOffsetsPair6Total OBJECT-TYPE
        SYNTAX            RollCallString
        MAX-ACCESS        read-only
        STATUS            current
        DESCRIPTION
                "CMNT: - 
                 TYPE: - Display
                 PAGE: - Delay
                    Pair 6 Total  cmdID= 10169  "
        ::= { kudosConv3CtrlEntries 10169 }


    i3AudioDelayGlobalDelayPairOffsetsPair7 OBJECT-TYPE
        SYNTAX            INTEGER
        MAX-ACCESS        read-write
        STATUS            current
        DESCRIPTION
                "CMNT: - 
                 TYPE: - Number
                 PAGE: - Delay
                    Pair 7  cmdID= 10161
                    min= -40  max= 200  step= 1  format= %0.0f ms  div_scale= 1  preset= 0
                    Min = -40 ms  Max = 200 ms  Step = 1 ms  Preset = 0 ms  "
        ::= { kudosConv3CtrlEntries 10161 }


    i3AudioDelayGlobalDelayPairOffsetsPair7Total OBJECT-TYPE
        SYNTAX            RollCallString
        MAX-ACCESS        read-only
        STATUS            current
        DESCRIPTION
                "CMNT: - 
                 TYPE: - Display
                 PAGE: - Delay
                    Pair 7 Total  cmdID= 10170  "
        ::= { kudosConv3CtrlEntries 10170 }


    i3AudioDelayGlobalDelayPairOffsetsPair8 OBJECT-TYPE
        SYNTAX            INTEGER
        MAX-ACCESS        read-write
        STATUS            current
        DESCRIPTION
                "CMNT: - 
                 TYPE: - Number
                 PAGE: - Delay
                    Pair 8  cmdID= 10162
                    min= -40  max= 200  step= 1  format= %0.0f ms  div_scale= 1  preset= 0
                    Min = -40 ms  Max = 200 ms  Step = 1 ms  Preset = 0 ms  "
        ::= { kudosConv3CtrlEntries 10162 }


    i3AudioDelayGlobalDelayPairOffsetsPair8Total OBJECT-TYPE
        SYNTAX            RollCallString
        MAX-ACCESS        read-only
        STATUS            current
        DESCRIPTION
                "CMNT: - 
                 TYPE: - Display
                 PAGE: - Delay
                    Pair 8 Total  cmdID= 10171  "
        ::= { kudosConv3CtrlEntries 10171 }


    i3AudioDelayGlobalDelayAudio OBJECT-TYPE
        SYNTAX            INTEGER
        MAX-ACCESS        read-write
        STATUS            current
        DESCRIPTION
                "CMNT: - 
                 TYPE: - Number
                 PAGE: - Delay
                    Audio  cmdID= 10163
                    min= -40  max= 200  step= 1  format= %0.0f ms  div_scale= 1  preset= 0
                    Min = -40 ms  Max = 200 ms  Step = 1 ms  Preset = 0 ms  "
        ::= { kudosConv3CtrlEntries 10163 }


    i3AudioDelayGlobalDelayAudioTotal OBJECT-TYPE
        SYNTAX            RollCallString
        MAX-ACCESS        read-only
        STATUS            current
        DESCRIPTION
                "CMNT: - 
                 TYPE: - Display
                 PAGE: - Delay
                    Audio Total  cmdID= 10172  "
        ::= { kudosConv3CtrlEntries 10172 }


    i3AudioDelayGlobalDelayVideoTotal OBJECT-TYPE
        SYNTAX            RollCallString
        MAX-ACCESS        read-only
        STATUS            current
        DESCRIPTION
                "CMNT: - 
                 TYPE: - Display
                 PAGE: - Delay
                    Video Total  cmdID= 10173  "
        ::= { kudosConv3CtrlEntries 10173 }


    i3AudioShuffleOutputPair1LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10182
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10182 }


    i3AudioShuffleOutputPair1LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10198  "
        ::= { kudosConv3CtrlEntries 10198 }


    i3AudioShuffleOutputPair1LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10214
                    Use Routing  value= 0
                    Tone  value= 1
                    Silence  value= 2  "
        ::= { kudosConv3CtrlEntries 10214 }


    i3AudioShuffleOutputPair1RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10190
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10190 }


    i3AudioShuffleOutputPair1RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10206  "
        ::= { kudosConv3CtrlEntries 10206 }


    i3AudioShuffleOutputPair1RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10222
                    Use Routing  value= 0
                    Tone  value= 1
                    Silence  value= 2  "
        ::= { kudosConv3CtrlEntries 10222 }


    i3AudioShuffleOutputPair2LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10183
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10183 }


    i3AudioShuffleOutputPair2LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10199  "
        ::= { kudosConv3CtrlEntries 10199 }


    i3AudioShuffleOutputPair2LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10215
                    Use Routing  value= 0
                    Tone  value= 1
                    Silence  value= 2  "
        ::= { kudosConv3CtrlEntries 10215 }


    i3AudioShuffleOutputPair2RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10191
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10191 }


    i3AudioShuffleOutputPair2RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10207  "
        ::= { kudosConv3CtrlEntries 10207 }


    i3AudioShuffleOutputPair2RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10223
                    Use Routing  value= 0
                    Tone  value= 1
                    Silence  value= 2  "
        ::= { kudosConv3CtrlEntries 10223 }


    i3AudioShuffleOutputPair3LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10184
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10184 }


    i3AudioShuffleOutputPair3LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10200  "
        ::= { kudosConv3CtrlEntries 10200 }


    i3AudioShuffleOutputPair3LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10216
                    Use Routing  value= 0
                    Tone  value= 1
                    Silence  value= 2  "
        ::= { kudosConv3CtrlEntries 10216 }


    i3AudioShuffleOutputPair3RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10192
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10192 }


    i3AudioShuffleOutputPair3RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10208  "
        ::= { kudosConv3CtrlEntries 10208 }


    i3AudioShuffleOutputPair3RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10224
                    Use Routing  value= 0
                    Tone  value= 1
                    Silence  value= 2  "
        ::= { kudosConv3CtrlEntries 10224 }


    i3AudioShuffleOutputPair4LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10185
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10185 }


    i3AudioShuffleOutputPair4LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10201  "
        ::= { kudosConv3CtrlEntries 10201 }


    i3AudioShuffleOutputPair4LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10217
                    Use Routing  value= 0
                    Tone  value= 1
                    Silence  value= 2  "
        ::= { kudosConv3CtrlEntries 10217 }


    i3AudioShuffleOutputPair4RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10193
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10193 }


    i3AudioShuffleOutputPair4RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10209  "
        ::= { kudosConv3CtrlEntries 10209 }


    i3AudioShuffleOutputPair4RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10225
                    Use Routing  value= 0
                    Tone  value= 1
                    Silence  value= 2  "
        ::= { kudosConv3CtrlEntries 10225 }


    i3AudioShuffleOutputPair5LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10186
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10186 }


    i3AudioShuffleOutputPair5LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10202  "
        ::= { kudosConv3CtrlEntries 10202 }


    i3AudioShuffleOutputPair5LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10218
                    Use Routing  value= 0
                    Tone  value= 1
                    Silence  value= 2  "
        ::= { kudosConv3CtrlEntries 10218 }


    i3AudioShuffleOutputPair5RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10194
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10194 }


    i3AudioShuffleOutputPair5RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10210  "
        ::= { kudosConv3CtrlEntries 10210 }


    i3AudioShuffleOutputPair5RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10226
                    Use Routing  value= 0
                    Tone  value= 1
                    Silence  value= 2  "
        ::= { kudosConv3CtrlEntries 10226 }


    i3AudioShuffleOutputPair6LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10187
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10187 }


    i3AudioShuffleOutputPair6LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10203  "
        ::= { kudosConv3CtrlEntries 10203 }


    i3AudioShuffleOutputPair6LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10219
                    Use Routing  value= 0
                    Tone  value= 1
                    Silence  value= 2  "
        ::= { kudosConv3CtrlEntries 10219 }


    i3AudioShuffleOutputPair6RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10195
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10195 }


    i3AudioShuffleOutputPair6RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10211  "
        ::= { kudosConv3CtrlEntries 10211 }


    i3AudioShuffleOutputPair6RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10227
                    Use Routing  value= 0
                    Tone  value= 1
                    Silence  value= 2  "
        ::= { kudosConv3CtrlEntries 10227 }


    i3AudioShuffleOutputPair7LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10188
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10188 }


    i3AudioShuffleOutputPair7LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10204  "
        ::= { kudosConv3CtrlEntries 10204 }


    i3AudioShuffleOutputPair7LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10220
                    Use Routing  value= 0
                    Tone  value= 1
                    Silence  value= 2  "
        ::= { kudosConv3CtrlEntries 10220 }


    i3AudioShuffleOutputPair7RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10196
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10196 }


    i3AudioShuffleOutputPair7RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10212  "
        ::= { kudosConv3CtrlEntries 10212 }


    i3AudioShuffleOutputPair7RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10228
                    Use Routing  value= 0
                    Tone  value= 1
                    Silence  value= 2  "
        ::= { kudosConv3CtrlEntries 10228 }


    i3AudioShuffleOutputPair8LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10189
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10189 }


    i3AudioShuffleOutputPair8LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10205  "
        ::= { kudosConv3CtrlEntries 10205 }


    i3AudioShuffleOutputPair8LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10221
                    Use Routing  value= 0
                    Tone  value= 1
                    Silence  value= 2  "
        ::= { kudosConv3CtrlEntries 10221 }


    i3AudioShuffleOutputPair8RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10197
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv3CtrlEntries 10197 }


    i3AudioShuffleOutputPair8RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10213  "
        ::= { kudosConv3CtrlEntries 10213 }


    i3AudioShuffleOutputPair8RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10229
                    Use Routing  value= 0
                    Tone  value= 1
                    Silence  value= 2  "
        ::= { kudosConv3CtrlEntries 10229 }


    i3AudioShuffleOutputPairs18StatusPair1 OBJECT-TYPE
        SYNTAX            RollCallString
        MAX-ACCESS        read-only
        STATUS            current
        DESCRIPTION
                "CMNT: - 
                 TYPE: - Display
                 PAGE: - Shuffle
                    Pair 1  cmdID= 10174  "
        ::= { kudosConv3CtrlEntries 10174 }


    i3AudioShuffleOutputPairs18StatusPair2 OBJECT-TYPE
        SYNTAX            RollCallString
        MAX-ACCESS        read-only
        STATUS            current
        DESCRIPTION
                "CMNT: - 
                 TYPE: - Display
                 PAGE: - Shuffle
                    Pair 2  cmdID= 10175  "
        ::= { kudosConv3CtrlEntries 10175 }


    i3AudioShuffleOutputPairs18StatusPair3 OBJECT-TYPE
        SYNTAX            RollCallString
        MAX-ACCESS        read-only
        STATUS            current
        DESCRIPTION
                "CMNT: - 
                 TYPE: - Display
                 PAGE: - Shuffle
                    Pair 3  cmdID= 10176  "
        ::= { kudosConv3CtrlEntries 10176 }


    i3AudioShuffleOutputPairs18StatusPair4 OBJECT-TYPE
        SYNTAX            RollCallString
        MAX-ACCESS        read-only
        STATUS            current
        DESCRIPTION
                "CMNT: - 
                 TYPE: - Display
                 PAGE: - Shuffle
                    Pair 4  cmdID= 10177  "
        ::= { kudosConv3CtrlEntries 10177 }


    i3AudioShuffleOutputPairs18StatusPair5 OBJECT-TYPE
        SYNTAX            RollCallString
        MAX-ACCESS        read-only
        STATUS            current
        DESCRIPTION
                "CMNT: - 
                 TYPE: - Display
                 PAGE: - Shuffle
                    Pair 5  cmdID= 10178  "
        ::= { kudosConv3CtrlEntries 10178 }


    i3AudioShuffleOutputPairs18StatusPair6 OBJECT-TYPE
        SYNTAX            RollCallString
        MAX-ACCESS        read-only
        STATUS            current
        DESCRIPTION
                "CMNT: - 
                 TYPE: - Display
                 PAGE: - Shuffle
                    Pair 6  cmdID= 10179  "
        ::= { kudosConv3CtrlEntries 10179 }


    i3AudioShuffleOutputPairs18StatusPair7 OBJECT-TYPE
        SYNTAX            RollCallString
        MAX-ACCESS        read-only
        STATUS            current
        DESCRIPTION
                "CMNT: - 
                 TYPE: - Display
                 PAGE: - Shuffle
                    Pair 7  cmdID= 10180  "
        ::= { kudosConv3CtrlEntries 10180 }


    i3AudioShuffleOutputPairs18StatusPair8 OBJECT-TYPE
        SYNTAX            RollCallString
        MAX-ACCESS        read-only
        STATUS            current
        DESCRIPTION
                "CMNT: - 
                 TYPE: - Display
                 PAGE: - Shuffle
                    Pair 8  cmdID= 10181  "
        ::= { kudosConv3CtrlEntries 10181 }


    i3TimecodeSourceHD OBJECT-TYPE
        SYNTAX            INTEGER {
                            valLTC(0),
                            valVITC(1)
                            }
        MAX-ACCESS        read-write
        STATUS            current
        DESCRIPTION
                "CMNT: - 
                 TYPE: - RadiobuttonList
                 PAGE: - Timecode
                    Source (HD)  cmdID= 10230
                    LTC  value= 0
                    VITC  value= 1  "
        ::= { kudosConv3CtrlEntries 10230 }


    i3TimecodeSourceSD OBJECT-TYPE
        SYNTAX            INTEGER {
                            valVITC(0),
                            valATCLTC(1),
                            valATCVITC(2)
                            }
        MAX-ACCESS        read-write
        STATUS            current
        DESCRIPTION
                "CMNT: - 
                 TYPE: - RadiobuttonList
                 PAGE: - Timecode
                    Source (SD)  cmdID= 10231
                    VITC  value= 0
                    ATC LTC  value= 1
                    ATC VITC  value= 2  "
        ::= { kudosConv3CtrlEntries 10231 }


    i3TimecodeStatus OBJECT-TYPE
        SYNTAX            RollCallString
        MAX-ACCESS        read-only
        STATUS            current
        DESCRIPTION
                "CMNT: - 
                 TYPE: - Display
                 PAGE: - Timecode
                    Status  cmdID= 10239  "
        ::= { kudosConv3CtrlEntries 10239 }


    i3TimecodeMode OBJECT-TYPE
        SYNTAX            INTEGER {
                            valFollowInput(0),
                            valGenerate(1),
                            valInputTrigger(2)
                            }
        MAX-ACCESS        read-write
        STATUS            current
        DESCRIPTION
                "CMNT: - 
                 TYPE: - RadiobuttonList
                 PAGE: - Timecode
                    Mode  cmdID= 10232
                    Follow Input  value= 0
                    Generate  value= 1
                    Input Trigger  value= 2  "
        ::= { kudosConv3CtrlEntries 10232 }


    i3TimecodeVITCEnable OBJECT-TYPE
        SYNTAX            INTEGER { disable(0), enable(1)  }
        MAX-ACCESS        read-write
        STATUS            current
        DESCRIPTION
                "CMNT: - 
                 TYPE: - Checkbox
                 PAGE: - Timecode
                    VITC Enable  cmdID= 10238  "
        ::= { kudosConv3CtrlEntries 10238 }


    i3TimecodeOutputLine525 OBJECT-TYPE
        SYNTAX            INTEGER
        MAX-ACCESS        read-write
        STATUS            current
        DESCRIPTION
                "CMNT: - 
                 TYPE: - Number
                 PAGE: - Timecode
                    Output Line (525)  cmdID= 10233
                    min= 11  max= 17  step= 1  format= %0.0f  div_scale= 1  preset= 14
                    Min = 11  Max = 17  Step = 1  Preset = 14  "
        ::= { kudosConv3CtrlEntries 10233 }


    i3TimecodeOutputLine625 OBJECT-TYPE
        SYNTAX            INTEGER
        MAX-ACCESS        read-write
        STATUS            current
        DESCRIPTION
                "CMNT: - 
                 TYPE: - Number
                 PAGE: - Timecode
                    Output Line (625)  cmdID= 10234
                    min= 7  max= 20  step= 1  format= %0.0f  div_scale= 1  preset= 19
                    Min = 7  Max = 20  Step = 1  Preset = 19  "
        ::= { kudosConv3CtrlEntries 10234 }


    i3TimecodeOutputLineStatus OBJECT-TYPE
        SYNTAX            RollCallString
        MAX-ACCESS        read-only
        STATUS            current
        DESCRIPTION
                "CMNT: - 
                 TYPE: - Display
                 PAGE: - Timecode
                    Output Line Status  cmdID= 10338  "
        ::= { kudosConv3CtrlEntries 10338 }


    i3TimecodeInputTriggerEntry OBJECT-TYPE
        SYNTAX            RollCallString
        MAX-ACCESS        read-write
        STATUS            current
        DESCRIPTION
                "CMNT: - 
                 TYPE: - Editstring
                 PAGE: - Timecode
                    Input Trigger Entry  cmdID= 10240
                    preset= 00:00:00:00"
        ::= { kudosConv3CtrlEntries 10240 }


    i3TimecodeOutputTimecodeEntry OBJECT-TYPE
        SYNTAX            RollCallString
        MAX-ACCESS        read-write
        STATUS            current
        DESCRIPTION
                "CMNT: - 
                 TYPE: - Editstring
                 PAGE: - Timecode
                    Output Timecode Entry  cmdID= 10241
                    preset= 00:00:00:00"
        ::= { kudosConv3CtrlEntries 10241 }


    i3TimecodeEntry OBJECT-TYPE
        SYNTAX            RollCallString
        MAX-ACCESS        read-write
        STATUS            current
        DESCRIPTION
                "CMNT: - 
                 TYPE: - Editstring
                 PAGE: - Timecode
                    Timecode Entry  cmdID= 10237
                    preset= 00:00:00:00"
        ::= { kudosConv3CtrlEntries 10237 }


    i3TimecodeLoad OBJECT-TYPE
        SYNTAX            INTEGER { noAction(0),valTimecodeLoad(1) }
        MAX-ACCESS        read-write
        STATUS            current
        DESCRIPTION
                "CMNT: - 
                 TYPE: - Button
                 PAGE: - Timecode
                    Timecode Load  cmdID= 10316
                    value= 1  "
        ::= { kudosConv3CtrlEntries 10316 }


    i3TimecodeOnTimecodeLoss OBJECT-TYPE
        SYNTAX            INTEGER {
                            valFreeze(0),
                            valFreeRun(1)
                            }
        MAX-ACCESS        read-write
        STATUS            current
        DESCRIPTION
                "CMNT: - 
                 TYPE: - RadiobuttonList
                 PAGE: - Timecode
                    On Timecode Loss  cmdID= 10235
                    Freeze  value= 0
                    Free Run  value= 1  "
        ::= { kudosConv3CtrlEntries 10235 }


    i3TimecodeNondropFrame OBJECT-TYPE
        SYNTAX            INTEGER { disable(0), enable(1)  }
        MAX-ACCESS        read-write
        STATUS            current
        DESCRIPTION
                "CMNT: - 
                 TYPE: - Checkbox
                 PAGE: - Timecode
                    Non-drop Frame  cmdID= 10236  "
        ::= { kudosConv3CtrlEntries 10236 }


    i3MetadataClosedCaptionsInputStatus OBJECT-TYPE
        SYNTAX            RollCallString
        MAX-ACCESS        read-only
        STATUS            current
        DESCRIPTION
                "CMNT: - 
                 TYPE: - Display
                 PAGE: - Metadata
                    Input Status  cmdID= 10250  "
        ::= { kudosConv3CtrlEntries 10250 }


    i3MetadataClosedCaptionsCEA608OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-608 Output Enable  cmdID= 10242
                    Off  value= 0
                    On  value= 1  "
        ::= { kudosConv3CtrlEntries 10242 }


    i3MetadataClosedCaptionsCEA708OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-708 Output Enable  cmdID= 10243
                    Off  value= 0
                    On  value= 1  "
        ::= { kudosConv3CtrlEntries 10243 }


    i3MetadataClosedCaptionsCEA708OutputLine OBJECT-TYPE
        SYNTAX            INTEGER
        MAX-ACCESS        read-write
        STATUS            current
        DESCRIPTION
                "CMNT: - 
                 TYPE: - Number
                 PAGE: - Metadata
                    CEA-708 Output Line  cmdID= 10244
                    min= 8  max= 20  step= 1  format= %0.0f  div_scale= 1  preset= 10
                    Min = 8  Max = 20  Step = 1  Preset = 10  "
        ::= { kudosConv3CtrlEntries 10244 }


    i3MetadataClosedCaptionsCEA708OutputLineStatus OBJECT-TYPE
        SYNTAX            RollCallString
        MAX-ACCESS        read-only
        STATUS            current
        DESCRIPTION
                "CMNT: - 
                 TYPE: - Display
                 PAGE: - Metadata
                    CEA-708 Output Line Status  cmdID= 10252  "
        ::= { kudosConv3CtrlEntries 10252 }


    i3MetadataTeletext625CaptionsSource OBJECT-TYPE
        SYNTAX            INTEGER {
                            valWST(0),
                            valCEAn608(1)
                            }
        MAX-ACCESS        read-write
        STATUS            current
        DESCRIPTION
                "CMNT: - 
                 TYPE: - RadiobuttonList
                 PAGE: - Metadata
                    625 Captions Source  cmdID= 10337
                    WST  value= 0
                    CEA-608  value= 1  "
        ::= { kudosConv3CtrlEntries 10337 }


    i3MetadataTeletextPresentStatus OBJECT-TYPE
        SYNTAX            RollCallString
        MAX-ACCESS        read-only
        STATUS            current
        DESCRIPTION
                "CMNT: - 
                 TYPE: - Display
                 PAGE: - Metadata
                    Teletext Present Status  cmdID= 10251  "
        ::= { kudosConv3CtrlEntries 10251 }


    i3MetadataTeletextWSTInputLine OBJECT-TYPE
        SYNTAX            INTEGER
        MAX-ACCESS        read-write
        STATUS            current
        DESCRIPTION
                "CMNT: - 
                 TYPE: - Number
                 PAGE: - Metadata
                    WST Input Line  cmdID= 10245
                    min= 7  max= 22  step= 1  format= %0.0f  div_scale= 1  preset= 10
                    Min = 7  Max = 22  Step = 1  Preset = 10  "
        ::= { kudosConv3CtrlEntries 10245 }


    i3MetadataTeletextWSTOutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    WST Output Enable  cmdID= 10246
                    Off  value= 0
                    On  value= 1  "
        ::= { kudosConv3CtrlEntries 10246 }


    i3MetadataTeletextWSTOutputLine OBJECT-TYPE
        SYNTAX            INTEGER
        MAX-ACCESS        read-write
        STATUS            current
        DESCRIPTION
                "CMNT: - 
                 TYPE: - Number
                 PAGE: - Metadata
                    WST Output Line  cmdID= 10253
                    min= 7  max= 22  step= 1  format= %0.0f  div_scale= 1  preset= 10
                    Min = 7  Max = 22  Step = 1  Preset = 10  "
        ::= { kudosConv3CtrlEntries 10253 }


    i3MetadataTeletextWSTOutputLineStatus OBJECT-TYPE
        SYNTAX            RollCallString
        MAX-ACCESS        read-only
        STATUS            current
        DESCRIPTION
                "CMNT: - 
                 TYPE: - Display
                 PAGE: - Metadata
                    WST Output Line Status  cmdID= 10341  "
        ::= { kudosConv3CtrlEntries 10341 }


    i3MetadataTeletextRDD08InputLine OBJECT-TYPE
        SYNTAX            INTEGER
        MAX-ACCESS        read-write
        STATUS            current
        DESCRIPTION
                "CMNT: - 
                 TYPE: - Number
                 PAGE: - Metadata
                    RDD-08 Input Line  cmdID= 10248
                    min= 8  max= 20  step= 1  format= %0.0f  div_scale= 1  preset= 10
                    Min = 8  Max = 20  Step = 1  Preset = 10  "
        ::= { kudosConv3CtrlEntries 10248 }


    i3MetadataTeletextRDD08OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    RDD-08 Output Enable  cmdID= 10247
                    Off  value= 0
                    On  value= 1  "
        ::= { kudosConv3CtrlEntries 10247 }


    i3MetadataTeletextRDD08OutputLine OBJECT-TYPE
        SYNTAX            INTEGER
        MAX-ACCESS        read-write
        STATUS            current
        DESCRIPTION
                "CMNT: - 
                 TYPE: - Number
                 PAGE: - Metadata
                    RDD-08 Output Line  cmdID= 10249
                    min= 8  max= 20  step= 1  format= %0.0f  div_scale= 1  preset= 10
                    Min = 8  Max = 20  Step = 1  Preset = 10  "
        ::= { kudosConv3CtrlEntries 10249 }


    i3MetadataTeletextRDD08OutputLineStatus OBJECT-TYPE
        SYNTAX            RollCallString
        MAX-ACCESS        read-only
        STATUS            current
        DESCRIPTION
                "CMNT: - 
                 TYPE: - Display
                 PAGE: - Metadata
                    RDD-08 Output Line Status  cmdID= 10340  "
        ::= { kudosConv3CtrlEntries 10340 }


    i3MemorySelect OBJECT-TYPE
        SYNTAX            INTEGER {
                            valMemory1(1),
                            valMemory2(2),
                            valMemory3(3),
                            valMemory4(4),
                            valMemory5(5),
                            valMemory6(6),
                            valMemory7(7),
                            valMemory8(8)
                            }
        MAX-ACCESS        read-write
        STATUS            current
        DESCRIPTION
                "CMNT: - 
                 TYPE: - RadiobuttonList
                 PAGE: - Memory
                    Memory Select  cmdID= 10254
                    Memory 1  value= 1
                    Memory 2  value= 2
                    Memory 3  value= 3
                    Memory 4  value= 4
                    Memory 5  value= 5
                    Memory 6  value= 6
                    Memory 7  value= 7
                    Memory 8  value= 8  "
        ::= { kudosConv3CtrlEntries 10254 }


    i3MemorySaveMemory OBJECT-TYPE
        SYNTAX            INTEGER { noAction(0),valSaveMemory(1) }
        MAX-ACCESS        read-write
        STATUS            current
        DESCRIPTION
                "CMNT: - 
                 TYPE: - Button
                 PAGE: - Memory
                    Save Memory  cmdID= 10255
                    value= 1  "
        ::= { kudosConv3CtrlEntries 10255 }


    i3MemoryRecallMemory OBJECT-TYPE
        SYNTAX            INTEGER { noAction(0),valRecallMemory(1) }
        MAX-ACCESS        read-write
        STATUS            current
        DESCRIPTION
                "CMNT: - 
                 TYPE: - Button
                 PAGE: - Memory
                    Recall Memory  cmdID= 10256
                    value= 1  "
        ::= { kudosConv3CtrlEntries 10256 }


    i3MemoryResettoDefaults OBJECT-TYPE
        SYNTAX            INTEGER { noAction(0),valResettoDefaults(1) }
        MAX-ACCESS        read-write
        STATUS            current
        DESCRIPTION
                "CMNT: - 
                 TYPE: - Button
                 PAGE: - Memory
                    Reset to Defaults  cmdID= 10258
                    value= 1  "
        ::= { kudosConv3CtrlEntries 10258 }


    i3MemoryNameChangeName OBJECT-TYPE
        SYNTAX            RollCallString
        MAX-ACCESS        read-write
        STATUS            current
        DESCRIPTION
                "CMNT: - 
                 TYPE: - Editstring
                 PAGE: - Memory
                    Change Name  cmdID= 10257
                    preset= "
        ::= { kudosConv3CtrlEntries 10257 }


    i3RollCallUnitName OBJECT-TYPE
        SYNTAX            RollCallString
        MAX-ACCESS        read-write
        STATUS            current
        DESCRIPTION
                "CMNT: - 
                 TYPE: - Editstring
                 PAGE: - RollCall
                    Unit Name  cmdID= 10312
                    preset= IQP"
        ::= { kudosConv3CtrlEntries 10312 }


    i3SNMPControlEnable OBJECT-TYPE
        SYNTAX            INTEGER { disable(0), enable(1)  }
        MAX-ACCESS        read-write
        STATUS            current
        DESCRIPTION
                "CMNT: - 
                 TYPE: - Checkbox
                 PAGE: - SNMP
                    Control Enable  cmdID= 10342  "
        ::= { kudosConv3CtrlEntries 10342 }


    i3SNMPTrapsEnable OBJECT-TYPE
        SYNTAX            INTEGER { disable(0), enable(1)  }
        MAX-ACCESS        read-write
        STATUS            current
        DESCRIPTION
                "CMNT: - 
                 TYPE: - Checkbox
                 PAGE: - SNMP
                    Traps Enable  cmdID= 10343  "
        ::= { kudosConv3CtrlEntries 10343 }


    i3SNMPResendTraps OBJECT-TYPE
        SYNTAX            INTEGER { noAction(0),valResendTraps(1) }
        MAX-ACCESS        read-write
        STATUS            current
        DESCRIPTION
                "CMNT: - 
                 TYPE: - Button
                 PAGE: - SNMP
                    Resend Traps  cmdID= 10344
                    value= 1  "
        ::= { kudosConv3CtrlEntries 10344 }


    i3LoggingInputIdentEnable OBJECT-TYPE
        SYNTAX            INTEGER { disable(0), enable(1)  }
        MAX-ACCESS        read-write
        STATUS            current
        DESCRIPTION
                "CMNT: - 
                 TYPE: - Checkbox
                 PAGE: - Logging
                    Input Ident Enable  cmdID= 10261  "
        ::= { kudosConv3CtrlEntries 10261 }


    i3LoggingInputStandardEnable OBJECT-TYPE
        SYNTAX            INTEGER { disable(0), enable(1)  }
        MAX-ACCESS        read-write
        STATUS            current
        DESCRIPTION
                "CMNT: - 
                 TYPE: - Checkbox
                 PAGE: - Logging
                    Input Standard Enable  cmdID= 10259  "
        ::= { kudosConv3CtrlEntries 10259 }


    i3LoggingInputStateEnable OBJECT-TYPE
        SYNTAX            INTEGER { disable(0), enable(1)  }
        MAX-ACCESS        read-write
        STATUS            current
        DESCRIPTION
                "CMNT: - 
                 TYPE: - Checkbox
                 PAGE: - Logging
                    Input State Enable  cmdID= 10263  "
        ::= { kudosConv3CtrlEntries 10263 }


    i3LoggingOutputStandardEnable OBJECT-TYPE
        SYNTAX            INTEGER { disable(0), enable(1)  }
        MAX-ACCESS        read-write
        STATUS            current
        DESCRIPTION
                "CMNT: - 
                 TYPE: - Checkbox
                 PAGE: - Logging
                    Output Standard Enable  cmdID= 10267  "
        ::= { kudosConv3CtrlEntries 10267 }


    i3LoggingOutputIdentEnable OBJECT-TYPE
        SYNTAX            INTEGER { disable(0), enable(1)  }
        MAX-ACCESS        read-write
        STATUS            current
        DESCRIPTION
                "CMNT: - 
                 TYPE: - Checkbox
                 PAGE: - Logging
                    Output Ident Enable  cmdID= 10265  "
        ::= { kudosConv3CtrlEntries 10265 }


    i3LoggingTimecodeEnable OBJECT-TYPE
        SYNTAX            INTEGER { disable(0), enable(1)  }
        MAX-ACCESS        read-write
        STATUS            current
        DESCRIPTION
                "CMNT: - 
                 TYPE: - Checkbox
                 PAGE: - Logging
                    Timecode Enable  cmdID= 10346  "
        ::= { kudosConv3CtrlEntries 10346 }


    i3LoggingClosedCaptionInputEnable OBJECT-TYPE
        SYNTAX            INTEGER { disable(0), enable(1)  }
        MAX-ACCESS        read-write
        STATUS            current
        DESCRIPTION
                "CMNT: - 
                 TYPE: - Checkbox
                 PAGE: - Logging
                    Closed Caption Input Enable  cmdID= 10348  "
        ::= { kudosConv3CtrlEntries 10348 }


    i3LoggingWSTEnable OBJECT-TYPE
        SYNTAX            INTEGER { disable(0), enable(1)  }
        MAX-ACCESS        read-write
        STATUS            current
        DESCRIPTION
                "CMNT: - 
                 TYPE: - Checkbox
                 PAGE: - Logging
                    WST Enable  cmdID= 10350  "
        ::= { kudosConv3CtrlEntries 10350 }


    i3LoggingRDD08Enable OBJECT-TYPE
        SYNTAX            INTEGER { disable(0), enable(1)  }
        MAX-ACCESS        read-write
        STATUS            current
        DESCRIPTION
                "CMNT: - 
                 TYPE: - Checkbox
                 PAGE: - Logging
                    RDD08 Enable  cmdID= 10352  "
        ::= { kudosConv3CtrlEntries 10352 }


    i3LoggingCEA708Enable OBJECT-TYPE
        SYNTAX            INTEGER { disable(0), enable(1)  }
        MAX-ACCESS        read-write
        STATUS            current
        DESCRIPTION
                "CMNT: - 
                 TYPE: - Checkbox
                 PAGE: - Logging
                    CEA-708 Enable  cmdID= 10354  "
        ::= { kudosConv3CtrlEntries 10354 }


    i3LoggingSMPTE2016Enable OBJECT-TYPE
        SYNTAX            INTEGER { disable(0), enable(1)  }
        MAX-ACCESS        read-write
        STATUS            current
        DESCRIPTION
                "CMNT: - 
                 TYPE: - Checkbox
                 PAGE: - Logging
                    SMPTE 2016 Enable  cmdID= 10356  "
        ::= { kudosConv3CtrlEntries 10356 }


    i3LoggingSMPTEL23Enable OBJECT-TYPE
        SYNTAX            INTEGER { disable(0), enable(1)  }
        MAX-ACCESS        read-write
        STATUS            current
        DESCRIPTION
                "CMNT: - 
                 TYPE: - Checkbox
                 PAGE: - Logging
                    SMPTE L23 Enable  cmdID= 10358  "
        ::= { kudosConv3CtrlEntries 10358 }


    i3LoggingSignallingEnable OBJECT-TYPE
        SYNTAX            INTEGER { disable(0), enable(1)  }
        MAX-ACCESS        read-write
        STATUS            current
        DESCRIPTION
                "CMNT: - 
                 TYPE: - Checkbox
                 PAGE: - Logging
                    Signalling Enable  cmdID= 10360  "
        ::= { kudosConv3CtrlEntries 10360 }
    kudosConv3StatEntries OBJECT IDENTIFIER ::= { kudosIQP 12 }


    i3LoggingInputIdentStatus OBJECT-TYPE
        SYNTAX            RollCallString
        MAX-ACCESS        read-only
        STATUS            current
        DESCRIPTION
                "CMNT: - Channel Name
                 TYPE: - Display
                 PAGE: - Logging
                    Input Ident Status  cmdID= 10262  "
        ::= { kudosConv3StatEntries 10262 }


    i3LoggingInputStandardStatus OBJECT-TYPE
        SYNTAX            RollCallString
        MAX-ACCESS        read-only
        STATUS            current
        DESCRIPTION
                "CMNT: - WARN: or format
                 TYPE: - Display
                 PAGE: - Logging
                    Input Standard Status  cmdID= 10260  "
        ::= { kudosConv3StatEntries 10260 }


    i3LoggingInputStateStatus OBJECT-TYPE
        SYNTAX            RollCallString
        MAX-ACCESS        read-only
        STATUS            current
        DESCRIPTION
                "CMNT: - WARN: or OK
                 TYPE: - Display
                 PAGE: - Logging
                    Input State Status  cmdID= 10264  "
        ::= { kudosConv3StatEntries 10264 }


    i3LoggingOutputStandardStatus OBJECT-TYPE
        SYNTAX            RollCallString
        MAX-ACCESS        read-only
        STATUS            current
        DESCRIPTION
                "CMNT: - WARN: or format
                 TYPE: - Display
                 PAGE: - Logging
                    Output Standard Status  cmdID= 10268  "
        ::= { kudosConv3StatEntries 10268 }


    i3LoggingOutputIdentStatus OBJECT-TYPE
        SYNTAX            RollCallString
        MAX-ACCESS        read-only
        STATUS            current
        DESCRIPTION
                "CMNT: - Channel Name
                 TYPE: - Display
                 PAGE: - Logging
                    Output Ident Status  cmdID= 10266  "
        ::= { kudosConv3StatEntries 10266 }


    i3LoggingTimeCodeStatus OBJECT-TYPE
        SYNTAX            RollCallString
        MAX-ACCESS        read-only
        STATUS            current
        DESCRIPTION
                "CMNT: - LOST or OK
                 TYPE: - Display
                 PAGE: - Logging
                    TimeCode Status  cmdID= 10347  "
        ::= { kudosConv3StatEntries 10347 }


    i3LoggingClosedCaptionInputStatus OBJECT-TYPE
        SYNTAX            RollCallString
        MAX-ACCESS        read-only
        STATUS            current
        DESCRIPTION
                "CMNT: - LOST or OK
                 TYPE: - Display
                 PAGE: - Logging
                    Closed Caption Input Status  cmdID= 10349  "
        ::= { kudosConv3StatEntries 10349 }


    i3LoggingWSTOutputLineStatus OBJECT-TYPE
        SYNTAX            RollCallString
        MAX-ACCESS        read-only
        STATUS            current
        DESCRIPTION
                "CMNT: - off or line number
                 TYPE: - Display
                 PAGE: - Logging
                    WST Output Line Status  cmdID= 10351  "
        ::= { kudosConv3StatEntries 10351 }


    i3LoggingRDD08OutputLineStatus OBJECT-TYPE
        SYNTAX            RollCallString
        MAX-ACCESS        read-only
        STATUS            current
        DESCRIPTION
                "CMNT: - off or line number
                 TYPE: - Display
                 PAGE: - Logging
                    RDD08 Output Line Status  cmdID= 10353  "
        ::= { kudosConv3StatEntries 10353 }


    i3LoggingCEA708OutputLineStatus OBJECT-TYPE
        SYNTAX            RollCallString
        MAX-ACCESS        read-only
        STATUS            current
        DESCRIPTION
                "CMNT: - off or line number
                 TYPE: - Display
                 PAGE: - Logging
                    CEA-708 Output Line Status  cmdID= 10355  "
        ::= { kudosConv3StatEntries 10355 }


    i3Logging2016OutputLineStatus OBJECT-TYPE
        SYNTAX            RollCallString
        MAX-ACCESS        read-only
        STATUS            current
        DESCRIPTION
                "CMNT: - off or line number
                 TYPE: - Display
                 PAGE: - Logging
                    2016 Output Line Status  cmdID= 10357  "
        ::= { kudosConv3StatEntries 10357 }


    i3LoggingL23OutputLineStatus OBJECT-TYPE
        SYNTAX            RollCallString
        MAX-ACCESS        read-only
        STATUS            current
        DESCRIPTION
                "CMNT: - off or line number
                 TYPE: - Display
                 PAGE: - Logging
                    L23 Output Line Status  cmdID= 10359  "
        ::= { kudosConv3StatEntries 10359 }


    i3LoggingSignallingStatus OBJECT-TYPE
        SYNTAX            RollCallString
        MAX-ACCESS        read-only
        STATUS            current
        DESCRIPTION
                "CMNT: - NONE or OK
                 TYPE: - Display
                 PAGE: - Logging
                    Signalling Status  cmdID= 10361  "
        ::= { kudosConv3StatEntries 10361 }


    i3LoggingMSGStatus OBJECT-TYPE
        SYNTAX            RollCallString
        MAX-ACCESS        read-only
        STATUS            current
        DESCRIPTION
                "CMNT: - 
                 TYPE: - Display
                 PAGE: - Logging
                    MSG Status  cmdID= 10269  "
        ::= { kudosConv3StatEntries 10269 }
    kudosConv4NoteEntries OBJECT IDENTIFIER ::= { kudosIQP 13 }


    i4InputIdentStatus NOTIFICATION-TYPE
        OBJECTS            { i4LoggingInputIdentStatus } 
        STATUS            current
        DESCRIPTION
                "CMNT: - Channel Name
                 TYPE: - Display
                 PAGE: - Logging
                    Input Ident Status  cmdID= 5000  "
        ::= { kudosConv4NoteEntries 5000 }


    i4InputStandardStatus NOTIFICATION-TYPE
        OBJECTS            { i4LoggingInputStandardStatus } 
        STATUS            current
        DESCRIPTION
                "CMNT: - WARN: or format
                 TYPE: - Display
                 PAGE: - Logging
                    Input Standard Status  cmdID= 5001  "
        ::= { kudosConv4NoteEntries 5001 }


    i4InputStateStatus NOTIFICATION-TYPE
        OBJECTS            { i4LoggingInputStateStatus } 
        STATUS            current
        DESCRIPTION
                "CMNT: - WARN: or OK
                 TYPE: - Display
                 PAGE: - Logging
                    Input State Status  cmdID= 5002  "
        ::= { kudosConv4NoteEntries 5002 }


    i4OutputStandardStatus NOTIFICATION-TYPE
        OBJECTS            { i4LoggingOutputStandardStatus } 
        STATUS            current
        DESCRIPTION
                "CMNT: - WARN: or format
                 TYPE: - Display
                 PAGE: - Logging
                    Output Standard Status  cmdID= 5003  "
        ::= { kudosConv4NoteEntries 5003 }


    i4OutputIdentStatus NOTIFICATION-TYPE
        OBJECTS            { i4LoggingOutputIdentStatus } 
        STATUS            current
        DESCRIPTION
                "CMNT: - Channel Name
                 TYPE: - Display
                 PAGE: - Logging
                    Output Ident Status  cmdID= 5004  "
        ::= { kudosConv4NoteEntries 5004 }


    i4TimeCodeStatus NOTIFICATION-TYPE
        OBJECTS            { i4LoggingTimeCodeStatus } 
        STATUS            current
        DESCRIPTION
                "CMNT: - LOST or OK
                 TYPE: - Display
                 PAGE: - Logging
                    TimeCode Status  cmdID= 5005  "
        ::= { kudosConv4NoteEntries 5005 }


    i4ClosedCaptionInputStatus NOTIFICATION-TYPE
        OBJECTS            { i4LoggingClosedCaptionInputStatus } 
        STATUS            current
        DESCRIPTION
                "CMNT: - LOST or OK
                 TYPE: - Display
                 PAGE: - Logging
                    Closed Caption Input Status  cmdID= 5006  "
        ::= { kudosConv4NoteEntries 5006 }


    i4WSTOutputLineStatus NOTIFICATION-TYPE
        OBJECTS            { i4LoggingWSTOutputLineStatus } 
        STATUS            current
        DESCRIPTION
                "CMNT: - off or line number
                 TYPE: - Display
                 PAGE: - Logging
                    WST Output Line Status  cmdID= 5007  "
        ::= { kudosConv4NoteEntries 5007 }


    i4RDD08OutputLineStatus NOTIFICATION-TYPE
        OBJECTS            { i4LoggingRDD08OutputLineStatus } 
        STATUS            current
        DESCRIPTION
                "CMNT: - off or line number
                 TYPE: - Display
                 PAGE: - Logging
                    RDD08 Output Line Status  cmdID= 5008  "
        ::= { kudosConv4NoteEntries 5008 }


    i4CEA708OutputLineStatus NOTIFICATION-TYPE
        OBJECTS            { i4LoggingCEA708OutputLineStatus } 
        STATUS            current
        DESCRIPTION
                "CMNT: - off or line number
                 TYPE: - Display
                 PAGE: - Logging
                    CEA-708 Output Line Status  cmdID= 5009  "
        ::= { kudosConv4NoteEntries 5009 }


    i42016OutputLineStatus NOTIFICATION-TYPE
        OBJECTS            { i4Logging2016OutputLineStatus } 
        STATUS            current
        DESCRIPTION
                "CMNT: - off or line number
                 TYPE: - Display
                 PAGE: - Logging
                    2016 Output Line Status  cmdID= 5010  "
        ::= { kudosConv4NoteEntries 5010 }


    i4L23OutputLineStatus NOTIFICATION-TYPE
        OBJECTS            { i4LoggingL23OutputLineStatus } 
        STATUS            current
        DESCRIPTION
                "CMNT: - off or line number
                 TYPE: - Display
                 PAGE: - Logging
                    L23 Output Line Status  cmdID= 5011  "
        ::= { kudosConv4NoteEntries 5011 }


    i4SignallingStatus NOTIFICATION-TYPE
        OBJECTS            { i4LoggingSignallingStatus } 
        STATUS            current
        DESCRIPTION
                "CMNT: - NONE or OK
                 TYPE: - Display
                 PAGE: - Logging
                    Signalling Status  cmdID= 5012  "
        ::= { kudosConv4NoteEntries 5012 }


    i4MSGStatus NOTIFICATION-TYPE
        OBJECTS            { i4LoggingMSGStatus } 
        STATUS            current
        DESCRIPTION
                "CMNT: - 
                 TYPE: - Display
                 PAGE: - Logging
                    MSG Status  cmdID= 5013  "
        ::= { kudosConv4NoteEntries 5013 }
    kudosConv4CtrlEntries OBJECT IDENTIFIER ::= { kudosIQP 14 }


    i4InputSelect OBJECT-TYPE
        SYNTAX            INTEGER {
                            valSDI1(0),
                            valSDI2(1),
                            valSDI3(2),
                            valSDI4(3),
                            valCVBSA(4),
                            valCVBSB(5),
                            valCVBSC(6),
                            valCVBSD(7),
                            valSFPA1(8),
                            valSFPA2(9),
                            valSFPB1(10),
                            valSFPB2(11)
                            }
        MAX-ACCESS        read-write
        STATUS            current
        DESCRIPTION
                "CMNT: - 
                 TYPE: - RadiobuttonList
                 PAGE: - Input
                    Input Select  cmdID= 10020
                    SDI 1  value= 0
                    SDI 2  value= 1
                    SDI 3  value= 2
                    SDI 4  value= 3
                    CVBS A  value= 4
                    CVBS B  value= 5
                    CVBS C  value= 6
                    CVBS D  value= 7
                    SFP A1  value= 8
                    SFP A2  value= 9
                    SFP B1  value= 10
                    SFP B2  value= 11  "
        ::= { kudosConv4CtrlEntries 10020 }


    i4InputStatusSDI1 OBJECT-TYPE
        SYNTAX            RollCallString
        MAX-ACCESS        read-only
        STATUS            current
        DESCRIPTION
                "CMNT: - 
                 TYPE: - Display
                 PAGE: - Input
                    SDI 1  cmdID= 10270  "
        ::= { kudosConv4CtrlEntries 10270 }


    i4InputStatusSDI2 OBJECT-TYPE
        SYNTAX            RollCallString
        MAX-ACCESS        read-only
        STATUS            current
        DESCRIPTION
                "CMNT: - 
                 TYPE: - Display
                 PAGE: - Input
                    SDI 2  cmdID= 10271  "
        ::= { kudosConv4CtrlEntries 10271 }


    i4InputStatusSDI3 OBJECT-TYPE
        SYNTAX            RollCallString
        MAX-ACCESS        read-only
        STATUS            current
        DESCRIPTION
                "CMNT: - 
                 TYPE: - Display
                 PAGE: - Input
                    SDI 3  cmdID= 10272  "
        ::= { kudosConv4CtrlEntries 10272 }


    i4InputStatusSDI4 OBJECT-TYPE
        SYNTAX            RollCallString
        MAX-ACCESS        read-only
        STATUS            current
        DESCRIPTION
                "CMNT: - 
                 TYPE: - Display
                 PAGE: - Input
                    SDI 4  cmdID= 10273  "
        ::= { kudosConv4CtrlEntries 10273 }


    i4InputStatusCVBS1 OBJECT-TYPE
        SYNTAX            RollCallString
        MAX-ACCESS        read-only
        STATUS            current
        DESCRIPTION
                "CMNT: - 
                 TYPE: - Display
                 PAGE: - Input
                    CVBS 1  cmdID= 10274  "
        ::= { kudosConv4CtrlEntries 10274 }


    i4InputStatusCVBS2 OBJECT-TYPE
        SYNTAX            RollCallString
        MAX-ACCESS        read-only
        STATUS            current
        DESCRIPTION
                "CMNT: - 
                 TYPE: - Display
                 PAGE: - Input
                    CVBS 2  cmdID= 10275  "
        ::= { kudosConv4CtrlEntries 10275 }


    i4InputStatusCVBS3 OBJECT-TYPE
        SYNTAX            RollCallString
        MAX-ACCESS        read-only
        STATUS            current
        DESCRIPTION
                "CMNT: - 
                 TYPE: - Display
                 PAGE: - Input
                    CVBS 3  cmdID= 10276  "
        ::= { kudosConv4CtrlEntries 10276 }


    i4InputStatusCVBS4 OBJECT-TYPE
        SYNTAX            RollCallString
        MAX-ACCESS        read-only
        STATUS            current
        DESCRIPTION
                "CMNT: - 
                 TYPE: - Display
                 PAGE: - Input
                    CVBS 4  cmdID= 10277  "
        ::= { kudosConv4CtrlEntries 10277 }


    i4InputStatusSFP1 OBJECT-TYPE
        SYNTAX            RollCallString
        MAX-ACCESS        read-only
        STATUS            current
        DESCRIPTION
                "CMNT: - 
                 TYPE: - Display
                 PAGE: - Input
                    SFP 1  cmdID= 10278  "
        ::= { kudosConv4CtrlEntries 10278 }


    i4InputStatusSFP2 OBJECT-TYPE
        SYNTAX            RollCallString
        MAX-ACCESS        read-only
        STATUS            current
        DESCRIPTION
                "CMNT: - 
                 TYPE: - Display
                 PAGE: - Input
                    SFP 2  cmdID= 10279  "
        ::= { kudosConv4CtrlEntries 10279 }


    i4InputStatusSFP3 OBJECT-TYPE
        SYNTAX            RollCallString
        MAX-ACCESS        read-only
        STATUS            current
        DESCRIPTION
                "CMNT: - 
                 TYPE: - Display
                 PAGE: - Input
                    SFP 3  cmdID= 10280  "
        ::= { kudosConv4CtrlEntries 10280 }


    i4InputStatusSFP4 OBJECT-TYPE
        SYNTAX            RollCallString
        MAX-ACCESS        read-only
        STATUS            current
        DESCRIPTION
                "CMNT: - 
                 TYPE: - Display
                 PAGE: - Input
                    SFP 4  cmdID= 10281  "
        ::= { kudosConv4CtrlEntries 10281 }


    i4InputStatusCurrentInputStandard OBJECT-TYPE
        SYNTAX            RollCallString
        MAX-ACCESS        read-only
        STATUS            current
        DESCRIPTION
                "CMNT: - 
                 TYPE: - Display
                 PAGE: - Input
                    Current Input Standard  cmdID= 10313  "
        ::= { kudosConv4CtrlEntries 10313 }


    i4OutputFormat OBJECT-TYPE
        SYNTAX            INTEGER {
                            val525625(0),
                            val720p(1),
                            val1080i(2),
                            val1080pnA(3),
                            val1080pnB(4)
                            }
        MAX-ACCESS        read-write
        STATUS            current
        DESCRIPTION
                "CMNT: - 
                 TYPE: - RadiobuttonList
                 PAGE: - Output
                    Output Format  cmdID= 10025
                    525/625  value= 0
                    720p  value= 1
                    1080i  value= 2
                    1080p-A  value= 3
                    1080p-B  value= 4  "
        ::= { kudosConv4CtrlEntries 10025 }


    i4OutputDefaultFieldRate OBJECT-TYPE
        SYNTAX            INTEGER {
                            valLastValidInput(0),
                            val23Hz(1),
                            val24Hz(2),
                            val25Hz(3),
                            val29Hz(4),
                            val30Hz(5),
                            val50Hz(6),
                            val59Hz(7),
                            val60Hz(8)
                            }
        MAX-ACCESS        read-write
        STATUS            current
        DESCRIPTION
                "CMNT: - 
                 TYPE: - RadiobuttonList
                 PAGE: - Output
                    Default Field Rate  cmdID= 10026
                    Last Valid Input  value= 0
                    23 Hz  value= 1
                    24 Hz  value= 2
                    25 Hz  value= 3
                    29 Hz  value= 4
                    30 Hz  value= 5
                    50 Hz  value= 6
                    59 Hz  value= 7
                    60 Hz  value= 8  "
        ::= { kudosConv4CtrlEntries 10026 }


    i4OutputStandard OBJECT-TYPE
        SYNTAX            INTEGER {
                            val62550i(2),
                            val52559i(3),
                            val72023p(4),
                            val72024p(5),
                            val72025p(6),
                            val72029p(7),
                            val72030p(8),
                            val72050p(9),
                            val72059p(10),
                            val72060p(11),
                            val108023p(12),
                            val108024p(13),
                            val108025p(14),
                            val108029p(15),
                            val108030p(16),
                            val108050i(17),
                            val108059i(18),
                            val108060i(19),
                            val108023psf(20),
                            val108024psf(21),
                            val108025psf(50),
                            val108029psf(51),
                            val108050pnA(22),
                            val108059pnA(23),
                            val108060pnA(24),
                            val108050pnB(25),
                            val108059pnB(26),
                            val108060pnB(27)
                            }
        MAX-ACCESS        read-write
        STATUS            current
        DESCRIPTION
                "CMNT: - 
                 TYPE: - RadiobuttonList
                 PAGE: - Output
                    Output Standard  cmdID= 10024
                    625 50i  value= 2
                    525 59i  value= 3
                    720 23p  value= 4
                    720 24p  value= 5
                    720 25p  value= 6
                    720 29p  value= 7
                    720 30p  value= 8
                    720 50p  value= 9
                    720 59p  value= 10
                    720 60p  value= 11
                    1080 23p  value= 12
                    1080 24p  value= 13
                    1080 25p  value= 14
                    1080 29p  value= 15
                    1080 30p  value= 16
                    1080 50i  value= 17
                    1080 59i  value= 18
                    1080 60i  value= 19
                    1080 23psf  value= 20
                    1080 24psf  value= 21
                    1080 25psf  value= 50
                    1080 29psf  value= 51
                    1080 50p-A  value= 22
                    1080 59p-A  value= 23
                    1080 60p-A  value= 24
                    1080 50p-B  value= 25
                    1080 59p-B  value= 26
                    1080 60p-B  value= 27  "
        ::= { kudosConv4CtrlEntries 10024 }


    i4OutputCurrentOutputStandard OBJECT-TYPE
        SYNTAX            RollCallString
        MAX-ACCESS        read-only
        STATUS            current
        DESCRIPTION
                "CMNT: - 
                 TYPE: - Display
                 PAGE: - Output
                    Current Output Standard  cmdID= 10314  "
        ::= { kudosConv4CtrlEntries 10314 }


    i4OutputBlankingEmbeddedAudio OBJECT-TYPE
        SYNTAX            INTEGER {
                            valEnable(0),
                            valBlank(1)
                            }
        MAX-ACCESS        read-write
        STATUS            current
        DESCRIPTION
                "CMNT: - 
                 TYPE: - RadiobuttonList
                 PAGE: - Output
                    Embedded Audio  cmdID= 10021
                    Enable  value= 0
                    Blank  value= 1  "
        ::= { kudosConv4CtrlEntries 10021 }


    i4OutputBlankingVAncillaryData OBJECT-TYPE
        SYNTAX            INTEGER {
                            valPass(0),
                            valStrip(1)
                            }
        MAX-ACCESS        read-write
        STATUS            current
        DESCRIPTION
                "CMNT: - 
                 TYPE: - RadiobuttonList
                 PAGE: - Output
                    V Ancillary Data  cmdID= 10022
                    Pass  value= 0
                    Strip  value= 1  "
        ::= { kudosConv4CtrlEntries 10022 }


    i4OutputBlankingSDHalfLine OBJECT-TYPE
        SYNTAX            INTEGER {
                            valPass(0),
                            valBlank(1)
                            }
        MAX-ACCESS        read-write
        STATUS            current
        DESCRIPTION
                "CMNT: - 
                 TYPE: - RadiobuttonList
                 PAGE: - Output
                    SD Half Line  cmdID= 10023
                    Pass  value= 0
                    Blank  value= 1  "
        ::= { kudosConv4CtrlEntries 10023 }


    i4OutputTestPatterns OBJECT-TYPE
        SYNTAX            INTEGER {
                            valOff(0),
                            valBlack(1),
                            valRamp(2),
                            valBars(3)
                            }
        MAX-ACCESS        read-write
        STATUS            current
        DESCRIPTION
                "CMNT: - 
                 TYPE: - RadiobuttonList
                 PAGE: - Output
                    Test Patterns  cmdID= 10054
                    Off  value= 0
                    Black  value= 1
                    Ramp  value= 2
                    Bars  value= 3  "
        ::= { kudosConv4CtrlEntries 10054 }


    i4OutputScrollingCaptionGeneratorCaptionEntry OBJECT-TYPE
        SYNTAX            RollCallString
        MAX-ACCESS        read-write
        STATUS            current
        DESCRIPTION
                "CMNT: - 
                 TYPE: - Editstring
                 PAGE: - Output
                    Caption Entry  cmdID= 10050
                    preset= Channel Number"
        ::= { kudosConv4CtrlEntries 10050 }


    i4OutputScrollingCaptionGeneratorCaptionScroll OBJECT-TYPE
        SYNTAX            INTEGER { disable(0), enable(1)  }
        MAX-ACCESS        read-write
        STATUS            current
        DESCRIPTION
                "CMNT: - 
                 TYPE: - Checkbox
                 PAGE: - Output
                    Caption Scroll  cmdID= 10052  "
        ::= { kudosConv4CtrlEntries 10052 }


    i4OutputScrollingCaptionGeneratorCaptionEnable OBJECT-TYPE
        SYNTAX            INTEGER { disable(0), enable(1)  }
        MAX-ACCESS        read-write
        STATUS            current
        DESCRIPTION
                "CMNT: - 
                 TYPE: - Checkbox
                 PAGE: - Output
                    Caption Enable  cmdID= 10051  "
        ::= { kudosConv4CtrlEntries 10051 }


    i4OutputFreeze OBJECT-TYPE
        SYNTAX            INTEGER { disable(0), enable(1)  }
        MAX-ACCESS        read-write
        STATUS            current
        DESCRIPTION
                "CMNT: - 
                 TYPE: - Checkbox
                 PAGE: - Output
                    Freeze  cmdID= 10053  "
        ::= { kudosConv4CtrlEntries 10053 }


    i4OutputLegalization OBJECT-TYPE
        SYNTAX            INTEGER {
                            valOff(0),
                            val700mV(1),
                            val721mV(2),
                            val735mV(3),
                            val746mV(4)
                            }
        MAX-ACCESS        read-write
        STATUS            current
        DESCRIPTION
                "CMNT: - 
                 TYPE: - RadiobuttonList
                 PAGE: - Output
                    Legalization  cmdID= 10049
                    Off  value= 0
                    700mV  value= 1
                    721mV  value= 2
                    735mV  value= 3
                    746mV  value= 4  "
        ::= { kudosConv4CtrlEntries 10049 }


    i4OutputLogoControlPreShaped OBJECT-TYPE
        SYNTAX            INTEGER { disable(0), enable(1)  }
        MAX-ACCESS        read-write
        STATUS            current
        DESCRIPTION
                "CMNT: - 
                 TYPE: - Checkbox
                 PAGE: - Output
                    Pre-Shaped  cmdID= 10055  "
        ::= { kudosConv4CtrlEntries 10055 }


    i4OutputLogoControlTake OBJECT-TYPE
        SYNTAX            INTEGER { disable(0), enable(1)  }
        MAX-ACCESS        read-write
        STATUS            current
        DESCRIPTION
                "CMNT: - 
                 TYPE: - Checkbox
                 PAGE: - Output
                    Take  cmdID= 10056  "
        ::= { kudosConv4CtrlEntries 10056 }


    i4OutputLogoControlHPosition OBJECT-TYPE
        SYNTAX            INTEGER
        MAX-ACCESS        read-write
        STATUS            current
        DESCRIPTION
                "CMNT: - 
                 TYPE: - Number
                 PAGE: - Output
                    H Position  cmdID= 10057
                    min= 0  max= 100  step= 1  format= %0.0f  div_scale= 1  preset= 10
                    Min = 0  Max = 100  Step = 1  Preset = 10  "
        ::= { kudosConv4CtrlEntries 10057 }


    i4OutputLogoControlVPosition OBJECT-TYPE
        SYNTAX            INTEGER
        MAX-ACCESS        read-write
        STATUS            current
        DESCRIPTION
                "CMNT: - 
                 TYPE: - Number
                 PAGE: - Output
                    V Position  cmdID= 10058
                    min= 0  max= 100  step= 1  format= %0.0f  div_scale= 1  preset= 10
                    Min = 0  Max = 100  Step = 1  Preset = 10  "
        ::= { kudosConv4CtrlEntries 10058 }


    i4OutputLogoControlTransparency OBJECT-TYPE
        SYNTAX            INTEGER
        MAX-ACCESS        read-write
        STATUS            current
        DESCRIPTION
                "CMNT: - 
                 TYPE: - Number
                 PAGE: - Output
                    Transparency  cmdID= 10059
                    min= 0  max= 100  step= 1  format= %0.0f  div_scale= 1  preset= 10
                    Min = 0  Max = 100  Step = 1  Preset = 10  "
        ::= { kudosConv4CtrlEntries 10059 }


    i4OutputLogoControlDelete OBJECT-TYPE
        SYNTAX            INTEGER { noAction(0),valDelete(1) }
        MAX-ACCESS        read-write
        STATUS            current
        DESCRIPTION
                "CMNT: - 
                 TYPE: - Button
                 PAGE: - Output
                    Delete  cmdID= 10060
                    value= 1  "
        ::= { kudosConv4CtrlEntries 10060 }


    i4OutputLogoControlCurrentSelectedLogo OBJECT-TYPE
        SYNTAX            RollCallString
        MAX-ACCESS        read-only
        STATUS            current
        DESCRIPTION
                "CMNT: - 
                 TYPE: - Display
                 PAGE: - Output
                    Current Selected Logo  cmdID= 10062  "
        ::= { kudosConv4CtrlEntries 10062 }


    i4OutputLogoControlLogoStatus OBJECT-TYPE
        SYNTAX            RollCallString
        MAX-ACCESS        read-only
        STATUS            current
        DESCRIPTION
                "CMNT: - 
                 TYPE: - Display
                 PAGE: - Output
                    Logo Status  cmdID= 15001  "
        ::= { kudosConv4CtrlEntries 15001 }


    i4OutputLogoControlLogoState OBJECT-TYPE
        SYNTAX            RollCallString
        MAX-ACCESS        read-only
        STATUS            current
        DESCRIPTION
                "CMNT: - 
                 TYPE: - Display
                 PAGE: - Output
                    Logo State  cmdID= 10063  "
        ::= { kudosConv4CtrlEntries 10063 }


    i4OutputLogoControlNewLogo OBJECT-TYPE
        SYNTAX            RollCallString
        MAX-ACCESS        read-write
        STATUS            current
        DESCRIPTION
                "CMNT: - 
                 TYPE: - Editstring
                 PAGE: - Output
                    New Logo  cmdID= 15000
                    preset= startupqwerty"
        ::= { kudosConv4CtrlEntries 15000 }


    i4OutputLogoControlLogoSelect OBJECT-TYPE
        SYNTAX            INTEGER {
                            valNoneSelected(-1),
                            valLogo1(1),
                            valLogo2(2),
                            valLogo3(3),
                            valLogo4(4),
                            valLogo5(5),
                            valLogo6(6),
                            valLogo7(7),
                            valLogo8(8),
                            valLogo9(9),
                            valLogo10(10),
                            valLogo11(11),
                            valLogo12(12),
                            valLogo13(13),
                            valLogo14(14),
                            valLogo15(15),
                            valLogo16(16),
                            valLogo17(17),
                            valLogo18(18),
                            valLogo19(19),
                            valLogo20(20),
                            valLogo21(21),
                            valLogo22(22),
                            valLogo23(23),
                            valLogo24(24),
                            valLogo25(25),
                            valLogo26(26),
                            valLogo27(27),
                            valLogo28(28),
                            valLogo29(29),
                            valLogo30(30),
                            valLogo31(31),
                            valLogo32(32),
                            valLogo33(33),
                            valLogo34(34),
                            valLogo35(35),
                            valLogo36(36),
                            valLogo37(37),
                            valLogo38(38),
                            valLogo39(39),
                            valLogo40(40),
                            valLogo41(41),
                            valLogo42(42),
                            valLogo43(43),
                            valLogo44(44),
                            valLogo45(45),
                            valLogo46(46),
                            valLogo47(47),
                            valLogo48(48),
                            valLogo49(49),
                            valLogo50(50),
                            valLogo51(51),
                            valLogo52(52),
                            valLogo53(53),
                            valLogo54(54),
                            valLogo55(55),
                            valLogo56(56),
                            valLogo57(57),
                            valLogo58(58),
                            valLogo59(59),
                            valLogo60(60),
                            valLogo61(61),
                            valLogo62(62),
                            valLogo63(63),
                            valLogo64(64)
                            }
        MAX-ACCESS        read-write
        STATUS            current
        DESCRIPTION
                "CMNT: - 
                 TYPE: - RadiobuttonList
                 PAGE: - Output
                    Logo Select  cmdID= 10061
                    None Selected  value= -1
                    Logo 1  value= 1
                    Logo 2  value= 2
                    Logo 3  value= 3
                    Logo 4  value= 4
                    Logo 5  value= 5
                    Logo 6  value= 6
                    Logo 7  value= 7
                    Logo 8  value= 8
                    Logo 9  value= 9
                    Logo 10  value= 10
                    Logo 11  value= 11
                    Logo 12  value= 12
                    Logo 13  value= 13
                    Logo 14  value= 14
                    Logo 15  value= 15
                    Logo 16  value= 16
                    Logo 17  value= 17
                    Logo 18  value= 18
                    Logo 19  value= 19
                    Logo 20  value= 20
                    Logo 21  value= 21
                    Logo 22  value= 22
                    Logo 23  value= 23
                    Logo 24  value= 24
                    Logo 25  value= 25
                    Logo 26  value= 26
                    Logo 27  value= 27
                    Logo 28  value= 28
                    Logo 29  value= 29
                    Logo 30  value= 30
                    Logo 31  value= 31
                    Logo 32  value= 32
                    Logo 33  value= 33
                    Logo 34  value= 34
                    Logo 35  value= 35
                    Logo 36  value= 36
                    Logo 37  value= 37
                    Logo 38  value= 38
                    Logo 39  value= 39
                    Logo 40  value= 40
                    Logo 41  value= 41
                    Logo 42  value= 42
                    Logo 43  value= 43
                    Logo 44  value= 44
                    Logo 45  value= 45
                    Logo 46  value= 46
                    Logo 47  value= 47
                    Logo 48  value= 48
                    Logo 49  value= 49
                    Logo 50  value= 50
                    Logo 51  value= 51
                    Logo 52  value= 52
                    Logo 53  value= 53
                    Logo 54  value= 54
                    Logo 55  value= 55
                    Logo 56  value= 56
                    Logo 57  value= 57
                    Logo 58  value= 58
                    Logo 59  value= 59
                    Logo 60  value= 60
                    Logo 61  value= 61
                    Logo 62  value= 62
                    Logo 63  value= 63
                    Logo 64  value= 64  "
        ::= { kudosConv4CtrlEntries 10061 }


    i4VideoProcAmpEnable OBJECT-TYPE
        SYNTAX            INTEGER { disable(0), enable(1)  }
        MAX-ACCESS        read-write
        STATUS            current
        DESCRIPTION
                "CMNT: - 
                 TYPE: - Checkbox
                 PAGE: - Video
                    Enable  cmdID= 10047  "
        ::= { kudosConv4CtrlEntries 10047 }


    i4VideoProcAmpContrast OBJECT-TYPE
        SYNTAX            INTEGER
        MAX-ACCESS        read-write
        STATUS            current
        DESCRIPTION
                "CMNT: - 
                 TYPE: - Number
                 PAGE: - Video
                    Contrast  cmdID= 10043
                    min= -60  max= 60  step= 2  format= %0.1fdB  div_scale= 10  preset= 0
                    Min = -6.0dB  Max = 6.0dB  Step = 0.2dB  Preset = 0.0dB  "
        ::= { kudosConv4CtrlEntries 10043 }


    i4VideoProcAmpSaturation OBJECT-TYPE
        SYNTAX            INTEGER
        MAX-ACCESS        read-write
        STATUS            current
        DESCRIPTION
                "CMNT: - 
                 TYPE: - Number
                 PAGE: - Video
                    Saturation  cmdID= 10044
                    min= -60  max= 60  step= 2  format= %0.1fdB  div_scale= 10  preset= 0
                    Min = -6.0dB  Max = 6.0dB  Step = 0.2dB  Preset = 0.0dB  "
        ::= { kudosConv4CtrlEntries 10044 }


    i4VideoProcAmpBlackLevel OBJECT-TYPE
        SYNTAX            INTEGER
        MAX-ACCESS        read-write
        STATUS            current
        DESCRIPTION
                "CMNT: - 
                 TYPE: - Number
                 PAGE: - Video
                    Black Level  cmdID= 10045
                    min= -1000  max= 1000  step= 8  format= %0.1fmV  div_scale= 10  preset= 0
                    Min = -100.0mV  Max = 100.0mV  Step = 0.8mV  Preset = 0.0mV  "
        ::= { kudosConv4CtrlEntries 10045 }


    i4VideoProcAmpGamma OBJECT-TYPE
        SYNTAX            INTEGER
        MAX-ACCESS        read-write
        STATUS            current
        DESCRIPTION
                "CMNT: - 
                 TYPE: - Number
                 PAGE: - Video
                    Gamma  cmdID= 10046
                    min= 4  max= 17  step= 1  format= %0.1f  div_scale= 10  preset= 10
                    Min = 0.4  Max = 1.7  Step = 0.1  Preset = 1.0  "
        ::= { kudosConv4CtrlEntries 10046 }


    i4VideoProcAmpYCOffset OBJECT-TYPE
        SYNTAX            INTEGER
        MAX-ACCESS        read-write
        STATUS            current
        DESCRIPTION
                "CMNT: - 
                 TYPE: - Number
                 PAGE: - Video
                    YC Offset  cmdID= 10048
                    min= -20  max= 20  step= 2  format= %0.0f  div_scale= 1  preset= 0
                    Min = -20  Max = 20  Step = 2  Preset = 0  "
        ::= { kudosConv4CtrlEntries 10048 }


    i4VideoEnhanceNonlinearEnhancerEnable OBJECT-TYPE
        SYNTAX            INTEGER { disable(0), enable(1)  }
        MAX-ACCESS        read-write
        STATUS            current
        DESCRIPTION
                "CMNT: - 
                 TYPE: - Checkbox
                 PAGE: - Enhance
                    Enable  cmdID= 10036  "
        ::= { kudosConv4CtrlEntries 10036 }


    i4VideoEnhanceNonlinearEnhancerLevel OBJECT-TYPE
        SYNTAX            INTEGER
        MAX-ACCESS        read-write
        STATUS            current
        DESCRIPTION
                "CMNT: - 
                 TYPE: - Number
                 PAGE: - Enhance
                    Level  cmdID= 10039
                    min= 0  max= 192  step= 1  format= %0.0f  div_scale= 1  preset= 0
                    Min = 0  Max = 192  Step = 1  Preset = 0  "
        ::= { kudosConv4CtrlEntries 10039 }


    i4VideoEnhanceNonlinearEnhancerMode OBJECT-TYPE
        SYNTAX            INTEGER {
                            valLow(0),
                            valMedium(1),
                            valHigh(2),
                            valSuper(3),
                            valManual(4)
                            }
        MAX-ACCESS        read-write
        STATUS            current
        DESCRIPTION
                "CMNT: - 
                 TYPE: - RadiobuttonList
                 PAGE: - Enhance
                    Mode  cmdID= 10037
                    Low  value= 0
                    Medium  value= 1
                    High  value= 2
                    Super  value= 3
                    Manual  value= 4  "
        ::= { kudosConv4CtrlEntries 10037 }


    i4VideoEnhanceNonlinearEnhancerFrequencyBand OBJECT-TYPE
        SYNTAX            INTEGER {
                            valLow(0),
                            valMedium(1),
                            valHigh(2)
                            }
        MAX-ACCESS        read-write
        STATUS            current
        DESCRIPTION
                "CMNT: - 
                 TYPE: - RadiobuttonList
                 PAGE: - Enhance
                    Frequency Band  cmdID= 10038
                    Low  value= 0
                    Medium  value= 1
                    High  value= 2  "
        ::= { kudosConv4CtrlEntries 10038 }


    i4VideoEnhanceNonlinearEnhancerNoiseRejection OBJECT-TYPE
        SYNTAX            INTEGER
        MAX-ACCESS        read-write
        STATUS            current
        DESCRIPTION
                "CMNT: - 
                 TYPE: - Number
                 PAGE: - Enhance
                    Noise Rejection  cmdID= 10040
                    min= 0  max= 100  step= 1  format= %0.0f  div_scale= 1  preset= 0
                    Min = 0  Max = 100  Step = 1  Preset = 0  "
        ::= { kudosConv4CtrlEntries 10040 }


    i4VideoEnhanceConversionAperturePreset OBJECT-TYPE
        SYNTAX            INTEGER { noAction(0),valPreset(1) }
        MAX-ACCESS        read-write
        STATUS            current
        DESCRIPTION
                "CMNT: - 
                 TYPE: - Button
                 PAGE: - Enhance
                    Preset  cmdID= 10335
                    value= 1  "
        ::= { kudosConv4CtrlEntries 10335 }


    i4VideoConversionApertureHorizontalSharpness OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Conversion Aperture
                    Sharpness  cmdID= 10072
                    Soft 2  value= 0
                    Soft 1  value= 1
                    Normal  value= 2
                    Sharp 1  value= 3
                    Sharp 2  value= 4  "
        ::= { kudosConv4CtrlEntries 10072 }


    i4VideoConversionApertureHorizontalDetail OBJECT-TYPE
        SYNTAX            INTEGER {
                            valLow2(0),
                            valLow1(1),
                            valNormal(2),
                            valHigh1(3),
                            valHigh2(4)
                            }
        MAX-ACCESS        read-write
        STATUS            current
        DESCRIPTION
                "CMNT: - 
                 TYPE: - RadiobuttonList
                 PAGE: - Conversion Aperture
                    Detail  cmdID= 10073
                    Low 2  value= 0
                    Low 1  value= 1
                    Normal  value= 2
                    High 1  value= 3
                    High 2  value= 4  "
        ::= { kudosConv4CtrlEntries 10073 }


    i4VideoConversionApertureVerticalLevel OBJECT-TYPE
        SYNTAX            INTEGER {
                            valSoft2(0),
                            valSoft1(1),
                            valNormal(2),
                            valSharp1(3),
                            valSharp2(4)
                            }
        MAX-ACCESS        read-write
        STATUS            current
        DESCRIPTION
                "CMNT: - 
                 TYPE: - RadiobuttonList
                 PAGE: - Conversion Aperture
                    Level  cmdID= 10042
                    Soft 2  value= 0
                    Soft 1  value= 1
                    Normal  value= 2
                    Sharp 1  value= 3
                    Sharp 2  value= 4  "
        ::= { kudosConv4CtrlEntries 10042 }


    i4VideoConversionApertureVerticalFrequencyBand OBJECT-TYPE
        SYNTAX            INTEGER {
                            valLow(0),
                            valMedium(1),
                            valHigh(2)
                            }
        MAX-ACCESS        read-write
        STATUS            current
        DESCRIPTION
                "CMNT: - 
                 TYPE: - RadiobuttonList
                 PAGE: - Conversion Aperture
                    Frequency Band  cmdID= 10041
                    Low  value= 0
                    Medium  value= 1
                    High  value= 2  "
        ::= { kudosConv4CtrlEntries 10041 }


    i4VideoNoiseReductionEnable OBJECT-TYPE
        SYNTAX            INTEGER { disable(0), enable(1)  }
        MAX-ACCESS        read-write
        STATUS            current
        DESCRIPTION
                "CMNT: - 
                 TYPE: - Checkbox
                 PAGE: - Video
                    Enable  cmdID= 10031  "
        ::= { kudosConv4CtrlEntries 10031 }


    i4VideoNoiseReductionRecursiveLuma OBJECT-TYPE
        SYNTAX            INTEGER
        MAX-ACCESS        read-write
        STATUS            current
        DESCRIPTION
                "CMNT: - 
                 TYPE: - Number
                 PAGE: - Noise Reduction
                    Luma  cmdID= 10027
                    min= 0  max= 7  step= 1  format= %0.0f  div_scale= 1  preset= 0
                    Min = 0  Max = 7  Step = 1  Preset = 0  "
        ::= { kudosConv4CtrlEntries 10027 }


    i4VideoNoiseReductionRecursiveChroma OBJECT-TYPE
        SYNTAX            INTEGER
        MAX-ACCESS        read-write
        STATUS            current
        DESCRIPTION
                "CMNT: - 
                 TYPE: - Number
                 PAGE: - Noise Reduction
                    Chroma  cmdID= 10028
                    min= 0  max= 7  step= 1  format= %0.0f  div_scale= 1  preset= 0
                    Min = 0  Max = 7  Step = 1  Preset = 0  "
        ::= { kudosConv4CtrlEntries 10028 }


    i4VideoNoiseReductionRecursiveMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10029
                    Auto  value= 0
                    Manual  value= 1  "
        ::= { kudosConv4CtrlEntries 10029 }


    i4VideoNoiseReductionRecursiveThreshold OBJECT-TYPE
        SYNTAX            INTEGER
        MAX-ACCESS        read-write
        STATUS            current
        DESCRIPTION
                "CMNT: - 
                 TYPE: - Number
                 PAGE: - Noise Reduction
                    Threshold  cmdID= 10030
                    min= 0  max= 7  step= 1  format= %0.0f  div_scale= 1  preset= 0
                    Min = 0  Max = 7  Step = 1  Preset = 0  "
        ::= { kudosConv4CtrlEntries 10030 }


    i4VideoNoiseReductionSpatialLevel OBJECT-TYPE
        SYNTAX            INTEGER
        MAX-ACCESS        read-write
        STATUS            current
        DESCRIPTION
                "CMNT: - 
                 TYPE: - Number
                 PAGE: - Noise Reduction
                    Level  cmdID= 10033
                    min= 0  max= 7  step= 1  format= %0.0f  div_scale= 1  preset= 0
                    Min = 0  Max = 7  Step = 1  Preset = 0  "
        ::= { kudosConv4CtrlEntries 10033 }


    i4VideoNoiseReductionSpatialMode OBJECT-TYPE
        SYNTAX            INTEGER {
                            valAuto(0),
                            valManual(1)
                            }
        MAX-ACCESS        read-write
        STATUS            current
        DESCRIPTION
                "CMNT: - 
                 TYPE: - RadiobuttonList
                 PAGE: - Noise Reduction
                    Mode  cmdID= 10032
                    Auto  value= 0
                    Manual  value= 1  "
        ::= { kudosConv4CtrlEntries 10032 }


    i4VideoNoiseReductionSpatialThreshold OBJECT-TYPE
        SYNTAX            INTEGER
        MAX-ACCESS        read-write
        STATUS            current
        DESCRIPTION
                "CMNT: - 
                 TYPE: - Number
                 PAGE: - Noise Reduction
                    Threshold  cmdID= 10034
                    min= 1  max= 4  step= 1  format= %0.0f  div_scale= 1  preset= 1
                    Min = 1  Max = 4  Step = 1  Preset = 1  "
        ::= { kudosConv4CtrlEntries 10034 }


    i4VideoNoiseReductionSplitScreen OBJECT-TYPE
        SYNTAX            INTEGER { disable(0), enable(1)  }
        MAX-ACCESS        read-write
        STATUS            current
        DESCRIPTION
                "CMNT: - 
                 TYPE: - Checkbox
                 PAGE: - Video
                    Split Screen  cmdID= 10035  "
        ::= { kudosConv4CtrlEntries 10035 }


    i4ConvertUpConversionCleanEdgeUpconversion OBJECT-TYPE
        SYNTAX            INTEGER { disable(0), enable(1)  }
        MAX-ACCESS        read-write
        STATUS            current
        DESCRIPTION
                "CMNT: - 
                 TYPE: - Checkbox
                 PAGE: - Convert
                    Clean Edge Upconversion  cmdID= 10069  "
        ::= { kudosConv4CtrlEntries 10069 }


    i4ConvertMotionProcessingMotionProcess OBJECT-TYPE
        SYNTAX            INTEGER { disable(0), enable(1)  }
        MAX-ACCESS        read-write
        STATUS            current
        DESCRIPTION
                "CMNT: - 
                 TYPE: - Checkbox
                 PAGE: - Convert
                    Motion Process  cmdID= 10064  "
        ::= { kudosConv4CtrlEntries 10064 }


    i4ConvertMotionProcessingEnhancedMotion OBJECT-TYPE
        SYNTAX            INTEGER { disable(0), enable(1)  }
        MAX-ACCESS        read-write
        STATUS            current
        DESCRIPTION
                "CMNT: - 
                 TYPE: - Checkbox
                 PAGE: - Convert
                    Enhanced Motion  cmdID= 10065  "
        ::= { kudosConv4CtrlEntries 10065 }


    i4ConvertMotionProcessingStillProcess OBJECT-TYPE
        SYNTAX            INTEGER { disable(0), enable(1)  }
        MAX-ACCESS        read-write
        STATUS            current
        DESCRIPTION
                "CMNT: - 
                 TYPE: - Checkbox
                 PAGE: - Convert
                    Still Process  cmdID= 10066  "
        ::= { kudosConv4CtrlEntries 10066 }


    i4ConvertMotionProcessingEnhancedStill OBJECT-TYPE
        SYNTAX            INTEGER { disable(0), enable(1)  }
        MAX-ACCESS        read-write
        STATUS            current
        DESCRIPTION
                "CMNT: - 
                 TYPE: - Checkbox
                 PAGE: - Convert
                    Enhanced Still  cmdID= 10067  "
        ::= { kudosConv4CtrlEntries 10067 }


    i4ConvertMotionProcessingEnhancedFilm OBJECT-TYPE
        SYNTAX            INTEGER { disable(0), enable(1)  }
        MAX-ACCESS        read-write
        STATUS            current
        DESCRIPTION
                "CMNT: - 
                 TYPE: - Checkbox
                 PAGE: - Convert
                    Enhanced Film  cmdID= 10068  "
        ::= { kudosConv4CtrlEntries 10068 }


    i4ConvertMotionProcessingEnhancedDeinterlace OBJECT-TYPE
        SYNTAX            INTEGER { disable(0), enable(1)  }
        MAX-ACCESS        read-write
        STATUS            current
        DESCRIPTION
                "CMNT: - 
                 TYPE: - Checkbox
                 PAGE: - Convert
                    Enhanced De-interlace  cmdID= 10071  "
        ::= { kudosConv4CtrlEntries 10071 }


    i4ConvertMotionProcessingCleanCut OBJECT-TYPE
        SYNTAX            INTEGER { disable(0), enable(1)  }
        MAX-ACCESS        read-write
        STATUS            current
        DESCRIPTION
                "CMNT: - 
                 TYPE: - Checkbox
                 PAGE: - Convert
                    Clean Cut  cmdID= 10070  "
        ::= { kudosConv4CtrlEntries 10070 }


    i4ConvertInputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10323  "
        ::= { kudosConv4CtrlEntries 10323 }


    i4ConvertInputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10324
                    2:3  value= 0
                    2:2 (psf)  value= 1  "
        ::= { kudosConv4CtrlEntries 10324 }


    i4ConvertInputCadence23Source OBJECT-TYPE
        SYNTAX            INTEGER {
                            valAutomatic(0),
                            valInputTimecode(1)
                            }
        MAX-ACCESS        read-write
        STATUS            current
        DESCRIPTION
                "CMNT: - 
                 TYPE: - RadiobuttonList
                 PAGE: - Convert
                    2:3 Source  cmdID= 10325
                    Automatic  value= 0
                    Input Timecode  value= 1  "
        ::= { kudosConv4CtrlEntries 10325 }


    i4ConvertInputCadence23StartHour OBJECT-TYPE
        SYNTAX            INTEGER
        MAX-ACCESS        read-write
        STATUS            current
        DESCRIPTION
                "CMNT: - 
                 TYPE: - Number
                 PAGE: - Convert
                    2:3 Start Hour  cmdID= 10326
                    min= 0  max= 23  step= 1  format= %0.0f  div_scale= 1  preset= 1
                    Min = 0  Max = 23  Step = 1  Preset = 1  "
        ::= { kudosConv4CtrlEntries 10326 }


    i4ConvertOutputCadenceFilmCadence OBJECT-TYPE
        SYNTAX            INTEGER { disable(0), enable(1)  }
        MAX-ACCESS        read-write
        STATUS            current
        DESCRIPTION
                "CMNT: - 
                 TYPE: - Checkbox
                 PAGE: - Convert
                    Film Cadence  cmdID= 10327  "
        ::= { kudosConv4CtrlEntries 10327 }


    i4ConvertOutputCadence59Cadence OBJECT-TYPE
        SYNTAX            INTEGER {
                            val23(0),
                            val22psf(1)
                            }
        MAX-ACCESS        read-write
        STATUS            current
        DESCRIPTION
                "CMNT: - 
                 TYPE: - RadiobuttonList
                 PAGE: - Convert
                    59 Cadence  cmdID= 10328
                    2:3  value= 0
                    2:2 (psf)  value= 1  "
        ::= { kudosConv4CtrlEntries 10328 }


    i4ConvertOutputCadence23Source OBJECT-TYPE
        SYNTAX            INTEGER {
                            valFreeRun(0),
                            valOutputTimecode(1)
                            }
        MAX-ACCESS        read-write
        STATUS            current
        DESCRIPTION
                "CMNT: - 
                 TYPE: - RadiobuttonList
                 PAGE: - Convert
                    2:3 Source  cmdID= 10329
                    Free Run  value= 0
                    Output Timecode  value= 1  "
        ::= { kudosConv4CtrlEntries 10329 }


    i4ConvertOutputCadence23StartHour OBJECT-TYPE
        SYNTAX            INTEGER
        MAX-ACCESS        read-write
        STATUS            current
        DESCRIPTION
                "CMNT: - 
                 TYPE: - Number
                 PAGE: - Convert
                    2:3 Start Hour  cmdID= 10330
                    min= 0  max= 23  step= 1  format= %0.0f  div_scale= 1  preset= 1
                    Min = 0  Max = 23  Step = 1  Preset = 1  "
        ::= { kudosConv4CtrlEntries 10330 }


    i4ARCSyncMode OBJECT-TYPE
        SYNTAX            INTEGER { disable(0), enable(1)  }
        MAX-ACCESS        read-write
        STATUS            current
        DESCRIPTION
                "CMNT: - 
                 TYPE: - Checkbox
                 PAGE: - ARC
                    Sync Mode  cmdID= 10079  "
        ::= { kudosConv4CtrlEntries 10079 }


    i4ARCSignalingDetected OBJECT-TYPE
        SYNTAX            RollCallString
        MAX-ACCESS        read-only
        STATUS            current
        DESCRIPTION
                "CMNT: - 
                 TYPE: - Display
                 PAGE: - ARC
                    Signaling Detected  cmdID= 10315  "
        ::= { kudosConv4CtrlEntries 10315 }


    i4ARCSidebarKeyingOutputCropMode OBJECT-TYPE
        SYNTAX            INTEGER {
                            valOff(0),
                            valOutputCrop(1),
                            valSidebarKey(2)
                            }
        MAX-ACCESS        read-write
        STATUS            current
        DESCRIPTION
                "CMNT: - 
                 TYPE: - RadiobuttonList
                 PAGE: - ARC
                    Mode  cmdID= 10091
                    Off  value= 0
                    Output Crop  value= 1
                    Sidebar Key  value= 2  "
        ::= { kudosConv4CtrlEntries 10091 }


    i4ARCSidebarKeyingOutputCropSidebarKeySource OBJECT-TYPE
        SYNTAX            INTEGER {
                            valSDI1(0),
                            valSDI2(1),
                            valSDI3(2),
                            valSDI4(3),
                            valCVBSA(4),
                            valCVBSB(5),
                            valCVBSC(6),
                            valCVBSD(7),
                            valSFPA1(8),
                            valSFPA2(9),
                            valSFPA3(10),
                            valSFPA4(11),
                            valOutput(20)
                            }
        MAX-ACCESS        read-write
        STATUS            current
        DESCRIPTION
                "CMNT: - 
                 TYPE: - RadiobuttonList
                 PAGE: - ARC
                    Sidebar Key Source  cmdID= 10092
                    SDI 1  value= 0
                    SDI 2  value= 1
                    SDI 3  value= 2
                    SDI 4  value= 3
                    CVBS A  value= 4
                    CVBS B  value= 5
                    CVBS C  value= 6
                    CVBS D  value= 7
                    SFP A1  value= 8
                    SFP A2  value= 9
                    SFP A3  value= 10
                    SFP A4  value= 11
                    Output  value= 20  "
        ::= { kudosConv4CtrlEntries 10092 }


    i4ARCSidebarKeyingOutputCropOutputCropPositionTop OBJECT-TYPE
        SYNTAX            INTEGER
        MAX-ACCESS        read-write
        STATUS            current
        DESCRIPTION
                "CMNT: - 
                 TYPE: - Number
                 PAGE: - Sidebar Keying & Output Crop
                    Top  cmdID= 10093
                    min= 0  max= 99  step= 1  format= %0.0f%%  div_scale= 1  preset= 0
                    Min = 0%  Max = 99%  Step = 1%  Preset = 0%  "
        ::= { kudosConv4CtrlEntries 10093 }


    i4ARCSidebarKeyingOutputCropOutputCropPositionBottom OBJECT-TYPE
        SYNTAX            INTEGER
        MAX-ACCESS        read-write
        STATUS            current
        DESCRIPTION
                "CMNT: - 
                 TYPE: - Number
                 PAGE: - Sidebar Keying & Output Crop
                    Bottom  cmdID= 10094
                    min= 0  max= 99  step= 1  format= %0.0f%%  div_scale= 1  preset= 0
                    Min = 0%  Max = 99%  Step = 1%  Preset = 0%  "
        ::= { kudosConv4CtrlEntries 10094 }


    i4ARCSidebarKeyingOutputCropOutputCropPositionLeft OBJECT-TYPE
        SYNTAX            INTEGER
        MAX-ACCESS        read-write
        STATUS            current
        DESCRIPTION
                "CMNT: - 
                 TYPE: - Number
                 PAGE: - Sidebar Keying & Output Crop
                    Left  cmdID= 10095
                    min= 0  max= 99  step= 1  format= %0.0f%%  div_scale= 1  preset= 0
                    Min = 0%  Max = 99%  Step = 1%  Preset = 0%  "
        ::= { kudosConv4CtrlEntries 10095 }


    i4ARCSidebarKeyingOutputCropOutputCropPositionRight OBJECT-TYPE
        SYNTAX            INTEGER
        MAX-ACCESS        read-write
        STATUS            current
        DESCRIPTION
                "CMNT: - 
                 TYPE: - Number
                 PAGE: - Sidebar Keying & Output Crop
                    Right  cmdID= 10096
                    min= 0  max= 99  step= 1  format= %0.0f%%  div_scale= 1  preset= 0
                    Min = 0%  Max = 99%  Step = 1%  Preset = 0%  "
        ::= { kudosConv4CtrlEntries 10096 }


    i4ARCPostScalingControlPostScalingEnable OBJECT-TYPE
        SYNTAX            INTEGER { disable(0), enable(1)  }
        MAX-ACCESS        read-write
        STATUS            current
        DESCRIPTION
                "CMNT: - 
                 TYPE: - Checkbox
                 PAGE: - ARC
                    Post Scaling Enable  cmdID= 10078  "
        ::= { kudosConv4CtrlEntries 10078 }


    i4ARCPostScalingControlSize OBJECT-TYPE
        SYNTAX            INTEGER
        MAX-ACCESS        read-write
        STATUS            current
        DESCRIPTION
                "CMNT: - 
                 TYPE: - Number
                 PAGE: - ARC
                    Size  cmdID= 10074
                    min= 80  max= 120  step= 1  format= %0.0f%%  div_scale= 1  preset= 100
                    Min = 80%  Max = 120%  Step = 1%  Preset = 100%  "
        ::= { kudosConv4CtrlEntries 10074 }


    i4ARCPostScalingControlAspect OBJECT-TYPE
        SYNTAX            INTEGER
        MAX-ACCESS        read-write
        STATUS            current
        DESCRIPTION
                "CMNT: - 
                 TYPE: - Number
                 PAGE: - ARC
                    Aspect  cmdID= 10075
                    min= 70  max= 150  step= 1  format= %0.0f%%  div_scale= 1  preset= 100
                    Min = 70%  Max = 150%  Step = 1%  Preset = 100%  "
        ::= { kudosConv4CtrlEntries 10075 }


    i4ARCPostScalingControlPan OBJECT-TYPE
        SYNTAX            INTEGER
        MAX-ACCESS        read-write
        STATUS            current
        DESCRIPTION
                "CMNT: - 
                 TYPE: - Number
                 PAGE: - ARC
                    Pan  cmdID= 10076
                    min= -50  max= 50  step= 1  format= %0.0f%  div_scale= 1  preset= 0
                    Min = -50  Max = 50  Step = 1  Preset = 0  "
        ::= { kudosConv4CtrlEntries 10076 }


    i4ARCPostScalingControlTilt OBJECT-TYPE
        SYNTAX            INTEGER
        MAX-ACCESS        read-write
        STATUS            current
        DESCRIPTION
                "CMNT: - 
                 TYPE: - Number
                 PAGE: - ARC
                    Tilt  cmdID= 10077
                    min= -50  max= 50  step= 1  format= %0.0f%  div_scale= 1  preset= 0
                    Min = -50  Max = 50  Step = 1  Preset = 0  "
        ::= { kudosConv4CtrlEntries 10077 }


    i4ARCScalerConfigUsePresets OBJECT-TYPE
        SYNTAX            INTEGER { disable(0), enable(1)  }
        MAX-ACCESS        read-write
        STATUS            current
        DESCRIPTION
                "CMNT: - 
                 TYPE: - Checkbox
                 PAGE: - ARC
                    Use Presets  cmdID= 10110  "
        ::= { kudosConv4CtrlEntries 10110 }


    i4ARCScalerConfigPresetsSDInputis702 OBJECT-TYPE
        SYNTAX            INTEGER { disable(0), enable(1)  }
        MAX-ACCESS        read-write
        STATUS            current
        DESCRIPTION
                "CMNT: - 
                 TYPE: - Checkbox
                 PAGE: - Scaler Config
                    SD Input is 702  cmdID= 10080  "
        ::= { kudosConv4CtrlEntries 10080 }


    i4ARCScalerConfigPresetsSDOutputis702 OBJECT-TYPE
        SYNTAX            INTEGER { disable(0), enable(1)  }
        MAX-ACCESS        read-write
        STATUS            current
        DESCRIPTION
                "CMNT: - 
                 TYPE: - Checkbox
                 PAGE: - Scaler Config
                    SD Output is 702  cmdID= 10081  "
        ::= { kudosConv4CtrlEntries 10081 }


    i4ARCPresetsSDCrossConversionSelectStdPreset OBJECT-TYPE
        SYNTAX            INTEGER {
                            valNone(0),
                            val169LB43HC(1),
                            val169LB169Ana(2),
                            val169LB149LB(3),
                            val169Ana43HC(4),
                            val169Ana169LB(5),
                            val169Ana149LB(6)
                            }
        MAX-ACCESS        read-write
        STATUS            current
        DESCRIPTION
                "CMNT: - 
                 TYPE: - RadiobuttonList
                 PAGE: - Presets
                    Select Std Preset  cmdID= 10082
                    None  value= 0
                    16:9 LB > 4:3 HC  value= 1
                    16:9 LB > 16:9 Ana  value= 2
                    16:9 LB > 14:9 LB  value= 3
                    16:9 Ana > 4:3 HC  value= 4
                    16:9 Ana > 16:9 LB  value= 5
                    16:9 Ana > 14:9 LB  value= 6  "
        ::= { kudosConv4CtrlEntries 10082 }


    i4ARCPresetsHDCrossConversionSelectStdPreset OBJECT-TYPE
        SYNTAX            INTEGER {
                            valNone(0),
                            val149PB169VC(1),
                            val43PB169VC(2),
                            val43PB149PBVC(3)
                            }
        MAX-ACCESS        read-write
        STATUS            current
        DESCRIPTION
                "CMNT: - 
                 TYPE: - RadiobuttonList
                 PAGE: - Presets
                    Select Std Preset  cmdID= 10083
                    None  value= 0
                    14:9 PB > 16:9 VC  value= 1
                    4:3 PB > 16:9 VC  value= 2
                    4:3 PB > 14:9 PB VC  value= 3  "
        ::= { kudosConv4CtrlEntries 10083 }


    i4ARCPresetsUpConversionSelectStdPreset OBJECT-TYPE
        SYNTAX            INTEGER {
                            val43169VC(0),
                            val4343PB(1),
                            val169LB169(2),
                            val169Ana169(3),
                            val149LB149PB(4)
                            }
        MAX-ACCESS        read-write
        STATUS            current
        DESCRIPTION
                "CMNT: - 
                 TYPE: - RadiobuttonList
                 PAGE: - Presets
                    Select Std Preset  cmdID= 10084
                    4:3 > 16:9 VC  value= 0
                    4:3 > 4:3 PB  value= 1
                    16:9 LB > 16:9  value= 2
                    16:9 Ana > 16:9  value= 3
                    14:9 LB > 14:9 PB  value= 4  "
        ::= { kudosConv4CtrlEntries 10084 }


    i4ARCPresetsDownConversionSelectStdPreset OBJECT-TYPE
        SYNTAX            INTEGER {
                            val16943HC(0),
                            val169169LB(1),
                            val169169Ana(2),
                            val43PB43(3),
                            val149PB149LB(4)
                            }
        MAX-ACCESS        read-write
        STATUS            current
        DESCRIPTION
                "CMNT: - 
                 TYPE: - RadiobuttonList
                 PAGE: - Presets
                    Select Std Preset  cmdID= 10085
                    16:9 > 4:3 HC  value= 0
                    16:9 > 16:9 LB  value= 1
                    16:9 > 16:9 Ana  value= 2
                    4:3 PB > 4:3  value= 3
                    14:9 PB > 14:9 LB  value= 4  "
        ::= { kudosConv4CtrlEntries 10085 }


    i4ARCScalerConfigInputConfigInputSignallingSource OBJECT-TYPE
        SYNTAX            INTEGER {
                            valSMPTE2016(0),
                            valL23ETSI(1),
                            valL23AFD(2),
                            valVISMPTE(3),
                            valVIAFD(4)
                            }
        MAX-ACCESS        read-write
        STATUS            current
        DESCRIPTION
                "CMNT: - 
                 TYPE: - RadiobuttonList
                 PAGE: - Scaler Config
                    Input Signalling Source  cmdID= 10090
                    SMPTE 2016  value= 0
                    L23 ETSI  value= 1
                    L23 AFD  value= 2
                    VI SMPTE  value= 3
                    VI AFD  value= 4  "
        ::= { kudosConv4CtrlEntries 10090 }


    i4ARCInputConfigIfInputSignallingNotPresentForceInputFormat OBJECT-TYPE
        SYNTAX            INTEGER { disable(0), enable(1)  }
        MAX-ACCESS        read-write
        STATUS            current
        DESCRIPTION
                "CMNT: - 
                 TYPE: - Checkbox
                 PAGE: - Input Config
                    Force Input Format  cmdID= 10109  "
        ::= { kudosConv4CtrlEntries 10109 }


    i4ARCInputConfigIfInputSignallingNotPresentSDInputFormat OBJECT-TYPE
        SYNTAX            INTEGER {
                            valNormal(0),
                            valAnamorphic(1),
                            val169Letterbox(2),
                            val149Letterbox(3)
                            }
        MAX-ACCESS        read-write
        STATUS            current
        DESCRIPTION
                "CMNT: - 
                 TYPE: - RadiobuttonList
                 PAGE: - Input Config
                    SD Input Format  cmdID= 10086
                    Normal  value= 0
                    Anamorphic  value= 1
                    16:9 Letterbox  value= 2
                    14:9 Letterbox  value= 3  "
        ::= { kudosConv4CtrlEntries 10086 }


    i4ARCInputConfigIfInputSignallingNotPresentHDInputFormat OBJECT-TYPE
        SYNTAX            INTEGER {
                            valNormal(0),
                            val149Pillarbox(1),
                            val43Pillarbox(2)
                            }
        MAX-ACCESS        read-write
        STATUS            current
        DESCRIPTION
                "CMNT: - 
                 TYPE: - RadiobuttonList
                 PAGE: - Input Config
                    HD Input Format  cmdID= 10087
                    Normal  value= 0
                    14:9 Pillarbox  value= 1
                    4:3 Pillarbox  value= 2  "
        ::= { kudosConv4CtrlEntries 10087 }


    i4ARCScalerConfigOutputConfigConversionScaling OBJECT-TYPE
        SYNTAX            INTEGER {
                            valFittoHeight(0),
                            valFittoWidth(1),
                            val149(2)
                            }
        MAX-ACCESS        read-write
        STATUS            current
        DESCRIPTION
                "CMNT: - 
                 TYPE: - RadiobuttonList
                 PAGE: - Scaler Config
                    Conversion Scaling  cmdID= 10089
                    Fit to Height  value= 0
                    Fit to Width  value= 1
                    14:9  value= 2  "
        ::= { kudosConv4CtrlEntries 10089 }


    i4ARCScalerConfigOutputConfigSDOutputFormat OBJECT-TYPE
        SYNTAX            INTEGER {
                            valNormal(0),
                            valAnamorphic(1)
                            }
        MAX-ACCESS        read-write
        STATUS            current
        DESCRIPTION
                "CMNT: - 
                 TYPE: - RadiobuttonList
                 PAGE: - Scaler Config
                    SD Output Format  cmdID= 10088
                    Normal  value= 0
                    Anamorphic  value= 1  "
        ::= { kudosConv4CtrlEntries 10088 }


    i4ARCOutputSignallingConfigSMPTE2016Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10104
                    Auto  value= 0
                    Pass  value= 1
                    Force  value= 2
                    Delete  value= 3  "
        ::= { kudosConv4CtrlEntries 10104 }


    i4ARCOutputSignallingConfigSMPTE2016OutputLinePAL OBJECT-TYPE
        SYNTAX            INTEGER
        MAX-ACCESS        read-write
        STATUS            current
        DESCRIPTION
                "CMNT: - 
                 TYPE: - Number
                 PAGE: - Output Signalling Config
                    Output Line PAL  cmdID= 10332
                    min= 7  max= 22  step= 1  format= %0.0f  div_scale= 1  preset= 12
                    Min = 7  Max = 22  Step = 1  Preset = 12  "
        ::= { kudosConv4CtrlEntries 10332 }


    i4ARCOutputSignallingConfigSMPTE2016OutputLineNTSC OBJECT-TYPE
        SYNTAX            INTEGER
        MAX-ACCESS        read-write
        STATUS            current
        DESCRIPTION
                "CMNT: - 
                 TYPE: - Number
                 PAGE: - Output Signalling Config
                    Output Line NTSC  cmdID= 10333
                    min= 11  max= 19  step= 1  format= %0.0f  div_scale= 1  preset= 11
                    Min = 11  Max = 19  Step = 1  Preset = 11  "
        ::= { kudosConv4CtrlEntries 10333 }


    i4ARCOutputSignallingConfigSMPTE2016OutputLineHD OBJECT-TYPE
        SYNTAX            INTEGER
        MAX-ACCESS        read-write
        STATUS            current
        DESCRIPTION
                "CMNT: - 
                 TYPE: - Number
                 PAGE: - Output Signalling Config
                    Output Line HD  cmdID= 10331
                    min= 9  max= 20  step= 1  format= %0.0f  div_scale= 1  preset= 11
                    Min = 9  Max = 20  Step = 1  Preset = 11  "
        ::= { kudosConv4CtrlEntries 10331 }


    i4ARCOutputSignallingConfigSMPTE2016OutputLineStatus OBJECT-TYPE
        SYNTAX            RollCallString
        MAX-ACCESS        read-only
        STATUS            current
        DESCRIPTION
                "CMNT: - 
                 TYPE: - Display
                 PAGE: - Output Signalling Config
                    Output Line Status  cmdID= 10334  "
        ::= { kudosConv4CtrlEntries 10334 }


    i4ARCOutputSignallingConfigVIMode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10101
                    Auto  value= 0
                    Pass  value= 1
                    Force  value= 2
                    Delete  value= 3  "
        ::= { kudosConv4CtrlEntries 10101 }


    i4ARCOutputSignallingConfigVIOutputFormat OBJECT-TYPE
        SYNTAX            INTEGER {
                            valSMPTE(0),
                            valAFD(1)
                            }
        MAX-ACCESS        read-write
        STATUS            current
        DESCRIPTION
                "CMNT: - 
                 TYPE: - RadiobuttonList
                 PAGE: - Output Signalling Config
                    Output Format  cmdID= 10102
                    SMPTE  value= 0
                    AFD  value= 1  "
        ::= { kudosConv4CtrlEntries 10102 }


    i4ARCOutputSignallingConfigVIPassData OBJECT-TYPE
        SYNTAX            INTEGER { disable(0), enable(1)  }
        MAX-ACCESS        read-write
        STATUS            current
        DESCRIPTION
                "CMNT: - 
                 TYPE: - Checkbox
                 PAGE: - ARC
                    VI Pass Data  cmdID= 10103  "
        ::= { kudosConv4CtrlEntries 10103 }


    i4ARCOutputSignallingConfigL23Mode OBJECT-TYPE
        SYNTAX            INTEGER {
                            valAuto(0),
                            valPass(1),
                            valForce(2),
                            valDelete(3)
                            }
        MAX-ACCESS        read-write
        STATUS            current
        DESCRIPTION
                "CMNT: - 
                 TYPE: - RadiobuttonList
                 PAGE: - Output Signalling Config
                    Mode  cmdID= 10099
                    Auto  value= 0
                    Pass  value= 1
                    Force  value= 2
                    Delete  value= 3  "
        ::= { kudosConv4CtrlEntries 10099 }


    i4ARCOutputSignallingConfigL23OutputFormat OBJECT-TYPE
        SYNTAX            INTEGER {
                            valETSI(0),
                            valAFD(1)
                            }
        MAX-ACCESS        read-write
        STATUS            current
        DESCRIPTION
                "CMNT: - 
                 TYPE: - RadiobuttonList
                 PAGE: - Output Signalling Config
                    Output Format  cmdID= 10100
                    ETSI  value= 0
                    AFD  value= 1  "
        ::= { kudosConv4CtrlEntries 10100 }


    i4ARCOutputSignallingConfigL23InputLine OBJECT-TYPE
        SYNTAX            INTEGER
        MAX-ACCESS        read-write
        STATUS            current
        DESCRIPTION
                "CMNT: - 
                 TYPE: - Number
                 PAGE: - Output Signalling Config
                    Input Line  cmdID= 10097
                    min= 10  max= 23  step= 1  format= %0.0f  div_scale= 1  preset= 23
                    Min = 10  Max = 23  Step = 1  Preset = 23  "
        ::= { kudosConv4CtrlEntries 10097 }


    i4ARCOutputSignallingConfigL23OutputLine OBJECT-TYPE
        SYNTAX            INTEGER
        MAX-ACCESS        read-write
        STATUS            current
        DESCRIPTION
                "CMNT: - 
                 TYPE: - Number
                 PAGE: - Output Signalling Config
                    Output Line  cmdID= 10098
                    min= 10  max= 23  step= 1  format= %0.0f  div_scale= 1  preset= 23
                    Min = 10  Max = 23  Step = 1  Preset = 23  "
        ::= { kudosConv4CtrlEntries 10098 }


    i4ARCOutputSignallingConfigL23OutputLineStatus OBJECT-TYPE
        SYNTAX            RollCallString
        MAX-ACCESS        read-only
        STATUS            current
        DESCRIPTION
                "CMNT: - 
                 TYPE: - Display
                 PAGE: - Output Signalling Config
                    Output Line Status  cmdID= 10339  "
        ::= { kudosConv4CtrlEntries 10339 }


    i4ARCL23AFDUserBitsForceUserBitsValue OBJECT-TYPE
        SYNTAX            INTEGER { disable(0), enable(1)  }
        MAX-ACCESS        read-write
        STATUS            current
        DESCRIPTION
                "CMNT: - 
                 TYPE: - Checkbox
                 PAGE: - L23
                    Force User Bits Value  cmdID= 10336  "
        ::= { kudosConv4CtrlEntries 10336 }


    i4ARCL23AFDUserBitsUserBitsValue OBJECT-TYPE
        SYNTAX            INTEGER
        MAX-ACCESS        read-write
        STATUS            current
        DESCRIPTION
                "CMNT: - 
                 TYPE: - Number
                 PAGE: - L23
                    User Bits Value  cmdID= 10111
                    min= 0  max= 15  step= 1  format= %0.0f  div_scale= 1  preset= 0
                    Min = 0  Max = 15  Step = 1  Preset = 0  "
        ::= { kudosConv4CtrlEntries 10111 }


    i4ARCOutputSignallingConfigForceModeConfigSMPTE2016 OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val43AFD8(8),
                            val43AFD9(9),
                            val43AFD10(10),
                            val43AFD11(11),
                            val43AFD12(12),
                            val43AFD13(13),
                            val43AFD14(14),
                            val43AFD15(15),
                            val169AFD0(16),
                            val169AFD1(17),
                            val169AFD2(18),
                            val169AFD3(19),
                            val169AFD4(20),
                            val169AFD5(21),
                            val169AFD6(22),
                            val169AFD7(23),
                            val169AFD8(24),
                            val169AFD9(25),
                            val169AFD10(26),
                            val169AFD11(27),
                            val169AFD12(28),
                            val169AFD13(29),
                            val169AFD14(30),
                            val169AFD15(31)
                            }
        MAX-ACCESS        read-write
        STATUS            current
        DESCRIPTION
                "CMNT: - 
                 TYPE: - RadiobuttonList
                 PAGE: - Output Signalling Config
                    SMPTE 2016  cmdID= 10107
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    4:3 AFD 8  value= 8
                    4:3 AFD 9  value= 9
                    4:3 AFD 10  value= 10
                    4:3 AFD 11  value= 11
                    4:3 AFD 12  value= 12
                    4:3 AFD 13  value= 13
                    4:3 AFD 14  value= 14
                    4:3 AFD 15  value= 15
                    16:9 AFD 0  value= 16
                    16:9 AFD 1  value= 17
                    16:9 AFD 2  value= 18
                    16:9 AFD 3  value= 19
                    16:9 AFD 4  value= 20
                    16:9 AFD 5  value= 21
                    16:9 AFD 6  value= 22
                    16:9 AFD 7  value= 23
                    16:9 AFD 8  value= 24
                    16:9 AFD 9  value= 25
                    16:9 AFD 10  value= 26
                    16:9 AFD 11  value= 27
                    16:9 AFD 12  value= 28
                    16:9 AFD 13  value= 29
                    16:9 AFD 14  value= 30
                    16:9 AFD 15  value= 31  "
        ::= { kudosConv4CtrlEntries 10107 }


    i4ARCOutputSignallingConfigForceModeConfigSMPTERP186 OBJECT-TYPE
        SYNTAX            INTEGER {
                            val43(0),
                            val169(1)
                            }
        MAX-ACCESS        read-write
        STATUS            current
        DESCRIPTION
                "CMNT: - 
                 TYPE: - RadiobuttonList
                 PAGE: - Output Signalling Config
                    SMPTE RP186  cmdID= 10108
                    4:3  value= 0
                    16:9  value= 1  "
        ::= { kudosConv4CtrlEntries 10108 }


    i4ARCOutputSignallingConfigForceModeConfigAFD OBJECT-TYPE
        SYNTAX            INTEGER {
                            val43AFD0(0),
                            val43AFD1(1),
                            val43AFD2(2),
                            val43AFD3(3),
                            val43AFD4(4),
                            val43AFD5(5),
                            val43AFD6(6),
                            val43AFD7(7),
                            val169AFD0(8),
                            val169AFD1(9),
                            val169AFD2(10),
                            val169AFD3(11),
                            val169AFD4(12),
                            val169AFD5(13),
                            val169AFD6(14),
                            val169AFD7(15)
                            }
        MAX-ACCESS        read-write
        STATUS            current
        DESCRIPTION
                "CMNT: - 
                 TYPE: - RadiobuttonList
                 PAGE: - Output Signalling Config
                    AFD  cmdID= 10105
                    4:3 AFD 0  value= 0
                    4:3 AFD 1  value= 1
                    4:3 AFD 2  value= 2
                    4:3 AFD 3  value= 3
                    4:3 AFD 4  value= 4
                    4:3 AFD 5  value= 5
                    4:3 AFD 6  value= 6
                    4:3 AFD 7  value= 7
                    16:9 AFD 0  value= 8
                    16:9 AFD 1  value= 9
                    16:9 AFD 2  value= 10
                    16:9 AFD 3  value= 11
                    16:9 AFD 4  value= 12
                    16:9 AFD 5  value= 13
                    16:9 AFD 6  value= 14
                    16:9 AFD 7  value= 15  "
        ::= { kudosConv4CtrlEntries 10105 }


    i4ARCOutputSignallingConfigForceModeConfigETSI OBJECT-TYPE
        SYNTAX            INTEGER {
                            val43FF(0),
                            val149Centre(1),
                            val149Top(2),
                            val169Centre(3),
                            val169Top(4),
                            valGr169Centre(5),
                            val43SP149(6),
                            val169FF(7)
                            }
        MAX-ACCESS        read-write
        STATUS            current
        DESCRIPTION
                "CMNT: - 
                 TYPE: - RadiobuttonList
                 PAGE: - Output Signalling Config
                    ETSI  cmdID= 10106
                    4:3 FF  value= 0
                    14:9 Centre  value= 1
                    14:9 Top  value= 2
                    16:9 Centre  value= 3
                    16:9 Top  value= 4
                    Gr 16:9 Centre  value= 5
                    4:3 SP 14:9  value= 6
                    16:9 FF  value= 7  "
        ::= { kudosConv4CtrlEntries 10106 }


    i4AudioRoutingInputPairsStatusEmbedded1 OBJECT-TYPE
        SYNTAX            RollCallString
        MAX-ACCESS        read-only
        STATUS            current
        DESCRIPTION
                "CMNT: - 
                 TYPE: - Display
                 PAGE: - Routing
                    Embedded 1  cmdID= 10282  "
        ::= { kudosConv4CtrlEntries 10282 }


    i4AudioRoutingInputPairsStatusEmbedded2 OBJECT-TYPE
        SYNTAX            RollCallString
        MAX-ACCESS        read-only
        STATUS            current
        DESCRIPTION
                "CMNT: - 
                 TYPE: - Display
                 PAGE: - Routing
                    Embedded 2  cmdID= 10283  "
        ::= { kudosConv4CtrlEntries 10283 }


    i4AudioRoutingInputPairsStatusEmbedded3 OBJECT-TYPE
        SYNTAX            RollCallString
        MAX-ACCESS        read-only
        STATUS            current
        DESCRIPTION
                "CMNT: - 
                 TYPE: - Display
                 PAGE: - Routing
                    Embedded 3  cmdID= 10284  "
        ::= { kudosConv4CtrlEntries 10284 }


    i4AudioRoutingInputPairsStatusEmbedded4 OBJECT-TYPE
        SYNTAX            RollCallString
        MAX-ACCESS        read-only
        STATUS            current
        DESCRIPTION
                "CMNT: - 
                 TYPE: - Display
                 PAGE: - Routing
                    Embedded 4  cmdID= 10285  "
        ::= { kudosConv4CtrlEntries 10285 }


    i4AudioRoutingInputPairsStatusEmbedded5 OBJECT-TYPE
        SYNTAX            RollCallString
        MAX-ACCESS        read-only
        STATUS            current
        DESCRIPTION
                "CMNT: - 
                 TYPE: - Display
                 PAGE: - Routing
                    Embedded 5  cmdID= 10286  "
        ::= { kudosConv4CtrlEntries 10286 }


    i4AudioRoutingInputPairsStatusEmbedded6 OBJECT-TYPE
        SYNTAX            RollCallString
        MAX-ACCESS        read-only
        STATUS            current
        DESCRIPTION
                "CMNT: - 
                 TYPE: - Display
                 PAGE: - Routing
                    Embedded 6  cmdID= 10287  "
        ::= { kudosConv4CtrlEntries 10287 }


    i4AudioRoutingInputPairsStatusEmbedded7 OBJECT-TYPE
        SYNTAX            RollCallString
        MAX-ACCESS        read-only
        STATUS            current
        DESCRIPTION
                "CMNT: - 
                 TYPE: - Display
                 PAGE: - Routing
                    Embedded 7  cmdID= 10288  "
        ::= { kudosConv4CtrlEntries 10288 }


    i4AudioRoutingInputPairsStatusEmbedded8 OBJECT-TYPE
        SYNTAX            RollCallString
        MAX-ACCESS        read-only
        STATUS            current
        DESCRIPTION
                "CMNT: - 
                 TYPE: - Display
                 PAGE: - Routing
                    Embedded 8  cmdID= 10289  "
        ::= { kudosConv4CtrlEntries 10289 }


    i4AudioRoutingInputPairsStatusAES1 OBJECT-TYPE
        SYNTAX            RollCallString
        MAX-ACCESS        read-only
        STATUS            current
        DESCRIPTION
                "CMNT: - 
                 TYPE: - Display
                 PAGE: - Routing
                    AES 1  cmdID= 10290  "
        ::= { kudosConv4CtrlEntries 10290 }


    i4AudioRoutingInputPairsStatusAES2 OBJECT-TYPE
        SYNTAX            RollCallString
        MAX-ACCESS        read-only
        STATUS            current
        DESCRIPTION
                "CMNT: - 
                 TYPE: - Display
                 PAGE: - Routing
                    AES 2  cmdID= 10291  "
        ::= { kudosConv4CtrlEntries 10291 }


    i4AudioRoutingInputPairsStatusAES3 OBJECT-TYPE
        SYNTAX            RollCallString
        MAX-ACCESS        read-only
        STATUS            current
        DESCRIPTION
                "CMNT: - 
                 TYPE: - Display
                 PAGE: - Routing
                    AES 3  cmdID= 10292  "
        ::= { kudosConv4CtrlEntries 10292 }


    i4AudioRoutingInputPairsStatusAES4 OBJECT-TYPE
        SYNTAX            RollCallString
        MAX-ACCESS        read-only
        STATUS            current
        DESCRIPTION
                "CMNT: - 
                 TYPE: - Display
                 PAGE: - Routing
                    AES 4  cmdID= 10293  "
        ::= { kudosConv4CtrlEntries 10293 }


    i4AudioRoutingInputPairsStatusAnalog1 OBJECT-TYPE
        SYNTAX            RollCallString
        MAX-ACCESS        read-only
        STATUS            current
        DESCRIPTION
                "CMNT: - 
                 TYPE: - Display
                 PAGE: - Routing
                    Analog 1  cmdID= 10294  "
        ::= { kudosConv4CtrlEntries 10294 }


    i4AudioRoutingInputPairsStatusAnalog2 OBJECT-TYPE
        SYNTAX            RollCallString
        MAX-ACCESS        read-only
        STATUS            current
        DESCRIPTION
                "CMNT: - 
                 TYPE: - Display
                 PAGE: - Routing
                    Analog 2  cmdID= 10295  "
        ::= { kudosConv4CtrlEntries 10295 }


    i4AudioRoutingInputPairsStatusAnalog3 OBJECT-TYPE
        SYNTAX            RollCallString
        MAX-ACCESS        read-only
        STATUS            current
        DESCRIPTION
                "CMNT: - 
                 TYPE: - Display
                 PAGE: - Routing
                    Analog 3  cmdID= 10296  "
        ::= { kudosConv4CtrlEntries 10296 }


    i4AudioRoutingInputPairsStatusAnalog4 OBJECT-TYPE
        SYNTAX            RollCallString
        MAX-ACCESS        read-only
        STATUS            current
        DESCRIPTION
                "CMNT: - 
                 TYPE: - Display
                 PAGE: - Routing
                    Analog 4  cmdID= 10297  "
        ::= { kudosConv4CtrlEntries 10297 }


    i4AudioRoutingInputPairsStatusDolbyDecoder1 OBJECT-TYPE
        SYNTAX            RollCallString
        MAX-ACCESS        read-only
        STATUS            current
        DESCRIPTION
                "CMNT: - 
                 TYPE: - Display
                 PAGE: - Routing
                    Dolby Decoder 1  cmdID= 10298  "
        ::= { kudosConv4CtrlEntries 10298 }


    i4AudioRoutingInputPairsStatusDolbyDecoder2 OBJECT-TYPE
        SYNTAX            RollCallString
        MAX-ACCESS        read-only
        STATUS            current
        DESCRIPTION
                "CMNT: - 
                 TYPE: - Display
                 PAGE: - Routing
                    Dolby Decoder 2  cmdID= 10299  "
        ::= { kudosConv4CtrlEntries 10299 }


    i4AudioRoutingInputPairsStatusDolbyDecoder3 OBJECT-TYPE
        SYNTAX            RollCallString
        MAX-ACCESS        read-only
        STATUS            current
        DESCRIPTION
                "CMNT: - 
                 TYPE: - Display
                 PAGE: - Routing
                    Dolby Decoder 3  cmdID= 10300  "
        ::= { kudosConv4CtrlEntries 10300 }


    i4AudioRoutingInputPairsStatusDolbyDecoder4 OBJECT-TYPE
        SYNTAX            RollCallString
        MAX-ACCESS        read-only
        STATUS            current
        DESCRIPTION
                "CMNT: - 
                 TYPE: - Display
                 PAGE: - Routing
                    Dolby Decoder 4  cmdID= 10301  "
        ::= { kudosConv4CtrlEntries 10301 }


    i4AudioRoutingInputPairsStatusDolbyDownmix OBJECT-TYPE
        SYNTAX            RollCallString
        MAX-ACCESS        read-only
        STATUS            current
        DESCRIPTION
                "CMNT: - 
                 TYPE: - Display
                 PAGE: - Routing
                    Dolby Downmix  cmdID= 10302  "
        ::= { kudosConv4CtrlEntries 10302 }


    i4AudioRoutingInputPairsStatusDolbyEncoder OBJECT-TYPE
        SYNTAX            RollCallString
        MAX-ACCESS        read-only
        STATUS            current
        DESCRIPTION
                "CMNT: - 
                 TYPE: - Display
                 PAGE: - Routing
                    Dolby Encoder  cmdID= 10303  "
        ::= { kudosConv4CtrlEntries 10303 }


    i4AudioRoutingProcessPair1InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10112
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv4CtrlEntries 10112 }


    i4AudioRoutingProcessPair2InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10113
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv4CtrlEntries 10113 }


    i4AudioRoutingProcessPair3InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10114
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv4CtrlEntries 10114 }


    i4AudioRoutingProcessPair4InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10115
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv4CtrlEntries 10115 }


    i4AudioRoutingProcessPair5InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10116
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv4CtrlEntries 10116 }


    i4AudioRoutingProcessPair6InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10117
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv4CtrlEntries 10117 }


    i4AudioRoutingProcessPair7InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10118
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv4CtrlEntries 10118 }


    i4AudioRoutingProcessPair8InputPairsSource OBJECT-TYPE
        SYNTAX            INTEGER {
                            valEmbedded1(1),
                            valEmbedded2(2),
                            valEmbedded3(3),
                            valEmbedded4(4),
                            valEmbedded5(5),
                            valEmbedded6(6),
                            valEmbedded7(7),
                            valEmbedded8(8),
                            valAES1(9),
                            valAES2(10),
                            valAES3(11),
                            valAES4(12),
                            valAnalog1(13),
                            valAnalog2(14),
                            valAnalog3(15),
                            valAnalog4(16),
                            valDolbyDecoder1(17),
                            valDolbyDecoder2(18),
                            valDolbyDecoder3(19),
                            valDolbyDecoder4(20),
                            valDolbyDownmix(21),
                            valDolbyEncoder(22)
                            }
        MAX-ACCESS        read-write
        STATUS            current
        DESCRIPTION
                "CMNT: - 
                 TYPE: - RadiobuttonList
                 PAGE: - Routing
                    Input Pairs Source  cmdID= 10119
                    Embedded 1  value= 1
                    Embedded 2  value= 2
                    Embedded 3  value= 3
                    Embedded 4  value= 4
                    Embedded 5  value= 5
                    Embedded 6  value= 6
                    Embedded 7  value= 7
                    Embedded 8  value= 8
                    AES 1  value= 9
                    AES 2  value= 10
                    AES 3  value= 11
                    AES 4  value= 12
                    Analog 1  value= 13
                    Analog 2  value= 14
                    Analog 3  value= 15
                    Analog 4  value= 16
                    Dolby Decoder 1  value= 17
                    Dolby Decoder 2  value= 18
                    Dolby Decoder 3  value= 19
                    Dolby Decoder 4  value= 20
                    Dolby Downmix  value= 21
                    Dolby Encoder  value= 22  "
        ::= { kudosConv4CtrlEntries 10119 }


    i4AudioRoutingProcessPairs18StatusPair1 OBJECT-TYPE
        SYNTAX            RollCallString
        MAX-ACCESS        read-only
        STATUS            current
        DESCRIPTION
                "CMNT: - 
                 TYPE: - Display
                 PAGE: - Routing
                    Pair 1  cmdID= 10304  "
        ::= { kudosConv4CtrlEntries 10304 }


    i4AudioRoutingProcessPairs18StatusPair2 OBJECT-TYPE
        SYNTAX            RollCallString
        MAX-ACCESS        read-only
        STATUS            current
        DESCRIPTION
                "CMNT: - 
                 TYPE: - Display
                 PAGE: - Routing
                    Pair 2  cmdID= 10305  "
        ::= { kudosConv4CtrlEntries 10305 }


    i4AudioRoutingProcessPairs18StatusPair3 OBJECT-TYPE
        SYNTAX            RollCallString
        MAX-ACCESS        read-only
        STATUS            current
        DESCRIPTION
                "CMNT: - 
                 TYPE: - Display
                 PAGE: - Routing
                    Pair 3  cmdID= 10306  "
        ::= { kudosConv4CtrlEntries 10306 }


    i4AudioRoutingProcessPairs18StatusPair4 OBJECT-TYPE
        SYNTAX            RollCallString
        MAX-ACCESS        read-only
        STATUS            current
        DESCRIPTION
                "CMNT: - 
                 TYPE: - Display
                 PAGE: - Routing
                    Pair 4  cmdID= 10307  "
        ::= { kudosConv4CtrlEntries 10307 }


    i4AudioRoutingProcessPairs18StatusPair5 OBJECT-TYPE
        SYNTAX            RollCallString
        MAX-ACCESS        read-only
        STATUS            current
        DESCRIPTION
                "CMNT: - 
                 TYPE: - Display
                 PAGE: - Routing
                    Pair 5  cmdID= 10308  "
        ::= { kudosConv4CtrlEntries 10308 }


    i4AudioRoutingProcessPairs18StatusPair6 OBJECT-TYPE
        SYNTAX            RollCallString
        MAX-ACCESS        read-only
        STATUS            current
        DESCRIPTION
                "CMNT: - 
                 TYPE: - Display
                 PAGE: - Routing
                    Pair 6  cmdID= 10309  "
        ::= { kudosConv4CtrlEntries 10309 }


    i4AudioRoutingProcessPairs18StatusPair7 OBJECT-TYPE
        SYNTAX            RollCallString
        MAX-ACCESS        read-only
        STATUS            current
        DESCRIPTION
                "CMNT: - 
                 TYPE: - Display
                 PAGE: - Routing
                    Pair 7  cmdID= 10310  "
        ::= { kudosConv4CtrlEntries 10310 }


    i4AudioRoutingProcessPairs18StatusPair8 OBJECT-TYPE
        SYNTAX            RollCallString
        MAX-ACCESS        read-only
        STATUS            current
        DESCRIPTION
                "CMNT: - 
                 TYPE: - Display
                 PAGE: - Routing
                    Pair 8  cmdID= 10311  "
        ::= { kudosConv4CtrlEntries 10311 }


    i4AudioControlGainPair1L OBJECT-TYPE
        SYNTAX            INTEGER
        MAX-ACCESS        read-write
        STATUS            current
        DESCRIPTION
                "CMNT: - 
                 TYPE: - Number
                 PAGE: - Control
                    Pair 1 L  cmdID= 10120
                    min= -180  max= 180  step= 1  format= %0.1fdB  div_scale= 10  preset= 0
                    Min = -18.0dB  Max = 18.0dB  Step = 0.1dB  Preset = 0.0dB  "
        ::= { kudosConv4CtrlEntries 10120 }


    i4AudioControlGainPair1R OBJECT-TYPE
        SYNTAX            INTEGER
        MAX-ACCESS        read-write
        STATUS            current
        DESCRIPTION
                "CMNT: - 
                 TYPE: - Number
                 PAGE: - Control
                    Pair 1 R  cmdID= 10121
                    min= -180  max= 180  step= 1  format= %0.1fdB  div_scale= 10  preset= 0
                    Min = -18.0dB  Max = 18.0dB  Step = 0.1dB  Preset = 0.0dB  "
        ::= { kudosConv4CtrlEntries 10121 }


    i4AudioControlGainPair2L OBJECT-TYPE
        SYNTAX            INTEGER
        MAX-ACCESS        read-write
        STATUS            current
        DESCRIPTION
                "CMNT: - 
                 TYPE: - Number
                 PAGE: - Control
                    Pair 2 L  cmdID= 10122
                    min= -180  max= 180  step= 1  format= %0.1fdB  div_scale= 10  preset= 0
                    Min = -18.0dB  Max = 18.0dB  Step = 0.1dB  Preset = 0.0dB  "
        ::= { kudosConv4CtrlEntries 10122 }


    i4AudioControlGainPair2R OBJECT-TYPE
        SYNTAX            INTEGER
        MAX-ACCESS        read-write
        STATUS            current
        DESCRIPTION
                "CMNT: - 
                 TYPE: - Number
                 PAGE: - Control
                    Pair 2 R  cmdID= 10123
                    min= -180  max= 180  step= 1  format= %0.1fdB  div_scale= 10  preset= 0
                    Min = -18.0dB  Max = 18.0dB  Step = 0.1dB  Preset = 0.0dB  "
        ::= { kudosConv4CtrlEntries 10123 }


    i4AudioControlGainPair3L OBJECT-TYPE
        SYNTAX            INTEGER
        MAX-ACCESS        read-write
        STATUS            current
        DESCRIPTION
                "CMNT: - 
                 TYPE: - Number
                 PAGE: - Control
                    Pair 3 L  cmdID= 10124
                    min= -180  max= 180  step= 1  format= %0.1fdB  div_scale= 10  preset= 0
                    Min = -18.0dB  Max = 18.0dB  Step = 0.1dB  Preset = 0.0dB  "
        ::= { kudosConv4CtrlEntries 10124 }


    i4AudioControlGainPair3R OBJECT-TYPE
        SYNTAX            INTEGER
        MAX-ACCESS        read-write
        STATUS            current
        DESCRIPTION
                "CMNT: - 
                 TYPE: - Number
                 PAGE: - Control
                    Pair 3 R  cmdID= 10125
                    min= -180  max= 180  step= 1  format= %0.1fdB  div_scale= 10  preset= 0
                    Min = -18.0dB  Max = 18.0dB  Step = 0.1dB  Preset = 0.0dB  "
        ::= { kudosConv4CtrlEntries 10125 }


    i4AudioControlGainPair4L OBJECT-TYPE
        SYNTAX            INTEGER
        MAX-ACCESS        read-write
        STATUS            current
        DESCRIPTION
                "CMNT: - 
                 TYPE: - Number
                 PAGE: - Control
                    Pair 4 L  cmdID= 10126
                    min= -180  max= 180  step= 1  format= %0.1fdB  div_scale= 10  preset= 0
                    Min = -18.0dB  Max = 18.0dB  Step = 0.1dB  Preset = 0.0dB  "
        ::= { kudosConv4CtrlEntries 10126 }


    i4AudioControlGainPair4R OBJECT-TYPE
        SYNTAX            INTEGER
        MAX-ACCESS        read-write
        STATUS            current
        DESCRIPTION
                "CMNT: - 
                 TYPE: - Number
                 PAGE: - Control
                    Pair 4 R  cmdID= 10127
                    min= -180  max= 180  step= 1  format= %0.1fdB  div_scale= 10  preset= 0
                    Min = -18.0dB  Max = 18.0dB  Step = 0.1dB  Preset = 0.0dB  "
        ::= { kudosConv4CtrlEntries 10127 }


    i4AudioControlGainPair5L OBJECT-TYPE
        SYNTAX            INTEGER
        MAX-ACCESS        read-write
        STATUS            current
        DESCRIPTION
                "CMNT: - 
                 TYPE: - Number
                 PAGE: - Control
                    Pair 5 L  cmdID= 10128
                    min= -180  max= 180  step= 1  format= %0.1fdB  div_scale= 10  preset= 0
                    Min = -18.0dB  Max = 18.0dB  Step = 0.1dB  Preset = 0.0dB  "
        ::= { kudosConv4CtrlEntries 10128 }


    i4AudioControlGainPair5R OBJECT-TYPE
        SYNTAX            INTEGER
        MAX-ACCESS        read-write
        STATUS            current
        DESCRIPTION
                "CMNT: - 
                 TYPE: - Number
                 PAGE: - Control
                    Pair 5 R  cmdID= 10129
                    min= -180  max= 180  step= 1  format= %0.1fdB  div_scale= 10  preset= 0
                    Min = -18.0dB  Max = 18.0dB  Step = 0.1dB  Preset = 0.0dB  "
        ::= { kudosConv4CtrlEntries 10129 }


    i4AudioControlGainPair6L OBJECT-TYPE
        SYNTAX            INTEGER
        MAX-ACCESS        read-write
        STATUS            current
        DESCRIPTION
                "CMNT: - 
                 TYPE: - Number
                 PAGE: - Control
                    Pair 6 L  cmdID= 10130
                    min= -180  max= 180  step= 1  format= %0.1fdB  div_scale= 10  preset= 0
                    Min = -18.0dB  Max = 18.0dB  Step = 0.1dB  Preset = 0.0dB  "
        ::= { kudosConv4CtrlEntries 10130 }


    i4AudioControlGainPair6R OBJECT-TYPE
        SYNTAX            INTEGER
        MAX-ACCESS        read-write
        STATUS            current
        DESCRIPTION
                "CMNT: - 
                 TYPE: - Number
                 PAGE: - Control
                    Pair 6 R  cmdID= 10131
                    min= -180  max= 180  step= 1  format= %0.1fdB  div_scale= 10  preset= 0
                    Min = -18.0dB  Max = 18.0dB  Step = 0.1dB  Preset = 0.0dB  "
        ::= { kudosConv4CtrlEntries 10131 }


    i4AudioControlGainPair7L OBJECT-TYPE
        SYNTAX            INTEGER
        MAX-ACCESS        read-write
        STATUS            current
        DESCRIPTION
                "CMNT: - 
                 TYPE: - Number
                 PAGE: - Control
                    Pair 7 L  cmdID= 10132
                    min= -180  max= 180  step= 1  format= %0.1fdB  div_scale= 10  preset= 0
                    Min = -18.0dB  Max = 18.0dB  Step = 0.1dB  Preset = 0.0dB  "
        ::= { kudosConv4CtrlEntries 10132 }


    i4AudioControlGainPair7R OBJECT-TYPE
        SYNTAX            INTEGER
        MAX-ACCESS        read-write
        STATUS            current
        DESCRIPTION
                "CMNT: - 
                 TYPE: - Number
                 PAGE: - Control
                    Pair 7 R  cmdID= 10133
                    min= -180  max= 180  step= 1  format= %0.1fdB  div_scale= 10  preset= 0
                    Min = -18.0dB  Max = 18.0dB  Step = 0.1dB  Preset = 0.0dB  "
        ::= { kudosConv4CtrlEntries 10133 }


    i4AudioControlGainPair8L OBJECT-TYPE
        SYNTAX            INTEGER
        MAX-ACCESS        read-write
        STATUS            current
        DESCRIPTION
                "CMNT: - 
                 TYPE: - Number
                 PAGE: - Control
                    Pair 8 L  cmdID= 10134
                    min= -180  max= 180  step= 1  format= %0.1fdB  div_scale= 10  preset= 0
                    Min = -18.0dB  Max = 18.0dB  Step = 0.1dB  Preset = 0.0dB  "
        ::= { kudosConv4CtrlEntries 10134 }


    i4AudioControlGainPair8R OBJECT-TYPE
        SYNTAX            INTEGER
        MAX-ACCESS        read-write
        STATUS            current
        DESCRIPTION
                "CMNT: - 
                 TYPE: - Number
                 PAGE: - Control
                    Pair 8 R  cmdID= 10135
                    min= -180  max= 180  step= 1  format= %0.1fdB  div_scale= 10  preset= 0
                    Min = -18.0dB  Max = 18.0dB  Step = 0.1dB  Preset = 0.0dB  "
        ::= { kudosConv4CtrlEntries 10135 }


    i4AudioControlToneFrequency OBJECT-TYPE
        SYNTAX            INTEGER
        MAX-ACCESS        read-write
        STATUS            current
        DESCRIPTION
                "CMNT: - 
                 TYPE: - Number
                 PAGE: - Audio
                    Tone Frequency  cmdID= 10152
                    min= 100  max= 10000  step= 100  format= %0.1f KHz  div_scale= 1000  preset= 1000
                    Min = 0.1 KHz  Max = 10.0 KHz  Step = 0.1 KHz  Preset = 1.0 KHz  "
        ::= { kudosConv4CtrlEntries 10152 }


    i4AudioControlDolbyEAlignmentOffset OBJECT-TYPE
        SYNTAX            INTEGER
        MAX-ACCESS        read-write
        STATUS            current
        DESCRIPTION
                "CMNT: - 
                 TYPE: - Number
                 PAGE: - Audio
                    Dolby E Alignment Offset  cmdID= 10154
                    min= -10  max= 10  step= 1  format= %0.0f Lines  div_scale= 1  preset= 0
                    Min = -10 Lines  Max = 10 Lines  Step = 1 Lines  Preset = 0 Lines  "
        ::= { kudosConv4CtrlEntries 10154 }


    i4AudioDelayGlobalDelayPairOffsetsPair1 OBJECT-TYPE
        SYNTAX            INTEGER
        MAX-ACCESS        read-write
        STATUS            current
        DESCRIPTION
                "CMNT: - 
                 TYPE: - Number
                 PAGE: - Delay
                    Pair 1  cmdID= 10155
                    min= -40  max= 200  step= 1  format= %0.0f ms  div_scale= 1  preset= 0
                    Min = -40 ms  Max = 200 ms  Step = 1 ms  Preset = 0 ms  "
        ::= { kudosConv4CtrlEntries 10155 }


    i4AudioDelayGlobalDelayPairOffsetsPair1Total OBJECT-TYPE
        SYNTAX            RollCallString
        MAX-ACCESS        read-only
        STATUS            current
        DESCRIPTION
                "CMNT: - 
                 TYPE: - Display
                 PAGE: - Delay
                    Pair 1 Total  cmdID= 10164  "
        ::= { kudosConv4CtrlEntries 10164 }


    i4AudioDelayGlobalDelayPairOffsetsPair2 OBJECT-TYPE
        SYNTAX            INTEGER
        MAX-ACCESS        read-write
        STATUS            current
        DESCRIPTION
                "CMNT: - 
                 TYPE: - Number
                 PAGE: - Delay
                    Pair 2  cmdID= 10156
                    min= -40  max= 200  step= 1  format= %0.0f ms  div_scale= 1  preset= 0
                    Min = -40 ms  Max = 200 ms  Step = 1 ms  Preset = 0 ms  "
        ::= { kudosConv4CtrlEntries 10156 }


    i4AudioDelayGlobalDelayPairOffsetsPair2Total OBJECT-TYPE
        SYNTAX            RollCallString
        MAX-ACCESS        read-only
        STATUS            current
        DESCRIPTION
                "CMNT: - 
                 TYPE: - Display
                 PAGE: - Delay
                    Pair 2 Total  cmdID= 10165  "
        ::= { kudosConv4CtrlEntries 10165 }


    i4AudioDelayGlobalDelayPairOffsetsPair3 OBJECT-TYPE
        SYNTAX            INTEGER
        MAX-ACCESS        read-write
        STATUS            current
        DESCRIPTION
                "CMNT: - 
                 TYPE: - Number
                 PAGE: - Delay
                    Pair 3  cmdID= 10157
                    min= -40  max= 200  step= 1  format= %0.0f ms  div_scale= 1  preset= 0
                    Min = -40 ms  Max = 200 ms  Step = 1 ms  Preset = 0 ms  "
        ::= { kudosConv4CtrlEntries 10157 }


    i4AudioDelayGlobalDelayPairOffsetsPair3Total OBJECT-TYPE
        SYNTAX            RollCallString
        MAX-ACCESS        read-only
        STATUS            current
        DESCRIPTION
                "CMNT: - 
                 TYPE: - Display
                 PAGE: - Delay
                    Pair 3 Total  cmdID= 10166  "
        ::= { kudosConv4CtrlEntries 10166 }


    i4AudioDelayGlobalDelayPairOffsetsPair4 OBJECT-TYPE
        SYNTAX            INTEGER
        MAX-ACCESS        read-write
        STATUS            current
        DESCRIPTION
                "CMNT: - 
                 TYPE: - Number
                 PAGE: - Delay
                    Pair 4  cmdID= 10158
                    min= -40  max= 200  step= 1  format= %0.0f ms  div_scale= 1  preset= 0
                    Min = -40 ms  Max = 200 ms  Step = 1 ms  Preset = 0 ms  "
        ::= { kudosConv4CtrlEntries 10158 }


    i4AudioDelayGlobalDelayPairOffsetsPair4Total OBJECT-TYPE
        SYNTAX            RollCallString
        MAX-ACCESS        read-only
        STATUS            current
        DESCRIPTION
                "CMNT: - 
                 TYPE: - Display
                 PAGE: - Delay
                    Pair 4 Total  cmdID= 10167  "
        ::= { kudosConv4CtrlEntries 10167 }


    i4AudioDelayGlobalDelayPairOffsetsPair5 OBJECT-TYPE
        SYNTAX            INTEGER
        MAX-ACCESS        read-write
        STATUS            current
        DESCRIPTION
                "CMNT: - 
                 TYPE: - Number
                 PAGE: - Delay
                    Pair 5  cmdID= 10159
                    min= -40  max= 200  step= 1  format= %0.0f ms  div_scale= 1  preset= 0
                    Min = -40 ms  Max = 200 ms  Step = 1 ms  Preset = 0 ms  "
        ::= { kudosConv4CtrlEntries 10159 }


    i4AudioDelayGlobalDelayPairOffsetsPair5Total OBJECT-TYPE
        SYNTAX            RollCallString
        MAX-ACCESS        read-only
        STATUS            current
        DESCRIPTION
                "CMNT: - 
                 TYPE: - Display
                 PAGE: - Delay
                    Pair 5 Total  cmdID= 10168  "
        ::= { kudosConv4CtrlEntries 10168 }


    i4AudioDelayGlobalDelayPairOffsetsPair6 OBJECT-TYPE
        SYNTAX            INTEGER
        MAX-ACCESS        read-write
        STATUS            current
        DESCRIPTION
                "CMNT: - 
                 TYPE: - Number
                 PAGE: - Delay
                    Pair 6  cmdID= 10160
                    min= -40  max= 200  step= 1  format= %0.0f ms  div_scale= 1  preset= 0
                    Min = -40 ms  Max = 200 ms  Step = 1 ms  Preset = 0 ms  "
        ::= { kudosConv4CtrlEntries 10160 }


    i4AudioDelayGlobalDelayPairOffsetsPair6Total OBJECT-TYPE
        SYNTAX            RollCallString
        MAX-ACCESS        read-only
        STATUS            current
        DESCRIPTION
                "CMNT: - 
                 TYPE: - Display
                 PAGE: - Delay
                    Pair 6 Total  cmdID= 10169  "
        ::= { kudosConv4CtrlEntries 10169 }


    i4AudioDelayGlobalDelayPairOffsetsPair7 OBJECT-TYPE
        SYNTAX            INTEGER
        MAX-ACCESS        read-write
        STATUS            current
        DESCRIPTION
                "CMNT: - 
                 TYPE: - Number
                 PAGE: - Delay
                    Pair 7  cmdID= 10161
                    min= -40  max= 200  step= 1  format= %0.0f ms  div_scale= 1  preset= 0
                    Min = -40 ms  Max = 200 ms  Step = 1 ms  Preset = 0 ms  "
        ::= { kudosConv4CtrlEntries 10161 }


    i4AudioDelayGlobalDelayPairOffsetsPair7Total OBJECT-TYPE
        SYNTAX            RollCallString
        MAX-ACCESS        read-only
        STATUS            current
        DESCRIPTION
                "CMNT: - 
                 TYPE: - Display
                 PAGE: - Delay
                    Pair 7 Total  cmdID= 10170  "
        ::= { kudosConv4CtrlEntries 10170 }


    i4AudioDelayGlobalDelayPairOffsetsPair8 OBJECT-TYPE
        SYNTAX            INTEGER
        MAX-ACCESS        read-write
        STATUS            current
        DESCRIPTION
                "CMNT: - 
                 TYPE: - Number
                 PAGE: - Delay
                    Pair 8  cmdID= 10162
                    min= -40  max= 200  step= 1  format= %0.0f ms  div_scale= 1  preset= 0
                    Min = -40 ms  Max = 200 ms  Step = 1 ms  Preset = 0 ms  "
        ::= { kudosConv4CtrlEntries 10162 }


    i4AudioDelayGlobalDelayPairOffsetsPair8Total OBJECT-TYPE
        SYNTAX            RollCallString
        MAX-ACCESS        read-only
        STATUS            current
        DESCRIPTION
                "CMNT: - 
                 TYPE: - Display
                 PAGE: - Delay
                    Pair 8 Total  cmdID= 10171  "
        ::= { kudosConv4CtrlEntries 10171 }


    i4AudioDelayGlobalDelayAudio OBJECT-TYPE
        SYNTAX            INTEGER
        MAX-ACCESS        read-write
        STATUS            current
        DESCRIPTION
                "CMNT: - 
                 TYPE: - Number
                 PAGE: - Delay
                    Audio  cmdID= 10163
                    min= -40  max= 200  step= 1  format= %0.0f ms  div_scale= 1  preset= 0
                    Min = -40 ms  Max = 200 ms  Step = 1 ms  Preset = 0 ms  "
        ::= { kudosConv4CtrlEntries 10163 }


    i4AudioDelayGlobalDelayAudioTotal OBJECT-TYPE
        SYNTAX            RollCallString
        MAX-ACCESS        read-only
        STATUS            current
        DESCRIPTION
                "CMNT: - 
                 TYPE: - Display
                 PAGE: - Delay
                    Audio Total  cmdID= 10172  "
        ::= { kudosConv4CtrlEntries 10172 }


    i4AudioDelayGlobalDelayVideoTotal OBJECT-TYPE
        SYNTAX            RollCallString
        MAX-ACCESS        read-only
        STATUS            current
        DESCRIPTION
                "CMNT: - 
                 TYPE: - Display
                 PAGE: - Delay
                    Video Total  cmdID= 10173  "
        ::= { kudosConv4CtrlEntries 10173 }


    i4AudioShuffleOutputPair1LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10182
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10182 }


    i4AudioShuffleOutputPair1LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10198  "
        ::= { kudosConv4CtrlEntries 10198 }


    i4AudioShuffleOutputPair1LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10214
                    Use Routing  value= 0
                    Tone  value= 1
                    Silence  value= 2  "
        ::= { kudosConv4CtrlEntries 10214 }


    i4AudioShuffleOutputPair1RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10190
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10190 }


    i4AudioShuffleOutputPair1RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10206  "
        ::= { kudosConv4CtrlEntries 10206 }


    i4AudioShuffleOutputPair1RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10222
                    Use Routing  value= 0
                    Tone  value= 1
                    Silence  value= 2  "
        ::= { kudosConv4CtrlEntries 10222 }


    i4AudioShuffleOutputPair2LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10183
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10183 }


    i4AudioShuffleOutputPair2LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10199  "
        ::= { kudosConv4CtrlEntries 10199 }


    i4AudioShuffleOutputPair2LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10215
                    Use Routing  value= 0
                    Tone  value= 1
                    Silence  value= 2  "
        ::= { kudosConv4CtrlEntries 10215 }


    i4AudioShuffleOutputPair2RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10191
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10191 }


    i4AudioShuffleOutputPair2RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10207  "
        ::= { kudosConv4CtrlEntries 10207 }


    i4AudioShuffleOutputPair2RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10223
                    Use Routing  value= 0
                    Tone  value= 1
                    Silence  value= 2  "
        ::= { kudosConv4CtrlEntries 10223 }


    i4AudioShuffleOutputPair3LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10184
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10184 }


    i4AudioShuffleOutputPair3LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10200  "
        ::= { kudosConv4CtrlEntries 10200 }


    i4AudioShuffleOutputPair3LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10216
                    Use Routing  value= 0
                    Tone  value= 1
                    Silence  value= 2  "
        ::= { kudosConv4CtrlEntries 10216 }


    i4AudioShuffleOutputPair3RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10192
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10192 }


    i4AudioShuffleOutputPair3RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10208  "
        ::= { kudosConv4CtrlEntries 10208 }


    i4AudioShuffleOutputPair3RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10224
                    Use Routing  value= 0
                    Tone  value= 1
                    Silence  value= 2  "
        ::= { kudosConv4CtrlEntries 10224 }


    i4AudioShuffleOutputPair4LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10185
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10185 }


    i4AudioShuffleOutputPair4LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10201  "
        ::= { kudosConv4CtrlEntries 10201 }


    i4AudioShuffleOutputPair4LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10217
                    Use Routing  value= 0
                    Tone  value= 1
                    Silence  value= 2  "
        ::= { kudosConv4CtrlEntries 10217 }


    i4AudioShuffleOutputPair4RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10193
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10193 }


    i4AudioShuffleOutputPair4RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10209  "
        ::= { kudosConv4CtrlEntries 10209 }


    i4AudioShuffleOutputPair4RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10225
                    Use Routing  value= 0
                    Tone  value= 1
                    Silence  value= 2  "
        ::= { kudosConv4CtrlEntries 10225 }


    i4AudioShuffleOutputPair5LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10186
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10186 }


    i4AudioShuffleOutputPair5LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10202  "
        ::= { kudosConv4CtrlEntries 10202 }


    i4AudioShuffleOutputPair5LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10218
                    Use Routing  value= 0
                    Tone  value= 1
                    Silence  value= 2  "
        ::= { kudosConv4CtrlEntries 10218 }


    i4AudioShuffleOutputPair5RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10194
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10194 }


    i4AudioShuffleOutputPair5RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10210  "
        ::= { kudosConv4CtrlEntries 10210 }


    i4AudioShuffleOutputPair5RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10226
                    Use Routing  value= 0
                    Tone  value= 1
                    Silence  value= 2  "
        ::= { kudosConv4CtrlEntries 10226 }


    i4AudioShuffleOutputPair6LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10187
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10187 }


    i4AudioShuffleOutputPair6LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10203  "
        ::= { kudosConv4CtrlEntries 10203 }


    i4AudioShuffleOutputPair6LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10219
                    Use Routing  value= 0
                    Tone  value= 1
                    Silence  value= 2  "
        ::= { kudosConv4CtrlEntries 10219 }


    i4AudioShuffleOutputPair6RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10195
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10195 }


    i4AudioShuffleOutputPair6RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10211  "
        ::= { kudosConv4CtrlEntries 10211 }


    i4AudioShuffleOutputPair6RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10227
                    Use Routing  value= 0
                    Tone  value= 1
                    Silence  value= 2  "
        ::= { kudosConv4CtrlEntries 10227 }


    i4AudioShuffleOutputPair7LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10188
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10188 }


    i4AudioShuffleOutputPair7LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10204  "
        ::= { kudosConv4CtrlEntries 10204 }


    i4AudioShuffleOutputPair7LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10220
                    Use Routing  value= 0
                    Tone  value= 1
                    Silence  value= 2  "
        ::= { kudosConv4CtrlEntries 10220 }


    i4AudioShuffleOutputPair7RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10196
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10196 }


    i4AudioShuffleOutputPair7RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10212  "
        ::= { kudosConv4CtrlEntries 10212 }


    i4AudioShuffleOutputPair7RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10228
                    Use Routing  value= 0
                    Tone  value= 1
                    Silence  value= 2  "
        ::= { kudosConv4CtrlEntries 10228 }


    i4AudioShuffleOutputPair8LProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10189
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10189 }


    i4AudioShuffleOutputPair8LInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10205  "
        ::= { kudosConv4CtrlEntries 10205 }


    i4AudioShuffleOutputPair8LControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10221
                    Use Routing  value= 0
                    Tone  value= 1
                    Silence  value= 2  "
        ::= { kudosConv4CtrlEntries 10221 }


    i4AudioShuffleOutputPair8RProcessPairsSource OBJECT-TYPE
        SYNTAX            INTEGER {
                            valPair1L(1),
                            valPair1R(2),
                            valPair2L(3),
                            valPair2R(4),
                            valPair3L(5),
                            valPair3R(6),
                            valPair4L(7),
                            valPair4R(8),
                            valPair5L(9),
                            valPair5R(10),
                            valPair6L(11),
                            valPair6R(12),
                            valPair7L(13),
                            valPair7R(14),
                            valPair8L(15),
                            valPair8R(16)
                            }
        MAX-ACCESS        read-write
        STATUS            current
        DESCRIPTION
                "CMNT: - 
                 TYPE: - RadiobuttonList
                 PAGE: - Shuffle
                    Process Pairs Source  cmdID= 10197
                    Pair 1 L  value= 1
                    Pair 1 R  value= 2
                    Pair 2 L  value= 3
                    Pair 2 R  value= 4
                    Pair 3 L  value= 5
                    Pair 3 R  value= 6
                    Pair 4 L  value= 7
                    Pair 4 R  value= 8
                    Pair 5 L  value= 9
                    Pair 5 R  value= 10
                    Pair 6 L  value= 11
                    Pair 6 R  value= 12
                    Pair 7 L  value= 13
                    Pair 7 R  value= 14
                    Pair 8 L  value= 15
                    Pair 8 R  value= 16  "
        ::= { kudosConv4CtrlEntries 10197 }


    i4AudioShuffleOutputPair8RInvertPhase OBJECT-TYPE
        SYNTAX            INTEGER { disable(0), enable(1)  }
        MAX-ACCESS        read-write
        STATUS            current
        DESCRIPTION
                "CMNT: - 
                 TYPE: - Checkbox
                 PAGE: - Shuffle
                    Invert Phase  cmdID= 10213  "
        ::= { kudosConv4CtrlEntries 10213 }


    i4AudioShuffleOutputPair8RControl OBJECT-TYPE
        SYNTAX            INTEGER {
                            valUseRouting(0),
                            valTone(1),
                            valSilence(2)
                            }
        MAX-ACCESS        read-write
        STATUS            current
        DESCRIPTION
                "CMNT: - 
                 TYPE: - RadiobuttonList
                 PAGE: - Shuffle
                    Control  cmdID= 10229
                    Use Routing  value= 0
                    Tone  value= 1
                    Silence  value= 2  "
        ::= { kudosConv4CtrlEntries 10229 }


    i4AudioShuffleOutputPairs18StatusPair1 OBJECT-TYPE
        SYNTAX            RollCallString
        MAX-ACCESS        read-only
        STATUS            current
        DESCRIPTION
                "CMNT: - 
                 TYPE: - Display
                 PAGE: - Shuffle
                    Pair 1  cmdID= 10174  "
        ::= { kudosConv4CtrlEntries 10174 }


    i4AudioShuffleOutputPairs18StatusPair2 OBJECT-TYPE
        SYNTAX            RollCallString
        MAX-ACCESS        read-only
        STATUS            current
        DESCRIPTION
                "CMNT: - 
                 TYPE: - Display
                 PAGE: - Shuffle
                    Pair 2  cmdID= 10175  "
        ::= { kudosConv4CtrlEntries 10175 }


    i4AudioShuffleOutputPairs18StatusPair3 OBJECT-TYPE
        SYNTAX            RollCallString
        MAX-ACCESS        read-only
        STATUS            current
        DESCRIPTION
                "CMNT: - 
                 TYPE: - Display
                 PAGE: - Shuffle
                    Pair 3  cmdID= 10176  "
        ::= { kudosConv4CtrlEntries 10176 }


    i4AudioShuffleOutputPairs18StatusPair4 OBJECT-TYPE
        SYNTAX            RollCallString
        MAX-ACCESS        read-only
        STATUS            current
        DESCRIPTION
                "CMNT: - 
                 TYPE: - Display
                 PAGE: - Shuffle
                    Pair 4  cmdID= 10177  "
        ::= { kudosConv4CtrlEntries 10177 }


    i4AudioShuffleOutputPairs18StatusPair5 OBJECT-TYPE
        SYNTAX            RollCallString
        MAX-ACCESS        read-only
        STATUS            current
        DESCRIPTION
                "CMNT: - 
                 TYPE: - Display
                 PAGE: - Shuffle
                    Pair 5  cmdID= 10178  "
        ::= { kudosConv4CtrlEntries 10178 }


    i4AudioShuffleOutputPairs18StatusPair6 OBJECT-TYPE
        SYNTAX            RollCallString
        MAX-ACCESS        read-only
        STATUS            current
        DESCRIPTION
                "CMNT: - 
                 TYPE: - Display
                 PAGE: - Shuffle
                    Pair 6  cmdID= 10179  "
        ::= { kudosConv4CtrlEntries 10179 }


    i4AudioShuffleOutputPairs18StatusPair7 OBJECT-TYPE
        SYNTAX            RollCallString
        MAX-ACCESS        read-only
        STATUS            current
        DESCRIPTION
                "CMNT: - 
                 TYPE: - Display
                 PAGE: - Shuffle
                    Pair 7  cmdID= 10180  "
        ::= { kudosConv4CtrlEntries 10180 }


    i4AudioShuffleOutputPairs18StatusPair8 OBJECT-TYPE
        SYNTAX            RollCallString
        MAX-ACCESS        read-only
        STATUS            current
        DESCRIPTION
                "CMNT: - 
                 TYPE: - Display
                 PAGE: - Shuffle
                    Pair 8  cmdID= 10181  "
        ::= { kudosConv4CtrlEntries 10181 }


    i4TimecodeSourceHD OBJECT-TYPE
        SYNTAX            INTEGER {
                            valLTC(0),
                            valVITC(1)
                            }
        MAX-ACCESS        read-write
        STATUS            current
        DESCRIPTION
                "CMNT: - 
                 TYPE: - RadiobuttonList
                 PAGE: - Timecode
                    Source (HD)  cmdID= 10230
                    LTC  value= 0
                    VITC  value= 1  "
        ::= { kudosConv4CtrlEntries 10230 }


    i4TimecodeSourceSD OBJECT-TYPE
        SYNTAX            INTEGER {
                            valVITC(0),
                            valATCLTC(1),
                            valATCVITC(2)
                            }
        MAX-ACCESS        read-write
        STATUS            current
        DESCRIPTION
                "CMNT: - 
                 TYPE: - RadiobuttonList
                 PAGE: - Timecode
                    Source (SD)  cmdID= 10231
                    VITC  value= 0
                    ATC LTC  value= 1
                    ATC VITC  value= 2  "
        ::= { kudosConv4CtrlEntries 10231 }


    i4TimecodeStatus OBJECT-TYPE
        SYNTAX            RollCallString
        MAX-ACCESS        read-only
        STATUS            current
        DESCRIPTION
                "CMNT: - 
                 TYPE: - Display
                 PAGE: - Timecode
                    Status  cmdID= 10239  "
        ::= { kudosConv4CtrlEntries 10239 }


    i4TimecodeMode OBJECT-TYPE
        SYNTAX            INTEGER {
                            valFollowInput(0),
                            valGenerate(1),
                            valInputTrigger(2)
                            }
        MAX-ACCESS        read-write
        STATUS            current
        DESCRIPTION
                "CMNT: - 
                 TYPE: - RadiobuttonList
                 PAGE: - Timecode
                    Mode  cmdID= 10232
                    Follow Input  value= 0
                    Generate  value= 1
                    Input Trigger  value= 2  "
        ::= { kudosConv4CtrlEntries 10232 }


    i4TimecodeVITCEnable OBJECT-TYPE
        SYNTAX            INTEGER { disable(0), enable(1)  }
        MAX-ACCESS        read-write
        STATUS            current
        DESCRIPTION
                "CMNT: - 
                 TYPE: - Checkbox
                 PAGE: - Timecode
                    VITC Enable  cmdID= 10238  "
        ::= { kudosConv4CtrlEntries 10238 }


    i4TimecodeOutputLine525 OBJECT-TYPE
        SYNTAX            INTEGER
        MAX-ACCESS        read-write
        STATUS            current
        DESCRIPTION
                "CMNT: - 
                 TYPE: - Number
                 PAGE: - Timecode
                    Output Line (525)  cmdID= 10233
                    min= 11  max= 17  step= 1  format= %0.0f  div_scale= 1  preset= 14
                    Min = 11  Max = 17  Step = 1  Preset = 14  "
        ::= { kudosConv4CtrlEntries 10233 }


    i4TimecodeOutputLine625 OBJECT-TYPE
        SYNTAX            INTEGER
        MAX-ACCESS        read-write
        STATUS            current
        DESCRIPTION
                "CMNT: - 
                 TYPE: - Number
                 PAGE: - Timecode
                    Output Line (625)  cmdID= 10234
                    min= 7  max= 20  step= 1  format= %0.0f  div_scale= 1  preset= 19
                    Min = 7  Max = 20  Step = 1  Preset = 19  "
        ::= { kudosConv4CtrlEntries 10234 }


    i4TimecodeOutputLineStatus OBJECT-TYPE
        SYNTAX            RollCallString
        MAX-ACCESS        read-only
        STATUS            current
        DESCRIPTION
                "CMNT: - 
                 TYPE: - Display
                 PAGE: - Timecode
                    Output Line Status  cmdID= 10338  "
        ::= { kudosConv4CtrlEntries 10338 }


    i4TimecodeInputTriggerEntry OBJECT-TYPE
        SYNTAX            RollCallString
        MAX-ACCESS        read-write
        STATUS            current
        DESCRIPTION
                "CMNT: - 
                 TYPE: - Editstring
                 PAGE: - Timecode
                    Input Trigger Entry  cmdID= 10240
                    preset= 00:00:00:00"
        ::= { kudosConv4CtrlEntries 10240 }


    i4TimecodeOutputTimecodeEntry OBJECT-TYPE
        SYNTAX            RollCallString
        MAX-ACCESS        read-write
        STATUS            current
        DESCRIPTION
                "CMNT: - 
                 TYPE: - Editstring
                 PAGE: - Timecode
                    Output Timecode Entry  cmdID= 10241
                    preset= 00:00:00:00"
        ::= { kudosConv4CtrlEntries 10241 }


    i4TimecodeEntry OBJECT-TYPE
        SYNTAX            RollCallString
        MAX-ACCESS        read-write
        STATUS            current
        DESCRIPTION
                "CMNT: - 
                 TYPE: - Editstring
                 PAGE: - Timecode
                    Timecode Entry  cmdID= 10237
                    preset= 00:00:00:00"
        ::= { kudosConv4CtrlEntries 10237 }


    i4TimecodeLoad OBJECT-TYPE
        SYNTAX            INTEGER { noAction(0),valTimecodeLoad(1) }
        MAX-ACCESS        read-write
        STATUS            current
        DESCRIPTION
                "CMNT: - 
                 TYPE: - Button
                 PAGE: - Timecode
                    Timecode Load  cmdID= 10316
                    value= 1  "
        ::= { kudosConv4CtrlEntries 10316 }


    i4TimecodeOnTimecodeLoss OBJECT-TYPE
        SYNTAX            INTEGER {
                            valFreeze(0),
                            valFreeRun(1)
                            }
        MAX-ACCESS        read-write
        STATUS            current
        DESCRIPTION
                "CMNT: - 
                 TYPE: - RadiobuttonList
                 PAGE: - Timecode
                    On Timecode Loss  cmdID= 10235
                    Freeze  value= 0
                    Free Run  value= 1  "
        ::= { kudosConv4CtrlEntries 10235 }


    i4TimecodeNondropFrame OBJECT-TYPE
        SYNTAX            INTEGER { disable(0), enable(1)  }
        MAX-ACCESS        read-write
        STATUS            current
        DESCRIPTION
                "CMNT: - 
                 TYPE: - Checkbox
                 PAGE: - Timecode
                    Non-drop Frame  cmdID= 10236  "
        ::= { kudosConv4CtrlEntries 10236 }


    i4MetadataClosedCaptionsInputStatus OBJECT-TYPE
        SYNTAX            RollCallString
        MAX-ACCESS        read-only
        STATUS            current
        DESCRIPTION
                "CMNT: - 
                 TYPE: - Display
                 PAGE: - Metadata
                    Input Status  cmdID= 10250  "
        ::= { kudosConv4CtrlEntries 10250 }


    i4MetadataClosedCaptionsCEA608OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-608 Output Enable  cmdID= 10242
                    Off  value= 0
                    On  value= 1  "
        ::= { kudosConv4CtrlEntries 10242 }


    i4MetadataClosedCaptionsCEA708OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    CEA-708 Output Enable  cmdID= 10243
                    Off  value= 0
                    On  value= 1  "
        ::= { kudosConv4CtrlEntries 10243 }


    i4MetadataClosedCaptionsCEA708OutputLine OBJECT-TYPE
        SYNTAX            INTEGER
        MAX-ACCESS        read-write
        STATUS            current
        DESCRIPTION
                "CMNT: - 
                 TYPE: - Number
                 PAGE: - Metadata
                    CEA-708 Output Line  cmdID= 10244
                    min= 8  max= 20  step= 1  format= %0.0f  div_scale= 1  preset= 10
                    Min = 8  Max = 20  Step = 1  Preset = 10  "
        ::= { kudosConv4CtrlEntries 10244 }


    i4MetadataClosedCaptionsCEA708OutputLineStatus OBJECT-TYPE
        SYNTAX            RollCallString
        MAX-ACCESS        read-only
        STATUS            current
        DESCRIPTION
                "CMNT: - 
                 TYPE: - Display
                 PAGE: - Metadata
                    CEA-708 Output Line Status  cmdID= 10252  "
        ::= { kudosConv4CtrlEntries 10252 }


    i4MetadataTeletext625CaptionsSource OBJECT-TYPE
        SYNTAX            INTEGER {
                            valWST(0),
                            valCEAn608(1)
                            }
        MAX-ACCESS        read-write
        STATUS            current
        DESCRIPTION
                "CMNT: - 
                 TYPE: - RadiobuttonList
                 PAGE: - Metadata
                    625 Captions Source  cmdID= 10337
                    WST  value= 0
                    CEA-608  value= 1  "
        ::= { kudosConv4CtrlEntries 10337 }


    i4MetadataTeletextPresentStatus OBJECT-TYPE
        SYNTAX            RollCallString
        MAX-ACCESS        read-only
        STATUS            current
        DESCRIPTION
                "CMNT: - 
                 TYPE: - Display
                 PAGE: - Metadata
                    Teletext Present Status  cmdID= 10251  "
        ::= { kudosConv4CtrlEntries 10251 }


    i4MetadataTeletextWSTInputLine OBJECT-TYPE
        SYNTAX            INTEGER
        MAX-ACCESS        read-write
        STATUS            current
        DESCRIPTION
                "CMNT: - 
                 TYPE: - Number
                 PAGE: - Metadata
                    WST Input Line  cmdID= 10245
                    min= 7  max= 22  step= 1  format= %0.0f  div_scale= 1  preset= 10
                    Min = 7  Max = 22  Step = 1  Preset = 10  "
        ::= { kudosConv4CtrlEntries 10245 }


    i4MetadataTeletextWSTOutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    WST Output Enable  cmdID= 10246
                    Off  value= 0
                    On  value= 1  "
        ::= { kudosConv4CtrlEntries 10246 }


    i4MetadataTeletextWSTOutputLine OBJECT-TYPE
        SYNTAX            INTEGER
        MAX-ACCESS        read-write
        STATUS            current
        DESCRIPTION
                "CMNT: - 
                 TYPE: - Number
                 PAGE: - Metadata
                    WST Output Line  cmdID= 10253
                    min= 7  max= 22  step= 1  format= %0.0f  div_scale= 1  preset= 10
                    Min = 7  Max = 22  Step = 1  Preset = 10  "
        ::= { kudosConv4CtrlEntries 10253 }


    i4MetadataTeletextWSTOutputLineStatus OBJECT-TYPE
        SYNTAX            RollCallString
        MAX-ACCESS        read-only
        STATUS            current
        DESCRIPTION
                "CMNT: - 
                 TYPE: - Display
                 PAGE: - Metadata
                    WST Output Line Status  cmdID= 10341  "
        ::= { kudosConv4CtrlEntries 10341 }


    i4MetadataTeletextRDD08InputLine OBJECT-TYPE
        SYNTAX            INTEGER
        MAX-ACCESS        read-write
        STATUS            current
        DESCRIPTION
                "CMNT: - 
                 TYPE: - Number
                 PAGE: - Metadata
                    RDD-08 Input Line  cmdID= 10248
                    min= 8  max= 20  step= 1  format= %0.0f  div_scale= 1  preset= 10
                    Min = 8  Max = 20  Step = 1  Preset = 10  "
        ::= { kudosConv4CtrlEntries 10248 }


    i4MetadataTeletextRDD08OutputEnable OBJECT-TYPE
        SYNTAX            INTEGER {
                            valOff(0),
                            valOn(1)
                            }
        MAX-ACCESS        read-write
        STATUS            current
        DESCRIPTION
                "CMNT: - 
                 TYPE: - RadiobuttonList
                 PAGE: - Metadata
                    RDD-08 Output Enable  cmdID= 10247
                    Off  value= 0
                    On  value= 1  "
        ::= { kudosConv4CtrlEntries 10247 }


    i4MetadataTeletextRDD08OutputLine OBJECT-TYPE
        SYNTAX            INTEGER
        MAX-ACCESS        read-write
        STATUS            current
        DESCRIPTION
                "CMNT: - 
                 TYPE: - Number
                 PAGE: - Metadata
                    RDD-08 Output Line  cmdID= 10249
                    min= 8  max= 20  step= 1  format= %0.0f  div_scale= 1  preset= 10
                    Min = 8  Max = 20  Step = 1  Preset = 10  "
        ::= { kudosConv4CtrlEntries 10249 }


    i4MetadataTeletextRDD08OutputLineStatus OBJECT-TYPE
        SYNTAX            RollCallString
        MAX-ACCESS        read-only
        STATUS            current
        DESCRIPTION
                "CMNT: - 
                 TYPE: - Display
                 PAGE: - Metadata
                    RDD-08 Output Line Status  cmdID= 10340  "
        ::= { kudosConv4CtrlEntries 10340 }


    i4MemorySelect OBJECT-TYPE
        SYNTAX            INTEGER {
                            valMemory1(1),
                            valMemory2(2),
                            valMemory3(3),
                            valMemory4(4),
                            valMemory5(5),
                            valMemory6(6),
                            valMemory7(7),
                            valMemory8(8)
                            }
        MAX-ACCESS        read-write
        STATUS            current
        DESCRIPTION
                "CMNT: - 
                 TYPE: - RadiobuttonList
                 PAGE: - Memory
                    Memory Select  cmdID= 10254
                    Memory 1  value= 1
                    Memory 2  value= 2
                    Memory 3  value= 3
                    Memory 4  value= 4
                    Memory 5  value= 5
                    Memory 6  value= 6
                    Memory 7  value= 7
                    Memory 8  value= 8  "
        ::= { kudosConv4CtrlEntries 10254 }


    i4MemorySaveMemory OBJECT-TYPE
        SYNTAX            INTEGER { noAction(0),valSaveMemory(1) }
        MAX-ACCESS        read-write
        STATUS            current
        DESCRIPTION
                "CMNT: - 
                 TYPE: - Button
                 PAGE: - Memory
                    Save Memory  cmdID= 10255
                    value= 1  "
        ::= { kudosConv4CtrlEntries 10255 }


    i4MemoryRecallMemory OBJECT-TYPE
        SYNTAX            INTEGER { noAction(0),valRecallMemory(1) }
        MAX-ACCESS        read-write
        STATUS            current
        DESCRIPTION
                "CMNT: - 
                 TYPE: - Button
                 PAGE: - Memory
                    Recall Memory  cmdID= 10256
                    value= 1  "
        ::= { kudosConv4CtrlEntries 10256 }


    i4MemoryResettoDefaults OBJECT-TYPE
        SYNTAX            INTEGER { noAction(0),valResettoDefaults(1) }
        MAX-ACCESS        read-write
        STATUS            current
        DESCRIPTION
                "CMNT: - 
                 TYPE: - Button
                 PAGE: - Memory
                    Reset to Defaults  cmdID= 10258
                    value= 1  "
        ::= { kudosConv4CtrlEntries 10258 }


    i4MemoryNameChangeName OBJECT-TYPE
        SYNTAX            RollCallString
        MAX-ACCESS        read-write
        STATUS            current
        DESCRIPTION
                "CMNT: - 
                 TYPE: - Editstring
                 PAGE: - Memory
                    Change Name  cmdID= 10257
                    preset= "
        ::= { kudosConv4CtrlEntries 10257 }


    i4RollCallUnitName OBJECT-TYPE
        SYNTAX            RollCallString
        MAX-ACCESS        read-write
        STATUS            current
        DESCRIPTION
                "CMNT: - 
                 TYPE: - Editstring
                 PAGE: - RollCall
                    Unit Name  cmdID= 10312
                    preset= IQP"
        ::= { kudosConv4CtrlEntries 10312 }


    i4SNMPControlEnable OBJECT-TYPE
        SYNTAX            INTEGER { disable(0), enable(1)  }
        MAX-ACCESS        read-write
        STATUS            current
        DESCRIPTION
                "CMNT: - 
                 TYPE: - Checkbox
                 PAGE: - SNMP
                    Control Enable  cmdID= 10342  "
        ::= { kudosConv4CtrlEntries 10342 }


    i4SNMPTrapsEnable OBJECT-TYPE
        SYNTAX            INTEGER { disable(0), enable(1)  }
        MAX-ACCESS        read-write
        STATUS            current
        DESCRIPTION
                "CMNT: - 
                 TYPE: - Checkbox
                 PAGE: - SNMP
                    Traps Enable  cmdID= 10343  "
        ::= { kudosConv4CtrlEntries 10343 }


    i4SNMPResendTraps OBJECT-TYPE
        SYNTAX            INTEGER { noAction(0),valResendTraps(1) }
        MAX-ACCESS        read-write
        STATUS            current
        DESCRIPTION
                "CMNT: - 
                 TYPE: - Button
                 PAGE: - SNMP
                    Resend Traps  cmdID= 10344
                    value= 1  "
        ::= { kudosConv4CtrlEntries 10344 }


    i4LoggingInputIdentEnable OBJECT-TYPE
        SYNTAX            INTEGER { disable(0), enable(1)  }
        MAX-ACCESS        read-write
        STATUS            current
        DESCRIPTION
                "CMNT: - 
                 TYPE: - Checkbox
                 PAGE: - Logging
                    Input Ident Enable  cmdID= 10261  "
        ::= { kudosConv4CtrlEntries 10261 }


    i4LoggingInputStandardEnable OBJECT-TYPE
        SYNTAX            INTEGER { disable(0), enable(1)  }
        MAX-ACCESS        read-write
        STATUS            current
        DESCRIPTION
                "CMNT: - 
                 TYPE: - Checkbox
                 PAGE: - Logging
                    Input Standard Enable  cmdID= 10259  "
        ::= { kudosConv4CtrlEntries 10259 }


    i4LoggingInputStateEnable OBJECT-TYPE
        SYNTAX            INTEGER { disable(0), enable(1)  }
        MAX-ACCESS        read-write
        STATUS            current
        DESCRIPTION
                "CMNT: - 
                 TYPE: - Checkbox
                 PAGE: - Logging
                    Input State Enable  cmdID= 10263  "
        ::= { kudosConv4CtrlEntries 10263 }


    i4LoggingOutputStandardEnable OBJECT-TYPE
        SYNTAX            INTEGER { disable(0), enable(1)  }
        MAX-ACCESS        read-write
        STATUS            current
        DESCRIPTION
                "CMNT: - 
                 TYPE: - Checkbox
                 PAGE: - Logging
                    Output Standard Enable  cmdID= 10267  "
        ::= { kudosConv4CtrlEntries 10267 }


    i4LoggingOutputIdentEnable OBJECT-TYPE
        SYNTAX            INTEGER { disable(0), enable(1)  }
        MAX-ACCESS        read-write
        STATUS            current
        DESCRIPTION
                "CMNT: - 
                 TYPE: - Checkbox
                 PAGE: - Logging
                    Output Ident Enable  cmdID= 10265  "
        ::= { kudosConv4CtrlEntries 10265 }


    i4LoggingTimecodeEnable OBJECT-TYPE
        SYNTAX            INTEGER { disable(0), enable(1)  }
        MAX-ACCESS        read-write
        STATUS            current
        DESCRIPTION
                "CMNT: - 
                 TYPE: - Checkbox
                 PAGE: - Logging
                    Timecode Enable  cmdID= 10346  "
        ::= { kudosConv4CtrlEntries 10346 }


    i4LoggingClosedCaptionInputEnable OBJECT-TYPE
        SYNTAX            INTEGER { disable(0), enable(1)  }
        MAX-ACCESS        read-write
        STATUS            current
        DESCRIPTION
                "CMNT: - 
                 TYPE: - Checkbox
                 PAGE: - Logging
                    Closed Caption Input Enable  cmdID= 10348  "
        ::= { kudosConv4CtrlEntries 10348 }


    i4LoggingWSTEnable OBJECT-TYPE
        SYNTAX            INTEGER { disable(0), enable(1)  }
        MAX-ACCESS        read-write
        STATUS            current
        DESCRIPTION
                "CMNT: - 
                 TYPE: - Checkbox
                 PAGE: - Logging
                    WST Enable  cmdID= 10350  "
        ::= { kudosConv4CtrlEntries 10350 }


    i4LoggingRDD08Enable OBJECT-TYPE
        SYNTAX            INTEGER { disable(0), enable(1)  }
        MAX-ACCESS        read-write
        STATUS            current
        DESCRIPTION
                "CMNT: - 
                 TYPE: - Checkbox
                 PAGE: - Logging
                    RDD08 Enable  cmdID= 10352  "
        ::= { kudosConv4CtrlEntries 10352 }


    i4LoggingCEA708Enable OBJECT-TYPE
        SYNTAX            INTEGER { disable(0), enable(1)  }
        MAX-ACCESS        read-write
        STATUS            current
        DESCRIPTION
                "CMNT: - 
                 TYPE: - Checkbox
                 PAGE: - Logging
                    CEA-708 Enable  cmdID= 10354  "
        ::= { kudosConv4CtrlEntries 10354 }


    i4LoggingSMPTE2016Enable OBJECT-TYPE
        SYNTAX            INTEGER { disable(0), enable(1)  }
        MAX-ACCESS        read-write
        STATUS            current
        DESCRIPTION
                "CMNT: - 
                 TYPE: - Checkbox
                 PAGE: - Logging
                    SMPTE 2016 Enable  cmdID= 10356  "
        ::= { kudosConv4CtrlEntries 10356 }


    i4LoggingSMPTEL23Enable OBJECT-TYPE
        SYNTAX            INTEGER { disable(0), enable(1)  }
        MAX-ACCESS        read-write
        STATUS            current
        DESCRIPTION
                "CMNT: - 
                 TYPE: - Checkbox
                 PAGE: - Logging
                    SMPTE L23 Enable  cmdID= 10358  "
        ::= { kudosConv4CtrlEntries 10358 }


    i4LoggingSignallingEnable OBJECT-TYPE
        SYNTAX            INTEGER { disable(0), enable(1)  }
        MAX-ACCESS        read-write
        STATUS            current
        DESCRIPTION
                "CMNT: - 
                 TYPE: - Checkbox
                 PAGE: - Logging
                    Signalling Enable  cmdID= 10360  "
        ::= { kudosConv4CtrlEntries 10360 }
    kudosConv4StatEntries OBJECT IDENTIFIER ::= { kudosIQP 15 }


    i4LoggingInputIdentStatus OBJECT-TYPE
        SYNTAX            RollCallString
        MAX-ACCESS        read-only
        STATUS            current
        DESCRIPTION
                "CMNT: - Channel Name
                 TYPE: - Display
                 PAGE: - Logging
                    Input Ident Status  cmdID= 10262  "
        ::= { kudosConv4StatEntries 10262 }


    i4LoggingInputStandardStatus OBJECT-TYPE
        SYNTAX            RollCallString
        MAX-ACCESS        read-only
        STATUS            current
        DESCRIPTION
                "CMNT: - WARN: or format
                 TYPE: - Display
                 PAGE: - Logging
                    Input Standard Status  cmdID= 10260  "
        ::= { kudosConv4StatEntries 10260 }


    i4LoggingInputStateStatus OBJECT-TYPE
        SYNTAX            RollCallString
        MAX-ACCESS        read-only
        STATUS            current
        DESCRIPTION
                "CMNT: - WARN: or OK
                 TYPE: - Display
                 PAGE: - Logging
                    Input State Status  cmdID= 10264  "
        ::= { kudosConv4StatEntries 10264 }


    i4LoggingOutputStandardStatus OBJECT-TYPE
        SYNTAX            RollCallString
        MAX-ACCESS        read-only
        STATUS            current
        DESCRIPTION
                "CMNT: - WARN: or format
                 TYPE: - Display
                 PAGE: - Logging
                    Output Standard Status  cmdID= 10268  "
        ::= { kudosConv4StatEntries 10268 }


    i4LoggingOutputIdentStatus OBJECT-TYPE
        SYNTAX            RollCallString
        MAX-ACCESS        read-only
        STATUS            current
        DESCRIPTION
                "CMNT: - Channel Name
                 TYPE: - Display
                 PAGE: - Logging
                    Output Ident Status  cmdID= 10266  "
        ::= { kudosConv4StatEntries 10266 }


    i4LoggingTimeCodeStatus OBJECT-TYPE
        SYNTAX            RollCallString
        MAX-ACCESS        read-only
        STATUS            current
        DESCRIPTION
                "CMNT: - LOST or OK
                 TYPE: - Display
                 PAGE: - Logging
                    TimeCode Status  cmdID= 10347  "
        ::= { kudosConv4StatEntries 10347 }


    i4LoggingClosedCaptionInputStatus OBJECT-TYPE
        SYNTAX            RollCallString
        MAX-ACCESS        read-only
        STATUS            current
        DESCRIPTION
                "CMNT: - LOST or OK
                 TYPE: - Display
                 PAGE: - Logging
                    Closed Caption Input Status  cmdID= 10349  "
        ::= { kudosConv4StatEntries 10349 }


    i4LoggingWSTOutputLineStatus OBJECT-TYPE
        SYNTAX            RollCallString
        MAX-ACCESS        read-only
        STATUS            current
        DESCRIPTION
                "CMNT: - off or line number
                 TYPE: - Display
                 PAGE: - Logging
                    WST Output Line Status  cmdID= 10351  "
        ::= { kudosConv4StatEntries 10351 }


    i4LoggingRDD08OutputLineStatus OBJECT-TYPE
        SYNTAX            RollCallString
        MAX-ACCESS        read-only
        STATUS            current
        DESCRIPTION
                "CMNT: - off or line number
                 TYPE: - Display
                 PAGE: - Logging
                    RDD08 Output Line Status  cmdID= 10353  "
        ::= { kudosConv4StatEntries 10353 }


    i4LoggingCEA708OutputLineStatus OBJECT-TYPE
        SYNTAX            RollCallString
        MAX-ACCESS        read-only
        STATUS            current
        DESCRIPTION
                "CMNT: - off or line number
                 TYPE: - Display
                 PAGE: - Logging
                    CEA-708 Output Line Status  cmdID= 10355  "
        ::= { kudosConv4StatEntries 10355 }


    i4Logging2016OutputLineStatus OBJECT-TYPE
        SYNTAX            RollCallString
        MAX-ACCESS        read-only
        STATUS            current
        DESCRIPTION
                "CMNT: - off or line number
                 TYPE: - Display
                 PAGE: - Logging
                    2016 Output Line Status  cmdID= 10357  "
        ::= { kudosConv4StatEntries 10357 }


    i4LoggingL23OutputLineStatus OBJECT-TYPE
        SYNTAX            RollCallString
        MAX-ACCESS        read-only
        STATUS            current
        DESCRIPTION
                "CMNT: - off or line number
                 TYPE: - Display
                 PAGE: - Logging
                    L23 Output Line Status  cmdID= 10359  "
        ::= { kudosConv4StatEntries 10359 }


    i4LoggingSignallingStatus OBJECT-TYPE
        SYNTAX            RollCallString
        MAX-ACCESS        read-only
        STATUS            current
        DESCRIPTION
                "CMNT: - NONE or OK
                 TYPE: - Display
                 PAGE: - Logging
                    Signalling Status  cmdID= 10361  "
        ::= { kudosConv4StatEntries 10361 }


    i4LoggingMSGStatus OBJECT-TYPE
        SYNTAX            RollCallString
        MAX-ACCESS        read-only
        STATUS            current
        DESCRIPTION
                "CMNT: - 
                 TYPE: - Display
                 PAGE: - Logging
                    MSG Status  cmdID= 10269  "
        ::= { kudosConv4StatEntries 10269 }

END
