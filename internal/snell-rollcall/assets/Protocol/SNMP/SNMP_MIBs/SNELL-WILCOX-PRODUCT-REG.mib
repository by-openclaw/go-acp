-- ************************************************************************************
-- SNELL-WILCOX-PRODUCT-REG.mib:  Snell & Wilcox Product OID Registration Module
--
-- 08 September 2008, Jonathan Riches
--
-- Copyright (c) 2008 Snell & Wilcox Ltd
-- All rights reserved.
--
-- $Id: SNELL-WILCOX-PRODUCT-REG.mib 380 2015-03-23 12:30:02Z jonathanriches $
--
-- ************************************************************************************
--

SNELL-WILCOX-PRODUCT-REG DEFINITIONS ::= BEGIN

IMPORTS
	MODULE-IDENTITY, OBJECT-IDENTITY
		FROM SNMPv2-SMI
	snellWilcoxProductReg,
	snellWilcoxMibReg
		FROM SNELL-WILCOX-SMI;


snellWilcoxProductMIB MODULE-IDENTITY
	LAST-UPDATED 	"1305161501Z"
	ORGANIZATION 	"Snell Group"
	CONTACT-INFO
		"Postal:	Snell Group
					Generic Software Group
					Southleigh Park House
					Eastleigh Road
					Havant
					Hants  PO9 2PE
					UK

		   Tel: 	+44 (0) 2392 489000

		E-mail: 	snmp.support@snellwilcox.com"

	DESCRIPTION		"This module defines the object identifiers that are
					assigned to individual products and hence are
					returned as values for sysObjectID"

    REVISION        "1305161501Z"
    DESCRIPTION     "Extra card definitions added"
    
	REVISION    	"0611071147Z"
	DESCRIPTION		"Extra card definitions added"

	REVISION    	"0501241400Z"
	DESCRIPTION		"Updated contact details"

	REVISION    	"0302241230Z"
	DESCRIPTION		"Initial version of this MIB module."
	::= { snellWilcoxProductReg 1 }


-- Product Line sub-trees

snellWilcoxControlSystems OBJECT-IDENTITY
	STATUS			current
	DESCRIPTION		"Control systems providing remote control of Snell & Wilcox Products"
	::= { snellWilcoxProductReg 2 }

snellWilcoxModularProducts OBJECT-IDENTITY
	STATUS			current
	DESCRIPTION		"Modular products"
	::= { snellWilcoxProductReg 3 }

snellWilcoxStdsConvertorProducts OBJECT-IDENTITY
	STATUS			current
	DESCRIPTION		"Standards convertors"
	::= { snellWilcoxProductReg 4 }

snellWilcoxHdProducts OBJECT-IDENTITY
	STATUS			current
	DESCRIPTION		"High Definition video products"
	::= { snellWilcoxProductReg 5 }

snellWilcoxMpegProducts OBJECT-IDENTITY
	STATUS			current
	DESCRIPTION		"MPEG compression products"
	::= { snellWilcoxProductReg 6 }

snellWilcoxNoiseReductionProducts OBJECT-IDENTITY
	STATUS			current
	DESCRIPTION		"Noise reduction products"
	::= { snellWilcoxProductReg 7 }

snellWilcoxImageRestorationProducts OBJECT-IDENTITY
	STATUS			current
	DESCRIPTION		"Image restoration products"
	::= { snellWilcoxProductReg 8 }

snellWilcoxPostProductionProducts OBJECT-IDENTITY
	STATUS			current
	DESCRIPTION		"Production and Post Production Products"
	::= { snellWilcoxProductReg 9 }

snellWilcoxDisplaysProducts OBJECT-IDENTITY
	STATUS			current
	DESCRIPTION		"Display optimisation products"
	::= { snellWilcoxProductReg 10 }

snellWilcoxFileConversion OBJECT-IDENTITY
	STATUS 			current
	DESCRIPTION		"SNMP Values for the file conversion project."
	::= { snellWilcoxProductReg 11 }

snellWilcoxFileConversionSystem OBJECT IDENTIFIER
	::= { snellWilcoxFileConversion 1 }


-- Product Line  MIB sub-trees

snellWilcoxControlSystemsMib OBJECT-IDENTITY
	STATUS			current
	DESCRIPTION		"Control systems providing remote control of Snell & Wilcox Products"
	::= { snellWilcoxMibReg 2 }

snellWilcoxModularProductsMib OBJECT-IDENTITY
	STATUS			current
	DESCRIPTION		"Modular products"
	::= { snellWilcoxMibReg 3 }

snellWilcoxStdsConvertorProductsMib OBJECT-IDENTITY
	STATUS			current
	DESCRIPTION		"Standards convertors"
	::= { snellWilcoxMibReg 4 }

snellWilcoxHdProductsMib OBJECT-IDENTITY
	STATUS			current
	DESCRIPTION		"High Definition video products"
	::= { snellWilcoxMibReg 5 }

snellWilcoxMpegProductsMib OBJECT-IDENTITY
	STATUS			current
	DESCRIPTION		"MPEG compression products"
	::= { snellWilcoxMibReg 6 }

snellWilcoxNoiseReductionProductsMib OBJECT-IDENTITY
	STATUS			current
	DESCRIPTION		"Noise reduction products"
	::= { snellWilcoxMibReg 7 }

snellWilcoxImageRestorationProductsMib OBJECT-IDENTITY
	STATUS			current
	DESCRIPTION		"Image restoration products"
	::= { snellWilcoxMibReg 8 }

snellWilcoxPostProductionProductsMib OBJECT-IDENTITY
	STATUS			current
	DESCRIPTION		"Production and Post Production Products"
	::= { snellWilcoxMibReg 9 }

snellWilcoxDisplaysProductsMib OBJECT-IDENTITY
	STATUS			current
	DESCRIPTION		"Display optimisation products"
	::= { snellWilcoxMibReg 10 }


--  Control systems products
snellWilcoxRollMap 		OBJECT IDENTIFIER ::= { snellWilcoxControlSystems 1 }		-- RollMap PC software application


--  Modular products
snellWilcoxModular 	OBJECT IDENTIFIER ::= { snellWilcoxModularProducts 1 }          -- Must have this [set to 1] for table manipulation


moduleIQDMX8E		OBJECT IDENTIFIER ::= { snellWilcoxModular 6 }
moduleIQD1LPG		OBJECT IDENTIFIER ::= { snellWilcoxModular 8 }
moduleIQD1FPG		OBJECT IDENTIFIER ::= { snellWilcoxModular 10 }
moduleIQD1LSY		OBJECT IDENTIFIER ::= { snellWilcoxModular 16 }
moduleIQD1FSY		OBJECT IDENTIFIER ::= { snellWilcoxModular 17 }
moduleIQCBRG		OBJECT IDENTIFIER ::= { snellWilcoxModular 19 }		-- IQM 3U bridge
moduleIQADBB		OBJECT IDENTIFIER ::= { snellWilcoxModular 21 }
moduleIQDSDE		OBJECT IDENTIFIER ::= { snellWilcoxModular 30 }
moduleIQDMSDD		OBJECT IDENTIFIER ::= { snellWilcoxModular 32 }
moduleIQDMX4	    OBJECT IDENTIFIER ::= { snellWilcoxModular 39 }
moduleIQBAX		    OBJECT IDENTIFIER ::= { snellWilcoxModular 43 }
moduleIQBADC	    OBJECT IDENTIFIER ::= { snellWilcoxModular 51 }
moduleIQBDAC	    OBJECT IDENTIFIER ::= { snellWilcoxModular 52 }
moduleIQBAAD	    OBJECT IDENTIFIER ::= { snellWilcoxModular 53 }
moduleIQBDAD	    OBJECT IDENTIFIER ::= { snellWilcoxModular 54 }
moduleIQDMSDS	    OBJECT IDENTIFIER ::= { snellWilcoxModular 58 }
moduleIQD1DAC	    OBJECT IDENTIFIER ::= { snellWilcoxModular 59 }
moduleIQDMSDA	    OBJECT IDENTIFIER ::= { snellWilcoxModular 60 }
moduleIQBAI		    OBJECT IDENTIFIER ::= { snellWilcoxModular 61 }
moduleIQATBS	    OBJECT IDENTIFIER ::= { snellWilcoxModular 67 }
moduleIQBDDAS	    OBJECT IDENTIFIER ::= { snellWilcoxModular 86 }
moduleIQBDDAD	    OBJECT IDENTIFIER ::= { snellWilcoxModular 87 }
moduleIQBDAR	    OBJECT IDENTIFIER ::= { snellWilcoxModular 88 }
moduleIQBSYN	    OBJECT IDENTIFIER ::= { snellWilcoxModular 89 }
moduleIQBSYD	    OBJECT IDENTIFIER ::= { snellWilcoxModular 90 }
moduleIQBMX3	    OBJECT IDENTIFIER ::= { snellWilcoxModular 92 }
moduleIQBSFR        OBJECT IDENTIFIER ::= { snellWilcoxModular 97 }
moduleIQBAXR        OBJECT IDENTIFIER ::= { snellWilcoxModular 99 }
moduleIQBAIR        OBJECT IDENTIFIER ::= { snellWilcoxModular 100 }
moduleIQDMSDP       OBJECT IDENTIFIER ::= { snellWilcoxModular 101 }
moduleIQBADI        OBJECT IDENTIFIER ::= { snellWilcoxModular 103 }
moduleIQBAAI        OBJECT IDENTIFIER ::= { snellWilcoxModular 104 }
moduleIQBDACD       OBJECT IDENTIFIER ::= { snellWilcoxModular 105 }
moduleIQBADCD       OBJECT IDENTIFIER ::= { snellWilcoxModular 107 }
moduleIQAVDR        OBJECT IDENTIFIER ::= { snellWilcoxModular 108 }
moduleIQD1ADCK      OBJECT IDENTIFIER ::= { snellWilcoxModular 110 }
moduleIQBADX        OBJECT IDENTIFIER ::= { snellWilcoxModular 111 }
moduleIQBAAX        OBJECT IDENTIFIER ::= { snellWilcoxModular 112 }
moduleIQDAFS        OBJECT IDENTIFIER ::= { snellWilcoxModular 113 }
moduleIQCGPI        OBJECT IDENTIFIER ::= { snellWilcoxModular 126 }
moduleIQDNRS        OBJECT IDENTIFIER ::= { snellWilcoxModular 128 }
moduleIQDPF         OBJECT IDENTIFIER ::= { snellWilcoxModular 129 }
moduleIQDARCM       OBJECT IDENTIFIER ::= { snellWilcoxModular 137 }
moduleIQADBBG       OBJECT IDENTIFIER ::= { snellWilcoxModular 139 }
moduleIQBADCS       OBJECT IDENTIFIER ::= { snellWilcoxModular 140 }
moduleIQDAMDD       OBJECT IDENTIFIER ::= { snellWilcoxModular 142 }
moduleIQDAMDA       OBJECT IDENTIFIER ::= { snellWilcoxModular 144 }
moduleIQMDDA        OBJECT IDENTIFIER ::= { snellWilcoxModular 150 }
moduleIQMDDM        OBJECT IDENTIFIER ::= { snellWilcoxModular 151 }
moduleIQMMX2        OBJECT IDENTIFIER ::= { snellWilcoxModular 152 }
moduleIQDRT8        OBJECT IDENTIFIER ::= { snellWilcoxModular 158 }
moduleIQDSYN        OBJECT IDENTIFIER ::= { snellWilcoxModular 159 }
moduleIQDRT6        OBJECT IDENTIFIER ::= { snellWilcoxModular 160 }
moduleIQBRT8        OBJECT IDENTIFIER ::= { snellWilcoxModular 164 }
moduleIQDAVM		OBJECT IDENTIFIER ::= { snellWilcoxModular 165 }
moduleIQBDA7		OBJECT IDENTIFIER ::= { snellWilcoxModular 176 }
moduleIQBDA7S		OBJECT IDENTIFIER ::= { snellWilcoxModular 177 }
moduleIQBDA3S		OBJECT IDENTIFIER ::= { snellWilcoxModular 178 }
moduleIQDANR		OBJECT IDENTIFIER ::= { snellWilcoxModular 179 }
moduleIQDSDR        OBJECT IDENTIFIER ::= { snellWilcoxModular 181 }
moduleIQDLOG        OBJECT IDENTIFIER ::= { snellWilcoxModular 183 }
moduleIQMPAR        OBJECT IDENTIFIER ::= { snellWilcoxModular 195 }
moduleIQDARCP       OBJECT IDENTIFIER ::= { snellWilcoxModular 199 }
moduleIQDARCS       OBJECT IDENTIFIER ::= { snellWilcoxModular 200 }
moduleIQDMSES       OBJECT IDENTIFIER ::= { snellWilcoxModular 205 }
moduleIQACO         OBJECT IDENTIFIER ::= { snellWilcoxModular 206 }
moduleIQBCO         OBJECT IDENTIFIER ::= { snellWilcoxModular 207 }
moduleIQDCO         OBJECT IDENTIFIER ::= { snellWilcoxModular 208 }
moduleIQDMENCS      OBJECT IDENTIFIER ::= { snellWilcoxModular 215 }
moduleIQMDMO        OBJECT IDENTIFIER ::= { snellWilcoxModular 216 }
moduleIQBRT6		OBJECT IDENTIFIER ::= { snellWilcoxModular 227 }
moduleIQBAAID		OBJECT IDENTIFIER ::= { snellWilcoxModular 229 }
moduleIQDPR			OBJECT IDENTIFIER ::= { snellWilcoxModular 230 }
moduleIQDMSDAH		OBJECT IDENTIFIER ::= { snellWilcoxModular 236 }
moduleIQDARCMR		OBJECT IDENTIFIER ::= { snellWilcoxModular 241 }
moduleIQDRT8M		OBJECT IDENTIFIER ::= { snellWilcoxModular 249 }
moduleIQDAVMM		OBJECT IDENTIFIER ::= { snellWilcoxModular 251 }
moduleIQDMSDL		OBJECT IDENTIFIER ::= { snellWilcoxModular 261 }
moduleIQDDAC		OBJECT IDENTIFIER ::= { snellWilcoxModular 262 }
moduleIQDCPP		OBJECT IDENTIFIER ::= { snellWilcoxModular 269 }
moduleIQDARC8		OBJECT IDENTIFIER ::= { snellWilcoxModular 271 }
moduleIQDEAP		OBJECT IDENTIFIER ::= { snellWilcoxModular 279 }
moduleIQATBSD		OBJECT IDENTIFIER ::= { snellWilcoxModular 280 }
moduleIQDSDED		OBJECT IDENTIFIER ::= { snellWilcoxModular 284 }
moduleIQDSDES		OBJECT IDENTIFIER ::= { snellWilcoxModular 285 }
moduleIQDEAR	    OBJECT IDENTIFIER ::= { snellWilcoxModular 301 }
moduleIQORX		    OBJECT IDENTIFIER ::= { snellWilcoxModular 332 }
moduleIQOTX		    OBJECT IDENTIFIER ::= { snellWilcoxModular 333 }
moduleIQDKEY		OBJECT IDENTIFIER ::= { snellWilcoxModular 334 }
moduleIQSDA01		OBJECT IDENTIFIER ::= { snellWilcoxModular 339 }
moduleIQSYN20		OBJECT IDENTIFIER ::= { snellWilcoxModular 344 }
moduleIQSYN00		OBJECT IDENTIFIER ::= { snellWilcoxModular 349 }
moduleIQAVS00		OBJECT IDENTIFIER ::= { snellWilcoxModular 350 }
moduleIQAVS01		OBJECT IDENTIFIER ::= { snellWilcoxModular 351 }
moduleIQAVS10		OBJECT IDENTIFIER ::= { snellWilcoxModular 352 }
moduleIQAVS11		OBJECT IDENTIFIER ::= { snellWilcoxModular 353 }
moduleIQMUX00		OBJECT IDENTIFIER ::= { snellWilcoxModular 354 }
moduleIQMUX01		OBJECT IDENTIFIER ::= { snellWilcoxModular 355 }
moduleIQMUX02		OBJECT IDENTIFIER ::= { snellWilcoxModular 356 }
moduleIQMUX03		OBJECT IDENTIFIER ::= { snellWilcoxModular 357 }
moduleIQMUX10		OBJECT IDENTIFIER ::= { snellWilcoxModular 358 }
moduleIQMUX11		OBJECT IDENTIFIER ::= { snellWilcoxModular 359 }
moduleIQMUX12		OBJECT IDENTIFIER ::= { snellWilcoxModular 360 }
moduleIQMUX13		OBJECT IDENTIFIER ::= { snellWilcoxModular 361 }
moduleIQDMX00		OBJECT IDENTIFIER ::= { snellWilcoxModular 362 }
moduleIQDMX01		OBJECT IDENTIFIER ::= { snellWilcoxModular 363 }
moduleIQDMX02		OBJECT IDENTIFIER ::= { snellWilcoxModular 364 }
moduleIQDMX03		OBJECT IDENTIFIER ::= { snellWilcoxModular 365 }
moduleIQDMX10		OBJECT IDENTIFIER ::= { snellWilcoxModular 366 }
moduleIQDMX11		OBJECT IDENTIFIER ::= { snellWilcoxModular 367 }
moduleIQDMX12		OBJECT IDENTIFIER ::= { snellWilcoxModular 368 }
moduleIQDMX13		OBJECT IDENTIFIER ::= { snellWilcoxModular 369 }
moduleIQBRK00		OBJECT IDENTIFIER ::= { snellWilcoxModular 370 }
moduleIQDLY00		OBJECT IDENTIFIER ::= { snellWilcoxModular 378 }
moduleIQDLY01		OBJECT IDENTIFIER ::= { snellWilcoxModular 379 }
moduleIQUAV00		OBJECT IDENTIFIER ::= { snellWilcoxModular 380 }
moduleIQUAV01		OBJECT IDENTIFIER ::= { snellWilcoxModular 381 }
moduleIQDMX20		OBJECT IDENTIFIER ::= { snellWilcoxModular 384 }
moduleIQDMX21		OBJECT IDENTIFIER ::= { snellWilcoxModular 385 }
moduleIQMDA00		OBJECT IDENTIFIER ::= { snellWilcoxModular 386 }
moduleIQSYN21		OBJECT IDENTIFIER ::= { snellWilcoxModular 387 }
moduleIQMUX42		OBJECT IDENTIFIER ::= { snellWilcoxModular 389 }
moduleIQMUX43		OBJECT IDENTIFIER ::= { snellWilcoxModular 390 }
moduleIQSRT00		OBJECT IDENTIFIER ::= { snellWilcoxModular 391 }
moduleIQSRT10		OBJECT IDENTIFIER ::= { snellWilcoxModular 392 }
moduleIQSRT20		OBJECT IDENTIFIER ::= { snellWilcoxModular 398 }
moduleIQSRT21		OBJECT IDENTIFIER ::= { snellWilcoxModular 399 }
moduleIQMUX60		OBJECT IDENTIFIER ::= { snellWilcoxModular 404 }
moduleIQMUX61		OBJECT IDENTIFIER ::= { snellWilcoxModular 405 }
moduleIQARC00		OBJECT IDENTIFIER ::= { snellWilcoxModular 409 }
moduleIQARC01		OBJECT IDENTIFIER ::= { snellWilcoxModular 410 }
moduleIQDEC00		OBJECT IDENTIFIER ::= { snellWilcoxModular 412 }
moduleIQDEC01		OBJECT IDENTIFIER ::= { snellWilcoxModular 413 }
moduleIQDEC02		OBJECT IDENTIFIER ::= { snellWilcoxModular 414 }
moduleIQDEC03		OBJECT IDENTIFIER ::= { snellWilcoxModular 415 }
moduleIQDEC04		OBJECT IDENTIFIER ::= { snellWilcoxModular 416 }
moduleIQDEC05		OBJECT IDENTIFIER ::= { snellWilcoxModular 417 }
moduleIQH3A 		OBJECT IDENTIFIER ::= { snellWilcoxModular 429 }
moduleIQUDC00 		OBJECT IDENTIFIER ::= { snellWilcoxModular 430 }
moduleIQSDA10 		OBJECT IDENTIFIER ::= { snellWilcoxModular 436 }
moduleIQSDA11 		OBJECT IDENTIFIER ::= { snellWilcoxModular 437 }
moduleIQVDA00 		OBJECT IDENTIFIER ::= { snellWilcoxModular 438 }
moduleIQAES00 		OBJECT IDENTIFIER ::= { snellWilcoxModular 439 }
moduleIQVDA01 		OBJECT IDENTIFIER ::= { snellWilcoxModular 447 }
moduleIQSDA02 		OBJECT IDENTIFIER ::= { snellWilcoxModular 464 }
moduleIQSYN01 		OBJECT IDENTIFIER ::= { snellWilcoxModular 465 }
moduleIQMUX44		OBJECT IDENTIFIER ::= { snellWilcoxModular 472 }
moduleIQMUX45		OBJECT IDENTIFIER ::= { snellWilcoxModular 473 }
moduleIQH1A 		OBJECT IDENTIFIER ::= { snellWilcoxModular 475 }
moduleIQHIP00 		OBJECT IDENTIFIER ::= { snellWilcoxModular 484 }
moduleIQSDA22 		OBJECT IDENTIFIER ::= { snellWilcoxModular 487 }
moduleIQDSK00 		OBJECT IDENTIFIER ::= { snellWilcoxModular 490 }
moduleIQMUX46		OBJECT IDENTIFIER ::= { snellWilcoxModular 494 }
moduleIQMUX47		OBJECT IDENTIFIER ::= { snellWilcoxModular 495 }
moduleIQMUX48		OBJECT IDENTIFIER ::= { snellWilcoxModular 496 }
moduleIQMUX49		OBJECT IDENTIFIER ::= { snellWilcoxModular 497 }
moduleIQDBD00		OBJECT IDENTIFIER ::= { snellWilcoxModular 498 }
moduleIQDBD01		OBJECT IDENTIFIER ::= { snellWilcoxModular 499 }
moduleIQSDA30		OBJECT IDENTIFIER ::= { snellWilcoxModular 503 }
moduleIQSDA32		OBJECT IDENTIFIER ::= { snellWilcoxModular 504 }
moduleIQSDA34		OBJECT IDENTIFIER ::= { snellWilcoxModular 520 }
moduleIQSDA35		OBJECT IDENTIFIER ::= { snellWilcoxModular 525 }
moduleIQSYN30		OBJECT IDENTIFIER ::= { snellWilcoxModular 526 }
moduleIQSYN31		OBJECT IDENTIFIER ::= { snellWilcoxModular 527 }
moduleIQMUX30		OBJECT IDENTIFIER ::= { snellWilcoxModular 528 }
moduleIQMUX31		OBJECT IDENTIFIER ::= { snellWilcoxModular 529 }
moduleIQMUX32		OBJECT IDENTIFIER ::= { snellWilcoxModular 530 }
moduleIQDMX30		OBJECT IDENTIFIER ::= { snellWilcoxModular 531 }
moduleIQDMX30		OBJECT IDENTIFIER ::= { snellWilcoxModular 532 }
moduleIQDMX32		OBJECT IDENTIFIER ::= { snellWilcoxModular 533 }
moduleIQSYN22		OBJECT IDENTIFIER ::= { snellWilcoxModular 538 }
moduleIQUPC00		OBJECT IDENTIFIER ::= { snellWilcoxModular 539 }
moduleIQUPC01		OBJECT IDENTIFIER ::= { snellWilcoxModular 540 }
moduleIQDNC00		OBJECT IDENTIFIER ::= { snellWilcoxModular 541 }
moduleIQDCC00		OBJECT IDENTIFIER ::= { snellWilcoxModular 542 }
moduleIQUDC10		OBJECT IDENTIFIER ::= { snellWilcoxModular 543 }
moduleIQUDC11		OBJECT IDENTIFIER ::= { snellWilcoxModular 544 }
moduleIQUAV10		OBJECT IDENTIFIER ::= { snellWilcoxModular 545 }
moduleIQMUX33		OBJECT IDENTIFIER ::= { snellWilcoxModular 546 }
moduleIQDMX33		OBJECT IDENTIFIER ::= { snellWilcoxModular 547 }
moduleIQUCC00		OBJECT IDENTIFIER ::= { snellWilcoxModular 548 }
moduleIQDNC01		OBJECT IDENTIFIER ::= { snellWilcoxModular 549 }
moduleIQSYN33		OBJECT IDENTIFIER ::= { snellWilcoxModular 551 }
moduleIQDBE00		OBJECT IDENTIFIER ::= { snellWilcoxModular 562 }
moduleIQDBE01		OBJECT IDENTIFIER ::= { snellWilcoxModular 563 }
moduleIQDBE02		OBJECT IDENTIFIER ::= { snellWilcoxModular 564 }
moduleIQDBE03		OBJECT IDENTIFIER ::= { snellWilcoxModular 565 }
moduleIQOSY30		OBJECT IDENTIFIER ::= { snellWilcoxModular 571 }
moduleIQODB31		OBJECT IDENTIFIER ::= { snellWilcoxModular 572 }
moduleIQOMB31		OBJECT IDENTIFIER ::= { snellWilcoxModular 573 }
moduleIQHCO30		OBJECT IDENTIFIER ::= { snellWilcoxModular 574 }
moduleIQHCO31		OBJECT IDENTIFIER ::= { snellWilcoxModular 575 }
moduleIQOTR32		OBJECT IDENTIFIER ::= { snellWilcoxModular 583 }
moduleIQODU31		OBJECT IDENTIFIER ::= { snellWilcoxModular 584 }
moduleIQOMU31		OBJECT IDENTIFIER ::= { snellWilcoxModular 585 }
moduleIQOTR40		OBJECT IDENTIFIER ::= { snellWilcoxModular 588 }
moduleIQUDC12		OBJECT IDENTIFIER ::= { snellWilcoxModular 643 }
moduleIQASI82		OBJECT IDENTIFIER ::= { snellWilcoxModular 667 }
moduleIQHIP10		OBJECT IDENTIFIER ::= { snellWilcoxModular 668 }
moduleIQUDC30 		OBJECT IDENTIFIER ::= { snellWilcoxModular 680 }
moduleIQUDC31 		OBJECT IDENTIFIER ::= { snellWilcoxModular 686 }
moduleIQUDC32 		OBJECT IDENTIFIER ::= { snellWilcoxModular 683 }
moduleIQDB105		OBJECT IDENTIFIER ::= { snellWilcoxModular 732 }
moduleIQASI25		OBJECT IDENTIFIER ::= { snellWilcoxModular 771 }


--  Modular products MIBs
moduleIQDMX8EMIB	    OBJECT IDENTIFIER ::= { snellWilcoxModularProductsMib 6 }
moduleIQD1LPGMIB	    OBJECT IDENTIFIER ::= { snellWilcoxModularProductsMib 8 }
moduleIQD1FPGMIB	    OBJECT IDENTIFIER ::= { snellWilcoxModularProductsMib 10 }
moduleIQD1LSYMIB	    OBJECT IDENTIFIER ::= { snellWilcoxModularProductsMib 16 }
moduleIQD1FSYMIB	    OBJECT IDENTIFIER ::= { snellWilcoxModularProductsMib 17 }
moduleIQCBRGMIB		    OBJECT IDENTIFIER ::= { snellWilcoxModularProductsMib 19 }		-- IQM 3U bridge MIB
moduleIQADBBMIB		    OBJECT IDENTIFIER ::= { snellWilcoxModularProductsMib 21 }
moduleIQDSDEMIB	        OBJECT IDENTIFIER ::= { snellWilcoxModularProductsMib 30 }
moduleIQDMSDDMIB	    OBJECT IDENTIFIER ::= { snellWilcoxModularProductsMib 32 }
moduleIQDMX4MIB		    OBJECT IDENTIFIER ::= { snellWilcoxModularProductsMib 39 }
moduleIQBAXMIB		    OBJECT IDENTIFIER ::= { snellWilcoxModularProductsMib 43 }
moduleIQBADCMIB		    OBJECT IDENTIFIER ::= { snellWilcoxModularProductsMib 51 }
moduleIQBDACMIB		    OBJECT IDENTIFIER ::= { snellWilcoxModularProductsMib 52 }
moduleIQBAADMIB		    OBJECT IDENTIFIER ::= { snellWilcoxModularProductsMib 53 }
moduleIQBDADMIB		    OBJECT IDENTIFIER ::= { snellWilcoxModularProductsMib 54 }
moduleIQDMSDSMIB	    OBJECT IDENTIFIER ::= { snellWilcoxModularProductsMib 58 }
moduleIQD1DACMIB	    OBJECT IDENTIFIER ::= { snellWilcoxModularProductsMib 59 }
moduleIQDMSDAMIB		OBJECT IDENTIFIER ::= { snellWilcoxModularProductsMib 60 }
moduleIQBAIMIB		    OBJECT IDENTIFIER ::= { snellWilcoxModularProductsMib 61 }
moduleIQATBSMIB		    OBJECT IDENTIFIER ::= { snellWilcoxModularProductsMib 67 }
moduleIQBDDASMIB	    OBJECT IDENTIFIER ::= { snellWilcoxModularProductsMib 86 }
moduleIQBDDADMIB	    OBJECT IDENTIFIER ::= { snellWilcoxModularProductsMib 87 }
moduleIQBDARMIB	        OBJECT IDENTIFIER ::= { snellWilcoxModularProductsMib 88 }
moduleIQBSYNMIB	        OBJECT IDENTIFIER ::= { snellWilcoxModularProductsMib 89 }
moduleIQBSYDMIB	        OBJECT IDENTIFIER ::= { snellWilcoxModularProductsMib 90 }
moduleIQBMX3MIB	        OBJECT IDENTIFIER ::= { snellWilcoxModularProductsMib 92 }
moduleIQBSFRMIB         OBJECT IDENTIFIER ::= { snellWilcoxModularProductsMib 97 }
moduleIQBAXRMIB         OBJECT IDENTIFIER ::= { snellWilcoxModularProductsMib 99 }
moduleIQBAIRMIB         OBJECT IDENTIFIER ::= { snellWilcoxModularProductsMib 100 }
moduleIQDMSDPMIB        OBJECT IDENTIFIER ::= { snellWilcoxModularProductsMib 101 }
moduleIQBADIMIB         OBJECT IDENTIFIER ::= { snellWilcoxModularProductsMib 103 }
moduleIQBAAIMIB         OBJECT IDENTIFIER ::= { snellWilcoxModularProductsMib 104 }
moduleIQBDACDMIB        OBJECT IDENTIFIER ::= { snellWilcoxModularProductsMib 105 }
moduleIQBADCDMIB        OBJECT IDENTIFIER ::= { snellWilcoxModularProductsMib 107 }
moduleIQAVDRMIB         OBJECT IDENTIFIER ::= { snellWilcoxModularProductsMib 108 }
moduleIQD1ADCKMIB       OBJECT IDENTIFIER ::= { snellWilcoxModularProductsMib 110 }
moduleIQBADXMIB         OBJECT IDENTIFIER ::= { snellWilcoxModularProductsMib 111 }
moduleIQBAAXMIB         OBJECT IDENTIFIER ::= { snellWilcoxModularProductsMib 112 }
moduleIQDAFSMIB         OBJECT IDENTIFIER ::= { snellWilcoxModularProductsMib 113 }
moduleIQCGPIMIB         OBJECT IDENTIFIER ::= { snellWilcoxModularProductsMib 126 }
moduleIQDNRSMIB         OBJECT IDENTIFIER ::= { snellWilcoxModularProductsMib 128 }
moduleIQDPFMIB          OBJECT IDENTIFIER ::= { snellWilcoxModularProductsMib 129 }
moduleIQDARCMMIB        OBJECT IDENTIFIER ::= { snellWilcoxModularProductsMib 137 }
moduleIQADBBGMIB        OBJECT IDENTIFIER ::= { snellWilcoxModularProductsMib 139 }
moduleIQBADCSMIB        OBJECT IDENTIFIER ::= { snellWilcoxModularProductsMib 140 }
moduleIQDAMDDMIB        OBJECT IDENTIFIER ::= { snellWilcoxModularProductsMib 142 }
moduleIQDAMDAMIB        OBJECT IDENTIFIER ::= { snellWilcoxModularProductsMib 144 }
moduleIQMDDAMIB         OBJECT IDENTIFIER ::= { snellWilcoxModularProductsMib 150 }
moduleIQMDDMMIB         OBJECT IDENTIFIER ::= { snellWilcoxModularProductsMib 151 }
moduleIQMMX2MIB         OBJECT IDENTIFIER ::= { snellWilcoxModularProductsMib 152 }
moduleIQDRT8MIB         OBJECT IDENTIFIER ::= { snellWilcoxModularProductsMib 158 }
moduleIQDSYNMIB         OBJECT IDENTIFIER ::= { snellWilcoxModularProductsMib 159 }
moduleIQDRT6MIB         OBJECT IDENTIFIER ::= { snellWilcoxModularProductsMib 160 }
moduleIQBRT8MIB         OBJECT IDENTIFIER ::= { snellWilcoxModularProductsMib 164 }
moduleIQDAVMMIB		    OBJECT IDENTIFIER ::= { snellWilcoxModularProductsMib 165 }
moduleIQBDA7MIB		    OBJECT IDENTIFIER ::= { snellWilcoxModularProductsMib 176 }
moduleIQBDA7SMIB		OBJECT IDENTIFIER ::= { snellWilcoxModularProductsMib 177 }
moduleIQBDA3SMIB		OBJECT IDENTIFIER ::= { snellWilcoxModularProductsMib 178 }
moduleIQDANRMIB		    OBJECT IDENTIFIER ::= { snellWilcoxModularProductsMib 179 }
moduleIQDSDRMIB         OBJECT IDENTIFIER ::= { snellWilcoxModularProductsMib 181 }
moduleIQDLOGMIB         OBJECT IDENTIFIER ::= { snellWilcoxModularProductsMib 183 }
moduleIQMPARMIB         OBJECT IDENTIFIER ::= { snellWilcoxModularProductsMib 195 }
moduleIQDARCPMIB        OBJECT IDENTIFIER ::= { snellWilcoxModularProductsMib 199 }
moduleIQDARCSMIB        OBJECT IDENTIFIER ::= { snellWilcoxModularProductsMib 200 }
moduleIQDMSESMIB        OBJECT IDENTIFIER ::= { snellWilcoxModularProductsMib 205 }
moduleIQACOMIB          OBJECT IDENTIFIER ::= { snellWilcoxModularProductsMib 206 }
moduleIQBCOMIB          OBJECT IDENTIFIER ::= { snellWilcoxModularProductsMib 207 }
moduleIQDCOMIB          OBJECT IDENTIFIER ::= { snellWilcoxModularProductsMib 208 }
moduleIQDMENCSMIB       OBJECT IDENTIFIER ::= { snellWilcoxModularProductsMib 215 }
moduleIQMDMOMIB         OBJECT IDENTIFIER ::= { snellWilcoxModularProductsMib 216 }
moduleIQBRT6MIB		    OBJECT IDENTIFIER ::= { snellWilcoxModularProductsMib 227 }
moduleIQBAAIDMIB		OBJECT IDENTIFIER ::= { snellWilcoxModularProductsMib 229 }
moduleIQDPRMIB			OBJECT IDENTIFIER ::= { snellWilcoxModularProductsMib 230 }
moduleIQDMSDAHMIB		OBJECT IDENTIFIER ::= { snellWilcoxModularProductsMib 236 }
moduleIQDARCMRMIB		OBJECT IDENTIFIER ::= { snellWilcoxModularProductsMib 241 }
moduleIQDRT8MMIB		OBJECT IDENTIFIER ::= { snellWilcoxModularProductsMib 249 }
moduleIQDAVMMMIB		OBJECT IDENTIFIER ::= { snellWilcoxModularProductsMib 251 }
moduleIQDMSDLMIB		OBJECT IDENTIFIER ::= { snellWilcoxModularProductsMib 261 }
moduleIQDDACMIB		    OBJECT IDENTIFIER ::= { snellWilcoxModularProductsMib 262 }
moduleIQDCPPMIB		    OBJECT IDENTIFIER ::= { snellWilcoxModularProductsMib 269 }
moduleIQDARC8MIB	    OBJECT IDENTIFIER ::= { snellWilcoxModularProductsMib 271 }
moduleIQDEAPMIB		    OBJECT IDENTIFIER ::= { snellWilcoxModularProductsMib 279 }
moduleIQATBSDMIB	    OBJECT IDENTIFIER ::= { snellWilcoxModularProductsMib 280 }
moduleIQDSDEDMIB		OBJECT IDENTIFIER ::= { snellWilcoxModularProductsMib 284 }
moduleIQDSDESMIB		OBJECT IDENTIFIER ::= { snellWilcoxModularProductsMib 285 }
moduleIQDEARMIB			OBJECT IDENTIFIER ::= { snellWilcoxModularProductsMib 301 }
moduleIQORXMIB			OBJECT IDENTIFIER ::= { snellWilcoxModularProductsMib 332 }
moduleIQOTXMIB			OBJECT IDENTIFIER ::= { snellWilcoxModularProductsMib 333 }
moduleIQDKEYMIB			OBJECT IDENTIFIER ::= { snellWilcoxModularProductsMib 334 }
moduleIQSDA01MIB		OBJECT IDENTIFIER ::= { snellWilcoxModularProductsMib 339 }
moduleIQSYN20MIB		OBJECT IDENTIFIER ::= { snellWilcoxModularProductsMib 344 }
moduleIQSYN00MIB		OBJECT IDENTIFIER ::= { snellWilcoxModularProductsMib 349 }
moduleIQAVS00MIB		OBJECT IDENTIFIER ::= { snellWilcoxModularProductsMib 350 }
moduleIQAVS01MIB		OBJECT IDENTIFIER ::= { snellWilcoxModularProductsMib 351 }
moduleIQAVS10MIB		OBJECT IDENTIFIER ::= { snellWilcoxModularProductsMib 352 }
moduleIQAVS11MIB		OBJECT IDENTIFIER ::= { snellWilcoxModularProductsMib 353 }
moduleIQMUX00MIB		OBJECT IDENTIFIER ::= { snellWilcoxModularProductsMib 354 }
moduleIQMUX01MIB		OBJECT IDENTIFIER ::= { snellWilcoxModularProductsMib 355 }
moduleIQMUX02MIB		OBJECT IDENTIFIER ::= { snellWilcoxModularProductsMib 356 }
moduleIQMUX03MIB		OBJECT IDENTIFIER ::= { snellWilcoxModularProductsMib 357 }
moduleIQMUX10MIB		OBJECT IDENTIFIER ::= { snellWilcoxModularProductsMib 358 }
moduleIQMUX11MIB		OBJECT IDENTIFIER ::= { snellWilcoxModularProductsMib 359 }
moduleIQMUX12MIB		OBJECT IDENTIFIER ::= { snellWilcoxModularProductsMib 360 }
moduleIQMUX13MIB		OBJECT IDENTIFIER ::= { snellWilcoxModularProductsMib 361 }
moduleIQDMX00MIB		OBJECT IDENTIFIER ::= { snellWilcoxModularProductsMib 362 }
moduleIQDMX01MIB		OBJECT IDENTIFIER ::= { snellWilcoxModularProductsMib 363 }
moduleIQDMX02MIB		OBJECT IDENTIFIER ::= { snellWilcoxModularProductsMib 364 }
moduleIQDMX03MIB		OBJECT IDENTIFIER ::= { snellWilcoxModularProductsMib 365 }
moduleIQDMX10MIB		OBJECT IDENTIFIER ::= { snellWilcoxModularProductsMib 366 }
moduleIQDMX11MIB		OBJECT IDENTIFIER ::= { snellWilcoxModularProductsMib 367 }
moduleIQDMX12MIB		OBJECT IDENTIFIER ::= { snellWilcoxModularProductsMib 368 }
moduleIQDMX13MIB		OBJECT IDENTIFIER ::= { snellWilcoxModularProductsMib 369 }
moduleIQBRK00MIB		OBJECT IDENTIFIER ::= { snellWilcoxModularProductsMib 370 }
moduleIQDLY00MIB		OBJECT IDENTIFIER ::= { snellWilcoxModularProductsMib 378 }
moduleIQDLY01MIB		OBJECT IDENTIFIER ::= { snellWilcoxModularProductsMib 379 }
moduleIQUAV00MIB		OBJECT IDENTIFIER ::= { snellWilcoxModularProductsMib 380 }
moduleIQUAV01MIB		OBJECT IDENTIFIER ::= { snellWilcoxModularProductsMib 381 }
moduleIQDMX20MIB		OBJECT IDENTIFIER ::= { snellWilcoxModularProductsMib 384 }
moduleIQDMX21MIB		OBJECT IDENTIFIER ::= { snellWilcoxModularProductsMib 385 }
moduleIQMDA00MIB		OBJECT IDENTIFIER ::= { snellWilcoxModularProductsMib 386 }
moduleIQSYN21MIB		OBJECT IDENTIFIER ::= { snellWilcoxModularProductsMib 387 }
moduleIQMUX42MIB		OBJECT IDENTIFIER ::= { snellWilcoxModularProductsMib 389 }
moduleIQMUX43MIB		OBJECT IDENTIFIER ::= { snellWilcoxModularProductsMib 390 }
moduleIQSRT00MIB		OBJECT IDENTIFIER ::= { snellWilcoxModularProductsMib 391 }
moduleIQSRT10MIB		OBJECT IDENTIFIER ::= { snellWilcoxModularProductsMib 392 }
moduleIQSRT20MIB		OBJECT IDENTIFIER ::= { snellWilcoxModularProductsMib 398 }
moduleIQSRT21MIB		OBJECT IDENTIFIER ::= { snellWilcoxModularProductsMib 399 }
moduleIQMUX60MIB		OBJECT IDENTIFIER ::= { snellWilcoxModularProductsMib 404 }
moduleIQMUX61MIB		OBJECT IDENTIFIER ::= { snellWilcoxModularProductsMib 405 }
moduleIQARC00MIB		OBJECT IDENTIFIER ::= { snellWilcoxModularProductsMib 409 }
moduleIQARC01MIB		OBJECT IDENTIFIER ::= { snellWilcoxModularProductsMib 410 }
moduleIQDEC00MIB		OBJECT IDENTIFIER ::= { snellWilcoxModularProductsMib 412 }
moduleIQDEC01MIB		OBJECT IDENTIFIER ::= { snellWilcoxModularProductsMib 413 }
moduleIQDEC02MIB		OBJECT IDENTIFIER ::= { snellWilcoxModularProductsMib 414 }
moduleIQDEC03MIB		OBJECT IDENTIFIER ::= { snellWilcoxModularProductsMib 415 }
moduleIQDEC04MIB		OBJECT IDENTIFIER ::= { snellWilcoxModularProductsMib 416 }
moduleIQDEC05MIB		OBJECT IDENTIFIER ::= { snellWilcoxModularProductsMib 417 }
moduleIQH3AMIB  		OBJECT IDENTIFIER ::= { snellWilcoxModularProductsMib 429 }
moduleIQUDC00MIB  		OBJECT IDENTIFIER ::= { snellWilcoxModularProductsMib 430 }
moduleIQSDA10MIB  		OBJECT IDENTIFIER ::= { snellWilcoxModularProductsMib 436 }
moduleIQSDA11MIB  		OBJECT IDENTIFIER ::= { snellWilcoxModularProductsMib 437 }
moduleIQVDA00MIB  		OBJECT IDENTIFIER ::= { snellWilcoxModularProductsMib 438 }
moduleIQAES00MIB  		OBJECT IDENTIFIER ::= { snellWilcoxModularProductsMib 439 }
moduleIQVDA01MIB  		OBJECT IDENTIFIER ::= { snellWilcoxModularProductsMib 447 }
moduleIQSDA02MIB  		OBJECT IDENTIFIER ::= { snellWilcoxModularProductsMib 464 }
moduleIQSYN01MIB  		OBJECT IDENTIFIER ::= { snellWilcoxModularProductsMib 465 }
moduleIQMUX44MIB		OBJECT IDENTIFIER ::= { snellWilcoxModularProductsMib 472 }
moduleIQMUX45MIB		OBJECT IDENTIFIER ::= { snellWilcoxModularProductsMib 473 }
moduleIQH1AMIB  		OBJECT IDENTIFIER ::= { snellWilcoxModularProductsMib 475 }
moduleIQHIP00MIB  		OBJECT IDENTIFIER ::= { snellWilcoxModularProductsMib 484 }
moduleIQSDA22MIB  		OBJECT IDENTIFIER ::= { snellWilcoxModularProductsMib 487 }
moduleIQDSK00MIB  		OBJECT IDENTIFIER ::= { snellWilcoxModularProductsMib 490 }
moduleIQMUX46MIB		OBJECT IDENTIFIER ::= { snellWilcoxModularProductsMib 494 }
moduleIQMUX47MIB		OBJECT IDENTIFIER ::= { snellWilcoxModularProductsMib 495 }
moduleIQMUX48MIB		OBJECT IDENTIFIER ::= { snellWilcoxModularProductsMib 496 }
moduleIQMUX49MIB		OBJECT IDENTIFIER ::= { snellWilcoxModularProductsMib 497 }
moduleIQDBD00MIB		OBJECT IDENTIFIER ::= { snellWilcoxModularProductsMib 498 }
moduleIQDBD01MIB		OBJECT IDENTIFIER ::= { snellWilcoxModularProductsMib 499 }
moduleIQSDA30MIB		OBJECT IDENTIFIER ::= { snellWilcoxModularProductsMib 503 }
moduleIQSDA32MIB		OBJECT IDENTIFIER ::= { snellWilcoxModularProductsMib 504 }
moduleIQSDA34MIB		OBJECT IDENTIFIER ::= { snellWilcoxModularProductsMib 520 }
moduleIQSDA35MIB		OBJECT IDENTIFIER ::= { snellWilcoxModularProductsMib 525 }
moduleIQSYN30MIB		OBJECT IDENTIFIER ::= { snellWilcoxModularProductsMib 526 }
moduleIQSYN31MIB		OBJECT IDENTIFIER ::= { snellWilcoxModularProductsMib 527 }
moduleIQMUX30MIB		OBJECT IDENTIFIER ::= { snellWilcoxModularProductsMib 528 }
moduleIQMUX31MIB		OBJECT IDENTIFIER ::= { snellWilcoxModularProductsMib 529 }
moduleIQMUX32MIB		OBJECT IDENTIFIER ::= { snellWilcoxModularProductsMib 530 }
moduleIQDMX30MIB		OBJECT IDENTIFIER ::= { snellWilcoxModularProductsMib 531 }
moduleIQDMX31MIB		OBJECT IDENTIFIER ::= { snellWilcoxModularProductsMib 532 }
moduleIQDMX32MIB		OBJECT IDENTIFIER ::= { snellWilcoxModularProductsMib 533 }
moduleIQSYN22MIB		OBJECT IDENTIFIER ::= { snellWilcoxModularProductsMib 538 }
moduleIQUPC00MIB		OBJECT IDENTIFIER ::= { snellWilcoxModularProductsMib 539 }
moduleIQUPC01MIB		OBJECT IDENTIFIER ::= { snellWilcoxModularProductsMib 540 }
moduleIQDNC00MIB		OBJECT IDENTIFIER ::= { snellWilcoxModularProductsMib 541 }
moduleIQDCC00MIB		OBJECT IDENTIFIER ::= { snellWilcoxModularProductsMib 542 }
moduleIQUDC10MIB		OBJECT IDENTIFIER ::= { snellWilcoxModularProductsMib 543 }
moduleIQUDC11MIB		OBJECT IDENTIFIER ::= { snellWilcoxModularProductsMib 544 }
moduleIQUAV10MIB		OBJECT IDENTIFIER ::= { snellWilcoxModularProductsMib 545 }
moduleIQMUX33MIB		OBJECT IDENTIFIER ::= { snellWilcoxModularProductsMib 546 }
moduleIQDMX33MIB		OBJECT IDENTIFIER ::= { snellWilcoxModularProductsMib 547 }
moduleIQUCC00MIB		OBJECT IDENTIFIER ::= { snellWilcoxModularProductsMib 548 }
moduleIQDNC01MIB		OBJECT IDENTIFIER ::= { snellWilcoxModularProductsMib 549 }
moduleIQSYN33MIB		OBJECT IDENTIFIER ::= { snellWilcoxModularProductsMib 551 }
moduleIQDBE00MIB		OBJECT IDENTIFIER ::= { snellWilcoxModularProductsMib 562 }
moduleIQDBE01MIB		OBJECT IDENTIFIER ::= { snellWilcoxModularProductsMib 563 }
moduleIQDBE02MIB		OBJECT IDENTIFIER ::= { snellWilcoxModularProductsMib 564 }
moduleIQDBE03MIB		OBJECT IDENTIFIER ::= { snellWilcoxModularProductsMib 565 }
moduleIQOSY30MIB		OBJECT IDENTIFIER ::= { snellWilcoxModularProductsMib 571 }
moduleIQODB31MIB		OBJECT IDENTIFIER ::= { snellWilcoxModularProductsMib 572 }
moduleIQOMB31MIB		OBJECT IDENTIFIER ::= { snellWilcoxModularProductsMib 573 }
moduleIQHCO30MIB		OBJECT IDENTIFIER ::= { snellWilcoxModularProductsMib 574 }
moduleIQHCO31MIB		OBJECT IDENTIFIER ::= { snellWilcoxModularProductsMib 575 }
moduleIQOTR32MIB		OBJECT IDENTIFIER ::= { snellWilcoxModularProductsMib 583 }
moduleIQODU31MIB		OBJECT IDENTIFIER ::= { snellWilcoxModularProductsMib 584 }
moduleIQOMU31MIB		OBJECT IDENTIFIER ::= { snellWilcoxModularProductsMib 585 }
moduleIQOTR40MIB		OBJECT IDENTIFIER ::= { snellWilcoxModularProductsMib 588 }
moduleIQUDC12MIB 		OBJECT IDENTIFIER ::= { snellWilcoxModularProductsMib 643 }
moduleIQASI82MIB		OBJECT IDENTIFIER ::= { snellWilcoxModularProductsMib 667 }
moduleIQHIP10MIB		OBJECT IDENTIFIER ::= { snellWilcoxModularProductsMib 668 }
moduleIQUDC30MIB 		OBJECT IDENTIFIER ::= { snellWilcoxModularProductsMib 680 }
moduleIQUDC31MIB 		OBJECT IDENTIFIER ::= { snellWilcoxModularProductsMib 686 }
moduleIQUDC32MIB 		OBJECT IDENTIFIER ::= { snellWilcoxModularProductsMib 683 }
moduleIQDB105MIB		OBJECT IDENTIFIER ::= { snellWilcoxModularProductsMib 732 }
moduleIQASI25MIB		OBJECT IDENTIFIER ::= { snellWilcoxModularProductsMib 771 }


-- Standards convertors
conversionQuasarPhc			OBJECT IDENTIFIER ::= { snellWilcoxStdsConvertorProducts 466 }
conversionAlchemistHd		OBJECT IDENTIFIER ::= { snellWilcoxStdsConvertorProducts 471 }
conversionAlchemistHdTx		OBJECT IDENTIFIER ::= { snellWilcoxStdsConvertorProducts 485 }
conversionTBS800U3	  		OBJECT IDENTIFIER ::= { snellWilcoxStdsConvertorProducts 557 }
conversionTBS800B3	  		OBJECT IDENTIFIER ::= { snellWilcoxStdsConvertorProducts 558 }
conversionCVR800U3	  		OBJECT IDENTIFIER ::= { snellWilcoxStdsConvertorProducts 559 }
conversionCVR800B3	  		OBJECT IDENTIFIER ::= { snellWilcoxStdsConvertorProducts 560 }
conversionMACHHD3	  		OBJECT IDENTIFIER ::= { snellWilcoxStdsConvertorProducts 561 }
conversionMACHHD4	  		OBJECT IDENTIFIER ::= { snellWilcoxStdsConvertorProducts 576 }
conversionMACHHD4E	  		OBJECT IDENTIFIER ::= { snellWilcoxStdsConvertorProducts 577 }
conversionAlchemistHd3G		OBJECT IDENTIFIER ::= { snellWilcoxStdsConvertorProducts 582 }
conversionCVR900U3	  		OBJECT IDENTIFIER ::= { snellWilcoxStdsConvertorProducts 603 }
conversionCVR900B3	  		OBJECT IDENTIFIER ::= { snellWilcoxStdsConvertorProducts 604 }
conversionKudosIQP			OBJECT IDENTIFIER ::= { snellWilcoxStdsConvertorProducts 626 }
conversionLC300				OBJECT IDENTIFIER ::= { snellWilcoxStdsConvertorProducts 735 }
conversionLC350				OBJECT IDENTIFIER ::= { snellWilcoxStdsConvertorProducts 736 }

conversionQuasarPhcMib		OBJECT IDENTIFIER ::= { snellWilcoxStdsConvertorProductsMib 466 }
conversionAlchemistHdMib	OBJECT IDENTIFIER ::= { snellWilcoxStdsConvertorProductsMib 471 }
conversionAlchemistHdTxMib	OBJECT IDENTIFIER ::= { snellWilcoxStdsConvertorProductsMib 485 }
conversionTBS800U3Mib	  	OBJECT IDENTIFIER ::= { snellWilcoxStdsConvertorProductsMib 557 }
conversionTBS800B3Mib	  	OBJECT IDENTIFIER ::= { snellWilcoxStdsConvertorProductsMib 558 }
conversionCVR800U3Mib	  	OBJECT IDENTIFIER ::= { snellWilcoxStdsConvertorProductsMib 559 }
conversionCVR800B3Mib	  	OBJECT IDENTIFIER ::= { snellWilcoxStdsConvertorProductsMib 560 }
conversionMACHHD3Mib	  	OBJECT IDENTIFIER ::= { snellWilcoxStdsConvertorProductsMib 561 }
conversionMACHHD4Mib	  	OBJECT IDENTIFIER ::= { snellWilcoxStdsConvertorProductsMib 576 }
conversionMACHHD4EMib	  	OBJECT IDENTIFIER ::= { snellWilcoxStdsConvertorProductsMib 577 }
conversionAlchemistHd3GMib	OBJECT IDENTIFIER ::= { snellWilcoxStdsConvertorProductsMib 582 }
conversionCVR900U3Mib	  	OBJECT IDENTIFIER ::= { snellWilcoxStdsConvertorProductsMib 603 }
conversionCVR900B3Mib	  	OBJECT IDENTIFIER ::= { snellWilcoxStdsConvertorProductsMib 604 }
conversionKudosIQPMib		OBJECT IDENTIFIER ::= { snellWilcoxStdsConvertorProductsMib 626 }
conversionLC300Mib		OBJECT IDENTIFIER ::= { snellWilcoxStdsConvertorProductsMib 735 }
conversionLC350Mib		OBJECT IDENTIFIER ::= { snellWilcoxStdsConvertorProductsMib 736 }


-- High Definition video products


-- MPEG compression products
snellWilcoxMosalina		OBJECT IDENTIFIER ::= { snellWilcoxMpegProducts 1 }			-- Mosalina MPEG analysis software application


-- Noise reduction products


-- Image restoration products


-- Production and Post Production Products


-- Display optimisation products


END
