-- *****************************************************************
-- SNELL-WILCOX-ROLLMAP.mib:  Snell & Wilcox RollCall logging proxy
--
-- March 2003, Sandy Kellagher
--
-- Copyright (c) 2003 Snell & Wilcox Ltd
-- All rights reserved.
-- 
-- $Id: SNELL-WILCOX-ROLLMAP.mib,v 1.3 2006/02/27 10:11:54 sandykellagher Exp $
--
-- *****************************************************************
--

SNELL-WILCOX-ROLLMAP 	DEFINITIONS ::= BEGIN

IMPORTS
	OBJECT-TYPE, MODULE-IDENTITY, NOTIFICATION-TYPE, Integer32, Unsigned32
        	FROM SNMPv2-SMI
	TEXTUAL-CONVENTION, DisplayString
        	FROM SNMPv2-TC
	snellWilcoxControlSystems
		FROM SNELL-WILCOX-PRODUCT-REG
	RollCallString, RollCallAddressString, RollCallUnitType, RollCallUnitTypeName, RollCallSysTime
			FROM SNELL-WILCOX-TC;


snellWilcoxRollMap 	MODULE-IDENTITY
	LAST-UPDATED 	"0602271000Z"
	ORGANIZATION 	"Snell & Wilcox Ltd"
	CONTACT-INFO
		"Postal:	Snell & Wilcox Ltd
					Generic Software Group
					Southleigh Park House
					Eastleigh Road
					Havant
					Hants  PO9 2PE
					UK
		
		   Tel: 	+44 (0) 2392 489000

		E-mail: 	snmp.support@snellwilcox.com"

	DESCRIPTION		"This module defines the SNMP fields that are generated by RollMap 
					from RollCall log fields. Note that an SNMP manager will not in 
					general be able to poll the value of these fields, since they are 
					updated whenever a new RollCall logging message arrives"

	REVISION    	"0602271000Z"
	DESCRIPTION		"Documented notification"

	REVISION    	"0501241400Z"
	DESCRIPTION		"Updated contact details"

	REVISION    	"0303151430Z"
	DESCRIPTION		"Initial version of this MIB module."
	::= { snellWilcoxControlSystems 1 }


snellWilcoxRollMapEvents 	OBJECT IDENTIFIER ::= { snellWilcoxRollMap 0 }


rollmapLogSourceUnitAddress OBJECT-TYPE
	SYNTAX  		RollCallAddressString
	MAX-ACCESS  	read-only
	STATUS  		current
	DESCRIPTION
	      "The RollCall address of the unit that generated the RollCall logging message."
	::= { snellWilcoxRollMap 1 }


rollmapLogSourceUnitName OBJECT-TYPE
	SYNTAX  		RollCallString
	MAX-ACCESS  	read-only
	STATUS  		current
	DESCRIPTION
	      "The RollCall unit name of the unit that generated the RollCall logging message."
	::= { snellWilcoxRollMap 2 }
                           

rollmapLogSourceUnitID OBJECT-TYPE
	SYNTAX  		RollCallUnitType
	MAX-ACCESS  	read-only
	STATUS  		current
	DESCRIPTION
	      "The RollCall unit ID code of the unit that generated the RollCall logging message."
	::= { snellWilcoxRollMap 3 }
                                   
                                   
rollmapLogSourceUnitTypeName OBJECT-TYPE
	SYNTAX  		RollCallUnitTypeName
	MAX-ACCESS  	read-only
	STATUS  		current
	DESCRIPTION
	      "The RollCall unit type name of the unit that generated the RollCall logging message."
	::= { snellWilcoxRollMap 4 }


rollmapLogEventTimeString OBJECT-TYPE
	SYNTAX  		DisplayString
	MAX-ACCESS  	read-only
	STATUS  		current
	DESCRIPTION
	      "This is the RollCall system time of the log event, expressed as an ASCII string."
	::= { snellWilcoxRollMap 5 }


rollmapLogEventState 	OBJECT-TYPE
	SYNTAX  		INTEGER 
					{
						unknown(0),
						good(1),
						warning(2),
						failure(3)
					}
	MAX-ACCESS  	read-only
	STATUS  		current
	DESCRIPTION
	      "This status code provides an overall status indicator for the unit."
	::= { snellWilcoxRollMap 6 }


rollmapLogEventMessage OBJECT-TYPE
	SYNTAX  		DisplayString
	MAX-ACCESS  	read-only
	STATUS  		current
	DESCRIPTION
	      "This is the RollCall logging string for the event, which consists of 
	      a comma-separated list of field=value pairs, eg 'INPUT=LOST,TEMP=OK'."
	::= { snellWilcoxRollMap 7 }



-- Events/notifications

rollMapLogEvent NOTIFICATION-TYPE
	OBJECTS { 
            rollmapLogSourceUnitAddress,
            rollmapLogSourceUnitName,
            rollmapLogSourceUnitID,
            rollmapLogSourceUnitTypeName,
            rollmapLogEventTimeString,
            rollmapLogEventState,
            rollmapLogEventMessage
	        }
	STATUS  		current
	DESCRIPTION
	      "This event is the trap that RollMap generates in response to new
	      logging data"
	::= { snellWilcoxRollMapEvents 1 }

                                   
END
